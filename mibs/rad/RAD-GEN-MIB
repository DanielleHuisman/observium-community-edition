RAD-GEN-MIB DEFINITIONS ::= BEGIN

-- Title:     RAD MIBs for Q3 2016 version 1.0
-- Copyright 2000 RAD Data Communications, Ltd.
-- All Rights Reserved.

-- It is RAD's intent to encourage the widespread use of
-- this Specification in connection with the management of
-- RAD products. RAD grants vendors, end-users,
-- and other interested parties a non-exclusive license to
-- use this Specification in connection with the management
-- of RAD products.

-- This Specification is supplied "as is," and RAD makes
-- no warranty, either express or implied, as to the use,
-- operation, condition, or performance of the Specification.


IMPORTS

       schedEntry     FROM  DISMAN-SCHEDULE-MIB
       entPhysicalAlias, entPhysicalDescr, PhysicalIndexOrZero     FROM  ENTITY-MIB
       IANAifType     FROM  IANAifType-MIB
       ifAlias, ifIndex     FROM  IF-MIB
       InetAddressType, InetAddress, InetPortNumber     FROM  INET-ADDRESS-MIB
       SnmpAdminString     FROM  SNMP-FRAMEWORK-MIB
       BfdDiagTC, BfdIntervalTC     FROM  BFD-TC-STD-MIB-R
       sysName     FROM  SNMPv2-MIB
       Integer32, Counter32, TimeTicks, 
       IpAddress, Gauge32, Unsigned32, 
       OBJECT-TYPE, MODULE-IDENTITY, NOTIFICATION-TYPE, 
       OBJECT-IDENTITY, Counter64     FROM  SNMPv2-SMI
       TimeStamp, TDomain, TAddress, 
       TEXTUAL-CONVENTION, DisplayString, RowStatus, 
       DateAndTime, RowPointer, MacAddress     FROM  SNMPv2-TC
       radGen, radSpecificDevices, systems, 
       fileTransfer     FROM  RAD-SMI-MIB
       FileType, RadEntityType, AlarmForwardingCause     FROM  RAD-TC; 


    radGenAll MODULE-IDENTITY
        LAST-UPDATED "201610191523Z"  -- October 19, 2016
        ORGANIZATION "RAD Data Communications Ltd."
        CONTACT-INFO
        "System Department

         Email:  mibs@rad.com
         Postal: RAD Data Communications Ltd.
                 24 Raoul Wallenberg St.
                 Tel-Aviv 6971920
                 Israel

         Phone:  +972-3-645-5421
         Fax:    +972-3-760-7844"
         DESCRIPTION
            "RAD General MIB."
    ::= { radGen 6 }


-- systems      OBJECT IDENTIFIER ::= { radGen 1 }  list of RAD products
-- agnt         OBJECT IDENTIFIER ::= { radGen 2 }  agent general tree
-- services     OBJECT IDENTIFIER ::= { radGen 3 }  See services.txt
-- radTransport OBJECT IDENTIFIER ::= { radGen 4 }  RAD transport tree
-- fmObjects    OBJECT IDENTIFIER ::= { radGen 5 }  Fault Management


sfp             OBJECT IDENTIFIER  ::= { radSpecificDevices 3 }
sfpConnector    OBJECT IDENTIFIER  ::= { sfp 4 }
sfpEvents       OBJECT IDENTIFIER  ::= { sfpConnector 0 }

radSysTR  OBJECT IDENTIFIER ::= { systems 1 } -- RAD Token Ring 

radRADring    OBJECT IDENTIFIER  ::= { radSysTR  1 }

radTMA  OBJECT IDENTIFIER  ::= { radSysTR  2 }

radRingMonitor    OBJECT IDENTIFIER  ::= { radSysTR  3 }

radSysFddi OBJECT IDENTIFIER ::= { systems 2 } -- RAD Fddi 

radFDX100  OBJECT IDENTIFIER ::= { radSysFddi  1 } -- RAD Fddi
 
radSysWan OBJECT IDENTIFIER ::= { systems 3 }  -- RAD Wan products

radSysWanEvents OBJECT-IDENTITY
     STATUS  current
     DESCRIPTION
     "The events for RAD Wan products."
     ::= { radSysWan 0 }

radMP2100      OBJECT IDENTIFIER ::= { radSysWan  1 }
radMP2104      OBJECT IDENTIFIER ::= { radSysWan  2 }
radMP2100B     OBJECT IDENTIFIER ::= { radSysWan  3 }
radMP2100F     OBJECT IDENTIFIER ::= { radSysWan  4 }

radMP2100H      OBJECT IDENTIFIER ::= { radSysWan  5 }
radMP2104H      OBJECT IDENTIFIER ::= { radSysWan  6 }
radMP2200B      OBJECT IDENTIFIER ::= { radSysWan  7 }
radMP2200F      OBJECT IDENTIFIER ::= { radSysWan  8 }

radMX3000       OBJECT IDENTIFIER ::= { radSysWan  9 }
radMX3004       OBJECT IDENTIFIER ::= { radSysWan 10 }
radMX30			OBJECT IDENTIFIER ::= { radSysWan 11 }
radMX300		OBJECT IDENTIFIER ::= { radSysWan 12 }

radVOIP         OBJECT IDENTIFIER ::= { radSysWan 13 }

radKM2100	    OBJECT IDENTIFIER ::= { radSysWan 15 }
radKM2104		OBJECT IDENTIFIER ::= { radSysWan 16 }

radDXC30        OBJECT IDENTIFIER ::= { radSysWan 20 }
radDXC10A       OBJECT IDENTIFIER ::= { radSysWan 21 }
radDXC8R        OBJECT IDENTIFIER ::= { radSysWan 22 }
radDXC30E       OBJECT IDENTIFIER ::= { radSysWan 23 }
radDXC3000      OBJECT IDENTIFIER ::= { radSysWan 24 }
radDXC8RNew     OBJECT IDENTIFIER ::= { radSysWan 25 }

radFcdT1LC       OBJECT IDENTIFIER ::= { radSysWan 26 }
radFcdE1LC       OBJECT IDENTIFIER ::= { radSysWan 27 }
radFcdT1L        OBJECT IDENTIFIER ::= { radSysWan 28 }
radFcdE1L        OBJECT IDENTIFIER ::= { radSysWan 29 }
radFcdT1         OBJECT IDENTIFIER ::= { radSysWan 30 }
radFcdE1         OBJECT IDENTIFIER ::= { radSysWan 31 }
radFcdE1I        OBJECT IDENTIFIER ::= { radSysWan 32 }
radFcdT1M        OBJECT IDENTIFIER ::= { radSysWan 33 }
radFcdE1M        OBJECT IDENTIFIER ::= { radSysWan 34 }
radFcdIP         OBJECT IDENTIFIER ::= { radSysWan 35} 
radFcdT1A        OBJECT IDENTIFIER ::= { radSysWan 36 }
radFcdE1A        OBJECT IDENTIFIER ::= { radSysWan 37 }
radFcdW          OBJECT IDENTIFIER ::= { radSysWan 38 }
radFcdSTM        OBJECT IDENTIFIER ::= { radSysWan 39 }

radHtuE1Sa      OBJECT IDENTIFIER ::= { radSysWan 40 }
radHtuE1        OBJECT IDENTIFIER ::= { radSysWan 41 }	 --card
radHtu2Sa       OBJECT IDENTIFIER ::= { radSysWan 42 }
radHtu2         OBJECT IDENTIFIER ::= { radSysWan 43 }	 --card
radAsmi450R768Sa OBJECT IDENTIFIER ::= { radSysWan 44 }
radAsmi450R768  OBJECT IDENTIFIER ::= { radSysWan 45 }	 --card
radAsmi450R1152Sa  OBJECT IDENTIFIER ::= { radSysWan 46 }
radAsmi450R1152 OBJECT IDENTIFIER ::= { radSysWan 47 }	 --card

radLrs12F        OBJECT IDENTIFIER ::= { radSysWan 48 }
radLrs12B        OBJECT IDENTIFIER ::= { radSysWan 49 }
radLrs52         OBJECT IDENTIFIER ::= { radSysWan 50 }

radHcdE1Sa       OBJECT IDENTIFIER ::= { radSysWan 51 }
radHcdE1         OBJECT IDENTIFIER ::= { radSysWan 52 }  --card
radHtuT1Sa       OBJECT IDENTIFIER ::= { radSysWan 53 }
radHtuT1         OBJECT IDENTIFIER ::= { radSysWan 54 }	 --card

radOptimux4E1         OBJECT IDENTIFIER ::= { radSysWan 55 }
radOptimux4T1         OBJECT IDENTIFIER ::= { radSysWan 56 }
radOptimuxXLE1         OBJECT IDENTIFIER ::= { radSysWan 57 }
radOptimuxXLT1         OBJECT IDENTIFIER ::= { radSysWan 58 }
radOptimuxXL16E1       OBJECT IDENTIFIER ::= { radSysWan 59 }

radImx64        OBJECT IDENTIFIER ::= { radSysWan 60 }
radImx6L        OBJECT IDENTIFIER ::= { radSysWan 61 }
radImx2         OBJECT IDENTIFIER ::= { radSysWan 62 }
radImx4T1       OBJECT IDENTIFIER ::= { radSysWan 63 }
radImx4E1       OBJECT IDENTIFIER ::= { radSysWan 64 }
radImx2T1E1     OBJECT IDENTIFIER ::= { radSysWan 65 }
radImxi4		OBJECT IDENTIFIER ::= { radSysWan 66 }

radOptimux155     OBJECT IDENTIFIER ::= { radSysWan 67 }  --SA
radOptimux4T1L    OBJECT IDENTIFIER ::= { radSysWan 68 }  --SA Low Cost
radOptimux4E1L    OBJECT IDENTIFIER ::= { radSysWan 69 }  --SA Low Cost
radHtuE1SaV2      OBJECT IDENTIFIER ::= { radSysWan 70 }
radHtuE1V2        OBJECT IDENTIFIER ::= { radSysWan 71 }  --card
radFomiE3         OBJECT IDENTIFIER ::= { radSysWan 72 }  --card
radFomiT3         OBJECT IDENTIFIER ::= { radSysWan 73 }  --card
radOpt4E1C        OBJECT IDENTIFIER ::= { radSysWan 74 }  --card
radOpt4T1C        OBJECT IDENTIFIER ::= { radSysWan 75 }  --card
radPrbiE3         OBJECT IDENTIFIER ::= { radSysWan 76 }  --SA
radPrbiT3         OBJECT IDENTIFIER ::= { radSysWan 77 }  --SA
radHcd4Sa         OBJECT IDENTIFIER ::= { radSysWan 78 }  --SA
radOptimuxT3      OBJECT IDENTIFIER ::= { radSysWan 79 }  --SA

radFRmon          OBJECT IDENTIFIER ::= { radSysWan 80 } 
radIpMux4         OBJECT IDENTIFIER ::= { radSysWan 81 } 
radIpMux1         OBJECT IDENTIFIER ::= { radSysWan 82 } 
radIpMux16        OBJECT IDENTIFIER ::= { radSysWan 83 } 
radIpMux1E        OBJECT IDENTIFIER ::= { radSysWan 84 }
radVmux2100       OBJECT IDENTIFIER ::= { radSysWan 85 }
radMP104          OBJECT IDENTIFIER ::= { radSysWan 86 }
radMP204          OBJECT IDENTIFIER ::= { radSysWan 87 }
radVmux110        OBJECT IDENTIFIER ::= { radSysWan 88 }
-- reserved for radVmux105        OBJECT IDENTIFIER ::= { radSysWan 89 }

radFcd155        OBJECT IDENTIFIER ::= { radSysWan 90 } --SA
radIpMux8        OBJECT IDENTIFIER ::= { radSysWan 91 }
radOptimux155DS3 OBJECT IDENTIFIER ::= { radSysWan 92 }  --SA
radOptimuxT3L    OBJECT IDENTIFIER ::= { radSysWan 93 }  --SA Low Cost
radGmux2000      OBJECT IDENTIFIER ::= { radSysWan 94 }
radOp16E1L		 OBJECT IDENTIFIER ::= { radSysWan 95 }  --19 inch box
radOp16E1LS      OBJECT IDENTIFIER ::= { radSysWan 96 }  --half 19 inch box (single)
radPRBm20        OBJECT IDENTIFIER ::= { radSysWan 97 }  -- half 19 inch box
radPRBm22        OBJECT IDENTIFIER ::= { radSysWan 98 }  -- 19 inch box 
radAsmi52A       OBJECT IDENTIFIER ::= { radSysWan 99 }  -- SA

radOpXLE1        OBJECT IDENTIFIER ::= { radSysWan 100 } -- New-Look
radOpXLT1        OBJECT IDENTIFIER ::= { radSysWan 101 } -- New-Look
radOpXL16E1      OBJECT IDENTIFIER ::= { radSysWan 102 } -- New-Look
radOp4E1         OBJECT IDENTIFIER ::= { radSysWan 103 } -- New-Look
radOp4T1         OBJECT IDENTIFIER ::= { radSysWan 104 } -- New-Look

radDxc4			 OBJECT IDENTIFIER ::= { radSysWan 105 }

radIpMux11       OBJECT IDENTIFIER ::= { radSysWan 106 }
radIpMux14       OBJECT IDENTIFIER ::= { radSysWan 107 }
radOp1550		  OBJECT IDENTIFIER ::= { radSysWan 108 }
-- reserved for radVplsMtu OBJECT IDENTIFIER ::= { radSysWan 109 }

radFdsl101       OBJECT IDENTIFIER ::= { radSysWan 110 } 
radFdsl201       OBJECT IDENTIFIER ::= { radSysWan 111 } 

radVmux120        OBJECT IDENTIFIER ::= { radSysWan 112 }													
radVmux2200       OBJECT IDENTIFIER ::= { radSysWan 113 }
radVmux400        OBJECT IDENTIFIER ::= { radSysWan 114 }

radIpMux116       OBJECT IDENTIFIER ::= { radSysWan 115 }

radOp4E1LNew      OBJECT IDENTIFIER ::= { radSysWan 116 } -- New SA Low Cost
radOp4T1LNew      OBJECT IDENTIFIER ::= { radSysWan 117 } -- New SA Low Cost

radFcd155E       OBJECT IDENTIFIER ::= { radSysWan 118 } -- 19 inch box, non APS
radFcd155ES      OBJECT IDENTIFIER ::= { radSysWan 119 } -- half 19 inch box, APS

radMP4100       OBJECT IDENTIFIER ::= { radSysWan 120 }

radAsmi52L       OBJECT IDENTIFIER ::= { radSysWan 121 }  -- SA Low Cost
radVmux210       OBJECT IDENTIFIER ::= { radSysWan 122 }
radOp34E1	     OBJECT IDENTIFIER ::= { radSysWan 123 }
radVmux312       OBJECT IDENTIFIER ::= { radSysWan 124 }
radVmux404       OBJECT IDENTIFIER ::= { radSysWan 125 }
radVmux420       OBJECT IDENTIFIER ::= { radSysWan 126 }
radIpMux12	     OBJECT IDENTIFIER ::= { radSysWan 127 }

radOptimux4E1V3dot5    OBJECT IDENTIFIER ::= { radSysWan 128 }
radOptimux4E1Mar06	   OBJECT IDENTIFIER ::= { radSysWan 129 }

radFcd155EwAPS       OBJECT IDENTIFIER ::= { radSysWan 130 } -- 19 inch box, APS

radOptimux4T1Mar06	   OBJECT IDENTIFIER ::= { radSysWan 131 }

radFcd155EwAPS2pdh       OBJECT IDENTIFIER ::= { radSysWan 132 } -- 19 inch box, APS,E3 & E1

radVmux320       OBJECT IDENTIFIER ::= { radSysWan 133 }

radMP2100VoIP    OBJECT IDENTIFIER ::= { radSysWan  134 }
radMP2104VoIP    OBJECT IDENTIFIER ::= { radSysWan  135 }

radIpMux24	     OBJECT IDENTIFIER ::= { radSysWan 136 }

radOp4E1NG1      OBJECT IDENTIFIER ::= { radSysWan 137 } -- OP-108
radOp4T1NG1      OBJECT IDENTIFIER ::= { radSysWan 138 } -- OP-106 
radOp25			 OBJECT IDENTIFIER ::= { radSysWan 139 } -- T1 interface

radAsmi54        OBJECT IDENTIFIER ::= { radSysWan 140 }  -- SA

radVmux314       OBJECT IDENTIFIER ::= { radSysWan 141 }

radFcd622        OBJECT IDENTIFIER ::= { radSysWan 142 }

radLrs22         OBJECT IDENTIFIER ::= { radSysWan 143 }

radUNT20E1        OBJECT IDENTIFIER ::= { radSysWan 144 }  
radIpMux2L	      OBJECT IDENTIFIER ::= { radSysWan 145 }  
radFcdE1E         OBJECT IDENTIFIER ::= { radSysWan 146 }  

radIpMux216	      OBJECT IDENTIFIER ::= { radSysWan 147 }

radLrs102         OBJECT IDENTIFIER ::= { radSysWan 148 }

radGmux2004 	  OBJECT IDENTIFIER ::= { radSysWan 149 }

radLrs102unbal   OBJECT IDENTIFIER ::= { radSysWan 150 } -- LRS102 Unbalanced 

radLrs16 	  OBJECT IDENTIFIER ::= { radSysWan 151 }

radVmux405		OBJECT IDENTIFIER ::= { radSysWan 152 }
radVmux425		OBJECT IDENTIFIER ::= { radSysWan 153 }
radMiniCVS    	OBJECT IDENTIFIER ::= { radSysWan 154 }

radIpMux155		OBJECT IDENTIFIER ::= { radSysWan 155 }


radSysBRG OBJECT IDENTIFIER ::= { systems 4 }  -- RAD Bridges products

radTRE1  OBJECT IDENTIFIER ::= { radSysBRG 1 }  -- RAD Bridges products

radTRE1D  OBJECT IDENTIFIER ::= { radSysBRG 2 }  -- RAD Bridges products

radTRE8  OBJECT IDENTIFIER ::= { radSysBRG 3 }  -- RAD Bridges products

radTRE8D  OBJECT IDENTIFIER ::= { radSysBRG 4 }  -- RAD Bridges products

radMBE1  OBJECT IDENTIFIER ::= { radSysBRG 5 }  -- RAD Bridges products

radMBE1D  OBJECT IDENTIFIER ::= { radSysBRG  6 }  -- RAD Bridges products

radMBE8  OBJECT IDENTIFIER ::= { radSysBRG  7 }  -- RAD Bridges products

radMBE8D  OBJECT IDENTIFIER ::= { radSysBRG  8 }  -- RAD Bridges products

radMLBT   OBJECT IDENTIFIER ::= { radSysBRG  9 }  -- RAD Bridges products 

radFEB4DAS    OBJECT IDENTIFIER ::= { radSysBRG  10 }  -- RAD Bridges products

radTrimBrg10  OBJECT IDENTIFIER ::= { radSysBRG 11 }  -- RAD Bridges products

radTrimBrg16  OBJECT IDENTIFIER ::= { radSysBRG 12 }  -- RAD Bridges products

radRRTRE8  OBJECT IDENTIFIER ::= { radSysBRG 13 }  -- RAD Bridges products

radRRTRE8D  OBJECT IDENTIFIER ::= { radSysBRG 14 }  -- RAD Bridges products

radRRMLBT   OBJECT IDENTIFIER ::= { radSysBRG 15 }  -- RAD Bridges products 

radRRMLBTF   OBJECT IDENTIFIER ::= { radSysBRG 16 }  -- RAD Bridges products 

radRRTRE1D  OBJECT IDENTIFIER ::= { radSysBRG 17 }  -- RAD Bridges products

radTRERAS  OBJECT IDENTIFIER ::= { radSysBRG 18 }  -- RAD Bridges products

radTRERASa  OBJECT IDENTIFIER ::= { radSysBRG 19 }  -- RAD Bridges products

radMBERAS  OBJECT IDENTIFIER ::= { radSysBRG 20 }  -- RAD Bridges products

radMBERASa  OBJECT IDENTIFIER ::= { radSysBRG 21 }  -- RAD Bridges products
 
radFEB4FDX   OBJECT IDENTIFIER ::= { radSysBRG 22 }  -- RAD Bridges products

radFEB4SAS  OBJECT IDENTIFIER ::= { radSysBRG 23 }  -- RAD Bridges products

radRRFTBDAS  OBJECT IDENTIFIER ::= { radSysBRG 24 }  -- RAD Bridges products

radRRFTBSAS  OBJECT IDENTIFIER ::= { radSysBRG 25 }  -- RAD Bridges products

radFTBDAS    OBJECT IDENTIFIER ::= { radSysBRG 26 }  -- RAD Bridges products

radFTBSAS    OBJECT IDENTIFIER ::= { radSysBRG 27 }  -- RAD Bridges products

radFastWay100    OBJECT IDENTIFIER ::= { radSysBRG 28 }  -- RAD Bridges products

radSysCnvrtr OBJECT IDENTIFIER ::= { systems 5 }  -- RAD Converters products

radSTC1   OBJECT IDENTIFIER ::= { radSysCnvrtr 1 }  -- RAD Converters products

radSTC2   OBJECT IDENTIFIER ::= { radSysCnvrtr 3 }  -- RAD Converters products

radSTC1UDP  OBJECT IDENTIFIER ::= { radSysCnvrtr 4 }  -- RAD Converters products

radSTC2UDP  OBJECT IDENTIFIER ::= { radSysCnvrtr 6 }  -- RAD Converters products

radFTC1   OBJECT IDENTIFIER ::= { radSysCnvrtr 10 }  -- RAD Converters products

radFTC2   OBJECT IDENTIFIER ::= { radSysCnvrtr 12 }  -- RAD Converters products

radFTC1UDP    OBJECT IDENTIFIER ::= { radSysCnvrtr 13 }  -- RAD Converters products

radFTC2UDP    OBJECT IDENTIFIER ::= { radSysCnvrtr 15 }  -- RAD Converters products

radSEC1   OBJECT IDENTIFIER ::= { radSysCnvrtr 20 }  -- RAD Converters products

radSEC2   OBJECT IDENTIFIER ::= { radSysCnvrtr 22 }  -- RAD Converters products

radSEC1UDP   OBJECT IDENTIFIER ::= { radSysCnvrtr 23 }  -- RAD Converters products

radSEC2UDP   OBJECT IDENTIFIER ::= { radSysCnvrtr 25 }  -- RAD Converters products

radFEC1   OBJECT IDENTIFIER ::= { radSysCnvrtr 30 }  -- RAD Converters products

radFEC2   OBJECT IDENTIFIER ::= { radSysCnvrtr 32 }  -- RAD Converters products

radFEC1UDP   OBJECT IDENTIFIER ::= { radSysCnvrtr 33 }  -- RAD Converters products

radFEC2UDP   OBJECT IDENTIFIER ::= { radSysCnvrtr 35 }  -- RAD Converters products

radRIC155   OBJECT IDENTIFIER ::= { radSysCnvrtr 36 }  -- RAD Converters products

radRICE1   OBJECT IDENTIFIER ::= { radSysCnvrtr 37 }  -- RAD Converters products

radETX102  OBJECT IDENTIFIER ::= { radSysCnvrtr 38 }  -- RAD Converters products

radRIC155GE OBJECT IDENTIFIER ::= { radSysCnvrtr 39 }  -- RAD Converters products

radRiciT3   OBJECT IDENTIFIER ::= { radSysCnvrtr 40 }  -- RAD Converters products

radRiciE3   OBJECT IDENTIFIER ::= { radSysCnvrtr 41 }  -- RAD Converters products

radRiciT1   OBJECT IDENTIFIER ::= { radSysCnvrtr 42 }  -- RAD Converters products

radETX202  OBJECT IDENTIFIER ::= { radSysCnvrtr 43 }  -- RAD Converters products

radETX105  OBJECT IDENTIFIER ::= { radSysCnvrtr 44 }  -- RAD Converters products

radETX205  OBJECT IDENTIFIER ::= { radSysCnvrtr 45 }  -- RAD Converters products

radRiciSE  OBJECT IDENTIFIER ::= { radSysCnvrtr 46 }  -- RAD Converters products

radRIC622GE OBJECT IDENTIFIER ::= { radSysCnvrtr 47 }  -- RAD Converters products

radSPH OBJECT IDENTIFIER ::= { radSysCnvrtr 48 }  -- RAD Converters products

radMiricE1T1 OBJECT IDENTIFIER ::= { radSysCnvrtr 49 }  -- RAD Converters products
radMiricE3T3 OBJECT IDENTIFIER ::= { radSysCnvrtr 50 }  -- RAD Converters products

radSPH4 OBJECT IDENTIFIER ::= { radSysCnvrtr 51 }  -- RAD Converters products

radEthAccess   OBJECT IDENTIFIER ::= {systems 6}
radETX510 		OBJECT IDENTIFIER ::= { radEthAccess  1 }
radEGate100		OBJECT IDENTIFIER ::= { radEthAccess  2 }
radEGate20 		OBJECT IDENTIFIER ::= { radEthAccess  3 }
radRici8E1		OBJECT IDENTIFIER ::= { radEthAccess  4 }	
radRici8T1		OBJECT IDENTIFIER ::= { radEthAccess  5 }	
radRici4E1		OBJECT IDENTIFIER ::= { radEthAccess  6 }	
radRici4T1		OBJECT IDENTIFIER ::= { radEthAccess  7 }	
radIMXI4		OBJECT IDENTIFIER ::= { radEthAccess  8 }-- for Khazahstan only
radETX550		OBJECT IDENTIFIER ::= { radEthAccess  9 }
radRici16		OBJECT IDENTIFIER ::= { radEthAccess 10 }
radETX102A		OBJECT IDENTIFIER ::= { radEthAccess 11 }
radETX202A		OBJECT IDENTIFIER ::= { radEthAccess 12 }
radETX201A		OBJECT IDENTIFIER ::= { radEthAccess 13 }
radETX201		OBJECT IDENTIFIER ::= { radEthAccess 14 }
radUNT20Ric	  	OBJECT IDENTIFIER ::= { radEthAccess 15 }
radRici4E1L		OBJECT IDENTIFIER ::= { radEthAccess 16 }	
radRici8E1L		OBJECT IDENTIFIER ::= { radEthAccess 17 }
radRici155GE 	OBJECT IDENTIFIER ::= { radEthAccess 18 }
radRici622GE 	OBJECT IDENTIFIER ::= { radEthAccess 19 }
radETX208		OBJECT IDENTIFIER ::= { radEthAccess 20 }
radETX202AW		OBJECT IDENTIFIER ::= { radEthAccess 21 }--for wide box of ETX202A
radETX102H		OBJECT IDENTIFIER ::= { radEthAccess 22 } -- Hardened metal box
radETX202H		OBJECT IDENTIFIER ::= { radEthAccess 23 } -- Hardened metal box
radETX205A              OBJECT IDENTIFIER ::= { radEthAccess 30 }
radETX220A              OBJECT IDENTIFIER ::= { radEthAccess 32 }
radETX203AM             OBJECT IDENTIFIER ::= { radEthAccess 33 }
radETX203AX             OBJECT IDENTIFIER ::= { radEthAccess 34 }
radETX2i                OBJECT IDENTIFIER ::= { radEthAccess 40 }
radETX2iHalf19Inch      OBJECT IDENTIFIER ::= { radEthAccess 43 }
radETX2iNebs            OBJECT IDENTIFIER ::= { radEthAccess 44 }
radETX2iVENebs          OBJECT IDENTIFIER ::= { radEthAccess 45 }
radETX203AXH            OBJECT IDENTIFIER ::= { radEthAccess 46 } -- ETX203AX\H, LEDs on front panel

radSysStkHub  OBJECT IDENTIFIER ::= { systems 7 }  -- RAD Stackable products

radRBHE    OBJECT IDENTIFIER ::= { radSysStkHub 1 }  -- RAD Stackable products

radRBHT    OBJECT IDENTIFIER ::= { radSysStkHub 2 }  -- RAD Stackable products

radRBHEEvents OBJECT-IDENTITY
     STATUS  current
     DESCRIPTION
     "The events for RAD Stackable products."
     ::= { radRBHE 0 }

radRBHTEvents OBJECT-IDENTITY
     STATUS  current
     DESCRIPTION
     "The events for RAD Stackable products."
     ::= { radRBHT 0 }

radETS4fddiDAS   OBJECT IDENTIFIER ::= { radSysStkHub 3 }  -- RAD Stackable products

radETS4fddiSAS   OBJECT IDENTIFIER ::= { radSysStkHub 4 }  -- RAD Stackable products

radSAHEMX  OBJECT IDENTIFIER ::= { radSysStkHub 5 }  -- RAD Stackable products

radSAHTM   OBJECT IDENTIFIER ::= { radSysStkHub 6 }  -- RAD Stackable products

radETS4   OBJECT IDENTIFIER ::= { radSysStkHub 7 }  -- RAD Stackable products

radSAHEMU  OBJECT IDENTIFIER ::= { radSysStkHub 8 }  -- RAD Stackable products


unknown    	OBJECT IDENTIFIER ::= { radSysStkHub 9 }  -- RAD Stackable products

radSAH16Eint   OBJECT IDENTIFIER ::= { radSysStkHub 10 }  -- RAD Stackable products

radSAH16Tint   OBJECT IDENTIFIER ::= { radSysStkHub 11 }  -- RAD Stackable products

radSAH16Eext   OBJECT IDENTIFIER ::= { radSysStkHub 12 }  -- RAD Stackable products

radSAH16Text   OBJECT IDENTIFIER ::= { radSysStkHub 13 }  -- RAD Stackable products



radSysPS OBJECT IDENTIFIER ::=  { systems 8 } -- RAD Packet Switch  (PS) products 

radSysPSEvents OBJECT-IDENTITY
     STATUS  current
     DESCRIPTION
     "The events for RAD Packet Switch  (PS) products."
     ::= { radSysPS 0 }

radSPS2  OBJECT IDENTIFIER ::=  { radSysPS 1 } -- RAD Packet Switch  (PS) products
radSPS3  OBJECT IDENTIFIER ::=  { radSysPS 2 } -- RAD Packet Switch  (PS) products
radSPS6  OBJECT IDENTIFIER ::=  { radSysPS 3 } -- RAD Packet Switch  (PS) products
radSPS9  OBJECT IDENTIFIER ::=  { radSysPS 4 } -- RAD Packet Switch  (PS) products
radSPS12 OBJECT IDENTIFIER ::=  { radSysPS 5 } -- RAD Packet Switch  (PS) products

radAPD2  OBJECT IDENTIFIER ::=  { radSysPS 6 } -- RAD Packet Switch  (PS) products
radAPD8  OBJECT IDENTIFIER ::=  { radSysPS 7 } -- RAD Packet Switch  (PS) products

radAPS8  OBJECT IDENTIFIER ::=  { radSysPS 8 } -- RAD Packet Switch  (PS) products
radAPS16 OBJECT IDENTIFIER ::=  { radSysPS 9 } -- RAD Packet Switch  (PS) products
radAPS24 OBJECT IDENTIFIER ::=  { radSysPS 10 } -- RAD Packet Switch  (PS) products

radSPS3S  OBJECT IDENTIFIER ::=  { radSysPS 11} -- RAD Packet Switch  (PS) products

radFPS8  OBJECT IDENTIFIER ::=  { radSysPS 12} -- RAD Packet Switch  (PS) products
radFPS12  OBJECT IDENTIFIER ::=  { radSysPS 13} -- RAD Packet Switch  (PS) products

radSPS3ScSL  OBJECT IDENTIFIER ::= { radSysPS 14} -- RAD Packet Switch  (PS) products
radSPS3Sc2S  OBJECT IDENTIFIER ::=  { radSysPS 15} -- RAD Packet Switch  (PS) products

radFPS8c OBJECT IDENTIFIER ::=  { radSysPS 16} -- RAD Packet Switch  (PS) products	  
radFPS4 OBJECT IDENTIFIER ::=  { radSysPS 17} -- RAD Packet Switch  (PS) products

radSPS4 OBJECT IDENTIFIER ::=  { radSysPS 18} -- RAD Packet Switch  (PS) products



radSysEth  OBJECT IDENTIFIER ::= { systems 9 } -- RAD Ethernet products 

radEP8T    OBJECT IDENTIFIER ::= {radSysEth 1} -- RAD Ethernet products

radEP4TAUI   OBJECT IDENTIFIER ::= {radSysEth 2} -- RAD Ethernet products

radEP4T2FL   OBJECT IDENTIFIER ::= {radSysEth 3} -- RAD Ethernet products

radEP4TFL    OBJECT IDENTIFIER ::= {radSysEth 4} -- RAD Ethernet products

radEP4FL     OBJECT IDENTIFIER ::= {radSysEth 5} -- RAD Ethernet products


radEPR8T   OBJECT IDENTIFIER ::= {radSysEth 7} -- RAD Ethernet products

radEPR4TAUI  OBJECT IDENTIFIER ::= {radSysEth 8} -- RAD Ethernet products

radEPR4T2FL  OBJECT IDENTIFIER ::= {radSysEth 9} -- RAD Ethernet products

radEPR4TFL   OBJECT IDENTIFIER ::= {radSysEth 10} -- RAD Ethernet products

radEPR4FL    OBJECT IDENTIFIER ::= {radSysEth 11} -- RAD Ethernet products



radSysRtr  OBJECT IDENTIFIER ::= { systems 11 } -- RAD Router products

radSysRtrEvents OBJECT-IDENTITY
     STATUS  current
     DESCRIPTION
     "The events for RAD Router products."
     ::= { radSysRtr 0 }

radRTED    OBJECT IDENTIFIER ::= {radSysRtr 1} -- RAD Router products

radRTEM    OBJECT IDENTIFIER ::= {radSysRtr 2} -- RAD Router products

radRTEC    OBJECT IDENTIFIER ::= {radSysRtr 3} -- RAD Router products

radWebRanger    OBJECT IDENTIFIER ::= {radSysRtr 4} -- RAD Router products

radTinyRouter   OBJECT IDENTIFIER ::= {radSysRtr 5} -- RAD Router products

radLA240	    OBJECT IDENTIFIER ::= {radSysRtr 6} -- RAD Router products

radSuperLan	    OBJECT IDENTIFIER ::= {radSysRtr 7} -- RAD Router products (LA-240)

radLA240I	    OBJECT IDENTIFIER ::= {radSysRtr 8} -- RAD Router products

radFcdIsdn      OBJECT IDENTIFIER ::= {radSysRtr 9} -- RAD Router products

radEFcdIp	    OBJECT IDENTIFIER ::= {radSysRtr 10} -- RAD Router products (FCD-IP/D)

radFcdIpD       OBJECT IDENTIFIER ::= {radSysRtr 11} -- RAD Router products

radFcdIpM       OBJECT IDENTIFIER ::= {radSysRtr 12} -- RAD Router products (LA-240)

radFcdIpL       OBJECT IDENTIFIER ::= {radSysRtr 13} -- RAD Router products


radSysAtm  OBJECT IDENTIFIER ::= { systems 12 } -- RAD ATM products 

radSysAtmEvents OBJECT-IDENTITY
     STATUS  current
     DESCRIPTION
     "The events for RAD ATM products."
     ::= { radSysAtm 0 }

radStarSwitch    OBJECT IDENTIFIER ::= {radSysAtm 1} --RAD StartSwitch products

radStarSwitchATM25    OBJECT IDENTIFIER ::= {radStarSwitch 1} --RAD StartSwitch products
radStarSwitchATM25L   OBJECT IDENTIFIER ::= {radStarSwitch 2} --RAD StartSwitch products
radStarSwitchATM155   OBJECT IDENTIFIER ::= {radStarSwitch 3} --RAD StartSwitch products


radAtmCsuDsu  OBJECT IDENTIFIER ::= {radSysAtm 2} --RAD CSU/DSU products 

radAmcdE1  OBJECT IDENTIFIER ::= {radAtmCsuDsu 1} -- RAD CSU/DSU products
radAmcdT1  OBJECT IDENTIFIER ::= {radAtmCsuDsu 2} -- RAD CSU/DSU products
radAce20E  OBJECT IDENTIFIER ::= {radAtmCsuDsu 3} -- RAD CSU/DSU products
radAce20T  OBJECT IDENTIFIER ::= {radAtmCsuDsu 4} -- RAD CSU/DSU products

radAce2005 OBJECT IDENTIFIER ::= { radAtmCsuDsu 5} -- RAD ACE2005
radAce2002 OBJECT IDENTIFIER ::= { radAtmCsuDsu 6} -- RAD ACE2002
radAce2002E OBJECT IDENTIFIER ::= { radAtmCsuDsu 7} -- RAD ACE2002E

radAce2E  OBJECT IDENTIFIER ::= {radAtmCsuDsu 8} -- RAD CSU/DSU products
radAce2T  OBJECT IDENTIFIER ::= {radAtmCsuDsu 9} -- RAD CSU/DSU products

radMlAtmE1  OBJECT IDENTIFIER ::= {radAtmCsuDsu 10} -- RAD ATM Piggy
radMlAtmT1  OBJECT IDENTIFIER ::= {radAtmCsuDsu 11} -- RAD ATM Piggy

radAmc102  OBJECT IDENTIFIER ::= {radAtmCsuDsu 12} -- RAD AMC102
radAmc102c  OBJECT IDENTIFIER ::= {radAtmCsuDsu 13} -- RAD AMC102 CARD

radAce202 OBJECT IDENTIFIER ::= { radAtmCsuDsu 14} -- RAD ACE202

radAce			OBJECT IDENTIFIER ::= {radSysAtm 3}	--RAD ACE products 
radAce101		OBJECT IDENTIFIER ::= {radAce 1}	-- RAD ACE101
radAce102		OBJECT IDENTIFIER ::= {radAce 2}	-- RAD ACE102
radAce50		OBJECT IDENTIFIER ::= {radAce 3}	-- RAD ACE50
radAce52		OBJECT IDENTIFIER ::= {radAce 4}	-- RAD ACE52
radAce52L		OBJECT IDENTIFIER ::= {radAce 5}	-- RAD ACE52L
-- for radAce51 which was canceled 
radAce201		OBJECT IDENTIFIER ::= {radAce 7}	-- RAD ACE201
radAce3200		OBJECT IDENTIFIER ::= {radAce 8}	-- RAD ACE3200
radAce3100		OBJECT IDENTIFIER ::= {radAce 9}	-- RAD ACE3100
radAce3400		OBJECT IDENTIFIER ::= {radAce 10}	-- RAD ACE3400
radAce3402		OBJECT IDENTIFIER ::= {radAce 11}	-- RAD ACE3402
radAce3100PSN	OBJECT IDENTIFIER ::= {radAce 12}	-- RAD ACE3100/PSN
radAce3200PSN	OBJECT IDENTIFIER ::= {radAce 13}	-- RAD ACE3200/PSN
radAce3400PSN	OBJECT IDENTIFIER ::= {radAce 14}	-- RAD ACE3400/PSN
radAce3402PSN	OBJECT IDENTIFIER ::= {radAce 15}	-- RAD ACE3402/PSN
radAce3600		OBJECT IDENTIFIER ::= {radAce 16}	-- RAD ACE3600
radAce3205		OBJECT IDENTIFIER ::= {radAce 17}	-- RAD ACE3205
radAce3105		OBJECT IDENTIFIER ::= {radAce 18}	-- RAD ACE3105
radAce3220		OBJECT IDENTIFIER ::= {radAce 19}	-- RAD ACE3220

radSysLA	  OBJECT IDENTIFIER ::= {systems 13} --RAD  IAD (Integrated Access Device) products
radLA140      OBJECT IDENTIFIER ::= {radSysLA 1} -- RAD LA-140
radLA110      OBJECT IDENTIFIER ::= {radSysLA 2} -- RAD LA-110
radLA104      OBJECT IDENTIFIER ::= {radSysLA 3} -- RAD LA-104 (LA-110 with IMA)
radLA130	  OBJECT IDENTIFIER ::= {radSysLA 4}
radLA210	  OBJECT IDENTIFIER ::= {radSysLA 5} -- RAD LA-210 

radSecurity     OBJECT IDENTIFIER ::= {systems 14} --RAD  AAA Security

radTest         OBJECT IDENTIFIER ::= {systems 15} -- RAD Test Network Element Performance
-- no objects should be added to this branch in RAD MIB.

radTrace                            OBJECT IDENTIFIER ::= {systems 16}

radAgnTrace            OBJECT IDENTIFIER ::= { radTrace 1}   -- Agent Trace debug

resetInformationTable  OBJECT-TYPE
    SYNTAX      SEQUENCE OF ResetInformationEntry
    MAX-ACCESS  not-accessible
    STATUS      current
    DESCRIPTION
        "This table traces the agent fatal error. "
    ::= { radAgnTrace 1 }

resetInformationEntry OBJECT-TYPE
    SYNTAX      ResetInformationEntry
    MAX-ACCESS  not-accessible
    STATUS      current
    DESCRIPTION  "This table has a single row entry and provides
                  Information related to the last reboot."
    INDEX {  resetInformationId }
    ::= { resetInformationTable  1 }

ResetInformationEntry ::= SEQUENCE {
    resetInformationId         Unsigned32,
    resetInformationLastReset  INTEGER,
    resetInformationFileName   SnmpAdminString,
    resetInformationLineNumber Unsigned32,
    resetInformationPC         Unsigned32,
    resetInformationExceptionCause  Unsigned32,
    resetInformationReason     INTEGER 
 }

resetInformationId       OBJECT-TYPE
    SYNTAX      Unsigned32
    MAX-ACCESS  not-accessible
    STATUS      current
    DESCRIPTION
    "resetInformationId =1"
    ::= {resetInformationEntry  1 }

resetInformationLastReset OBJECT-TYPE
    SYNTAX      INTEGER
    {
    coldStart(1),
    warmStart(2)
    }
    MAX-ACCESS  read-only
    STATUS      current
    DESCRIPTION
    "Type of last reset."
    ::= {resetInformationEntry  2 }

resetInformationFileName     OBJECT-TYPE
    SYNTAX      SnmpAdminString
    MAX-ACCESS  read-only
    STATUS      current
    DESCRIPTION
    "If the filename is empty then the object is not applicable"
    ::= {resetInformationEntry  3 }

resetInformationLineNumber     OBJECT-TYPE
    SYNTAX      Unsigned32
    MAX-ACCESS  read-only
    STATUS      current
    DESCRIPTION
    "if the line number value is zero then this object is not applicable"
    ::= {resetInformationEntry  4 }

resetInformationPC  OBJECT-TYPE
    SYNTAX      Unsigned32
    MAX-ACCESS  read-only
    STATUS      current
    DESCRIPTION
    "if the Program Counter value is zero then this object is not applicable "
    ::= {resetInformationEntry  5 }

resetInformationExceptionCause       OBJECT-TYPE
    SYNTAX      Unsigned32
    MAX-ACCESS  read-only
    STATUS      current
    DESCRIPTION
    "if the Exception Cause value is zero then this object is not applicable"
    ::= {resetInformationEntry  6 }

resetInformationReason OBJECT-TYPE
    SYNTAX      INTEGER
    {
    resetCommand                     (1),
    factoryDefaultCommand            (2),
    userDefaultCommand               (3),
    factoryDefaultAllCommand         (4),
    softwareInstallation             (5),
    unconfirmedStartupConfig         (6),
    unconfirmedSoftware              (7),
    configurationFileRejection       (8),
    resetAwaitingStartupConfigConfirm(9),
    resetAwaitingSoftwareConfirm     (10),
    configLoadedByZeroTouch          (11),
    otherReason                                 (255)
    }
    MAX-ACCESS  read-only
    STATUS      current
    DESCRIPTION
    "Reason for the last reset."
    ::= {resetInformationEntry  7 }



radZeroTouch                        OBJECT IDENTIFIER ::= {systems 17}

-- radSysTerminal  OBJECT IDENTIFIER ::= {systems 100} RAD Terminal Meta-MIB;
-- no objects should be added to this branch in RAD MIB.

-- End of radGen node

agnt OBJECT IDENTIFIER ::= { radGen 2}
-- agent general tree
-- Agent General



agnHwVersion OBJECT-TYPE
      SYNTAX  DisplayString
      MAX-ACCESS  read-write
      STATUS  current
      DESCRIPTION
      "ASCII string for description and display of the agent hardware version,
      as it is known by the agent software.The user can update the version
       upon request when he changes   components in the agent's module  "
      ::= { agnt 1 }

agnTrapMask OBJECT-TYPE   
      SYNTAX  Integer32 
      MAX-ACCESS  read-write    
      STATUS  current
      DESCRIPTION
      "The value of this attribute determines the type of traps the 
       agent should mask and not send to the management console. The 
       value is differently determined for different products. There are 
       mainly two methods:
       - an integer number, specifying the traps' severity.
       - a sum of 2**n, where n is a bit assigned to a certain 
         masked trap group.
       User should consult the product specification, to find out 
       the method employed."
      ::= { agnt 2 }

agnTrapValue OBJECT-TYPE
	SYNTAX  OCTET STRING
	MAX-ACCESS  read-only
	STATUS deprecated
	DESCRIPTION
	"The value of the trap decoded in internal RAD format. Full description is given
	  in the Trap definition file"
	::= {agnt 3}

agnChangeCnt OBJECT-TYPE
	SYNTAX  Counter32
	MAX-ACCESS  read-only
	STATUS current
	DESCRIPTION
	"The number of changes in system configuration that were  reported to the 
	manager since last cold start"
	::= {agnt 4 }

agnSpecific OBJECT-TYPE
      SYNTAX  OBJECT IDENTIFIER
      MAX-ACCESS  read-only
      STATUS  current
      DESCRIPTION
      " Object identifier of entity containing additional information 
      regarding this instance."
      ::= { agnt 5}

agnConfigMsg OBJECT-TYPE   
      SYNTAX  OCTET STRING
      MAX-ACCESS  read-only
      STATUS  current
      DESCRIPTION
      "Full configuration message  coded in internal RAD application format.
       This entry describes agent's configuration.

       For MP-2200 R3, this object describes agent's support of the V5.1
       feature: 1 octet ; bit 0 (LSB). 
       '1' - V5.1 feature is supported
       '0' - V5.1 feature is not supported."
      ::= { agnt 6 }

-- Manager table to record all IP addresses

mngTrapIpTable  OBJECT-TYPE
	SYNTAX  SEQUENCE OF MngEntry
	MAX-ACCESS  not-accessible
	STATUS current
	DESCRIPTION
	"This table indicates  the destination address of the traps.
	  Internally it will be limited to ten addresses. "
	::= { agnt 7 }

mngEntry OBJECT-TYPE
	SYNTAX  MngEntry
	MAX-ACCESS  not-accessible
	STATUS current
	DESCRIPTION  "An entry in table."
	INDEX {  mngID }
	::= { mngTrapIpTable 1 }


MngEntry  ::=
	    SEQUENCE {
	mngID
	  Integer32,
	mngIP
	  IpAddress,
	mngIPMask
	  IpAddress,
    mngTrapMask
      Integer32,
    mngAlarmTrapMask
      OCTET STRING,
    mngSnmpTrapUdpPort
      Unsigned32	
    }

mngID OBJECT-TYPE
	SYNTAX  Integer32 
	MAX-ACCESS  read-only
	STATUS current
	DESCRIPTION
	" This value indicates an index of a specific IP address"
	::= { mngEntry 1 }

mngIP OBJECT-TYPE
	SYNTAX  IpAddress 
	MAX-ACCESS  read-write
	STATUS current
	DESCRIPTION
	"This value indicates  the  destination address of the traps. IP 0.0.0.0 removes the entry. "
	::= { mngEntry 2 }

mngIPMask OBJECT-TYPE
	SYNTAX  IpAddress 
	MAX-ACCESS  read-write
	STATUS deprecated
	DESCRIPTION
	"This value indicates  the  mask of the destination addresses of the traps. "
	::= { mngEntry 3 }

mngTrapMask OBJECT-TYPE
	SYNTAX  Integer32 
	MAX-ACCESS  read-write
	STATUS current
	DESCRIPTION
      "The value of this attribute determines the type of traps the 
       agent should mask and not send to this NMS. The 
       value is differently determined for different products. There are 
       mainly two methods:
       - an integer number, specifying the traps' severity.
       - a sum of 2**n, where n is a bit assigned to a certain 
         masked trap group.
       User should consult the product specification, to find out 
       the method employed."
	::= { mngEntry 4 }

mngAlarmTrapMask OBJECT-TYPE
     SYNTAX  OCTET STRING
     MAX-ACCESS  read-write
     STATUS current
     DESCRIPTION
     "The value of this object determines the alarm traps that the 
      agent should mask (not send to this manager).
      The value is an Octet String, where each bit 
      is assigned to a certain trap.
        If the bit = 1, the trap will be masked.
        If the bit = 0, the trap will not be masked.
      For more details on the specific alarm traps masked, 
      see product specification."
    ::= { mngEntry 5 }

mngSnmpTrapUdpPort OBJECT-TYPE
	SYNTAX  Unsigned32 
	MAX-ACCESS  read-write
	STATUS  current
	DESCRIPTION
	"This variable enables to set the UDP port (socket) used for SNMP traps."
	::= { mngEntry 6 }
 

agnIndication OBJECT-TYPE
      SYNTAX  INTEGER {
         faulty  (1), -- =major
         warning (2),
         normal  (3), -- off
         minor   (4),
         major   (5),
         event   (6),
         critical(7)
        }
      MAX-ACCESS  read-only
      STATUS  current
      DESCRIPTION
      "Attribute describing the state of the entity the agent is responsible for.
       In case of a modular entity, the value of this attribute will be according
       to the component which is in the worst state.
       The order of severity (from top to bottom) is:
       critical-> major (or faulty)-> minor-> event-> warning-> normal (off)."
      ::= { agnt 8 }


agnMonitorModeCmd OBJECT-TYPE
	SYNTAX  INTEGER {
	notApplicable(1),
	off(2),
	on(3)
	}
	MAX-ACCESS  read-write
	STATUS current
	DESCRIPTION
	"Setting this attribute to ON, will enforce the agent to change its mode of operation to
	 Monitor Mode"
	::= {agnt 9}

agnLed OBJECT-TYPE
    SYNTAX  OCTET STRING
    MAX-ACCESS  read-only
    STATUS current
    DESCRIPTION
    "This entry specifies  the LEDs status of the agent module . Each led will be represented by 4
     bits  where the first 2 bits (left) will specify  the status :
     (00=NA, 01=OFF, 10=ON, 11=BLINK),
     and the next two bits (right) will specify the color :
     (00=GREEN, 01=RED, 10=YELLOW, 11=GRAY)"
    ::= {agnt 10}

trapTable  OBJECT-TYPE
	SYNTAX  SEQUENCE OF TrapEntry
	MAX-ACCESS  not-accessible
	STATUS current
	DESCRIPTION
	"This table may include the last few traps generated by the agent, for future retrieval. The table
	 has a limited capacity. If traps are not retrieved in proper time, they will be
	 over-written by new traps.
	 For other devices, it can include generic variables that will be attached to traps
	 as 'accessible-for-notify'."
	::= {agnt 11}

trapEntry OBJECT-TYPE
	SYNTAX  TrapEntry
	MAX-ACCESS  not-accessible
	STATUS current
	DESCRIPTION  "An entry in trapTable."
	INDEX {  trapID }
	::= { trapTable 1 }

TrapEntry  ::=
	    SEQUENCE {
	trapID
	  Integer32,
	trapVal
	  DisplayString,
    trapTimeSinceOccurrence
	   TimeTicks,
	trapNumeric
	  Integer32
	}

trapID OBJECT-TYPE
	SYNTAX  Integer32 
	MAX-ACCESS  read-only
	STATUS current
	DESCRIPTION
	" This object indicates an index of a specific trap.
	  Can be used also for any trap, while trapVal is used
	  as 'accessible-for-notify' or trapNumeric is used."
	::= { trapEntry 1 }

trapVal OBJECT-TYPE
	SYNTAX  DisplayString 
	MAX-ACCESS  read-only
	STATUS current
	DESCRIPTION
	"This object is the actual ASCII description  of the trap.
	 It can be used also as attached variable of traps, in order
	 to detail in explicit ASCII text, data of the trap.
	 In this case, it is used as 'accessible-for-notify'."
	::= { trapEntry 2 }

trapTimeSinceOccurrence OBJECT-TYPE
	 SYNTAX    TimeTicks
	MAX-ACCESS  read-only
	STATUS current
	DESCRIPTION
	"This object indicates the amount of  time passed since the occurrence of the event that
	 triggered this trap. "
	::= { trapEntry 3 }

trapNumeric OBJECT-TYPE
	SYNTAX  Integer32 
	MAX-ACCESS  accessible-for-notify
	STATUS current
	DESCRIPTION
	" This object is a numeric general parameter, that can be attached to any trap.
	  Values can be positive or negative."
	::= { trapEntry 4 }


fileTransfer  OBJECT IDENTIFIER ::= { agnt 12 }

fileServerIP  OBJECT-TYPE
	SYNTAX  IpAddress
	MAX-ACCESS  read-write
	STATUS  current
	DESCRIPTION
	"The IP address of the server from which the file is loaded "
	::= { fileTransfer 1 }

fileName  OBJECT-TYPE
	SYNTAX  DisplayString
	MAX-ACCESS  read-write
	STATUS  current
	DESCRIPTION
	"The name of the file to be loaded. For protection, read returns
	 NULL. "
	::= { fileTransfer 2 }

fileTransCmd  OBJECT-TYPE
	SYNTAX  INTEGER {
	                 swDwnLoad         (1),
					 configDwnLoad     (2),
					 configUpLoad      (3),
					 coProcDwnLoad     (4),
					 stateUpLoad       (5),
					 dwnLoadUserFile   (6),
					 upLoadUserFile    (7), 
					 swDwnLoadAndReset (8),
					 swUpLoad          (9),
					 swDwnLoad2BkupStorage(10),
					 bootDwnLoad      (11),
					 bootUpLoad       (12), 
					 swUpLoadFromBkupStorage(13),
					 licenseDwnLoad   (14),
					 configDwnLoadToDefaultFile(15),
					 noOp            (255)
					}
	MAX-ACCESS  read-write
	STATUS  current
	DESCRIPTION
	"The command to be executed on fileName at fileServerIP."
	::= { fileTransfer 3 }
 
-- tftp  group  

tftpRetryTimeOut OBJECT-TYPE
    SYNTAX  Integer32
    MAX-ACCESS  read-write
    STATUS  current
    DESCRIPTION
        " General Retransmission time-out value (seconds) "
    -- DEFVAL  { 15 }
    ::= { fileTransfer 4 }

tftpTotalTimeOut OBJECT-TYPE
    SYNTAX  Integer32
    MAX-ACCESS  read-write
    STATUS  current
    DESCRIPTION
        " Total Retransmission time-out value (seconds) "
    -- DEFVAL  { 60 }
    ::= { fileTransfer 5 }

tftpStatus OBJECT-TYPE
    SYNTAX  INTEGER {
		noOp(2),
		connecting(3),
		transferringData(4),
		endedTimeOut(5),
		endedOk(6),
		error(7)
	}
    MAX-ACCESS  read-write
    STATUS  current
    DESCRIPTION
    "Status of tftp session. When a session ended with success,
    the tftpStatus should be endedOk(6). Before restarting a
    tftp session, the NMS should set the tftpStatus to noOp(2).
    That's the reason of MAX-ACCESS read-write to this field."
    DEFVAL  { noOp}
    ::= { fileTransfer 6 }

tftpError OBJECT-TYPE
    SYNTAX  OCTET STRING ( SIZE(2) )
    MAX-ACCESS  read-only
    STATUS  current
    DESCRIPTION
    " The MSB represents the standard error code.
    The LSB represents the private error code.
    0x0000 is No Error
    0x0100 is File Not Found
	0x0200 is Access violation
	0x0300 is Disk full or allocation exceeded
    0x0400 is Illegal TFTP operation
    0x0500 is Unknown transfer ID
	0x0600 is File already exists
	0x0700 is No such user
    0x0001 is Server Overflow
    0x0002 is No empty UDP port
    0x0003 is No empty connection
    0x0004 is Illegal File Mode
    0x0007 is Illegal PDU size
	0x0008 is TFTP Server does not exist 
	0x0009 is Incorrect File
	0x000A is Wrong License format
	0x000B is License ID already used"
    DEFVAL  { '0000'h }
    ::= { fileTransfer 7 }

fileTransferToSubSystems OBJECT-TYPE
    SYNTAX  OCTET STRING 
    MAX-ACCESS  read-write
    STATUS  current
    DESCRIPTION
    " This object represents the sub-systems the fileTransCmd 
      refers to. It should be used when a system is divided 
      to sub-systems and each sub-system (or part of them) can 
	  have a different SW/Configuration.

	  Each bit of this object will represent one of the sub-systems.
	  Bit='1' - APPLY to respective sub-system
	  Bit='0' - DO NOT APPLY to respective sub-system

	  For the meaning of each bit, see product's specification.
	  User will select the sub-systems envolved by filling-in the bits
      that represent these sub-systems.
      In this case, the file represented by 'fileName' will 
	  include several parts, each representing one of the sub-systems.
	  The agent will refer only to the part/s indicated by this object.

      0 Octet Strings = not applicable  
      DEFVAL = 0h	for  the products that support this object."
    ::= { fileTransfer 8 }

fileNameWithinProduct  OBJECT-TYPE
	SYNTAX  DisplayString
	MAX-ACCESS  read-write
	STATUS  current
	DESCRIPTION
	"The file name used by the product within the product file system."
	::= { fileTransfer 9 }

--Internal SW Download table

intSwdlTable  OBJECT-TYPE 
      SYNTAX SEQUENCE OF IntSwdlEntry
      MAX-ACCESS not-accessible
      STATUS  current
      DESCRIPTION
      "This parameters table is for 
       internal Software down load. It also includes data 
       about all files contained in the Object from which 
       down-load is performed."
      ::= { fileTransfer 10 }

intSwdlEntry OBJECT-TYPE
      SYNTAX IntSwdlEntry
      MAX-ACCESS not-accessible
      STATUS current
	DESCRIPTION  "An entry in table."
	INDEX {intSwdlObjIdx, intSwdlFileIdx }
      ::= { intSwdlTable 1}

IntSwdlEntry ::=
      SEQUENCE {
      intSwdlObjIdx            Integer32,
	  intSwdlFileIdx           Integer32,
	  intSwdlFileName		   DisplayString,
	  intSwdlFileSwVer		   DisplayString,
	  intSwdlSwDate			   DisplayString,
	  intSwdlSize			   DisplayString,
	  intSwdlCmd			   INTEGER,
	  intSwdlToSubSystem	   OCTET STRING,
	  intSwdlCardType		   INTEGER,
	  intSwdlFlashIdx	   	   Integer32
      }

intSwdlObjIdx OBJECT-TYPE
      SYNTAX  Integer32
      MAX-ACCESS  read-only
      STATUS  current
      DESCRIPTION
      "The index of the object from which down-load is performed."
      ::= {intSwdlEntry 1}

intSwdlFileIdx OBJECT-TYPE
      SYNTAX  Integer32
      MAX-ACCESS  read-only
      STATUS  current
      DESCRIPTION
      "The index of the files included in intSwdlObjIdx.
       One of these files can be selected to be internally 
       downloaded."
      ::= {intSwdlEntry 2}

intSwdlFileName OBJECT-TYPE
      SYNTAX  	 DisplayString
      MAX-ACCESS  read-only
      STATUS  current
      DESCRIPTION
      "The name of the file."
      ::= {intSwdlEntry 3}

intSwdlFileSwVer OBJECT-TYPE
      SYNTAX  	 DisplayString
      MAX-ACCESS  read-only
      STATUS  current
      DESCRIPTION
      "The software version of the file."
      ::= {intSwdlEntry 4}

intSwdlSwDate OBJECT-TYPE
      SYNTAX  	 DisplayString
      MAX-ACCESS  read-only
      STATUS  current
      DESCRIPTION
      "The software version date of the file."
      ::= {intSwdlEntry 5}

intSwdlSize OBJECT-TYPE
      SYNTAX  	 DisplayString
      MAX-ACCESS  read-only
      STATUS  current
      DESCRIPTION
      "The size of the file."
      ::= {intSwdlEntry 6}

intSwdlCmd OBJECT-TYPE
      SYNTAX  	  INTEGER
	  				{
					notApplicable		(1),
					off		(2),
					on		(3)
					}
      MAX-ACCESS  read-write
      STATUS  current
      DESCRIPTION
      "The command to down-load a SW file to an object.
       The Agent will change the value of this MIB object to off(2) 
	  automatically, after accepting the command."
      ::= {intSwdlEntry 7}

intSwdlToSubSystem	OBJECT-TYPE   
      SYNTAX  OCTET STRING
      MAX-ACCESS  read-write
      STATUS  current
      DESCRIPTION
      " This object defines the subsystem for download.
       Bit='1'- APPLY to respective sub system.
       Bit='0'- DO NOT APPLY to respective sub system.
       For more details see product specification. 
       For every octet bit0=LSB, bit7=MSB"
      ::= { intSwdlEntry  8 }

intSwdlCardType OBJECT-TYPE
      SYNTAX  	  INTEGER
	  				{
  unknown        (1),  
  gstm1		 	 (220),   -- GMUX-2000 STM1 card
  goc3		 	 (221),   -- GMUX-2000 OC3 card
  gstm1D		 (222),   -- GMUX-2000 STM1 card with 2 ports
  goc3D 		 (223),   -- GMUX-2000 OC3 card	with 2 ports
  serverE1       (270),	  -- GMUX-2000 Server E1 Card
  serverT1       (271),	  -- GMUX-2000 Server T1 Card
  serverE1Pw     (272),   -- Gmux2000 Server E1 PW Card
  serverT1Pw     (273),   -- Gmux2000 Server T1 PW Card
  gigabitEth     (280),	  -- GMUX-2000 Gigabit ETH Card
  gigabitEth2    (281),	  -- Gmux2000 new Gigabit ETH Card	 - 2 GbE ports with SFP connector
  eth2           (282),	  -- Gmux2000 new ETH Card - 2 ETH ports with RJ45 connectors (10/100/1000)
  gigabitEth8    (283),	  -- Gmux2000 new Gigabit ETH Card	 - 8 GbE ports with SFP connector
  eth8           (284),	  -- Gmux2000 new ETH Card - 8 ETH ports with RJ45 connectors (10/100/1000)
  channelizedT3Pw1 (290),	 -- Gmux2000 Channelized T3 PW Card
  cesT128		 (300),	 -- Gmux-2000 CES T1 28 ports (external T1 ports) card.
  cesE128		 (301),	 -- Gmux-2000 CES E1 28 ports (external E1 ports) card.
  cesT1Pw28      (302),	 -- Gmux2000 CES T1 PW ports (external T1 ports) card.
  cesE1Pw28      (303),    -- Gmux2000 CES E1 PW ports (external E1 ports) card.
  vmxE1VeDe		 (310),	  -- Gmux-2000 Vmux E1 card with 16 external voice + 2 external Data ports.
  vmxE1VeDi		 (311),	  -- Gmux-2000 Vmux E1 card with 16 external voice + 2 internal Data ports.
  vmxE1ViDe		 (312),	  -- Gmux-2000 Vmux E1 card with 16 internal voice + 2 external Data ports.
  vmxE1ViDi		 (313),	  -- Gmux-2000 Vmux E1 card with 16 internal voice + 2 internal Data ports.
  vmxT1VeDe		 (314),	  -- Gmux-2000 Vmux T1 card with 16 external voice + 2 external Data ports.
  vmxT1VeDi		 (315),	  -- Gmux-2000 Vmux T1 card with 16 external voice + 2 internal Data ports.
  vmxT1ViDe		 (316),	  -- Gmux-2000 Vmux T1 card with 16 internal voice + 2 external Data ports.
  vmxT1ViDi		 (317),	  -- Gmux-2000 Vmux T1 card with 16 internal voice + 2 internal Data ports.
  vc12E1UeNe  (318),   -- Gmux-2000 Vmux E1 card with 12 external User (voice) + 2 external Network (Data) ports.
  vc12E1UeNi  (319),   -- Gmux-2000 Vmux E1 card with 12 external User (voice) + 2 internal Network (Data) ports.
  vc12E1UiNe  (320),   -- Gmux-2000 Vmux E1 card with 12 internal User (voice) + 2 external Network (Data) ports.
  vc12E1UiNi  (321),   -- Gmux-2000 Vmux E1 card with 12 internal User (voice) + 2 internal Network (Data) ports.
  vc12T1UeNe  (322),   -- Gmux-2000 Vmux T1 card with 12 external User (voice) + 2 external Network (Data) ports.
  vc12T1UeNi  (323),   -- Gmux-2000 Vmux T1 card with 12 external User (voice) + 2 internal Network (Data) ports.
  vc12T1UiNe  (324),   -- Gmux-2000 Vmux T1 card with 12 internal User (voice) + 2 external Network (Data) ports.
  vc12T1UiNi  (325),   -- Gmux-2000 Vmux T1 card with 12 internal User (voice) + 2 internal Network (Data) ports.
  vca16E1UeNe  (326),   -- Gmux-2000 VCA E1 card with 16 external User (voice) + 2 external Network (Data) ports.
  vca16E1UeNi  (327),   -- Gmux-2000 VCA E1 card with 16 external User (voice) + 2 internal Network (Data) ports.
  vca16E1UiNe  (328),   -- Gmux-2000 VCA E1 card with 16 internal User (voice) + 2 external Network (Data) ports.
  vca16E1UiNi  (329),   -- Gmux-2000 VCA E1 card with 16 internal User (voice) + 2 internal Network (Data) ports.
  vca16T1UeNe  (330),   -- Gmux-2000 VCA T1 card with 16 external User (voice) + 2 external Network (Data) ports.
  vca16T1UeNi  (331),   -- Gmux-2000 VCA T1 card with 16 external User (voice) + 2 internal Network (Data) ports.
  vca16T1UiNe  (332),   -- Gmux-2000 VCA T1 card with 16 internal User (voice) + 2 external Network (Data) ports.
  vca16T1UiNi  (333),   -- Gmux-2000 VCA T1 card with 16 internal User (voice) + 2 internal Network (Data) ports.
  vca12E1UeNe  (334),   -- Gmux-2000 VCA E1 card with 12 external User (voice) + 2 external Network (Data) ports.
  vca12E1UeNi  (335),   -- Gmux-2000 VCA E1 card with 12 external User (voice) + 2 internal Network (Data) ports.
  vca12E1UiNe  (336),   -- Gmux-2000 VCA E1 card with 12 internal User (voice) + 2 external Network (Data) ports.
  vca12E1UiNi  (337),   -- Gmux-2000 VCA E1 card with 12 internal User (voice) + 2 internal Network (Data) ports.
  vca12T1UeNe  (338),   -- Gmux-2000 VCA T1 card with 12 external User (voice) + 2 external Network (Data) ports.
  vca12T1UeNi  (339),   -- Gmux-2000 VCA T1 card with 12 external User (voice) + 2 internal Network (Data) ports.
  vca12T1UiNe  (340),   -- Gmux-2000 VCA T1 card with 12 internal User (voice) + 2 external Network (Data) ports.
  vca12T1UiNi  (341),   -- Gmux-2000 VCA T1 card with 12 internal User (voice) + 2 internal Network (Data) ports.
  vmg16E1Ue    (342),	-- Gmux-2000 VMG (Media Gateway) E1 card with 16 external User ports
  vmg16E1Ui    (343),	-- Gmux-2000 VMG (Media Gateway) E1 card with 16 internal User ports
  vmg16T1Ue    (344),	-- Gmux-2000 VMG (Media Gateway) T1 card with 16 external User ports
  vmg16T1Ui    (345),	-- Gmux-2000 VMG (Media Gateway) T1 card with 16 internal User ports
  vmg12E1Ue    (346),	-- Gmux-2000 VMG (Media Gateway) E1 card with 12 external User ports
  vmg12E1Ui    (347),	-- Gmux-2000 VMG (Media Gateway) E1 card with 12 internal User ports
  vmg12T1Ue    (348),	-- Gmux-2000 VMG (Media Gateway) T1 card with 12 external User ports
  vmg12T1Ui    (349)	-- Gmux-2000 VMG (Media Gateway) T1 card with 12 internal User ports


 }
      MAX-ACCESS  read-only
      STATUS  current
      DESCRIPTION
      "This object defines the Card type that this file is relevant for."
      ::= {intSwdlEntry 9}

intSwdlFlashIdx OBJECT-TYPE
      SYNTAX  Integer32
      MAX-ACCESS  read-only
      STATUS  current
      DESCRIPTION
      "The index of the flash memory this file is stored in (1 or 2)
      (Example: 1= The file is stored in flash No.1).
      ASMi52 file will always be stored in Flash No.2 (intSwdlFlashIdx=2)."
      ::= {intSwdlEntry 10}

--SW Download Status table

swdlStatusTable  OBJECT-TYPE 
      SYNTAX SEQUENCE OF SwdlStatusEntry
      MAX-ACCESS not-accessible
      STATUS  current
      DESCRIPTION
      "This parameters table is for software download status. 
       It also includes data about the files down-loaded or 
       attempted to be down-loaded."
      ::= { fileTransfer 11 }

swdlStatusEntry OBJECT-TYPE
      SYNTAX SwdlStatusEntry
      MAX-ACCESS not-accessible
      STATUS current
	DESCRIPTION  "An entry in table."
	INDEX {swdlStatusTypeIdx, swdlStatusIdx }
      ::= { swdlStatusTable 1}

SwdlStatusEntry ::=
      SEQUENCE {
      swdlStatusTypeIdx            Integer32,
	  swdlStatusIdx       		   Integer32,
	  swdlStatusFileName		   DisplayString,
	  swdlStatusSlot			   DisplayString,
	  swdlStatusSubSystem		   DisplayString,
	  swdlStatusStatus			   Integer32,
	  swdlStatusTime			   DisplayString
	       }

swdlStatusTypeIdx OBJECT-TYPE
      SYNTAX  Integer32
      MAX-ACCESS  read-only
      STATUS  current
      DESCRIPTION
      "The index of the down-load type (e.g. external (1) or internal (2))."
      ::= {swdlStatusEntry 1}

swdlStatusIdx OBJECT-TYPE
      SYNTAX  Integer32
      MAX-ACCESS  read-only
      STATUS  current
      DESCRIPTION
      "The index of the status rows."
      ::= {swdlStatusEntry 2}

swdlStatusFileName OBJECT-TYPE
      SYNTAX  	 DisplayString
      MAX-ACCESS  read-only
      STATUS  current
      DESCRIPTION
      "The name of the file."
      ::= {swdlStatusEntry 3}

swdlStatusSlot OBJECT-TYPE
      SYNTAX  	 DisplayString
      MAX-ACCESS  read-only
      STATUS  current
      DESCRIPTION
      "The slot of the updated (or attempted to be updated) object."
      ::= {swdlStatusEntry 4}

 swdlStatusSubSystem OBJECT-TYPE
      SYNTAX  	 DisplayString
      MAX-ACCESS  read-only
      STATUS  current
      DESCRIPTION
      "The subsystem that updated (or attempted to be updated)."
      ::= {swdlStatusEntry 5}

swdlStatusStatus  OBJECT-TYPE
      SYNTAX  	  Integer32
      MAX-ACCESS  read-only
      STATUS  current
      DESCRIPTION
      "The status of the down load process.
	  Value:  Fail (2), OK (3), InProcess (4)."
      ::= {swdlStatusEntry 6}

swdlStatusTime	   OBJECT-TYPE
          SYNTAX   DisplayString
          MAX-ACCESS  read-only
          STATUS  current
          DESCRIPTION
          "This MIB parameter indicates the time SW download was finished.
           The format shuld be YYYY-MM-DD, hh:mm:ss"
          ::= {swdlStatusEntry 7}

clearDwldStatusLog  OBJECT-TYPE
	SYNTAX  Integer32
	MAX-ACCESS  read-write
	STATUS  current
	DESCRIPTION
	"This object clears the status log.
	  Value: off(2), external(3), internal(4)
	  The Agent will change the value of this MIB object to off(2) 
	  automatically, after accepting the command ."
	::= { fileTransfer 12 }
									
autoFileTransfer  OBJECT IDENTIFIER ::= { fileTransfer 13}

-- Agent initiated auto file transfer.
									
autoFileTransferTable  OBJECT-TYPE 
      SYNTAX SEQUENCE OF AutoFileTransferEntry
      MAX-ACCESS not-accessible
      STATUS  current
      DESCRIPTION
      "Scheduling configuration table for 
       Agent initiated file transfer."
      ::= { autoFileTransfer 1 }

autoFileTransferEntry OBJECT-TYPE
      SYNTAX AutoFileTransferEntry
      MAX-ACCESS not-accessible
      STATUS current
      DESCRIPTION  "An entry in the table."
      INDEX { autoFileTransferType}
      ::= { autoFileTransferTable 1}

AutoFileTransferEntry ::=
      SEQUENCE {
                autoFileTransferType 
                  INTEGER,
                autoFileTransferServerIp
                  IpAddress,
                autoFileTransferFileName
                  SnmpAdminString,		
                autoFileTransferScheduling
                  INTEGER,
                autoFileTransferTimeRecurrence
                  Integer32,
                autoFileTransferOccurrenceRecurrence
                  Integer32 
               }

autoFileTransferType  OBJECT-TYPE
	SYNTAX INTEGER
	{
	alarmsBuffer    (1)
	}
	MAX-ACCESS  read-only
	STATUS  current
	DESCRIPTION
	"This object defines the type of file to be transferred 
	 by agent. "
	::= { autoFileTransferEntry 1 }

autoFileTransferServerIp  OBJECT-TYPE
	SYNTAX  IpAddress
	MAX-ACCESS  read-write
	STATUS  current
	DESCRIPTION
	"This object defines the IP Address of the
	 server to which the file is uploaded."
	::= { autoFileTransferEntry 2 }

autoFileTransferFileName  OBJECT-TYPE
	SYNTAX  SnmpAdminString
	MAX-ACCESS  read-write
	STATUS  current
	DESCRIPTION
	"This object defines the name of 
	 the file to be uploaded."
	::= { autoFileTransferEntry 3 }

autoFileTransferScheduling  OBJECT-TYPE
	SYNTAX INTEGER
	{
	notApplicable  (1),
	now            (2),
	recurrence     (3)	
	}
	MAX-ACCESS  read-write
	STATUS  current
	DESCRIPTION
	"This object defines schedule for TFTP Automatic session(s) 
	 initiated by Agent, according to the value selected:
     now          -  initiate immediate single session.

     recurrence- initiate single session 'every M time units'. 
                 or 'every N occurrences' or upon both, (earliest event).
                 Time reccurence period (M) is defined by
				 fileTransferTimeRecurrence.
				 Occurrence reccurence (N) is defined by 
				 fileTransferOccurrenceRecurrence.
                 Zero value means that the object is not relevant (not
                 taken into account for the recurrence). It is invalid 
                 that both will have zero values in our case (recurrence).
				 When both are non zero, file is transferred
				 upon earliest event"
	::= { autoFileTransferEntry 4 }

autoFileTransferTimeRecurrence  OBJECT-TYPE
	SYNTAX      Integer32 
	MAX-ACCESS  read-write
	STATUS      current
	DESCRIPTION										   
	"This object defines time reccurence interval, 
	 e.g. M can be 'every M days', 'every M hours' etc.
	 Zero is used to indicate 
	 there's no time reccurence (0= notApplicable).
	 This object is taken into account only 
	 if autoFileTransferScheduling = recurrence
	 For LA-110 time units are days."
	::= { autoFileTransferEntry 5 }

autoFileTransferOccurrenceRecurrence   OBJECT-TYPE
	SYNTAX      Integer32 
	MAX-ACCESS  read-write
	STATUS      current
	DESCRIPTION
	"This object defines Occurrence reccurence interval, 
	 e.g N can be in 'every N alarms', 'every N log entries' etc.
	 zero is used to indicate 
	 There's no Event Reccurence. (0= notApplicable) 
 	 This object is taken into account only 
	 if autoFileTransferScheduling = recurrence
	 Occurence Type (Alarms, etc.) is according
	 to autoFileTransferType."
	::= { autoFileTransferEntry 6 }

fileTransferServerPort OBJECT-TYPE
    SYNTAX  Unsigned32
    MAX-ACCESS  read-write
    STATUS  current
    DESCRIPTION
    "Server Port number used for File Transfer. 
     Applicable for SFTP.
     Valid values: 0..65535."
    -- DEFVAL  { 22 }
    ::= { fileTransfer 14 }

fileTransferProtocol OBJECT-TYPE
    SYNTAX  INTEGER
	{
	 tftp (1),	--default
	 sftp (2)
    }
    MAX-ACCESS  read-write
    STATUS  current
    DESCRIPTION
    "File Transfer protocol used."
    ::= { fileTransfer 15 }


systemReset  OBJECT-TYPE
    SYNTAX  INTEGER {
        off             (2),
        on              (3), --HW
        resetConfig     (4),
        resetMapping    (5),
        resetStandby    (6),
        factoryDefault  (7),
        userDefault     (8)
        }
    MAX-ACCESS  read-write
    STATUS  current
    DESCRIPTION
    "Reset action to be performed on the system.
     - resetConfig    (4) - reset to default configuration; in case of existing
                            user default configuration, it will be reset to this configuration
     - resetMapping   (5) - reset SDH/SONET mapping to default for all SDH/SONET links
     - resetStandby   (6) - can be used only by devices with redundancy on MAIN/CL
     - factoryDefault (7) - execute the factory-default command
     - userDefault    (8) - execute the user-default command"
    ::= { agnt 13 }

systemTiming  OBJECT IDENTIFIER ::= { agnt 14 }

systemDate OBJECT-TYPE
        SYNTAX  DisplayString
        MAX-ACCESS  read-write
        STATUS  current
        DESCRIPTION
           "System date."
        ::= { systemTiming 1 }

systemTime OBJECT-TYPE
        SYNTAX  DisplayString
        MAX-ACCESS  read-write
        STATUS  current
        DESCRIPTION
           "System time."
        ::= { systemTiming 2 }

systemTimeElapsed OBJECT-TYPE
       SYNTAX  Integer32 (0..899)
       MAX-ACCESS  read-only
       STATUS  current
       DESCRIPTION
       "The number of seconds that have elapsed since the
        beginning of the current error-measurement
        period. Same for all ports of the device."
       ::= { systemTiming 3 }

systemNtp  OBJECT IDENTIFIER ::= { systemTiming 4 } -- Network Time Protocol

systemNtpMode OBJECT-TYPE
	SYNTAX		INTEGER
	{
		disable			(2),
		broadcastClient	(3),
		unicastClient	(4)
	}
	MAX-ACCESS	read-write
	STATUS		current
	DESCRIPTION
	"This variable represents the NTP Mode."
	::= { systemNtp 1 }

systemNtpGmt OBJECT-TYPE
    SYNTAX      Integer32
    MAX-ACCESS  read-write
    STATUS      current
    DESCRIPTION
    "This variable represents the NTP GMT (Greenwich Mean Time),
     Possible values range is -12..12.
     For new devices/versions this variable will be in minutes."
    ::= { systemNtp 2 }

systemNtpServerAddressType OBJECT-TYPE
	SYNTAX		InetAddressType
	MAX-ACCESS	read-write
	STATUS		current
	DESCRIPTION
	"This variable represents the NTP Server Address Type."
	::= { systemNtp 3 }

systemNtpServerAddress OBJECT-TYPE
	SYNTAX		InetAddress
	MAX-ACCESS	read-write
	STATUS		current
	DESCRIPTION
	"This variable represents the NTP Server Address."
	::= { systemNtp 4 }

systemNtpUpdateInterval OBJECT-TYPE
    SYNTAX      Unsigned32
    MAX-ACCESS  read-write
    STATUS      current
    DESCRIPTION
    "This variable represents the NTP Update Interval,
     measured in seconds. It means, minimum time between two
     consecutive NTP requests."
    ::= { systemNtp 5 }

systemNtpCmd OBJECT-TYPE
	SYNTAX		INTEGER
	{
		off					(2),
		sendUpdateRequest	(3)
	}
	MAX-ACCESS	read-write
	STATUS		current
	DESCRIPTION
	"This variable represents NTP possible commands.
	 After the Agent accepts a command, it will automatically change
	 the value to off(2)."
	::= { systemNtp 6 }

systemNtpTimeSinceLastPoll OBJECT-TYPE
    SYNTAX Unsigned32
       MAX-ACCESS read-only
       STATUS current
    DESCRIPTION
    "Time in seconds, that passed from last polling of the configured
     SNTP servers. 0=Not Applicable (when this time is not known)."
    ::= { systemNtp 7 }

systemNtpModeBITS OBJECT-TYPE
    SYNTAX      BITS{
    broadcastClient(0)
    }
    MAX-ACCESS  read-write
    STATUS      current
    DESCRIPTION
    "If Bit 0 (broadcastClient) is '1', Broadcast Mode is enabled,
     meaning that the device listens to the NTP broadcast messages
     and learns timestamps from them.
     If disabled (Bit 0 = '0'), the device ignores NTP broadcast
     messages.
     Unicast mode is always enabled, therefore there is no special
     Bit for it."
    ::= { systemNtp 8 }

systemNtpCurrentSourceType OBJECT-TYPE
    SYNTAX    InetAddressType
    MAX-ACCESS  read-only
    STATUS      current
    DESCRIPTION
    "Type IP address of the NTP Server currently providing system TOD."
    ::= { systemNtp 9 }

systemNtpCurrentSource OBJECT-TYPE
    SYNTAX      InetAddress
    MAX-ACCESS  read-only
    STATUS      current
    DESCRIPTION
    "IP Address of the server (or local hardware) providing the
     current Date and Time of the device. In addition to valid IP
     address the following special values are used:
     127.0.0.1 = local HW clock is used.
     0.0.0.0 = no clock is available.
     0.0.0.1 = clock provided by NTP, potentially from multiple servers"
    ::= { systemNtp 10 }

sntpServerTable OBJECT-TYPE
    SYNTAX      SEQUENCE OF SntpServerEntry
    MAX-ACCESS  not-accessible
    STATUS      current
    DESCRIPTION
    "This table contains parameters for each NTP Server.
     Entries in the table can be dynamically created.
     The entries created by user via sntpServerRowStatus, can also be
     changed or removed.
     The table may include also Broadcast Servers, when Broadcast
     Client Mode is enabled. These are Servers from which the device
     received timestamp by Broadcast. Their entries are automatically
     created by the device. Entries of these Servers cannot
     be changed or removed."
    ::= { systemNtp 11 }

sntpServerEntry OBJECT-TYPE
    SYNTAX      SntpServerEntry
    MAX-ACCESS  not-accessible
    STATUS      current
    DESCRIPTION
    "An entry in the NTP Server table."
    INDEX {  sntpServerID }
    ::= { sntpServerTable 1 }

SntpServerEntry ::= SEQUENCE {
    sntpServerID                        Unsigned32,
    sntpServerRowStatus                 RowStatus,
    sntpServerAddressType               InetAddressType,
    sntpServerAddress                   InetAddress,
    sntpServerPort                      InetPortNumber,
    sntpServerPreference                Unsigned32,
    sntpServerAdminStatus               INTEGER,
    sntpServerType                      INTEGER,
    sntpServerLastReceivedTimestamp     DateAndTime,
    sntpServerLastReceivedStratum       Unsigned32,
    sntpServerTimeSinceLastReceivedMessage TimeTicks,
    sntpServerSendRequestNow            INTEGER 
 }

sntpServerID    OBJECT-TYPE
    SYNTAX      Unsigned32
    MAX-ACCESS  not-accessible
    STATUS      current
    DESCRIPTION
    "The number (index) of the NTP Server."
    ::= { sntpServerEntry 1 }

sntpServerRowStatus OBJECT-TYPE
    SYNTAX      RowStatus
    MAX-ACCESS  read-create
    STATUS      current
    DESCRIPTION
    "This object enables creation and deletion of entries
     in the sntpServerTable."
    ::= { sntpServerEntry 2 }

sntpServerAddressType OBJECT-TYPE
    SYNTAX      InetAddressType
    MAX-ACCESS  read-create
    STATUS      current
    DESCRIPTION
    "Server Address type, indicating IPv4(1) or IPv6(2)."
    ::= { sntpServerEntry 3 }

sntpServerAddress OBJECT-TYPE
    SYNTAX      InetAddress
    MAX-ACCESS  read-create
    STATUS      current
    DESCRIPTION
    "IP Address of the NTP Server."
    ::= { sntpServerEntry 4 }

sntpServerPort OBJECT-TYPE
    SYNTAX      InetPortNumber
    MAX-ACCESS  read-create
    STATUS      current
    DESCRIPTION
    "Source UDP port of the device for sending requests to
     a configured NTP Server."
    DEFVAL {123}
    ::= { sntpServerEntry 5 }

sntpServerPreference OBJECT-TYPE
    SYNTAX      Unsigned32
    MAX-ACCESS  read-create
    STATUS      current
    DESCRIPTION
    "This object marks the Preferred Server.
     1 = Preferred (only one Server can have this value)
     2 - Not Preferred."
    ::= { sntpServerEntry 6 }

sntpServerAdminStatus OBJECT-TYPE
    SYNTAX      INTEGER {
                up  (1),
                down(2)
                        }
    MAX-ACCESS  read-create
    STATUS      current
    DESCRIPTION
    "Administrative Status of the NTP Server."
    ::= { sntpServerEntry 7 }

sntpServerType OBJECT-TYPE
    SYNTAX     INTEGER {
               unicast  (1),
               broadcast(2)
                     }
    MAX-ACCESS  read-only
    STATUS      current
    DESCRIPTION
    "Type of the NTP Server."
    ::= { sntpServerEntry 8 }

sntpServerLastReceivedTimestamp OBJECT-TYPE
    SYNTAX      DateAndTime
    MAX-ACCESS  read-only
    STATUS      current
    DESCRIPTION
    "Last received Date and Time from the NTP Server, according to
     UTC Time.
     0000 0000 = Not Applicable."
    ::= { sntpServerEntry 9 }

sntpServerLastReceivedStratum OBJECT-TYPE
    SYNTAX      Unsigned32
    MAX-ACCESS  read-only
    STATUS      current
    DESCRIPTION
    "Last received Stratum from the NTP Server.
     0xFFFFFFFF = Not Applicable."
    ::= { sntpServerEntry 10 }

sntpServerTimeSinceLastReceivedMessage OBJECT-TYPE
    SYNTAX      TimeTicks
    MAX-ACCESS  read-only
    STATUS      current
    DESCRIPTION
    "Time passed since last received message from the NTP Server."
    ::= { sntpServerEntry 11 }

sntpServerSendRequestNow OBJECT-TYPE
    SYNTAX      INTEGER {
                off(2),
                on (3)
                        }
    MAX-ACCESS  read-create
    STATUS      current
    DESCRIPTION
    "Upon setting this parameter to 'on', an immediate request
     should be sent to the specified NTP Server.
     After sending the request, the value 'off' will be resumed.
     No action when setting this parameter to 'off'"
    ::= { sntpServerEntry 12 }

systemNtpLockingStatus OBJECT-TYPE
    SYNTAX      INTEGER
    {
    notApplicable        (1),
    acquisition          (2),
    accuracyInLimit      (3),
    accuracyOutOfLimit   (4)
    }
    MAX-ACCESS  read-only
    STATUS      current
    DESCRIPTION
    "NTP locking status.

    This object is only relevant when the value of systemNtpUpdateInterval is zero.
    Otherwise, the value notApplicable(1) is returned.
    "
    ::= { systemNtp 12 }

systemSummerTimeState OBJECT-TYPE
    SYNTAX Unsigned32
    MAX-ACCESS read-only
    STATUS current
    DESCRIPTION
    "When the agent is not in summer time this object returns 0.
     While in summer time it returns the number of minutes the clock has been moved."
    ::= { systemNtp 13 }

schedXTable OBJECT-TYPE
    SYNTAX      SEQUENCE OF SchedXEntry
    MAX-ACCESS  not-accessible
    STATUS      current
    DESCRIPTION
        "An Augment to the Schedule table
         (schedTable in DISMAN-SCHEDULE-MIB; RFC-3231)."
     ::= { systemTiming 5 }

schedXEntry OBJECT-TYPE
    SYNTAX      SchedXEntry
    MAX-ACCESS  not-accessible
    STATUS      current
    DESCRIPTION
       "An entry in the table."
    AUGMENTS { schedEntry }
     ::= { schedXTable 1 }

SchedXEntry ::= SEQUENCE {
    schedYear         Unsigned32,
    schedWeekInMonth		INTEGER,
    schedParam			Integer32,
    schedXWeek        BITS,
    schedAction       OCTET STRING 
 }

schedYear OBJECT-TYPE
    SYNTAX      Unsigned32
    MAX-ACCESS  read-create
    STATUS      current
    DESCRIPTION
    "The year during which the scheduled action should take place."
    ::= { schedXEntry 1 }

schedWeekInMonth OBJECT-TYPE
	SYNTAX		INTEGER {
     	first		(1),
	 	second 		(2),
	 	third 		(3),
	 	fourth 		(4),
	 	last 		(5)
	}
	MAX-ACCESS  read-create
	STATUS  	current
	DESCRIPTION
	"The week in month (schedMonth) during which the scheduled action
	 should take place."
	::= { schedXEntry 2 }

schedParam OBJECT-TYPE
	SYNTAX		Integer32
	MAX-ACCESS  read-create
	STATUS  	current
	DESCRIPTION
	"A Parameter that might be used whenever the scheduled action takes place.
	 
	 For summer-time schedule -
	 This variable represents the time offset (in minutes), meaning:
	 the number of minutes that should be added for summer-time."
	::= { schedXEntry 3 }

schedXWeek OBJECT-TYPE
    SYNTAX BITS {
        first   (0),
        second  (1),
        third   (2),
        fourth  (3),
        fifth   (4),
        last    (5)
    }
    MAX-ACCESS  read-create
    STATUS      current
    DESCRIPTION
    "The set of weeks within a month (schedMonth) during which the scheduled action
     should take place."
    DEFVAL { {} }
    ::= { schedXEntry 4 }

schedAction OBJECT-TYPE
    SYNTAX OCTET STRING (SIZE (0..1024))
    MAX-ACCESS read-create
    STATUS current
    DESCRIPTION
    "The action that should take place when the schedule is executed.
     By default it is '60' for summer time start, and empty string otherwise."
    ::= { schedXEntry 5 }






systemPort  OBJECT IDENTIFIER ::= { agnt 15 }

physicalConnectorTable OBJECT-TYPE
    SYNTAX  SEQUENCE OF PhysicalConnectorEntry
    MAX-ACCESS  not-accessible
    STATUS current
    DESCRIPTION
    "This table includes the connector type of ports or interfaces."
    ::= {systemPort 1}

physicalConnectorEntry OBJECT-TYPE
    SYNTAX  PhysicalConnectorEntry
    MAX-ACCESS  not-accessible
    STATUS current
    DESCRIPTION  "An entry in table."
    INDEX {portIdx}
    ::= { physicalConnectorTable 1 }

PhysicalConnectorEntry ::= SEQUENCE {
    portIdx                         Integer32,
    physicalConnector               INTEGER,
    portOptWaveLength               INTEGER,
    portOptMode                     INTEGER,
    portBalance                     INTEGER,
    portDdmSupport                      INTEGER,
    portMfgName                         SnmpAdminString,
    portTypicalMaxRange                 Unsigned32,
    physicalConnectorString             SnmpAdminString,
    portVendorPartNo                    SnmpAdminString,
    physicalConnectorUsed               INTEGER,
    physicalConnectorSfpWaveLength      Unsigned32 
 }

portIdx OBJECT-TYPE
    SYNTAX  Integer32
    MAX-ACCESS  read-only
    STATUS current
    DESCRIPTION
    "This object is an index of the specific port or interface.
     For a port, the index will be as agreed between agent and
     application.
     For an interface, ifIndex may be used."
    ::= { physicalConnectorEntry 1 }

physicalConnector OBJECT-TYPE
    SYNTAX      INTEGER {
        other             (1),
        v35               (2), --34 pin female
        rs530             (3), --DB25
        x21               (4), --DB15
        bnc               (5),
        utp               (6), --RJ45
        aui               (7),
        rs422             (8), --DB25
        crossUtp          (9), --RJ45
        rj45              (10),
        v24               (11), --DB25
        g703              (12), --TB5
        termBlock3AndRj45 (13),
        terminalBlock3    (14),
        terminalBlock5    (15),
        terminalBlock7    (16),
        db25              (17),
        db15              (18),
        rj45ethernet      (19),
        termBlock5AndRj45 (20),
        db9               (21),
        g703E1            (22), --BNC-RJ45-BNC
        g703E1-LTU        (23), --BNC-RJ45-BNC
        sc                (24), --sc optical
        st                (25), --st optical
        stl               (26),
        fc                (27), --fc optical
        tb5w              (28), --Term-Block-5-Wire (for HCD)
        termBlock6AndRj45 (29),
        ethBnc            (30),
        scsi26            (31), --SCSI with 26 pins
        eth4381           (32), --RJ45 with two embeded LEDs
        twoBnc            (33), --Two BNC
        scsi50            (34), --SCSI with 50 pins
        twoMiniBnc        (35), --Two mini BNC
        sf1               (36), --sf1=single fiber optical
        terminalBlock4    (37),
        sf2               (38), --sf2=single fiber optical
        db25Balanced      (39), --DB25 Balanced
        v36               (40),
        block4W           (41), --like in WR connector for Modems
        iripRj45          (42),
        irEthQRj45        (43),
        iripBnc           (44),
        rs530WA           (45), --rs530/IR that solves a wander problem for SDH network
        v35WA             (46), --v35/IR that solves a wander problem for SDH network
        irEthQBnc         (47),
        v35Db25           (48), --V.35 with connector DB25
        rj11              (49), --Used for FXS & FXO
        mtrj              (50), --optical
        lc                (51), --optical
        terminalBlock2    (52),
        irEth10s100       (53), --IR-ETH 10/100
        scsi68            (54), -- SCSI 68 pins
        sf3               (55), -- sf3=single fiber of sc optical
        fcLH              (56), -- fc Long Haul
        telco50           (57), -- TELCO 50
        telco64           (58), -- TELCO 64
        irEthQN           (59),
        terminalBlock6    (60),
        scLH              (61), -- sc Long Haul
        stLH              (62), -- st Long Haul
        lcLH              (63), -- lc Long Haul
        sfpIn             (64), -- SFP module is installed (In container)
        sfpOut            (65), -- SFP module is not installed (Out of container)
        db44              (66), -- DB44 (High Density D-type)
        db62              (67), -- DB62 (High Density D-type)
        v24Db9            (68), -- V.24 with connector DB9
        scsi40            (69), -- SCSI 40 pins
        sf1NineRow        (70), -- sf1 9-row
        sf2NineRow        (71), -- sf2 9-row
        sf3NineRow        (72), -- sf3 9-row
        smartSerial26     (73), -- QDC1113L (Cisco)
        miniUsb5          (74),
        db26              (75), -- DB26 (High Density D-Type)
        comboUtpSfpIn     (76), -- UTP+SFP combo, SFP module is installed
        comboUtpSfpOut    (77), -- UTP+SFP combo, SFP module is not installed
        hiDensity160Pin   (78), -- CISCO High Density Connector with 160 Pins
        xfpIn             (79), -- XFP module is installed (In container)
        xfpOut            (80), -- XFP module is not installed (Out of container)
        ssfpIn            (81), -- Smart SFP is installed
        ssfpOut           (82), -- Smart SFP is not plugged-in
        comboUtpSsfpIn    (83), -- Smart SFP is plugged-in on combo port
        comboUtpSsfpOut   (84), -- Smart SFP is not plugged-in on combo port
        scsi68DS          (85), -- Double Signaling SCSI 68 pins
        miniBnc           (86), -- mini BNC Connector
        sMA               (87), -- GPS Connector
        rj45Shdsl8w       (88), -- rj45Shdsl8w
        miniBncAndRj45    (89), -- Mini BNC & RJ45 Connectors (used for 1pps or EXT CLK)
        sfpPlusIn         (90), -- SFP+ module is installed (In container)
        sfpPlusOut        (91), -- SFP+ module is not installed (Out of container)
        none              (255)
        }
    MAX-ACCESS  read-only
    STATUS      current
    DESCRIPTION
            "The connector of the port/interface.
            other - none of the specified connectors
            none -  no connector."
    ::= { physicalConnectorEntry 2 }

portOptWaveLength OBJECT-TYPE
    SYNTAX  INTEGER {
        notApplicable(1),
        nm850(2),
        nm1310(3),
        nm1310Laser(4),
        nm1550Laser(5),
        nm1470Laser(6),
        nm1490Laser(7),
        nm1510Laser(8),
        nm1530Laser(9),
        nm1570Laser(10),
        nm1590Laser(11),
        nm1610Laser(12),
        nm1330Laser(13),
        nm1270Laser(14)
    }
    MAX-ACCESS  read-only
    STATUS  current
    DESCRIPTION
     "Wave Length of an Optical interface/port in [nm] and specification if
      Laser or not.
      notApplicable - for non-optical ports."
     ::= { physicalConnectorEntry 3 }

portOptMode OBJECT-TYPE
    SYNTAX  INTEGER {
        notApplicable(1),
        singleMode(2),
        multiMode(3)
    }
    MAX-ACCESS  read-only
    STATUS  current
    DESCRIPTION
     "Laser Mode of an Optical Laser interface/port.
       notApplicable - for non-Laser ports."
     ::= { physicalConnectorEntry 4 }

portBalance OBJECT-TYPE
    SYNTAX  INTEGER {
      notApplicable (1),
      unbalanced    (2),
      balanced      (3)
      }
      MAX-ACCESS  read-write
      STATUS  current
      DESCRIPTION
      "This object is according to the port Impedance.
       For T1 - always balanced.
       For E1 - there are different impedance values for balanced
                and unbalanced."
     ::= { physicalConnectorEntry 5 }

portDdmSupport  OBJECT-TYPE
    SYNTAX  INTEGER {
      notApplicable (1),
      no     (2),
      yes    (3)
      }
    MAX-ACCESS  read-only
      STATUS  current
      DESCRIPTION
      "SFP (Small Form Pluggable) port -support
       Digital Diagnostics Monitoring."
     ::= { physicalConnectorEntry 6 }

portMfgName OBJECT-TYPE
    SYNTAX      SnmpAdminString
    MAX-ACCESS  read-only
    STATUS      current
    DESCRIPTION
            "(SFP) Port Manufacturer name (Maximum - 16 characters)."
     ::= { physicalConnectorEntry 7 }

portTypicalMaxRange  OBJECT-TYPE
    SYNTAX  Unsigned32
    MAX-ACCESS  read-only
      STATUS  current
      DESCRIPTION
      "Maximum range supported by SFP port,
       in meter units."
     ::= { physicalConnectorEntry 8 }

physicalConnectorString  OBJECT-TYPE
    SYNTAX  SnmpAdminString
    MAX-ACCESS  read-only
      STATUS  current
      DESCRIPTION
      "(SFP) connector type. It can be Vendor Specific
       (unknown in advance). Being a string, the object is not
       affected by any future new connectors.
       This object will usually not be used
       for drawing the connector."
     ::= { physicalConnectorEntry 9 }

portVendorPartNo OBJECT-TYPE
    SYNTAX      SnmpAdminString
    MAX-ACCESS  read-only
    STATUS      current
    DESCRIPTION
            "SFP Vendor Part Number. Being a string, the object is not
            affected by any future new SFPs."
     ::= { physicalConnectorEntry 10 }

physicalConnectorUsed OBJECT-TYPE
    SYNTAX  INTEGER {
      notApplicable  (1),
      sfpOrRj45 (2),
      sfpOnly   (3),
      rj45Only  (4)
      }
      MAX-ACCESS  read-write
      STATUS  current
      DESCRIPTION
      "This object is relevant only when the value of physicalConnector
       is comboUtpSfpIn(76) or comboUtpSfpOut(77).
       sfpOrRj45 - (default value) If SFP is inserted (In), SFP is used
                   (RJ45 is not used (shut)).
                   If SFP is not inserted (Out), RJ45 is used.
       sfpOnly   - SFP is used (RJ45 always shut)
       rj45Only  - RJ45 is used (SFP always shut). "
     ::= { physicalConnectorEntry 11 }


physicalConnectorSfpWaveLength OBJECT-TYPE
    SYNTAX  Unsigned32
    UNITS   "hundredths of nm"
    MAX-ACCESS  read-only
    STATUS  current
    DESCRIPTION
    "Wavelength of a fiber optic SFP/XFP in units of hundredths of nm.
     The value zero is returned for non-optical ports.
    "
    ::= { physicalConnectorEntry 18 }

prtSupervisory  OBJECT IDENTIFIER ::= { systemPort 2 }

prtSpTable OBJECT-TYPE
      SYNTAX SEQUENCE OF PrtSpEntry
      MAX-ACCESS not-accessible
      STATUS current
	DESCRIPTION  "A table."
	::=  {prtSupervisory 1}

prtSpEntry OBJECT-TYPE
      SYNTAX PrtSpEntry
      MAX-ACCESS not-accessible
      STATUS current
      DESCRIPTION
      "Supervisory port parameter table."
      INDEX {prtSupervisoryIndex }
      ::= { prtSpTable 1}

PrtSpEntry ::=
      SEQUENCE {
      prtSupervisoryIndex         Integer32,
	  prtSupervisoryRate          INTEGER,
	  prtSupervisoryDataBits      INTEGER,
	  prtSupervisoryParity        INTEGER,
	  prtSupervisoryStopBits      INTEGER,
	  prtSupervisoryUsage         INTEGER,
	  prtSupervisoryInterface     INTEGER,
	  prtSupervisoryCTS		      INTEGER,
	  prtSupervisoryDcdDelay      INTEGER,
	  prtSupervisoryDSR		      INTEGER,
	  prtSupervisoryRoutProtocol  INTEGER
      }				  

prtSupervisoryIndex OBJECT-TYPE
      SYNTAX  Integer32
      MAX-ACCESS  read-only
      STATUS  current
      DESCRIPTION
      "The SP port index.
       For some products, having modules (cards): 
       The LS byte of the integer is the port index 1..255. 
       The MS byte is different than 0 only if the port belongs to 
       a module. In	that case it is the module number.
       For other products' index see their specification."
      ::= { prtSpEntry 1}

prtSupervisoryRate     OBJECT-TYPE
      SYNTAX  INTEGER
	      {
        auto      (1),
        s300bps   (2),
        s1200bps  (3),
        s2400bps  (4),
        s4800bps  (5),
        s9600bps  (6),
        s19200bps (7),
        s38400bps (8),
        s57600bps (9),
        s115200bps (10)
	      }
      MAX-ACCESS  read-write
      STATUS  current
      DESCRIPTION
      "This attribute indicates the operation rate (speed) of the 
       port.
       auto - automatic rate selection, by the agent."
      ::= { prtSpEntry 2}

prtSupervisoryDataBits OBJECT-TYPE
      SYNTAX  INTEGER
	      {
        dataBits7 (1),
        dataBits8 (2)
	      }
      MAX-ACCESS  read-write
      STATUS  current
      DESCRIPTION
      "This attribute indicates the number of data bits in an async 
       frame"
      ::= { prtSpEntry 3}

prtSupervisoryParity OBJECT-TYPE
      SYNTAX  INTEGER
	      {
        none  (1),
        odd   (2),
        even  (3)
	      }
      MAX-ACCESS  read-write
      STATUS  current
      DESCRIPTION
      "This attribute indicates the parity mode in an async frame"
      ::= { prtSpEntry 4}

prtSupervisoryStopBits OBJECT-TYPE
      SYNTAX  INTEGER
	      {
		notApplicable  (1),
        stopBits1      (2),
        stopBits1dot5  (3),
        stopBits2      (4)
	      }
      MAX-ACCESS  read-write
      STATUS  current
      DESCRIPTION
      "This attribute indicates the parity mode in an async frame."
      ::= { prtSpEntry 5}

prtSupervisoryUsage OBJECT-TYPE
      SYNTAX  INTEGER
	      {
		unknown (1),
		noUse   (2),
		terminal(3),
		nmsSlip (4),
		nmsPpp  (5),
		muxSlip (6),
		muxPpp  (7),
		dialOut (8)
	      }
      MAX-ACCESS  read-write
      STATUS  current
      DESCRIPTION
      "This attribute indicates the usage of the SP port."
      ::= { prtSpEntry 6}

prtSupervisoryInterface OBJECT-TYPE
      SYNTAX  INTEGER
	      {
		  notApplicable(1),
          dce  (2),
          dte  (3)
	      }
      MAX-ACCESS  read-write
      STATUS  current
      DESCRIPTION
      "This attribute indicates the supervisory port interface."
      ::= { prtSpEntry 7}

prtSupervisoryCTS OBJECT-TYPE
      SYNTAX  INTEGER
	      {
          	notApplicable   (1),
          	on            	(2),        --Old value for DCE.
			rts           	(3),        --Old value for DCE 
			dteWait         (4),        --DTE will wait for CTS to become active before transmit date.
			dteIgnore       (5)         --DTE will Ignore CTS signal and will transmit date anyway.
	      }
      MAX-ACCESS  read-write
      STATUS  current
      DESCRIPTION
	  "CTS line state." 
      ::= { prtSpEntry 8}

prtSupervisoryDcdDelay OBJECT-TYPE
      SYNTAX  INTEGER
	      {
          notApplicable (1),
          d0   (2),
          d10  (3),
		  d50  (4),
		  d100 (5),
		  d200 (6),
		  d300 (7)
	      }
      MAX-ACCESS  read-write
      STATUS  current
      DESCRIPTION
	  "DCD delay in msec." 
      ::= { prtSpEntry 9}

prtSupervisoryDSR OBJECT-TYPE
      SYNTAX  INTEGER
	      {
          notApplicable (1),
          on   (2),
          dtr  (3)
	      }
      MAX-ACCESS  read-write
      STATUS  current
      DESCRIPTION
	  "DSR line state." 
      ::= { prtSpEntry 10}

prtSupervisoryRoutProtocol OBJECT-TYPE
      SYNTAX  INTEGER
       {
        notApplicable (1),
  		none          (2),
        proprietary   (3),
        rip2          (4)
       }
      MAX-ACCESS  read-write
      STATUS  current
      DESCRIPTION
      "This attribute indicates the routing protocol of the port.
       notApplicable - for DP."
      ::= { prtSpEntry 11}




--Port Performance Data

prtPerformance  OBJECT IDENTIFIER ::= { systemPort 3 }

prtPerfTable OBJECT-TYPE
	SYNTAX  SEQUENCE OF PrtPerfEntry
	MAX-ACCESS  not-accessible
	STATUS current
	DESCRIPTION
	"This table includes G.826 ports or interfaces."
	::= {prtPerformance 1}

prtPerfEntry OBJECT-TYPE
	SYNTAX  PrtPerfEntry
	MAX-ACCESS  not-accessible
	STATUS current
	DESCRIPTION  "An entry in table."
	INDEX {prtPerfIdx, prtPerfPeriodRef}
	::= { prtPerfTable 1 }

PrtPerfEntry  ::=
	    SEQUENCE {
	prtPerfIdx
	  Integer32,
	prtPerfPeriodRef
	  INTEGER,
	prtPerfElapsedTime
	  Integer32,
	prtPerfUAS
	  Integer32,
	prtPerfES
	  Integer32,
	prtPerfSES
	  Integer32,
	prtPerfBBE
	  Integer32,
	prtPerfBlocksPerSec
	  Integer32,
	prtPerfTimeTag
	  TimeTicks,
	prtPerfSaveAndResetCmd
	  INTEGER
	  }

prtPerfIdx OBJECT-TYPE
	SYNTAX  Integer32 
	MAX-ACCESS  read-only
	STATUS current
	DESCRIPTION
	"This object is an index of the specific port or interface.
	 For a port, the index will be as agreed between agent and 
	 application.
	 For an interface, ifIndex may be used."
	::= { prtPerfEntry 1 }

prtPerfPeriodRef OBJECT-TYPE
	SYNTAX  INTEGER 
	      {
          currentPeriod (1),
          lastPeriod    (2)
	      }
	MAX-ACCESS  read-only
	STATUS  current
	DESCRIPTION
	"This object is an index that specifies which period of time, the next
	 5 objects refer to.
	 currentPeriod - the period since last prtPerfSaveAndResetCmd received or
	           since Start-up (if no prtPerfSaveAndResetCmd was received since
	           Start-up) until now.
	 lastPeriod - the period between last two commands of prtPerfSaveAndResetCmd.
	           - If only one command occured since Start-up: the period between 
	             Start-up and last command.
	           - If no command occured since Start-up: this period will not 
	             actually exist. In this case, he following 5 objects will be 0."
	::= { prtPerfEntry 2 }

prtPerfElapsedTime OBJECT-TYPE
	SYNTAX  Integer32 
	MAX-ACCESS  read-only
	STATUS  current
	DESCRIPTION
	"Elapsed Time in seconds.
	 - for prtPerfPeriodRef=currentPeriod:
	   The period since last prtPerfSaveAndResetCmd received or	since Start-up 
	   (if no prtPerfSaveAndResetCmd was received since	Start-up) until now.
	 - for prtPerfPeriodRef=lastPeriod:
	   The value of prtPerfElapsedTime when last prtPerfSaveAndResetCmd
	   was received."
	::= { prtPerfEntry 3 }

prtPerfUAS OBJECT-TYPE
	SYNTAX  Integer32 
	MAX-ACCESS  read-only
	STATUS  current
	DESCRIPTION
	"Number of Unavailable Seconds for the reference period (prtPerfPeriodRef)."
	::= { prtPerfEntry 4 }

prtPerfES OBJECT-TYPE
	SYNTAX  Integer32 
	MAX-ACCESS  read-only
	STATUS  current
	DESCRIPTION
	"Number of Errored Seconds for the reference period (prtPerfPeriodRef)."
	::= { prtPerfEntry 5 }

prtPerfSES OBJECT-TYPE
	SYNTAX  Integer32 
	MAX-ACCESS  read-only
	STATUS  current
	DESCRIPTION
	"Number of Severely Errored Seconds for the reference period (prtPerfPeriodRef)."
	::= { prtPerfEntry 6 }

prtPerfBBE OBJECT-TYPE
	SYNTAX  Integer32 
	MAX-ACCESS  read-only
	STATUS  current
	DESCRIPTION
	"Number of Background Block (or Frame) Errors for the reference period 
	 (prtPerfPeriodRef)."
	::= { prtPerfEntry 7 }

prtPerfBlocksPerSec OBJECT-TYPE
	SYNTAX  Integer32 
	MAX-ACCESS  read-only
	STATUS  current
	DESCRIPTION
	"Blocks per second (or frames per second) of the port/interface indicated by 
	 portIdx. This object is constant for a certain port/interface.
	 It is not affected by the prtPerfPeriodRef index."
	::= { prtPerfEntry 8 }

prtPerfTimeTag OBJECT-TYPE
	SYNTAX  TimeTicks 
	MAX-ACCESS  read-only
	STATUS  current
	DESCRIPTION
	"Time Tag of Last Period: sysUpTime when last prtPerfSaveAndResetCmd was
	 executed.
	 This object is applicable only for prtPerfPeriodRef=lastPeriod.
	 For prtPerfPeriodRef=currentPeriod, the value will always be 0."
	::= { prtPerfEntry 9 }

prtPerfSaveAndResetCmd OBJECT-TYPE
    SYNTAX   INTEGER
	      {
    		off(2),
	    	on (3)
	      }
    MAX-ACCESS  read-write
    STATUS  current
    DESCRIPTION
    "A command per port/interface, to Save data of Current Period in Last Period
     data-set and start a new counting period for Current Period.
     This object is applicable only for prtPerfPeriodRef=currentPeriod.
     Setting this object to on(3) for prtPerfPeriodRef=last, will cause the agent
     to return: Bad Value response.
     When setting validly this object to on(3), agent will perform the required 
     command and will reset automatically the value of this object to off(2).
     Setting this object to off(2), will do nothing."
    ::= { prtPerfEntry 10 }

--Port Test Data

prtTest OBJECT IDENTIFIER ::= { systemPort 4 }

prtTestTable OBJECT-TYPE
    SYNTAX  SEQUENCE OF PrtTestEntry
    MAX-ACCESS  not-accessible
    STATUS current
    DESCRIPTION
    "This table includes test data for ports or interfaces."
    ::= {prtTest 1}

prtTestEntry OBJECT-TYPE
    SYNTAX  PrtTestEntry
    MAX-ACCESS  not-accessible
    STATUS current
    DESCRIPTION  "An entry in table."
    INDEX {prtTestIdx}
    ::= { prtTestTable 1 }

PrtTestEntry ::= SEQUENCE {
    prtTestIdx         Integer32,
    prtTestCmdAndStatus         Integer32,
    	prtBertCounter Integer32,
		prtTestInitiator 	INTEGER,
    prtTestTimeout         Integer32,
		prtTestVctRxResult 	INTEGER,
		prtTestVctTxResult 	INTEGER,
		prtTestVctRxDistance 	Integer32,
		prtTestVctTxDistance 	Integer32,
		prtTestVctCmd 		INTEGER,
		prtTestVctRxCrossPair 	Integer32,
		prtTestVctTxCrossPair 	Integer32,
    prtTestActivationDelay         Unsigned32,
    prtTestMacSwapLoopDataMode         INTEGER,
		prtTestMacSwapLoopVlanId 	Integer32,
    prtTestMacSwapLoopDirection         INTEGER,
    prtTestMacSwapLoopDestAddr         MacAddress,
    prtTestMacSwapLoopSrcAddr         MacAddress,
		prtTestOamMinRoundTripDelay  	Unsigned32,
		prtTestOamMaxRoundTripDelay  	Unsigned32,
		prtTestOamAvgRoundTripDelay 	Unsigned32,
		prtTestOamTxInterval 		Unsigned32,
    prtTestDestinationIpAddress         IpAddress,
    prtTestForceTTL         Unsigned32,
		prtTestBwProfile 		Unsigned32,
    prtTestSourceIpAddress         IpAddress,
    prtTestRemainTime         Unsigned32 
 }

prtTestIdx OBJECT-TYPE
    SYNTAX  Integer32
    MAX-ACCESS  read-only
    STATUS current
    DESCRIPTION
    "This object is an index of the specific port or interface.
     For a port, the index will be as agreed between agent and
     application.
     For an interface, ifIndex may be used."
    ::= { prtTestEntry 1 }

prtTestCmdAndStatus OBJECT-TYPE
      SYNTAX  Integer32
      MAX-ACCESS  read-write
      STATUS  current
      DESCRIPTION
      "Setting this object to a value as detailed further on
       (except 0) will initiate a test on the specific port.
       The test/s requested will be set according to the respective
       bit. The value of this object will be a sum of (2**n), where n is
       the Bit:
         TEST                          BIT                       VALUE
        -----------                    ---                      ------
        reserved                        0                            1
        PayloadLoop=RLB                 1 (=Remote Loopback)         2
        LineLoop=DIG                    2 (=Digital)                 4
        OtherLoop                       3                            8
        InwardLoop=LLB                  4 (=Local Loopback)         16
        BERT                            5                           32
        LC                              6                           64
        ToneInjection                   7                          128
        Inband                          8                          256
        BERT Remote (or E1/T1 RLB)      9                          512
        Downstream-AIS (or E1/T1 LLB)  10                         1024
        Upstream-AIS                   11                         2048
        Rem-Loop-on-Rem-Unit           12                         4096
        MacSwapLoop                    13                         8192
        OamETHLoopback                 14                        16384
        OamETHLinkTrace                15                        32768
        IPSwapLoop                     16                        65536
        TrafficRoute                   17                       131072
        lbmResponder                   18                       262144
        macDestLoop                    19                       524288
        macSourceLoop                  20                      1048576
        udpLoop                        21                      2097152
        udpEcho                        22                      4194304
        twamp                          23                      8388608
        discardTraffic                 24                     16777216  

        e.g : If the requested value is 20 -> 010100  ->
              Bits 2 & 4 are set -> the requested tests are :
                                    LineLoopback=DIG
                                    InwardLoopback=LLB

       Not all tests combinations are valid.
       For valid test combination, see each product's specification.
       For LRS52, only single test is allowed simultaneously

       The terminology and order of the first tests (except BERT)
       is according to the one used for Test Status of DS1 and DS3 standards.
       The notations : RLB, LLB, DIG are the most used in RAD's products, but they
       can be different. For exact definition see product's spec.

       Setting this object to stop (value=0 ; all bits are 0),
       will stop all the user requested tests running on the
       selected port.

       When no test is running on the port, the Get value (test status)
       will be 0.

       PayloadLoop=RLB
         The received signal at this interface is looped
         through the device.  Typically the received signal
         is looped back for retransmission after it has
         passed through the device's framing function.

       LineLoop=DIG
         The received signal at this interface does not
         go through the device (minimum penetration) but
         is looped back out.

       OtherLoop
         Loopbacks that are not defined here.

       InwardLoop=LLB
         The sent signal at this interface is looped back
         through the device.

       LC
       This loop is applicable only for HSSI interface, towards the router .

       ToneInjection
       This loop is applicable for analog voice (like FXS).

       Downstream-AIS
       E1 AIS signal (all ones) is transmitted in the relevant channel
       toward the STM-1 line.

       Upstream-AIS
       E1 AIS signal (all ones) is generated in the relevant channel
       toward the local received tributary channel output

       Rem-Loop-on-Rem-Unit
       Request from far end device to activate remote loopback
       towards near-end device

       MacSwapLoop
         This loop is applicable for ethernet port. Loop is
         implemented by swapping the MAC addresses of the
         incoming message.

       OamETHLoopback
          Ethernet Loopback is used to verify connectivity of a MEP with a MIP
          or peer MEP(s) (ITU-T Y.1731, Clause 7.2).

       OamETHLinkTrace
          Ethernet Link Trace is an on-demand OAM function which can be used for
          the two following purposes:
          - Adjacent Relation Retrieval
          - Fault Localization
          (ITU-T Y.1731, Clause 7.3).

       IPSwapLoop
         This loop is applicable for ethernet port. Loop is
         implemented by swapping the IP addresses of the
         incoming message.In ETX-202A, this test causes also swapping of
         the the MAC address (bit 13 should also be set to 1).

       TrafficRoute
         Traffic Route is an on-demand flow function which can be used for
         flow activation for predefined time duration .

       lbmResponder
       Activate rfc2544 Loopback (lbm) responder (on flow level).

       macDestLoop
       This loop is applicable for Ethernet port. A packet with destination
       MAC address equal to macDestLoop will be looped.

       macSourceLoop
       This loop is applicable for Ethernet port. A packet with destination
       MAC address equal to macSourceLoop will be looped.

       udpLoop
       This loop is applicable for Ethernet port. UDP loop is
       implemented by swapping destination and source MAC addresses,
       IP addresses and UDP ports of the incoming message.

       udpEcho
       A debugging and measurement tool. An echo service simply sends back
       to the originating source any data it receives. A server listens for
       UDP datagrams on configurable UDP port. When a datagram is received,
       the data from it is sent back in an answering datagram.

       twamp
       This loop provides the functionality of TWAMP responder.
              
       discardTraffic
       Drop incoming traffic on the specified flow or port."
      ::= { prtTestEntry 2 }

prtBertCounter   OBJECT-TYPE
      SYNTAX  Integer32
      MAX-ACCESS  read-only
      STATUS  current
      DESCRIPTION
      "This object indicates the number of BERT errors encountered
       during the BERT operation.
       It is valid only when BERT (Bit Error Rate Test) is active on the 
       specific port.
       The Counter starts from zero (0) anytime BERT is initiated."
      ::= { prtTestEntry 3}

prtTestInitiator OBJECT-TYPE
    SYNTAX   INTEGER
	      {
    		unknown   (1),
    		user      (2),
	    	remoteUnit(3),
			dteRouter (4)
	      }
    MAX-ACCESS  read-only
    STATUS  current
    DESCRIPTION
    "This object indicates who initiated this port's test/s."
    ::= { prtTestEntry 4 }

prtTestTimeout OBJECT-TYPE
   SYNTAX   Integer32  (0..86400)
   MAX-ACCESS  read-write
   STATUS  current
   DESCRIPTION
   "This object is applicable only when a single
   test is running. It indicates the test
   activation timeout in minutes.
   For RICi-E1T1, RICi-E3T3 and LRS-16, the measurement
   unit is in seconds.
   When the timeout expires, the test is stopped.
   Value of 0 indicates test may run Forever "
   ::= { prtTestEntry 5 }

prtTestVctRxResult OBJECT-TYPE
    SYNTAX   INTEGER
	      {
    		notApplicable  (1),
    		fail		   (2),
	    	normal		   (3),
			open		   (4),
			short		   (5),
			shortToCrossPair (6),
			coupleWithCrossPair (7)
	      }
    MAX-ACCESS  read-only
    STATUS  current
    DESCRIPTION
    "This object indicates the result of the Vct on 
    the cable connected to the RX connector."
    ::= { prtTestEntry 6 }

prtTestVctTxResult OBJECT-TYPE
    SYNTAX   INTEGER
	      {
    		notApplicable  (1),
    		fail		   (2),
	    	normal		   (3),
			open		   (4),
			short		   (5),
			shortToCrossPair (6),
			coupleWithCrossPair (7)
	      }
    MAX-ACCESS  read-only
    STATUS  current
    DESCRIPTION
    "This object indicates the result of the Vct on 
    the cable connected to the TX connector."
    ::= { prtTestEntry 7 }

prtTestVctRxDistance OBJECT-TYPE
   SYNTAX   Integer32  
   MAX-ACCESS  read-only
   STATUS  current
   DESCRIPTION
   "This object indicates the distance in Meters 
   to the RX cable Open/ Short location discovered by the Vct.
   This parameter is applicable for Vct Result = Normal or Fail only, 
   Else the value of this parameter will be equal to 0."
   ::= { prtTestEntry 8 }

prtTestVctTxDistance OBJECT-TYPE
   SYNTAX   Integer32  
   MAX-ACCESS  read-only
   STATUS  current
   DESCRIPTION
   "This object indicates the distance in Meters 
   to the TX cable Open/ Short location discovered by the Vct.
   This parameter is applicable for Vct Result = Normal or Fail only, 
   Else the value of this parameter will be equal to 0."
   ::= { prtTestEntry 9 }

prtTestVctCmd OBJECT-TYPE
	SYNTAX  INTEGER
	{
	 off  (2),
	 on   (3)
	 	 }
	MAX-ACCESS  read-write
	STATUS current
	DESCRIPTION
	"Vct command.
	 on (3) = Start Vct on both cables connected to 
	 RX and TX connectors of this port.
	 Agent will perform the required command and change automatically 
	 the value of this object to off(2)."
    ::= { prtTestEntry 10 }

prtTestVctRxCrossPair OBJECT-TYPE
   SYNTAX   Integer32  
   MAX-ACCESS  read-only
   STATUS  current
   DESCRIPTION
   "This object should be equal to the Index (prtTestIdx) of the Rx cross pair. 
    This object is applicable only for Vct Result = shortToCrossPair or coupleWithCrossPair.
    This object was especially created for ETX-202. Currently not in use."
   ::= { prtTestEntry 11 }

prtTestVctTxCrossPair OBJECT-TYPE
   SYNTAX   Integer32  
   MAX-ACCESS  read-only
   STATUS  current
   DESCRIPTION
   "This object should be equal to the Index (prtTestIdx) of the Tx cross pair.
    This object is applicable only for Vct Result = shortToCrossPair or coupleWithCrossPair."
   ::= { prtTestEntry 12 }


prtTestActivationDelay OBJECT-TYPE
   SYNTAX   Unsigned32
   MAX-ACCESS  read-write
   STATUS  current
   DESCRIPTION
   "This object is applicable only when a single test is running.
   It indicates test activation delay in seconds.
   A Value of 0 indicates that the test starts immediately."
   ::= { prtTestEntry 13 }


prtTestMacSwapLoopDataMode OBJECT-TYPE
   SYNTAX      INTEGER
   {
       all          (1),
       allExceptMng (2),
       specificVlan (3)
   }
   MAX-ACCESS  read-write
   STATUS      current
   DESCRIPTION
   "This object defines which part
   of the data will be looped back."
   ::= { prtTestEntry 14 }


prtTestMacSwapLoopVlanId OBJECT-TYPE
   SYNTAX      Integer32
   MAX-ACCESS  read-write
   STATUS      current
   DESCRIPTION
   "This object specifies the VLAN ID  for 
   prtTestMacSwapLoopDataMode=specificVlan."
   ::= { prtTestEntry 15 }


prtTestMacSwapLoopDirection OBJECT-TYPE
   SYNTAX      INTEGER
   {
       local   (2),
       remote  (3)
   }
   MAX-ACCESS  read-write
   STATUS      current
   DESCRIPTION
   "This object defines the direction of the performed loopback.
   In ETX102 'local' corresponds to Ingress loop
   (either on User port or on Network port), and
   'remote' corresponds to Egress loop
   (either on User port or on Network port)."
   ::= { prtTestEntry 16 }


prtTestMacSwapLoopDestAddr  OBJECT-TYPE
    SYNTAX  MacAddress
    MAX-ACCESS  read-write
    STATUS current
    DESCRIPTION
    "Configures the MAC address that will be sent in the
     Destination field of the packet in the outgoing direction. "
    ::= { prtTestEntry 17 }

prtTestMacSwapLoopSrcAddr  OBJECT-TYPE
    SYNTAX  MacAddress
    MAX-ACCESS  read-write
    STATUS current
    DESCRIPTION
    "Configures the MAC address that will be sent in the
    Source field of the packet in the outgoing direction. "
    ::= { prtTestEntry 18 }

prtTestOamMinRoundTripDelay     OBJECT-TYPE
    SYNTAX        Unsigned32
    MAX-ACCESS    read-only
    STATUS        current
    DESCRIPTION
    "The mininal value of round trip delay of loopback message for a session of 
    OAM loopback.Units are msec."
     ::= { prtTestEntry 19 }

prtTestOamMaxRoundTripDelay     OBJECT-TYPE
    SYNTAX        Unsigned32
    MAX-ACCESS    read-only
    STATUS        current
    DESCRIPTION
    "The maximum value of round trip delay of loopback message for a session of 
    OAM loopback.Units are msec."
     ::= { prtTestEntry 20 }

prtTestOamAvgRoundTripDelay     OBJECT-TYPE
    SYNTAX        Unsigned32
    MAX-ACCESS    read-only
    STATUS        current
    DESCRIPTION
    "The average round trip delay of loopback message for a session of 
    OAM loopback.Units are msec."
     ::= { prtTestEntry 21 }

prtTestOamTxInterval  OBJECT-TYPE
     SYNTAX       Unsigned32
     MAX-ACCESS  read-write
     STATUS  current
     DESCRIPTION
     "Indicates the interval between loopback sent messages.Units are msec."
    ::= { prtTestEntry 22 }

prtTestDestinationIpAddress  OBJECT-TYPE
     SYNTAX       IpAddress
     MAX-ACCESS  read-write
     STATUS  current
     DESCRIPTION
     "Indicates the destination IP Address in the transmitted messages that
      are looped back."
    ::= { prtTestEntry 23 }

prtTestForceTTL  OBJECT-TYPE
     SYNTAX       Unsigned32
     MAX-ACCESS  read-write
     STATUS  current
     DESCRIPTION
     "Time-to-live.Number of hops the loopback message will go through the net
      before deciding to discard it."
    ::= { prtTestEntry 24 }

prtTestBwProfile  OBJECT-TYPE
     SYNTAX       Unsigned32
     MAX-ACCESS  read-write
     STATUS  deprecated
     DESCRIPTION
     "Indicates the BW profile (from bwProfileTable) that is assigned to the loopback test
      in order to limit the traffic that is looped back."
    ::= { prtTestEntry 25 }

prtTestSourceIpAddress  OBJECT-TYPE
     SYNTAX       IpAddress
     MAX-ACCESS  read-write
     STATUS  current
     DESCRIPTION
     "Indicates the source IP Address in the transmitted messages that
      are looped back."
    ::= { prtTestEntry 26 }

prtTestRemainTime OBJECT-TYPE
   SYNTAX   Unsigned32
   MAX-ACCESS  read-write
   STATUS  current
   DESCRIPTION
   "Indicates the remain time for test activation
   in seconds."
   ::= { prtTestEntry 27 }


--Port General Parameters

prtParam OBJECT IDENTIFIER ::= { systemPort 5 }

prtParamTable OBJECT-TYPE
    SYNTAX  SEQUENCE OF PrtParamEntry
    MAX-ACCESS  not-accessible
    STATUS current
    DESCRIPTION
    "This table includes general port parameters. The meaning is
     different for every product that supports it due to a general
     parameter - prtControlCnfg.

     For ACE2002:
     -This table is used as a mechanism to create the next interface index.
      The algorithm description:
      The NMS will send the agent the following get command: get(nextIfIndex.index),
      where index=interface on which the new index is dependent on.
      Upon this command the agent will generate and return the new index to the NMS.
     - This table is partially supported according to the interface type.
       Upon getNext function the irrelevant parameters will be skipped."
    ::= {prtParam 1}

prtParamEntry OBJECT-TYPE
    SYNTAX  PrtParamEntry
    MAX-ACCESS  not-accessible
    STATUS current
    DESCRIPTION  "An entry in table."
    INDEX {prtParamIdx}
    ::= { prtParamTable 1 }

PrtParamEntry ::= SEQUENCE {
    prtParamIdx                     Integer32,
   prtControlCnfg 	            Integer32,
    prtParamClkSrc                  INTEGER,
   prtParamPhantom	            INTEGER,
    prtParamResetStatsCmd           INTEGER,
   prtParamLastResetStatsTime	TimeStamp,
    prtParamInterfaceType           INTEGER,
   prtParamClearAlarm		  	INTEGER,
    prtParamLeds                    OCTET STRING,
   prtParamLineLength		  	INTEGER,
   prtParamUsage			  	INTEGER,
   prtParamMappingMode		    INTEGER,
   prtParamAlarmIndication	  	INTEGER,
   prtParamClkQualityLevel	    OCTET STRING,
    prtParamClkWaveShape            INTEGER,
   prtParamStatus			    INTEGER,
   prtParamSignalLevel		  	Integer32,
   prtParamClkUserQualityLevel  OCTET STRING,
   prtParamDataRate			    Unsigned32,
    prtParamLoopDetect              INTEGER,
   prtParamActUponLoopDetect    OCTET STRING,
   prtParamPSNLayer             INTEGER,
   prtParamRxSsm				INTEGER,
   prtParamClkSsmRxSource		INTEGER,
   prtParamFarEndDevice         Unsigned32,
   prtParamTxClk				INTEGER,
   prtParamSdBerThreshold       Unsigned32,
   prtParamLoopDetectStatus     INTEGER,
    prtParamSupportedFeatures       OCTET STRING,
    prtParamPortStatus              BITS,
    prtParamSsmTx                   INTEGER,
    prtParamAlias                   DisplayString,
    prtParamTxClockInstance         Unsigned32,
    prtParamEntPhysicalIndex        PhysicalIndexOrZero,
    prtParamSsmTxType               INTEGER 
 }

prtParamIdx OBJECT-TYPE
    SYNTAX  Integer32
    MAX-ACCESS  read-only
    STATUS current
    DESCRIPTION
    "This object is an index of the specific port or interface.
     For a port, the index will be as agreed between agent and
     application.
     For an interface, ifIndex may be used.

     For ACE2002:
     This parameter is the physical layer ifIndex of the slot on
     which the NMS requires the next interface index."
    ::= { prtParamEntry 1 }

prtControlCnfg OBJECT-TYPE
	SYNTAX  Integer32 
	MAX-ACCESS  read-write
	STATUS current
	DESCRIPTION
	"This object may be used for port RW general parameter/s.
	 For detailed meaning, see product's spec.
	 Supported by: PRBi-E3/T3.
	 
	 For ACE2002:
	 This parameter will include the value of the new index 
	 generated by agent.
	 
	 For Optimux-T3 and OP-155-1:
	 This parameter will be used for Release Remote LLB Command:
	 on=2= Set value only. Command to release LLB of Remote Unit.
	       Agent will return automatically to 'off' value after performing
	       the command.
	 off=3=Get value only.
	 
	 
	 For LA140
	 This parameter will be used as EchoCanceler per timeslot
	 off = 2 Echo Canceler is disabled
	 on =  3 Echo Canceler is enabled 
	 
	 For FCD-155
	 This parameter will be used to select the port that is
	 clock source for a PDH port, 
		 For E1/T1 PDH
		 VC12/VT1.5 = 2
		 SDH/SONET  = 3
		 For E3/T3 PDH
		 VC3/DS3  = 2
		 SDH/SONET = 3         
	 
	 For ACE-52
	 This parameter will be used as Transmit Frame Type, i.e. 
	 which type of frame the corresponding bridge port will transmit:
	 Untagged = 2
	 Tagged = 3 
	 ."
	::= { prtParamEntry 2 }

prtParamClkSrc OBJECT-TYPE
    SYNTAX  INTEGER {
       loopTiming    (1),
       localTiming   (2),
       throughTiming (3),
       adaptive      (4),
       master        (5),
       fallback      (6),
       station       (7),
       system        (8),
       notApplicable (255)
    }
    MAX-ACCESS  read-write
    STATUS  current
    DESCRIPTION
       "The source of Transmit Clock.
        'loopTiming' or 'loopback' indicates that the recovered receive clock
         is used as the transmit clock.

        'localTiming' or 'internal' indicates that a local clock
         source is used or when an external clock is
         attached to the box containing the interface.

        'throughTiming' or 'external' indicates that recovered receive clock
         from another card or interface is used as the transmit clock.

        'adaptive' indicates that the clock is recovered according
         to the received data flow rate.

        'master' and 'fallback' values may be used RO to
         indicate active clock.

         'station' - indicate clock received from station
          port is used as transmit clock."
    ::= { prtParamEntry 3 }

prtParamPhantom OBJECT-TYPE
    SYNTAX  INTEGER {
       notApplicable (1),
       disable       (2),
       enable        (3)
	}
	MAX-ACCESS  read-write
	STATUS current
	DESCRIPTION
	"Power feeding to another device."
	::= { prtParamEntry 4 }

prtParamResetStatsCmd OBJECT-TYPE
    SYNTAX      INTEGER {
        off             (2),
        on              (3),
        lacp            (4),
        l2cp            (5),
        elmi            (6),
        optPrtMonitor   (7),
        interval        (8),
        day             (9),
        efm             (10),
        lldp            (11)
        }
    MAX-ACCESS  read-write
    STATUS      current
    DESCRIPTION
            "on  (3)       - Reset all statistics of the selected port.
            lacp (4)       - Reset LACP statistics of the selected port.
            l2cp (5)       - Reset L2CP statistics of the selected port.
            elmi (6)       - Reset ELMI statistics of the selected port
            optPrtMonitor (7) - Reset optical port monitoring minimum
                                                  and maximum values, see OptPrtMonitorEntry
            interval (8)    - Reset current interval counters,
            day        (9)    - Reset current day counters.
            efm      (10)   - Reset oamefm counters."
    ::= { prtParamEntry 5 }

prtParamLastResetStatsTime OBJECT-TYPE
     SYNTAX  TimeStamp
     MAX-ACCESS  read-only
     STATUS  current
     DESCRIPTION
     "The value of MIB II's sysUpTime object at the last time that 
      prtParamResetStatsCmd was Set to on(3) for this port.  
      If prtParamResetStatsCmd was never Set to on(3) since last 
      re-initialization of the agent, then this object contains a zero value.
      This object enables calculating the running time of Statistics
      counters for this port, by: [sysUpTime-prtParamLastResetStatsTime].
      For some devices other types of 'Reset' may affect this parameter"
     ::= { prtParamEntry 6 }

prtParamInterfaceType OBJECT-TYPE
    SYNTAX  INTEGER {
        notApplicable (1),
        e1            (2),
        t1            (3),
        fr            (4),
        hdlc          (5),
        hdsl2         (6),
        shdsl         (7),
        adsl          (8),
        adsl2         (9),
        reAdsl2       (10),
        mPair         (11),
        efm           (12),  --64-65 Octets
        atmIma        (13),
        ds1           (14),
        f1544kHz      (15),  -- 1.544 MHz
        f2048kHz      (16),  -- 2.048 MHz
        f64kHz        (17),
        gps           (18),
        j1            (19),
        ethernet      (20),  -- All ethernet interfaces
        svi           (21),  -- Service virtual interface
        logicalMac    (22),
        lag           (23),  -- Link aggregation group
        sag           (24),  -- Service aggregation group
        sap           (25),  -- Service aggregation point
        etpTransport  (26),  -- ETP Transport port
        etpSubscriber (27),  -- ETP Subscriber port
        r1pps         (28),
        miniBnc       (29),
        e3            (30),
        t3            (31),
        sonetSdh      (32),
        ds1Opt        (33),  -- C.37.94 link of MP-4 VS-6/C.37 Card
        tdmBridge     (34)   -- TDM Bridge of MP-4 VS cards
        }
    MAX-ACCESS  read-write
    STATUS      current
    DESCRIPTION
            "The interface type of the port, or the frequency used as
            clock reference. Clock reference values may be either e1(2)
            or t1(3), gps (18) or wave with the specified frequency:
            f1544kHz(15), f2048kHz(16) or f64kHz (17).
            f1544kHz = 1.544 Mhz (T1 rate),
            f2048kHz = 2.048 Mhz = (E1 rate).
            When one of the frequency values (15), (16) is used, Clock
            reference signal may be have either Sine or Square waveshape
            Waveshape is defined by other object of this table:
            prtParamClkWaveShape."
    ::= { prtParamEntry 7 }

prtParamClearAlarm OBJECT-TYPE
    SYNTAX  INTEGER {
       off (2),
       on  (3)
    }
    MAX-ACCESS  read-write
    STATUS  current
    DESCRIPTION
       "Setting this attribute to ON, will enforce a clear 
       operation on the Port Alarms.
       Upon completion, the value will automatically change
       to off(2)."
	::= { prtParamEntry 8 }

prtParamLeds  OBJECT-TYPE
    SYNTAX  OCTET STRING
    MAX-ACCESS  read-only
    STATUS current
    DESCRIPTION
    "This entry specifies the LEDs status of the port.
     Each led is represented by 4 bits where the first 2 bits
     (left) specify  the status :
     (00=NA, 01=OFF, 10=ON, 11=BLINK),
     and the next two bits (right) specify the color :
     (00=GREEN, 01=RED, 10=YELLOW, 11=GRAY).
     The order of the LEDS is from top to bottom, left to right:
     For each row starting from the top,
     the LEDS are returned from left to right."
     ::= {prtParamEntry 9}

prtParamLineLength OBJECT-TYPE
    SYNTAX  INTEGER {
	   notApplicable (1),
       long    (2),
       normal  (3),
	   short   (4)
    }
    MAX-ACCESS  read-write
    STATUS  current
    DESCRIPTION
    "Line Length of the line connected to this port."
	::= { prtParamEntry 10 }

prtParamUsage OBJECT-TYPE
	SYNTAX  INTEGER {
	 notApplicable   (1),
	 user		     (2),
	 network	     (3)
	}
	MAX-ACCESS  read-write
	STATUS  current
	DESCRIPTION
	"Defines whether this port works as User port or as Network port."
	::= { prtParamEntry 11 }
		
prtParamMappingMode  OBJECT-TYPE
      SYNTAX INTEGER
      {
       notApplicable (1),
       off           (2),
       auto          (3),
	   manual        (4),
	   adjacent      (5)
      }
      MAX-ACCESS read-write
      STATUS current
      DESCRIPTION
      "This object defines path protection on SONET/SDH link
       Auto - SONET/SDH mapping for port is copied
       automatically to same TU on the redundant 
       SONET/SDH local (reside on same slot) link by agent.
       Manual - the user can configure the redundant 
       mapping for port on the same link
       or to the other link on any TU
       Adjacent - similar to auto, but mapping is copied
       automatically by agent to link on adjacent slot ."   
      ::= { prtParamEntry 12}

prtParamAlarmIndication OBJECT-TYPE
    SYNTAX INTEGER {
       notApplicable (1),
       off           (2),
       on            (3)
       }
    MAX-ACCESS read-only
    STATUS current
    DESCRIPTION
    "This object indicates status-aggregation of non-masked alarms 
    associated with all interface layers, related to this physical port.
    When at least one non-masked alarm exists on any layer, 
    value of this object is on (3). 
    
    Indication will be off (2) only when there's no active 
    non-masked alarm on any interface layer related to this port. 
    Masking an Alarm, will consider it as not exist for this indication.
    
    Example: When a port has an ATM higher layer and at least 
    one VC has alarm, value of this object will be on (3)"
    ::= {prtParamEntry 13}

prtParamClkQualityLevel OBJECT-TYPE
      SYNTAX  OCTET STRING	(SIZE (1))
      MAX-ACCESS  read-only
      STATUS  current
      DESCRIPTION
      "This parameter indicates quality level of clock signal.
       Quality is encoded according to SSM 
       (Synchronization Status Messages) encoding.
	   Bits 8 -5  of byte are encoded as follows (when bit1=0):
	   Left most bit - MSB(8) ---> LSB(5)
	   8765       
	   0000	Quality Unknown
       0010	PRC (Primary Reference Clock)    - Rec. G.811
       0100	SSU-T (Sync. Source Unit-Transit)- Rec. G.812 Transit
       1000	SSU-L (Sync. Source Unit Local)	 - Rec. G.812 Local
       1011	SEC (SDH Equipment Clock)
       1111	DNU (do not use for synchronization)
	   0001 PRS (=ST1 = Stratum 1 Traceable)
	   0111 ST2 (Stratum 2 Traceable)
	   1010 ST3 (Stratum 3 Traceable)
	   1100 SMC (SONET Minimum Clock Traceable)
	   1101 Stratum 3E Traceable
	   bit1 = '1' - indicates all octet is Not Applicable"
    ::= {prtParamEntry 14}

prtParamClkWaveShape OBJECT-TYPE
    SYNTAX  INTEGER {
       notApplicable (1),
       sine          (2),
       square        (3)
    }
    MAX-ACCESS  read-write
    STATUS  current
    DESCRIPTION
       "Wave shape of station clock source signal.
        This parameter is applicable only when prtParamInterfaceType value
        is one of the following: f1544kHz(15), f2048kHz(16)."
    ::= { prtParamEntry 15 }

prtParamStatus OBJECT-TYPE
    SYNTAX  INTEGER {
       notApplicable (1),
       up            (2),
       signalLoss    (3),
	   syncLoss      (4)
    }
    MAX-ACCESS  read-only
    STATUS  current
    DESCRIPTION
       "Station clock source Status."
	::= { prtParamEntry 16 }

prtParamSignalLevel	OBJECT-TYPE
    SYNTAX Integer32 
	MAX-ACCESS  read-only
	STATUS current
	DESCRIPTION 
	"This object indicates signal level (in thenth of dB units)
	 on selected port."
	::= { prtParamEntry 17 }

prtParamClkUserQualityLevel OBJECT-TYPE
   SYNTAX  OCTET STRING	(SIZE (1))
   MAX-ACCESS  read-write
   STATUS  current
   DESCRIPTION
   "This parameter allows user to mark quality level of clock.
    Quality is encoded according to SSM 
    (Synchronization Status Messages) encoding.
    Bits 8 -5  of byte are encoded as follows:
    Left most bit - MSB(8) ---> LSB(5)
    8765       
    0000	Quality Unknown
    0010	PRC (Primary Reference Clock) -   Rec. G.811
    0100	SSU-T (Sync. Source Unit-Transit) Rec. G.812 Transit
    1000	SSU-L (Sync. Source Unit Local)	- Rec. G.812 Local
    1011	SEC (SDH Equipment Clock)
    1111	DNU (do not use for synchronization)"
   ::= {prtParamEntry 18}

prtParamDataRate OBJECT-TYPE
     SYNTAX  Unsigned32 
     MAX-ACCESS  read-write
     STATUS  current
     DESCRIPTION
     "Rate of serial data port (V.11, V.24, V.35) 
      in kbps units."
     ::= { prtParamEntry 19}

prtParamLoopDetect OBJECT-TYPE
    SYNTAX  INTEGER
    {
     disable   (2),
     enable    (3)
    }
    MAX-ACCESS  read-write
    STATUS current
    DESCRIPTION
    "Enable/disable Loop Detection on a port.
     Examples of ports: physical, Channelized Bundle over TDM Uplink,
     Bridge Ports."
    ::= { prtParamEntry 20 }

prtParamActUponLoopDetect OBJECT-TYPE
	SYNTAX  OCTET STRING
	MAX-ACCESS  read-write
	STATUS current
	DESCRIPTION
	"This parameter is used to indicate which actions
	should be taken in case a loop is detected in the network the port is part of.
	Each action is represented by a bit.
	Currently defined (for RIC155GE/RIC622GE):
	Bit 0 - Transmit Shut Down
	Bit 1 - Forward Alarms
	If bit value = '1' then the action is taken.
	If bit value = '0' then the actions is not taken."
	::= { prtParamEntry 21 }


prtParamPSNLayer OBJECT-TYPE
	SYNTAX INTEGER
	{
	   l2 	(2), -- lan
	   l3	(3)  -- wan
	}
	MAX-ACCESS read-write
	STATUS current
	DESCRIPTION
	"This object indicates the network layer from which clock is derived."
	::= { prtParamEntry 22 }


prtParamRxSsm OBJECT-TYPE
	SYNTAX INTEGER
	{
	   disabled	(2),
	   rx	(3)
	}
	MAX-ACCESS read-write
	STATUS current
	DESCRIPTION
	"This object indicates if Station Clock SSM messages  
	 received will serve as criteria for clock selection."
	::= { prtParamEntry 23 }

prtParamClkSsmRxSource OBJECT-TYPE
	SYNTAX INTEGER
	{
       sa4 	(2), 
	   sa5	(3),
	   sa6  (4),
	   sa7  (5), 
	   sa8  (6)
	}
	MAX-ACCESS read-write
	STATUS current
	DESCRIPTION
	"This object indicates the Sa-bit of the E1 frame,
	 in which SSM messages are carried."
	::= { prtParamEntry 24 }

-- 	::= { prtParamEntry 25 }  reserved 


prtParamFarEndDevice OBJECT-TYPE
     SYNTAX  Unsigned32 
     MAX-ACCESS  read-write
     STATUS  current
     DESCRIPTION
     "Programmed Far-End device connected to this port. 
      This object is relevant for products having multiple DBs.
	  It will enable configuring offline, the relevant data.
      For MP-4100, LRS-102 OP-108/106 cards, the options will be:
	  1 = None (when a port is not connected to any remote device)
      2 = OP-108
      3 = OP-108/ETH
      4 = OP-106
      5 = OP-106/ETH
      6 = card of MP or LRS-102"
     ::= { prtParamEntry 26}

prtParamTxClk OBJECT-TYPE
    SYNTAX  INTEGER {
	   notApplicable (1),
       disable       (2),
       enable        (3)
    }
    MAX-ACCESS  read-write
    STATUS  current
    DESCRIPTION
       "enable/disable station clock signal output."
	::= { prtParamEntry 27 }	 

prtParamSdBerThreshold	OBJECT-TYPE
    SYNTAX Unsigned32 (0..9) 
	MAX-ACCESS  read-write
	STATUS current
	DESCRIPTION 
	"The Signal Degrade Bit Error Rate Threshold.
	 The negated value of this number is used as the exponent of
     10 for computing the threshold value for the Bit Error Rate (BER).
     For example, a value of 5 indicates a BER threshold of 10^-5.
     
     For disabling the signal degradation, the value will be: 0"
     ::= { prtParamEntry 28 }

prtParamLoopDetectStatus OBJECT-TYPE
    SYNTAX  INTEGER {
       notApplicable (1),
       noLoop        (2),
       loopDetected  (3)
    }
    MAX-ACCESS  read-only
    STATUS  current
    DESCRIPTION
    "This object shows whether a loop was detected on the current port."
	::= { prtParamEntry 29 }

prtParamSupportedFeatures OBJECT-TYPE
    SYNTAX  OCTET STRING
    MAX-ACCESS  read-only
    STATUS  current
    DESCRIPTION
    "This MIB object denotes supported features by the port/interface.
    The bit legend must be kept identical to all devices.
    Bit 0 = '1' denotes that the port/interface supports ETH OAM CFM.
    The agent can set this bit to 1 only if it set bit 1 in
    agnFunction[cfm(8)].agnFunctionAttributes to 1.
    For CSM Set bit 1 to '1' for each port that can be used as Rx clock source.
    "
    ::= { prtParamEntry 30 }

prtParamPortStatus OBJECT-TYPE
    SYNTAX      BITS {
        ais                     (0), -- Alarm Indication Signal exists
        rdi                     (1), -- Remote Defect Indication exists
        loopDetected            (2), -- A loop was detected
        faultPropagation        (3), -- Port is down due to Fault Propagation
        operStatus              (4), -- Port operational status is down (ifOperStatus = down(2))
        adminStatus             (5), -- Administrator set ifAdminStatus to down (2)
        notPresent              (6), -- some component is missing
        lowerLayerDown          (7), -- down due to state of lower-layer interface(s)
        macAccessSecViolation   (8), -- A MAC Access security violation occurred on this port
        signalDegradation       (9), -- Signal is degraded,
        unknown                 (10),-- status cannot be determined for some reason
        oamCriticalBitOn        (11),-- OAM (EFM) ah Critical Bit is on
        los                     (12),-- LOS (Loss Of Signal) alarm was detected
        autoNegotiationFailure  (13),-- auto-negotiation failed
        sfpFailure              (14),-- SFP/XFP failed
        lof                     (15), -- LOF (Loss Of Frame) alarm was detected
        serialRateGeneratorFailure (16), --  fault in Rate Generator of a Serial Port
        serialRs232RateNot64kbps   (17), -- rate fault in RS-232 serial port
        voiceComboFailure          (18), -- voice port combo failure
        belowMinimumMembers        (19), -- number of members are below the minimum
        allLinksDown               (20), -- All links are down
        linkFailSignaling          (21)  -- Ethernet Link Fail Signaling (Applicable for SFP+)
        }
    MAX-ACCESS  read-only
    STATUS      current
    DESCRIPTION
                "This object shows the status of the current port.
                The status is a bit map represented as a sum, therefore,
                it can represent multiple failures. When no failure,
                the value will be 0. This object should be supported in
                addition to the standard ifAdminStatus & ifOperStatus."
    ::= { prtParamEntry 31 }

prtParamSsmTx   OBJECT-TYPE
    SYNTAX      INTEGER {
        disable (2),
        enable  (3)
        }
    MAX-ACCESS  read-write
    STATUS      current
    DESCRIPTION
            "This object defines the SSM transmission from this port.
            For SDH/SONET interfaces the object means the following:
            disable (2):
                - force DNU (DUS) SSM message sending via TDM port
                - MAY stop SSM messages to PSN port i.e. stop message
                  sending via Ethernet port.
            enable  (3) - send SSM as defined by TX clock quality."
    ::= { prtParamEntry 34 }

prtParamAlias   OBJECT-TYPE
    SYNTAX      DisplayString (SIZE(0..255))
    MAX-ACCESS  read-write
    STATUS      current
    DESCRIPTION
    "This object is an 'alias' name for the interface as specified by
     a network manager, and provides a non-volatile 'handle' for the
     interface."
    ::= { prtParamEntry 36 }

prtParamTxClockInstance OBJECT-TYPE
    SYNTAX      Unsigned32
    MAX-ACCESS  read-write
    STATUS  current
    DESCRIPTION
            "This parameter specifies the instance of the clock domain
            that is used as transmision clock source. It is equal to the
            csmDomainEntry.csmDomainIdx when the CSM is used."
    ::= { prtParamEntry 38 }

prtParamEntPhysicalIndex    OBJECT-TYPE
    SYNTAX      PhysicalIndexOrZero
    MAX-ACCESS  read-only
    STATUS      current
    DESCRIPTION
        "The object contains index of the related entPhysicalEntry of
        the ENTITY-MIB (RFC 4133) and ENTITY-STATE-MIB (RFC 4268). The
        index is built accordign to the rules that are defined by the
        inventory.doc document."
    ::= { prtParamEntry 41 }

prtParamSsmTxType     OBJECT-TYPE
         SYNTAX  INTEGER
    {
       type1Prc         (1),
       type1SsuA        (2),
       type1SsuB        (3),
       type1Sec         (4),
       type1Dnu         (5),
       type1SsmBased    (6),

-- Remaining values until 20 are reserved for type 1.

       type2Prs         (21),
       type2Stu         (22),
       type2St2         (23),
       type2Tnc         (24),
       type2St3e        (25),
       type2St3         (26),
       type2Smc         (27),
       type2St4         (28),
       type2Dus         (29),
       type2SsmBased    (30),
       type2Prov        (31),


-- Remaining values until 40 are reserved for type 2.

       type3Unk         (41),
       type3Sec         (42),
       type3Dnu         (43),
       type3SsmBased    (44)

-- Remaining values until 60 are reserved for type 3.

    }
     MAX-ACCESS  read-write
     STATUS  current
     DESCRIPTION
     "This object defines the SSM transmission type from this port.."
    ::= { prtParamEntry 45 }

    
prtXTable OBJECT-TYPE
    SYNTAX  SEQUENCE OF PrtXEntry
    MAX-ACCESS  not-accessible
    STATUS current
    DESCRIPTION
    "This table includes general port parameters, indexed by ifIndex"
    ::= {prtParam 2}

prtXEntry OBJECT-TYPE
    SYNTAX  PrtXEntry
    MAX-ACCESS  not-accessible
    STATUS current
    DESCRIPTION  "An entry in table."
    INDEX {ifIndex}
    ::= { prtXTable 1 }

PrtXEntry ::= SEQUENCE {
    prtXCliPortString                  SnmpAdminString 
 }

prtXCliPortString     OBJECT-TYPE
    SYNTAX      SnmpAdminString
    MAX-ACCESS  read-only
    STATUS      current
    DESCRIPTION
    "The exact string that is used by the CLI to identify this interface.
     The string includes the port type and the port identifier.

      Example port strings:
      'ethernet main-a/1'
      'ethernet 1'
      'logical-mac 2'  "
   ::= { prtXEntry 1 }


prtIP OBJECT IDENTIFIER ::= { systemPort 6 }

prtIpParamTable OBJECT-TYPE
	SYNTAX  SEQUENCE OF PrtIpParamEntry
	MAX-ACCESS  not-accessible
	STATUS current
	DESCRIPTION  "A table - Parameters for IP Ports."
	::= {prtIP 1}

prtIpParamEntry OBJECT-TYPE
	SYNTAX  PrtIpParamEntry
	MAX-ACCESS  not-accessible
	STATUS current
	DESCRIPTION  "An entry in table."
	INDEX { prtIpParamConfigIdx, prtIpParamSlotIdx, prtIpParamIdx }
	::= { prtIpParamTable 1 }

PrtIpParamEntry  ::=
    SEQUENCE {
    prtIpParamConfigIdx	      Integer32,
    prtIpParamSlotIdx  	      Integer32,
    prtIpParamIdx             Integer32,
	prtIpParamHostIP	      IpAddress,
	prtIpParamHostMask	      IpAddress,
	prtIpParamDefaultGateway  IpAddress,
	prtIpParamMediaMode		  INTEGER,
	prtIpParamMediaRate		  INTEGER,
	prtIpParamMngVlanSupport  INTEGER,
	prtIpParamMngVlanId       Integer32,
	prtIpParamMngVlanPriority Integer32,
	prtIpParamRingMode		  INTEGER,
	prtIpParamProtIpEnable    INTEGER,
	prtIpParamTrafficPriority INTEGER,
	prtIpParamRemoteIP	      IpAddress,
	prtIpParamMaxTxBandwidth  INTEGER,
	prtIpParamTos             Integer32,
	prtIpParamConnect         INTEGER,
	prtIpParamAgingTime       Integer32,
	prtIpParamEncapsulationProt INTEGER,
	prtIpParamEncapProtPort   Integer32,
	prtIpParamVlanSupport     INTEGER,
	prtIpParamVlanId          Integer32,
	prtIpParamVlanPriority    Integer32,
	prtIpParamDoubleTagVlanId        Integer32,
	prtIpParamDoubleTagVlanPriority  Integer32,
	prtIpParamVlanTagging	  INTEGER,
	prtIpParamRateLimit		  Integer32,
	prtIpParamDefInterface    Integer32,
	prtIpParamMng             INTEGER,
	prtIpParamFloodedRateLimit  Integer32,
	prtIpParamBurstSize         Unsigned32,
	prtIpParamLimitPacketType   INTEGER, 
	prtIpParamKeepAliveInterval Integer32,
	prtIpParamKeepAliveThresh   Integer32,
 	prtIpParamP2pKeepAliveVlanId   Integer32,
	prtIpParamP2pKeepAliveVlanPrio Integer32,
	prtIpParamRingAdjacentMacAddr  MacAddress
	}

prtIpParamConfigIdx OBJECT-TYPE
	SYNTAX  Integer32 
	MAX-ACCESS  read-only
	STATUS current
	DESCRIPTION 
	"This object indicates the Configuration number (1..255) 
     referred.
     Value of 255 specifies the TmpCnfg (Scratch).
     For products having Agent and Edit configurations, 
     Write operation for the table entries is allowed only to 
     Config=255."
	::= { prtIpParamEntry 1 }

prtIpParamSlotIdx OBJECT-TYPE
    SYNTAX  Integer32   
    MAX-ACCESS  read-only
    STATUS  current
    DESCRIPTION
    "This object indicates a unique number of the slot position 
     in which the module is inserted.
     notApplicable = 255 (for products that don't have slots).
       
     For KM:
     kmxMlA (103),
     kmxMlB (104)."
    ::= { prtIpParamEntry 2 }

prtIpParamIdx OBJECT-TYPE
	SYNTAX  Integer32 
	MAX-ACCESS  read-only
	STATUS current
	DESCRIPTION
	"This object indicates a unique Port Index."
	::= { prtIpParamEntry 3 }

prtIpParamHostIP OBJECT-TYPE
    SYNTAX  IpAddress 
    MAX-ACCESS  read-write
    STATUS  current
    DESCRIPTION
    "The host interface IP address."
    ::= { prtIpParamEntry 4 }

prtIpParamHostMask OBJECT-TYPE
    SYNTAX  IpAddress 
    MAX-ACCESS  read-write
    STATUS  current
    DESCRIPTION
    "The host interface subnet mask."
    ::= { prtIpParamEntry 5 }

prtIpParamDefaultGateway OBJECT-TYPE
    SYNTAX  IpAddress
    MAX-ACCESS  read-write
    STATUS  current
    DESCRIPTION
    "Default Gateway's IP Address."
    ::= { prtIpParamEntry 6 }

prtIpParamMediaMode OBJECT-TYPE
    SYNTAX  INTEGER
	{
       notApplicable (1),
       halfDuplex    (2),
       fullDuplex    (3) 
    }
    MAX-ACCESS  read-only
    STATUS  current
    DESCRIPTION
    "This object indicates the real Media Mode."
    ::= { prtIpParamEntry 7 }

prtIpParamMediaRate OBJECT-TYPE
    SYNTAX  INTEGER
	{
       notApplicable (1),
       r10Mbps       (2),
       r100Mbps      (3) 
    }
    MAX-ACCESS  read-only
    STATUS  current
    DESCRIPTION
    "This object indicates the real Media Rate (Mbps)."
    ::= { prtIpParamEntry 8 }

prtIpParamMngVlanSupport OBJECT-TYPE
    SYNTAX  INTEGER 
    {
    notApplicable(1),
    no		(2),
    yes	    (3)
    }
    MAX-ACCESS  read-write
    STATUS  current
    DESCRIPTION
    "Management VLAN support (Tagging).
     no - No support of VLAN Tagging.
     yes - 4 VLAN bytes will be added to the frame."
    ::= { prtIpParamEntry 9 }

prtIpParamMngVlanId OBJECT-TYPE
     SYNTAX  Integer32 
     MAX-ACCESS  read-write
     STATUS  current
     DESCRIPTION
     "Management VLAN ID."
     ::= { prtIpParamEntry 10 }
  
prtIpParamMngVlanPriority OBJECT-TYPE
     SYNTAX  Integer32 
     MAX-ACCESS  read-write
     STATUS  current
     DESCRIPTION
     "Management VLAN Frame priority."
     ::= { prtIpParamEntry 11 }

prtIpParamRingMode OBJECT-TYPE
    SYNTAX  INTEGER
	{
       notApplicable (1),
       disable       (2),
       enable        (3) 
    }
    MAX-ACCESS  read-write
    STATUS  current
    DESCRIPTION
    "This object indicates If Ring Mode is enabled or not."
    ::= { prtIpParamEntry 12 }

prtIpParamProtIpEnable OBJECT-TYPE
    SYNTAX  INTEGER
	{
       notApplicable (1),
       disable       (2),
       enable        (3) 
    }
    MAX-ACCESS  read-write
    STATUS  current
    DESCRIPTION
    "This object indicates whether a list of Protected IP Addresses 
     is enabled or not. This object is applicable only if 
     prtIpParamRingMode=enable."
    ::= { prtIpParamEntry 13 }

prtIpParamTrafficPriority OBJECT-TYPE
    SYNTAX  INTEGER
	{
       notApplicable (1),
       low           (2),
       high          (3) 
    }
    MAX-ACCESS  read-write
    STATUS  current
    DESCRIPTION
    "This object indicates the traffic priority of this port."
    ::= { prtIpParamEntry 14 }

prtIpParamRemoteIP  OBJECT-TYPE
    SYNTAX  IpAddress 
    MAX-ACCESS  read-write
    STATUS  current
    DESCRIPTION
    "This is the IP Address of the remote device that is connected to the
     current device (Point to Point Application). It is used for sending OAM packets
     on the LAN to the remote side in order to check that the connection is OK."
    ::= { prtIpParamEntry 15 }

prtIpParamMaxTxBandwidth OBJECT-TYPE
    SYNTAX  INTEGER
	{
       full  (2),
       e1    (3),
	   t1    (4)
    }
    MAX-ACCESS  read-write
    STATUS  current
    DESCRIPTION
    "This object shows the Max Bandwidth allowed on the LAN.
     Full - means that a Maximum of 100 Mega Byte Rate may go through the LAN.
	 e1(3) means that the maximum is an E1 rate. t1(4) is for a maximum of a T1 rate."
    ::= { prtIpParamEntry 16 } 

prtIpParamTos OBJECT-TYPE
     SYNTAX  Integer32 
     MAX-ACCESS  read-write
     STATUS  current
     DESCRIPTION
     "TOS = Type of Service transmitted.
      Valid values: 0..255."
     ::= { prtIpParamEntry 17 }

prtIpParamConnect OBJECT-TYPE
    SYNTAX  INTEGER 
    {
    notApplicable(1),
    no		(2),
    yes	    (3)
    }
    MAX-ACCESS  read-write
    STATUS  current
    DESCRIPTION
    "Port Connection."
    ::= { prtIpParamEntry 18 }

prtIpParamAgingTime OBJECT-TYPE
     SYNTAX  Integer32 
     MAX-ACCESS  read-write
     STATUS  current
     DESCRIPTION
     "Aging Time in seconds."
     ::= { prtIpParamEntry 19 }

prtIpParamEncapsulationProt OBJECT-TYPE
    SYNTAX  INTEGER 
    {
    notApplicable(1),
    tcp		(2),
    udp	    (3)
    }
    MAX-ACCESS  read-write
    STATUS  current
    DESCRIPTION
    "Encapsulation Protocol."
    ::= { prtIpParamEntry 20 }

prtIpParamEncapProtPort OBJECT-TYPE
     SYNTAX  Integer32 
     MAX-ACCESS  read-write
     STATUS  current
     DESCRIPTION
     "Encapsulation Protocol Port (TCP/UDP Port)."
     ::= { prtIpParamEntry 21 }

prtIpParamVlanSupport OBJECT-TYPE
    SYNTAX  INTEGER 
    {
    notApplicable(1),
    no		(2),
    yes	    (3)
	    }
    MAX-ACCESS  read-write
    STATUS  current
    DESCRIPTION
    "VLAN support (Tagging).
     'no' - No support of VLAN Tagging.
     'yes' - 4 VLAN bytes will be added to the frame."
    ::= { prtIpParamEntry 22 }

prtIpParamVlanId OBJECT-TYPE
     SYNTAX  Integer32 
     MAX-ACCESS  read-write
     STATUS  current
     DESCRIPTION
     "VLAN Identifier."
     ::= { prtIpParamEntry 23 }
  
prtIpParamVlanPriority OBJECT-TYPE
     SYNTAX  Integer32 
     MAX-ACCESS  read-write
     STATUS  current
     DESCRIPTION
     "VLAN Frame priority."
     ::= { prtIpParamEntry 24 }

prtIpParamDoubleTagVlanId OBJECT-TYPE
     SYNTAX  Integer32 
     MAX-ACCESS  read-write
     STATUS  current
     DESCRIPTION
     "VLAN Identifier of the Double Tagging VLAN."
     ::= { prtIpParamEntry 25 }
  
prtIpParamDoubleTagVlanPriority OBJECT-TYPE
     SYNTAX  Integer32 
     MAX-ACCESS  read-write
     STATUS  current
     DESCRIPTION
     "VLAN Frame priority of the Double Tagging VLAN."
     ::= { prtIpParamEntry 26 }

prtIpParamVlanTagging OBJECT-TYPE
     SYNTAX  INTEGER 
     {
     notApplicable(1),
     unmodified	  (2),
	 tag		  (3),
	 doubleTag 	  (4),
 	 doubleTagAndFallBack (5),
	 untag        (6) 
     }
     MAX-ACCESS  read-write
     STATUS  current
     DESCRIPTION
     "VLAN Tagging.
      'unmodified' - No change will be done to the Frame.
      'tag' - Add Tag to Untagged Frames.
      'doubleTag' - Add Tag to all Frames.
      'doubleTagAndFallBack' - Double Tagging will have different rules for 
       VLANs that this port is member in, than these it is not a member in.
      'untag' - Remove Tag from tagged frames."
     ::= { prtIpParamEntry 27 }

prtIpParamRateLimit OBJECT-TYPE
     SYNTAX  Integer32 
     MAX-ACCESS  read-write
     STATUS  current
     DESCRIPTION
     "The maximum rate permitted to transfer via this port, in Kbps."
     ::= { prtIpParamEntry 28 }

prtIpParamDefInterface OBJECT-TYPE
     SYNTAX  Integer32 
     MAX-ACCESS  read-write
     STATUS  current
     DESCRIPTION
     "The Default Interface for packets with unresolved destination subnet.
      For internal-X port: 100 + X ."
     ::= { prtIpParamEntry 29 }

prtIpParamMng OBJECT-TYPE
    SYNTAX  INTEGER
	{
       notApplicable (1),
       disable       (2),
       enable        (3) 
    }
    MAX-ACCESS  read-write
    STATUS  current
    DESCRIPTION
    "This object indicates whether Management is enabled/disabled
     via this port."
    ::= { prtIpParamEntry 30 }


prtIpParamFloodedRateLimit OBJECT-TYPE
     SYNTAX  Integer32 
     MAX-ACCESS  read-write
     STATUS  current
     DESCRIPTION
     "The maximum rate permitted to transfer broadcast, multicast,
     and unicast flooded frames via this port, in Kbps.
     0 - Disable.
     In Ipmux14 this parameter is applicable when prtIpParamRateLimit=0 (disable)."
     ::= { prtIpParamEntry 31 }

prtIpParamBurstSize	 OBJECT-TYPE
     SYNTAX  Unsigned32 
     MAX-ACCESS  read-write
     STATUS  current
     DESCRIPTION
     "The burst size that the port can support beyond rate limitation
     determined in prtIpParamRateLimit.
     Burst Size is measured in bytes."
     ::= { prtIpParamEntry 32 }

prtIpParamLimitPacketType  OBJECT-TYPE
     SYNTAX  INTEGER 
     {
       all                      (1),
	   broadMultiFloodedUnicast (2),
	   broadcastMulticast       (3),
       broadcast                (4)
     }
     MAX-ACCESS  read-write
     STATUS  current
     DESCRIPTION
     "The packet type that will be rate limited. Rate limitation 
     determined in prtIpParamRateLimit.
     all - All packet types are rate limited.
	 broadMultiFloodedUnicast - Broadcast, Multicast and Flooded Unicast packets are rate limited.
     broadcastMulticast - Broadcast and Multicast packets are rate limited.
     broadcast - Broadcast packets are rate limited."
     ::= { prtIpParamEntry 33 }

prtIpParamKeepAliveInterval   OBJECT-TYPE
     SYNTAX  Integer32
     MAX-ACCESS  read-write
     STATUS  current
     DESCRIPTION
     "This parameter indicates the period of time (in msec.) 
     between two consequent Keep Alive messages."
     ::= { prtIpParamEntry 34 }

prtIpParamKeepAliveThresh	 OBJECT-TYPE
     SYNTAX  Integer32
     MAX-ACCESS  read-write
     STATUS  current
     DESCRIPTION
     "This parameter indicates the maximum number of 
     missed Keep Alive answer messages acceptable, after which link status will be failed."
     ::= { prtIpParamEntry 35 }


prtIpParamP2pKeepAliveVlanId OBJECT-TYPE
     SYNTAX  Integer32 
     MAX-ACCESS  read-write
     STATUS  current
     DESCRIPTION
     "Dedicated VLAN ID for keep alive messages."
     ::= { prtIpParamEntry 36 }

prtIpParamP2pKeepAliveVlanPrio OBJECT-TYPE
     SYNTAX  Integer32 
     MAX-ACCESS  read-write
     STATUS  current
     DESCRIPTION
     "VLAN priority for P2P keep alive messages ."
     ::= { prtIpParamEntry 37 }

prtIpParamRingAdjacentMacAddr  OBJECT-TYPE
     SYNTAX     MacAddress
     MAX-ACCESS  read-only
     STATUS  current
     DESCRIPTION
     "The MAC address of the adjacent NE connected to this port in an ETH ring.
       If the port is not a member of a ring, the value of this parameter
       will be 00-00-00-00-00-00."
     ::= { prtIpParamEntry 38 }
  


prtClkSrc OBJECT IDENTIFIER ::= { systemPort 7 }

prtClkSrcTable OBJECT-TYPE
	SYNTAX  SEQUENCE OF PrtClkSrcEntry
	MAX-ACCESS  not-accessible
	STATUS current
	DESCRIPTION  
	"A table - Parameters for  master and fallback 
     clock source of ports ."
	::= {prtClkSrc 1}

prtClkSrcEntry OBJECT-TYPE
    SYNTAX PrtClkSrcEntry
    MAX-ACCESS not-accessible
    STATUS current
	DESCRIPTION  "An entry in table."
	INDEX {prtClkSrcCnfgIdx, prtClkSrcPrtIdx, prtClkSrcIdx}
    ::= { prtClkSrcTable 1}

PrtClkSrcEntry ::=
    SEQUENCE {
    prtClkSrcCnfgIdx   Integer32,
    prtClkSrcPrtIdx	   Integer32,
    prtClkSrcIdx       INTEGER,
    prtClkSrcMode      INTEGER,
    prtClkSrcPrt       Integer32
	}

prtClkSrcCnfgIdx OBJECT-TYPE
    SYNTAX Integer32 (1..255)
    MAX-ACCESS not-accessible
    STATUS current
    DESCRIPTION
    "This attribute indicates the Idx of the Cnfg(1..255) being 
     accessed ; Idx of 255 relates to the TmpCnfg."
    ::= { prtClkSrcEntry 1}

prtClkSrcPrtIdx OBJECT-TYPE
    SYNTAX  Integer32
    MAX-ACCESS  not-accessible
    STATUS  current
    DESCRIPTION
    "This object indicates a unique Port Index (receiving clock).
     Refer to device specification for port Index"
    ::= { prtClkSrcEntry 2}

prtClkSrcIdx OBJECT-TYPE
    SYNTAX  INTEGER 
    {
    master    (1),
    fallback  (2)
    }
    MAX-ACCESS  not-accessible
    STATUS  current
    DESCRIPTION
    "An index in the table. 
     master   - refers Master clock parameters 
     fallback - refers Fallback clock parameters"
    ::= { prtClkSrcEntry 3}

prtClkSrcMode OBJECT-TYPE
    SYNTAX  INTEGER
    {
--  none            (1),
    internal        (2),
    rxClk           (3),
--  station         (4),
--  lbt             (5),
--  ntr             (6),
--	adaptive        (7),  
    notApplicable (255)
    }
    MAX-ACCESS  read-write
    STATUS  current
    DESCRIPTION
    "This entry indicates the source the nodal timing is 
     locked to."
    ::= { prtClkSrcEntry 4}

prtClkSrcPrt OBJECT-TYPE
    SYNTAX  Integer32
    MAX-ACCESS  read-write
    STATUS  current
    DESCRIPTION
    "This entry is valid only when working in rxClk mode.
	 It specifies the port from which the clock willl be taken.
	 Refer to device specification for source port Index"      
    ::= { prtClkSrcEntry 5}


opticalPort OBJECT IDENTIFIER ::= { systemPort 8 }

optPrtMonitorTable OBJECT-TYPE
    SYNTAX  SEQUENCE OF OptPrtMonitorEntry
    MAX-ACCESS  not-accessible
    STATUS current
    DESCRIPTION
    "A table -  optical port (e.g SFP) monitoring parameters,
     according to SFF-8472 Specification for Diagnostic Monitoring
     Interface for Optical Xcvrs. and ITU-T rec. G.958"
    ::= {opticalPort 1}

optPrtMonitorEntry OBJECT-TYPE
    SYNTAX OptPrtMonitorEntry
    MAX-ACCESS not-accessible
    STATUS current
    DESCRIPTION  "An entry in table."
    INDEX {optPrtMonitorPrtIdx,optPrtMonitorSample}
    ::= { optPrtMonitorTable 1}

OptPrtMonitorEntry ::= SEQUENCE {
    optPrtMonitorPrtIdx        Integer32,
    optPrtMonitorSample        INTEGER,
    optPrtMonitorTxPower       Integer32,
    optPrtMonitorLaserBias     Integer32,
    optPrtMonitorLaserTemp     Integer32,
    optPrtMonitorRxPower       Integer32,
    optPrtMonitorSupplyVoltage Integer32 
 }

optPrtMonitorPrtIdx OBJECT-TYPE
    SYNTAX  Integer32
    MAX-ACCESS  not-accessible
    STATUS  current
    DESCRIPTION
    "This object indicates a unique (optical) Port Index .
     Refer to device specification for port Index."
    ::= { optPrtMonitorEntry 1 }

optPrtMonitorSample OBJECT-TYPE
     SYNTAX  INTEGER {
         actual  (1),
         minimum (2),
         maximum (3)
        }
    MAX-ACCESS  not-accessible
    STATUS  current
    DESCRIPTION
    "This index indicates historic and current values -
     minimum, maximum  and actual (current) value.  "
    ::= { optPrtMonitorEntry 2 }

optPrtMonitorTxPower  OBJECT-TYPE
    SYNTAX  Integer32
    MAX-ACCESS  read-only
    STATUS  current
    DESCRIPTION
    "Transmitted optical power level.
     Value is given in units of hundredth (1/100) of dBm. "
    ::= { optPrtMonitorEntry 3 }

optPrtMonitorLaserBias  OBJECT-TYPE
    SYNTAX  Integer32
    MAX-ACCESS  read-only
    STATUS  current
    DESCRIPTION
    "LASER bias current level.
     Value is given in units of microAmper (uA)."
    ::= { optPrtMonitorEntry 4 }

optPrtMonitorLaserTemp OBJECT-TYPE
    SYNTAX  Integer32
    MAX-ACCESS  read-only
    STATUS  current
    DESCRIPTION
    "LASER temperature level,
     in hundredth (1/100) (C) degrees."
    ::= { optPrtMonitorEntry 5 }

optPrtMonitorRxPower  OBJECT-TYPE
    SYNTAX  Integer32
    MAX-ACCESS  read-only
    STATUS  current
    DESCRIPTION
    "Received optical power in units of hundredth (1/100) of dBm."
    ::= { optPrtMonitorEntry 6 }

optPrtMonitorSupplyVoltage OBJECT-TYPE
    SYNTAX  Integer32
    MAX-ACCESS  read-only
    STATUS  current
    DESCRIPTION
    "Supply voltage, in hundredth (1/100) of volts (V)."
    ::= { optPrtMonitorEntry 7 }
    
optPrtCnfgTable OBJECT-TYPE
    SYNTAX  SEQUENCE OF OptPrtCnfgEntry
    MAX-ACCESS  not-accessible
    STATUS current
    DESCRIPTION
    "A table -  optical port configuration"
    ::= { opticalPort 2 }

optPrtCnfgEntry OBJECT-TYPE
    SYNTAX OptPrtCnfgEntry
    MAX-ACCESS not-accessible
    STATUS current
    DESCRIPTION  "An entry in table."
    INDEX {optPrtCnfgIdx, optPrtCnfgPrtIdx}
    ::= { optPrtCnfgTable 1 }

OptPrtCnfgEntry ::= SEQUENCE {
    optPrtCnfgIdx     Unsigned32,
    optPrtCnfgPrtIdx  Unsigned32,
    optPrtCnfgALS     INTEGER 
 }

optPrtCnfgIdx OBJECT-TYPE
    SYNTAX  Unsigned32
    MAX-ACCESS  not-accessible
    STATUS  current
    DESCRIPTION
    "This attribute indicates the Idx of the Cnfg(1..255) being
     accessed ; Idx of 255 relates to the TmpCnfg.x."
    ::= { optPrtCnfgEntry 1 }

optPrtCnfgPrtIdx OBJECT-TYPE
    SYNTAX  Unsigned32
    MAX-ACCESS  not-accessible
    STATUS  current
    DESCRIPTION
    "This object indicates a unique (optical) Port Index .
     Refer to device specification for port Index."
    ::= { optPrtCnfgEntry 2 }

optPrtCnfgALS  OBJECT-TYPE
     SYNTAX  INTEGER {
         notApplicable (1),
         disable       (2),
         enable        (3)
        }
    MAX-ACCESS  read-write
    STATUS  current
    DESCRIPTION
    "enable/disable Automatic Laser Shutdown  "
    ::= { optPrtCnfgEntry 3 }
    
    
systemResetAllStatsCmd OBJECT-TYPE
      SYNTAX   INTEGER
          {
            off(2),
            on (3)
          }
      MAX-ACCESS  read-write
      STATUS  current
      DESCRIPTION
       "Reset statistics of all ports and connections of the device."
      ::= { agnt 16 }

systemClearTablesCmd OBJECT-TYPE
      SYNTAX   INTEGER
	      {
    		off(2),
	    	tempCnfgTables (3)
	      }
      MAX-ACCESS  read-write
      STATUS  current
      DESCRIPTION
       "tempCnfgTables - Set *RowStatus = destroy for all entries of 
                         some tables having *RowStatus object, for 
                         temporary configuration only! (255).
                         For the relevant tables, see product's specification.
                         This object should be used by WAN product applications 
                         before performing the Update operation, in order to clear 
                         old entries of these tables.
                         For MP-104/204 the entries will be destroyed for cnfg=1. 
        off - agent will automatically change to this value, after performing the 
              command. "
      ::= { agnt 17 }

systemParameter OBJECT-TYPE
      SYNTAX   Integer32
      MAX-ACCESS  read-write
      STATUS  current
      DESCRIPTION
       "This parameter can be used for different purposes: 
        - TELNET session time-out in seconds.
	   	- Ace20: when trying to create row in a table that already
				 has row with the same values, if set of values has to be unique
				 in table, this attribute is set to the index of the existing row.
		- Optimux-T3: when CH interfaces are RJ-45, user can select via this
		         object, the interface type for each Group of channels: T1 or E1:
		         The selection will be a sum of the following Bits.
		         '0' = T1
		         '1' = E1
		         Bit    Group               Value for each Bit having '1'
				  1		  1 (CH-1..CH-8)        	  1
				  2		  2 (CH-9..CH-12)       	  2
				  3		  3 (CH-13..CH-20)	          4
				  4		  4 (CH-21..CH-28)	          8
				 Examples:
				 15 = all Groups are selected to be E1
				  6 = Group 2 and Group 3 are selected to be E1 
				     (Group 1 and Group 4 are T1).
		- FCD-A, FCD-M: user can select via this object the configuration
		         used for Get values of MSDSL parameters that don't have
		         configuration index.
		         1  =active configuration
		         255=temporary configuration.
		         Set of this object should be done before Getting the MSDSL 
		         RW parameters.
		- Ace2002: This parameter indicates the number of intervals that
		         were successfully uploaded upon statistics collection session.        
		- FCD-IP, WR, FCD-IPD, LA-240:
		         This parameter indicates whether Telnet Access is enabled/disabled:
		         Values:
				 2 - Telnet Access is Disabled.
				 3 - Telnet Access is Enabled. 				 
        -Vmux-110: This parameter value equals to maximum number of bundles.
		-Optimux-155: Simmilar usage to Optimux T3. user can select via this
		         object, interface type T1 or E1 for each Group of 
		         channels (LIU):  LIU group consists of 7 channels. 
		         Up to 12 LIUs are represented (84 T1 Channels).
                 The selection will be a sum of the 2**n
                 For each bit:'0' = T1 ,'1' = E1
		         Bit    Group              
				  1		  1 (CH-1 ..  CH-7)   
				  2		  2 (CH-8 .. CH-14)  
				  3		  3 (CH-15 ..CH-21) 
                   ...
				  9		  9 (CH-56.. CH-63) 
                   ...
				  10	  10 (CH-64..CH-70) 
				  11	  11 (CH-71..CH-77) 
				  12	  12 (CH-78..CH-84) "
       ::= { agnt 18 }

 
agnGlobalAlarmMask OBJECT-TYPE   
      SYNTAX OCTET STRING 
      MAX-ACCESS  read-write    
      STATUS  current
      DESCRIPTION
      "The value of this attribute determines the alarm traps the 
       agent should mask and not send to the managers.
       Each bit from a certain octet represents a certain alarm."
      ::= { agnt 19 }

alarmSeverity   OBJECT-TYPE
      	SYNTAX   INTEGER
	      	{
			event		(3),
			minor		(4),
			major		(5),
	    	warning		(6),
			critical	(7)
	  		}
      	MAX-ACCESS  read-only
      	STATUS  current
      	DESCRIPTION
       	"This object specifies the severity of the alarms."
      ::= { agnt 20 }

alarmState   OBJECT-TYPE
      	SYNTAX   INTEGER
	      	{
			off (2), 	-- End, 
			on  (3) 	-- Start.
	  		}
      	MAX-ACCESS  read-only
      	STATUS  current
      	DESCRIPTION
       "."
      ::= { agnt 21 }


agnTestStatus OBJECT-TYPE
    SYNTAX  INTEGER
        {
         off            (2),
         on             (3)
        }

    MAX-ACCESS  read-only
    STATUS  current
    DESCRIPTION
    "Indicates the current test status (for all levels: system,
       card, port).
       This attribute will be set to:
         on(3): when there is at least one test in progress on the
                system/card/port
         off(2): when there is NO test in progress on the
                 system/card/port"
      ::= {agnt 22  }

systemSaveAndResetAllStatsCmd OBJECT-TYPE
      SYNTAX   INTEGER
	      {
    		off(2),
	    	on (3)
	      }
    MAX-ACCESS  read-write
    STATUS  current
    DESCRIPTION
    "on  - a command to Save data of Current Period in Last Period
           data-set and start a new counting period for Current Period.
     off - agent will automatically change to this value, after performing the 
           command."
      ::= { agnt 23 }

systemDefaultGateway OBJECT-TYPE
      SYNTAX   IpAddress
    MAX-ACCESS  read-write
    STATUS  current
    DESCRIPTION
    "Default Gateway's IP Address."
      ::= { agnt 24 }

-- PS Table
systemPsTable OBJECT-TYPE
    SYNTAX  SEQUENCE OF SystemPsEntry
    MAX-ACCESS  not-accessible
    STATUS current
    DESCRIPTION
    "This table describes the PS types of a device.
    Usage of this table is specified in the device's NMS SRS"
    ::= { agnt 25 }

systemPsEntry OBJECT-TYPE
    SYNTAX  SystemPsEntry
    MAX-ACCESS  not-accessible
    STATUS current
    DESCRIPTION  "An entry in table."
    INDEX {systemPsIndex1, systemPsIndex2}
    ::= { systemPsTable 1 }

SystemPsEntry ::= SEQUENCE {
    systemPsIndex1       Integer32,
    systemPsIndex2       Integer32,
    systemPsType       INTEGER,
    systemPsStatus       INTEGER,
    systemPsHotSwap       INTEGER 
 }

systemPsIndex1 OBJECT-TYPE
    SYNTAX  Integer32
    MAX-ACCESS  read-only
    STATUS current
    DESCRIPTION
    "First Index.
    In HUBs:
    1 = PS-A slot
    2 = PS-B slot
    3 = PS-C slot.
    In SA units:
    1 = PS1
    2 = PS2
    Default = 1"
    ::= { systemPsEntry 1 }

systemPsIndex2 OBJECT-TYPE
    SYNTAX  Integer32
    MAX-ACCESS  read-only
    STATUS current
    DESCRIPTION
    "Second Index.
    In HUBs:
    1 always.
    In SA units:
    1 = Local
    2 = Remote
    Default = 1."
    ::= { systemPsEntry 2 }

systemPsType OBJECT-TYPE
      SYNTAX  INTEGER
          {
          none      (1),
          ac        (2),
          dc        (3),
          acDc      (4),
          acPF      (5),
          dcPF      (6),
          acWithFan (7),
          dcWithFan (8),
          acHp      (9) -- High Power
          }
      MAX-ACCESS  read-only
      STATUS  current
      DESCRIPTION
      "The type of PS, for a stand-alone product.
      acDc - PS that supports both AC and DC.
      acPF - Power Feeding (phantom) box that is feeding another box by external AC.
      dcPF - Power Feeding (phantom) box that is feeding another box by external DC.
      acWithFan - AC PS with integrated FAN.
      dcWithFan - DC PS with integrated FAN.
      "
      ::= { systemPsEntry 3 }

systemPsStatus OBJECT-TYPE
      SYNTAX  INTEGER
          {
          notApplicable  (1),
          failed         (2),
          ok             (3),
          degraded       (4)
          }
      MAX-ACCESS  read-only
      STATUS  current
      DESCRIPTION
      "The Status of the PS unit."
      ::= { systemPsEntry 4 }

systemPsHotSwap OBJECT-TYPE
      SYNTAX  INTEGER
          {
          notApplicable  (1),
          fixed          (2),
          hotSwap        (3)
          }
      MAX-ACCESS  read-only
      STATUS  current
      DESCRIPTION
      "Is PS unit hot swap or fixed."
      ::= { systemPsEntry 5 }

agnFans OBJECT-TYPE
    SYNTAX  OCTET STRING
    MAX-ACCESS  read-only
    STATUS current
    DESCRIPTION
    "This entry specifies the FANs existence and status.
	 Each fan will be represented by 2 bits,
	 where the first bit (right) will specify the existence:
	 (0= Not exist, 1=exist),
     and the left bit will specify it's status
     (0= OK, 1=FAIL), so for each fan:
     00 - FAN does not exist
     01 - FAN exists and OK (Low Mode)
     10 - High Mode (FAN OK)
     11 - FAN exists and is Failed
     bits 0-1 are for first fan
     bits 2-3 are for 2nd fan (if exists)
     bits 4-5 are for 3nd fan (if exists)
     bits 6-7 are for 4nd fan (if exists)
     bits 8-9 are for 5nd fan (if exists)
     bits 10-11 are for 6nd fan (if exists)
     bits 12-13 are for 7nd fan (if exists)
     bits 14-15 are for 8nd fan (if exists)."
     ::= { agnt 26 }

agnSendTrapParameter OBJECT-TYPE
	SYNTAX  Integer32
	MAX-ACCESS  read-write
	STATUS current
	DESCRIPTION
	"This object specifies if the agent will attach a specific
	parameter to a trap.
	
	For ACE2002 the agent will attach or not the openViewSeverity 
	parameter according to the value of this parameter:
	1 - will attach openViewSeverity.
	0 - will not attach openViewSeverity."
     ::= { agnt 27 }

agnSensorsStatus OBJECT-TYPE
	SYNTAX  OCTET STRING
	MAX-ACCESS  read-only
	STATUS current
	DESCRIPTION
	"This entry specifies the Sensors (Temperature sensors or others)
	 existence and status. 
	 Each sensor will be represented by 2 bits,
	 where the first bit (right) will specify the existence:
	 (0= Not exist, 1=exist),
     and the left bit will specify it's status
     (0= OK, 1=FAIL), so for each sensor:
     00 - sensor does not exist
     01 - sensor exists and status is OK
     11 - sensor exists and status is not OK 
                  ( e.g. temperature exceeds pre-defined threshold)
	 bits 0-1 are for first sensor
	 bits 2-3 are for 2nd sensor (if exists)
	 and so on...
	 Bit 0 is the LSB."
     ::= { agnt 28 }

agnStationClockCard OBJECT-TYPE
	SYNTAX  INTEGER
	{
	 notApplicable	(1),
	 notExist       (2),
	 notValid       (3),
	 ok             (4)
	 }
	MAX-ACCESS  read-only
	STATUS current
	DESCRIPTION
	"This entry specifies the station clock card
	 existence and status. 
     notExist - station clock card (piggy) does not exist.
     notValid - station clock card exists but clock status is not valid.
     ok       - station clock card exists, and its status is OK 
     When the sepcific reason for clock status not being valid is known,
     it may be reported by lossOfSync or lossOfSignal values."
     ::= { agnt 29 }

xcIndexNext  OBJECT-TYPE
          SYNTAX         Integer32 (0..2147483647)
          MAX-ACCESS         read-only
          STATUS         current
          DESCRIPTION
           "This object contains an appropriate value to
            be used for xcIndex when creating
            entries in the xcTable.  The value
            0 indicates that no unassigned entries are
            available. To obtain the xcIndex
            value for a new entry, the manager issues a
            management protocol retrieval operation to obtain
            the current value of this object.  After each
            retrieval, the agent should modify the value to
            the next unassigned index.
            After a manager retrieves a value the agent will
            determine through its local policy when this index
            value will be made available for reuse."
          ::= { agnt 30 }

--XC Table
xcTable OBJECT-TYPE
      SYNTAX SEQUENCE OF XcEntry
      MAX-ACCESS not-accessible
      STATUS current
      DESCRIPTION
      "Configuration of system cross-connect entries.
      The table follows the behavior described in RFC 2515, 
      RFC 1604 regarding the creation deletion and modification 
      of an entry within the table."
      ::= { agnt 31 }

xcEntry OBJECT-TYPE
      SYNTAX XcEntry
      MAX-ACCESS not-accessible
      STATUS current
	DESCRIPTION  "An entry in table."
	INDEX { xcIndex, xcIfIndex1, xcVpi, xcVci, xcIfIndex2 }
      ::= { xcTable 1}

XcEntry ::=
      SEQUENCE {
	 xcIndex        Integer32,
     xcIfIndex1   	Integer32,
     xcVpi 	        Integer32,
     xcVci 	        Integer32,
     xcIfIndex2   	Integer32,
	 xcRowStatus    RowStatus,
	 xcDescr        DisplayString,
     xcAdminStatus     INTEGER,
     xcOperStatus      INTEGER,
     xcAttachedIfType  INTEGER,
     xcInputPriority   Integer32,
	 xcBitMapping      Integer32
      }

xcIndex OBJECT-TYPE
      SYNTAX  Integer32
      MAX-ACCESS  not-accessible
      STATUS  current
      DESCRIPTION
      "Cross Connect Identifier."
      ::= { xcEntry 1 }

xcIfIndex1 OBJECT-TYPE
      SYNTAX  Integer32
      MAX-ACCESS  not-accessible
      STATUS  current
      DESCRIPTION
      "The interface Index from the ifTable, which identify one side 
      of the connection."
      ::= { xcEntry 2 }

xcVpi OBJECT-TYPE
      SYNTAX  Integer32 
      MAX-ACCESS  not-accessible
      STATUS  current
      DESCRIPTION
      "The VPI value."
      ::= { xcEntry 3 }

xcVci OBJECT-TYPE
      SYNTAX  Integer32 
      MAX-ACCESS  not-accessible
      STATUS  current
      DESCRIPTION
      "The VCI value."
      ::= { xcEntry 4 }

xcIfIndex2 OBJECT-TYPE
      SYNTAX  Integer32
      MAX-ACCESS  not-accessible
      STATUS  current
      DESCRIPTION
      "The interface Index from the ifTable, which identifies the other 
      side of the connection."
      ::= { xcEntry 5 }

xcRowStatus  OBJECT-TYPE
      SYNTAX  RowStatus
     MAX-ACCESS   read-create
     STATUS   current
     DESCRIPTION
     "This parameter allows NMS to create/delete entries of this table."
     ::= { xcEntry 6 }

xcDescr  OBJECT-TYPE
     SYNTAX  DisplayString
     MAX-ACCESS   read-create
     STATUS   current
     DESCRIPTION
     "A textual string containing information about the
      xc entry."
     ::= { xcEntry 7 }


xcAdminStatus OBJECT-TYPE
        SYNTAX   INTEGER {
           up(1),
           down(2)
            }
      MAX-ACCESS  read-create
      STATUS  current
      DESCRIPTION
                 "The desired administrative status of this
            bi-directional cross-connect."
      ::= { xcEntry 8 }

xcOperStatus OBJECT-TYPE
        SYNTAX   INTEGER {
           up(1),
           down(2),
           unknown(3)
           }
      MAX-ACCESS  read-only
      STATUS  current
      DESCRIPTION
      "The operational status of this bi-directional 
      cross-connect."
      ::= { xcEntry 9 }

xcAttachedIfType OBJECT-TYPE
        SYNTAX   INTEGER {
          notApplicable(1),
          free         (2),
          routerAtm    (3),
          lis          (4)
          }
      MAX-ACCESS  read-only
      STATUS  current
      DESCRIPTION
      "This object indicates if the specific VCC is
      already attached to any interface, and indicates
      the type of the interface.
      This object's purpose is to ease the checking to 
      the NMS.
      notApplicable - used for entries that are not LAN (as HDLC), 
                      or when the VCC was attached to a bridge, or 
                      when this parameter is irrelevant.
      free          - the LAN VCC wasn't attached yet to any router 
                      interface. 
      routerAtm      - attached to an ATM router interface.
      lis           - attached to a LIS interface."
      ::= { xcEntry 10 }

xcInputPriority OBJECT-TYPE
        SYNTAX   Integer32  (1..4)
      MAX-ACCESS  read-create
      STATUS  current
      DESCRIPTION
      "This object is the priority, by which the LAN frames will be 
      internaly sent to the ATM HW. This parameter is applicable if 
      atmNteMdlInputPriorityMechanism=enabled.
      
      1 -  Highest priority. Will be the first to be sent to the ATM HW.
      4 -  Lowest priority. Will be the last to be sent to the ATM HW."
      ::= { xcEntry 11 }

xcBitMapping OBJECT-TYPE
        SYNTAX   Integer32
      MAX-ACCESS  read-only
      STATUS  current
      DESCRIPTION
      "This object maps this entry to a bit of an octet string.
      For ACE2002 this object maps the LAN VCC to the bit of the 
      VLAN Port Lists. If the value is '0' then it means that 
      this VCC is not mapped to a port list or it may be an HDSL
      entry."
      ::= { xcEntry 12 }

systemModule  OBJECT IDENTIFIER ::= { agnt 32 }


modlParam  OBJECT IDENTIFIER ::= { systemModule 1 }

modlParamTable OBJECT-TYPE
      SYNTAX SEQUENCE OF ModlParamEntry
      MAX-ACCESS not-accessible
      STATUS current
      DESCRIPTION
      "This table include parameters for system modules."
      ::= { modlParam 1 }

modlParamEntry OBJECT-TYPE
      SYNTAX ModlParamEntry
      MAX-ACCESS not-accessible
      STATUS current
	DESCRIPTION  "An entry in table."
	INDEX { modlParamIndex }
      ::= { modlParamTable 1}


ModlParamEntry ::=
      SEQUENCE {
	 modlParamIndex        	Integer32,
     modlParamReset 	    INTEGER,
     modlParamSwdlStatus	INTEGER,
	 modlParamLeds          OCTET STRING,
     modlParamType			INTEGER,
	 modlParamSwVer			DisplayString
      }

modlParamIndex OBJECT-TYPE
      SYNTAX  Integer32
      MAX-ACCESS  read-only
      STATUS  current
      DESCRIPTION
      "The module index.
       The index can be the slot number or any other module index as described
       in the specifications of the device.
       For Vmux-2100 device, the index will have values of: 1..4 for slots 1..4."
      ::= { modlParamEntry 1 }

modlParamReset  OBJECT-TYPE
	SYNTAX  INTEGER	{
	                 off         (2),
					 on          (3),
					 factory	 (4) 			 
				    }
	MAX-ACCESS  read-write
	STATUS  current
	DESCRIPTION
	"Reset action to be performed on the module. 
	 Set the parameter will be done always to on(3) or factory (4). 
	 After performing the Reset operation, Agent will automatically set the parameter to off(2)."
	::= { modlParamEntry 2 }
		   
modlParamSwdlStatus  OBJECT-TYPE
    SYNTAX  INTEGER	{
	notApplicable	(1),
	off         	(2),
	inProcess   	(3) 
		    }
    MAX-ACCESS  read-only
    STATUS  current
    DESCRIPTION
      "This parameter indicates whatever the swdl is in process or not."
    ::= {modlParamEntry 3}

modlParamLeds  OBJECT-TYPE
	SYNTAX  OCTET STRING
	MAX-ACCESS  read-only
	STATUS current
	DESCRIPTION
	"This entry specifies the LEDs status of the module.
	 Each led is represented by 4 bits where the first 2 bits (left) specify  the status :
	 (00=NA, 01=OFF, 10=ON, 11=BLINK),
     and the next two bits (right) specify the color :
     (00=GREEN, 01=RED, 10=YELLOW, 11=GRAY).
     The order of the LEDS is from top to bottom, left to right:
     For each row starting from the top, the LEDS are returned from left to right."
     ::= {modlParamEntry 4}

modlParamType  OBJECT-TYPE
	SYNTAX  INTEGER	{
		unknown			(2),
		empty			(3),
		miRicE1			(4),
		miRicT1			(5),
		miRicE3			(6),
		miRicT3			(7)
		}
	MAX-ACCESS  read-only
	STATUS  current
	DESCRIPTION
	"This attribute indicates the Module Type."
	::= { modlParamEntry 5 }

modlParamSwVer  OBJECT-TYPE
	SYNTAX  DisplayString
	MAX-ACCESS  read-only
	STATUS  current
	DESCRIPTION
	"This attribute indicates the Module's Software Version."
	::= { modlParamEntry 6 }


agnNearFarConnection OBJECT-TYPE   
      SYNTAX  INTEGER {
		 notApplicable	(1),
		 disconnected  	(2), 
		 connected 		(3)
		 		}
      MAX-ACCESS  read-only
      STATUS  current
      DESCRIPTION
      "This parameter describes the connection between near-end and far-end agents."   
      ::= { agnt 33 }

agnAccess OBJECT IDENTIFIER ::= {agnt 34}

agnTelnetAccess OBJECT-TYPE
    SYNTAX  INTEGER
    {
     disable       (2),
     enable        (3),
     managersOnly  (4),
     enableSecure  (5),     -- Deprecated; supported by agnSshAccess = enable(3)
     managersOnlySecure(6)  -- Deprecated; supported by agnSshAccess = managersOnly(4)
     }
    MAX-ACCESS  read-write
    STATUS current
    DESCRIPTION
    "Enable/Disable accessing the device via Telnet.

     disable - no one will be allowed to access the device via Telnet.
     enable - all users are allowed Telnet Access.
     managersOnly - Only manager stations listed in the manager's list are allowed.
     enableSecure - same as 'enable' above + only Secure data will be accepted (SSH)
     managersOnlySecure - same as 'managersOnly' above + only Secure data will be
               accepted (SSH)."
     ::= { agnAccess 1 }

agnWebAccess OBJECT-TYPE
    SYNTAX  INTEGER
    {
     disable       (2),
     enable        (3),
     managersOnly  (4),
     enableSecure  (5),
     managersOnlySecure(6)
     }
    MAX-ACCESS  read-write
    STATUS current
    DESCRIPTION
    "Enable/Disable accessing the device via Web.

     disable - no one will be allowed to access the device via Web.
     enable - all users are allowed Web Access.
     managersOnly - Only manager stations listed in the manager's list are allowed.
     enableSecure - same as 'enable' above + only Secure data will be accepted (SSL)
     managersOnlySecure - same as 'managersOnly' above + only Secure data will be
               accepted (SSL)."
     ::= { agnAccess 2 }

agnRadiusAccess  OBJECT-TYPE
	SYNTAX  INTEGER
	{
	 disable       (2),
	 enable        (3)
    }
	MAX-ACCESS  read-write
	STATUS current
	DESCRIPTION
	"Enable/Disable authentication via RADIUS server."
     ::= { agnAccess 3 }

agnSshAccess OBJECT-TYPE
    SYNTAX  INTEGER
    {
     disable       (2),
     enable        (3),
     managersOnly  (4)
    }
    MAX-ACCESS  read-write
    STATUS current
    DESCRIPTION
    "Enable/Disable accessing the device via SSH.

     disable - no one will be allowed to access the device via SSH.
     enable - all users are allowed SSH Access.
     managersOnly - Only manager stations listed in the manager's list are allowed."
    ::= { agnAccess 4 }

agnTacacsAccess  OBJECT-TYPE
    SYNTAX  INTEGER
    {
     disable       (2),
     enable        (3)
    }
    MAX-ACCESS  read-write
    STATUS current
    DESCRIPTION
    "Enable/Disable authentication via TACACS+ server."
     ::= { agnAccess 5 }

agnTftpAccess OBJECT-TYPE
    SYNTAX  INTEGER
    {
    disable       (2),
    enable        (3),
    managersOnly  (4)
    }
    MAX-ACCESS  read-write
    STATUS current
    DESCRIPTION
    "Enable/Disable accessing the device via TFTP.
    By default this option is enable.
    disable - no one will be allowed to access the device via TFTP.
    enable - all users are allowed TFTP Access.
    managersOnly - Only manager stations listed in the manager's list are allowed."
    ::= { agnAccess 7 }


agnSftpAccess OBJECT-TYPE
    SYNTAX  INTEGER
    {
    disable       (2),
    enable        (3),
    managersOnly  (4)
    }
    MAX-ACCESS  read-write
    STATUS current
    DESCRIPTION
    "Enable/Disable accessing the device via SFTP.
    By default this option is enable.
    disable - no one will be allowed to access the device via SFTP.
    enable - all users are allowed SFTP Access.
    managersOnly - Only manager stations listed in the manager's list are allowed."
    ::= { agnAccess 8 }

agnControlPortAccess OBJECT-TYPE
    SYNTAX  INTEGER
    {
    disable       (2),
    enable        (3)
    }
    MAX-ACCESS  read-write
    STATUS current
    DESCRIPTION
    "Enable/Disable the Control port management access.
     This command will be applied to all existing control ports."
     DEFVAL {enable}
    ::= { agnAccess 9 }

systemInterface  OBJECT IDENTIFIER  ::=  { agnt 35 }

SysIfEntityType ::= INTEGER
--  STATUS  current
--  DESCRIPTION
--  "This type defines the Entity Type above the created interface.
--   The values existing in IANAifType MIB
--   should be taken from there only.
--   Additional values can be added, starting from 1000 decimal,
--   when necessary."
    {
        other(1),
        ethernetLan(6),
        atm(37),
        fastEther(62),          -- Fast Ethernet (100BaseT)
        ipForward(142),         -- Router
        teLink(200),
        bridge(209)
    }

-- Interface Configuration Table

ifCreateTable OBJECT-TYPE
    SYNTAX  SEQUENCE OF IfCreateEntry
    MAX-ACCESS  not-accessible
    STATUS  current
    DESCRIPTION
    "The Interface Configuration Table.
     This table enables to create interfaces of Entities."
    ::= { systemInterface 1 }

ifCreateEntry OBJECT-TYPE
    SYNTAX  IfCreateEntry
    MAX-ACCESS  not-accessible
    STATUS  current
    DESCRIPTION
    "An entry in the Interface Configuration table."
    INDEX   { ifCreateEntityType , ifCreateEntityIdx ,
              ifCreateNumber }
    ::= { ifCreateTable 1 }

IfCreateEntry ::= SEQUENCE {
    ifCreateEntityType          SysIfEntityType,
    ifCreateEntityIdx           Integer32,
    ifCreateNumber              Integer32,
    ifCreateRowStatus           RowStatus,
    ifCreateType                IANAifType,
    ifCreateIndex               Integer32,
    ifCreateConnectedTo         Integer32,
    ifCreateParams              Unsigned32,
    ifCreateConnectionPointer   RowPointer 
 }

ifCreateEntityType OBJECT-TYPE
    SYNTAX  SysIfEntityType
    MAX-ACCESS  read-only
    STATUS  current
    DESCRIPTION
    "This object indicates the Type of the Entity that exists above the created interface.
     For a Logical Port, this value can be: other (1) when there is no fixed entity above it."
     ::= { ifCreateEntry 1 }

ifCreateEntityIdx OBJECT-TYPE
    SYNTAX  Integer32
    MAX-ACCESS  read-only
    STATUS  current
    DESCRIPTION
    "This object indicates the Index of the Entity that exists above the created interface.

     For example, row indices for created Bridge Port 4 of Bridge 2 = [209.2.4]:
     - ifCreateEntityType = bridge(209)
     - ifCreateEntityIdx = 2            - Bridge number 2
     - ifCreateNumber = 4               - Bridge Port number 4

     There are cases when an interface is created WITHOUT a real Entity above
     (ifCreateEntityType = other(1)).
     Therefore, as such created interfaces can have different types,
     this object represents a Virtual Entity above the created interface, as follows:

     ifCreateEntityIdx      Created Interface Type
     Value                  (WITHOUT real Entity above)
     -----------------      ---------------------------
     9987                   G.8275.1 PTP-Port
     9988                   SAP Port
     9989                   SAG Port
     9990                   SS7 Port
     9991                   GFP Port
     9992                   VCG Port
     9993                   HDLC Port
     9994                   ML PPP Port
     9995                   Router Interface
     9996                   PPP
     9997                   SVI
     9998                   Logical MAC
     9999                   Bridge: For devices like ACE-3xxx and new devices.
     9999                   N/A:    For devices like RICi-4/8/16.

     For example, row indices for created Bridge 3 (having ifCreateType = bridge(209)) = [1.9999.3]:
     - ifCreateEntityType = other(1)    - no real entity above
     - ifCreateEntityIdx = 9999         - Bridge (created interface type)
     - ifCreateNumber = 3               - Bridge number."
    ::= { ifCreateEntry 2 }

ifCreateNumber OBJECT-TYPE
    SYNTAX  Integer32
    MAX-ACCESS  read-only
    STATUS  current
    DESCRIPTION
    "This object indicates the number of the Interface that is created."
    ::= { ifCreateEntry 3 }

ifCreateRowStatus OBJECT-TYPE
    SYNTAX      RowStatus
    MAX-ACCESS  read-create
    STATUS      current
    DESCRIPTION
    "This object enables the user to
     create/delete entries in this table."
    ::= { ifCreateEntry 4 }

ifCreateType OBJECT-TYPE
    SYNTAX  IANAifType
    MAX-ACCESS  read-create
    STATUS  current
    DESCRIPTION
    "This object indicates the Type of the Interface that is created."
    ::= { ifCreateEntry 5 }

ifCreateIndex OBJECT-TYPE
    SYNTAX  Integer32
    MAX-ACCESS  read-only
    STATUS  current
    DESCRIPTION
    "This object indicates the ifIndex of the created Interface.
     The ifIndex is assigned by the device."
    ::= { ifCreateEntry 6 }

ifCreateConnectedTo OBJECT-TYPE
    SYNTAX  Integer32
    MAX-ACCESS  read-create
    STATUS  current
    DESCRIPTION
    "This object indicates the entity connected to the created Interface.
     The value of this object can be ifIndex of the connected entity or any other
     number that can identify it."
     ::= { ifCreateEntry 7 }

ifCreateParams OBJECT-TYPE
    SYNTAX  Unsigned32
    MAX-ACCESS  read-create
    STATUS  current
    DESCRIPTION
    "This object represents one or more parameters of the created Interface.
     Each group of bits (one or more bits) represents a specific parameter
     and its possible values.
     This object's mapping and interpretation will be specified in each
     device's specification documents.
     The parameter should be used within the create PDU assuming atomic operation."
    ::= { ifCreateEntry 8 }

ifCreateConnectionPointer OBJECT-TYPE
    SYNTAX      RowPointer
    MAX-ACCESS  read-create
    STATUS      current
    DESCRIPTION
    "This parameter represents the entity that is connected
     to this Interface.

     It can be used instead of ifCreateConnectedTo.

     It is an OBJECT IDENTIFIER.
     This parameter's SYNTAX allows the following possibilities:
     - can be simply used for entity that is not an interface
     - is not limited to include up to 32 bits

     The value of this parameter is a pointer to an existing row of a table,
     where the entity connected to this Interface is defined
     (i.e. the pointer uniquely identifies the connected entity).

     Examples:

     In case of an interface (from 2863.ifTable):
        points to 'ifEntry' of corresponding row
        = <ifEntry OID>.<ifIndex>

     In case of a VPI/VCI (from 2515.atmVclTable):
        points to 'atmVclEntry' of corresponding row
        = <atmVclEntry OID>.<ATM>.VPI.VCI

     In case no entity is connected, value = 0
     ."
    ::= { ifCreateEntry 9 }

interfacePerformance     OBJECT IDENTIFIER  ::=  { systemInterface 2 }

ifPerfTable OBJECT-TYPE
    SYNTAX  SEQUENCE OF IfPerfEntry
    MAX-ACCESS  not-accessible
    STATUS  current
    DESCRIPTION
    "Interface Performance Table.
    The propose of this table is to support statistics counters having 64 bit
    by using 2 parameters with syntax= Integer32.
    This is because SNMPv1 does not support Counter64 properly.
    For SNMPv3, ifPerfHCCounter (Counter64) may be supported. "
    ::= { interfacePerformance 1 }

ifPerfEntry OBJECT-TYPE
    SYNTAX  IfPerfEntry
    MAX-ACCESS  not-accessible
    STATUS  current
    DESCRIPTION
    "An entry in the Interface Performance Table."
    INDEX   { ifIndex, ifPerfCounterType }
    ::= { ifPerfTable 1 }

IfPerfEntry ::= SEQUENCE {
    ifPerfCounterType            Integer32,
    ifPerfLowCounterPart         Unsigned32,
    ifPerfHighCounterPart        Unsigned32,
    ifPerfHCCounter              Counter64 
 }

ifPerfCounterType OBJECT-TYPE
   SYNTAX  Integer32
   MAX-ACCESS  not-accessible
   STATUS  current
   DESCRIPTION
   "2nd index of the ifPerfTable.
   This parameter represents the Counter Type.
   Each application can have a different association between this object's
   value and counter type - see relevant application spec.

   For ETH use the following values:

    Value   Counter
    -----   ------------------
    1       Tx 64 (bytes)
    2       Tx 65-127 (bytes)
    3       Tx 128-255 (bytes)
    4       Tx 256-511 (bytes)
    5       Tx 512-1023 (bytes)
    6       Tx 1024-Max (bytes)
    7       Tx 1024-1518 (bytes)
    8       Tx Correct Frames
    9       Tx Error Frames
    10      Tx Discard Frames
    11      Total Collisions
    12      Tx Unicast Frames
    13      Tx Broadcast Frames
    14      Tx Multicast Frames
    15      Rx Correct Bytes/Octets
    16      Single Collision Frames
    17      Multiple Collision Frames
    18      Deferred Transmission Frames
    19      Late Collision Frames
    21      Rx Correct Frames
    22      FCS Errors Frames
    23      Rx Jabber
    24      Rx Fragments Frames
    25      Rx Undersize Frames
    26      Rx Oversize Frames
    27      Rx Discard Frames
    28      Rx Unicast Frames
    29      Rx Broadcast Frames
    30      Rx Multicast Frames
    31      Rx 1519-2047 (bytes)
    32      Rx 2048-Max (bytes)
    40      Tx 1519-2047 (bytes)
    41      Tx 2048-Max (bytes)
    42      Tx Oversize Frames
    43      Rx Frame Too Short
    44      Rx Error Frames
    45      CRC Error Frames --Rx
    46      Rx L2CP Discarded
    47      Rx OAM Discarded
    48      Rx Unknown Protocol Discarded
    49      Dropped Frames  --Tx
    50      Tx Correct Bytes/Octets
    51      Rx Overflow  -- FIFO overflow in MLPPP bundle
    52      Tx Fragments Frames

   For some applications (not ETH) the following values are used:
   1= Rx Octets, 2= Tx Octets, 3= Rx Frames, 4= Tx Frames, 5=Rx Dropped Frames,
   6= Tx Dropped Frames.
   Optionally, counter type description appears in agnListDecodingTable "
   ::= { ifPerfEntry 1 }


ifPerfLowCounterPart OBJECT-TYPE
   SYNTAX  Unsigned32
   MAX-ACCESS  read-only
   STATUS  current
   DESCRIPTION
   "In order to support Counters having 64 bit length,
   the performance counter is divided into two 32 bit parameters as follows:
   [  64 bit parameter ] = [  High 32 bit parameter ][ Low 32 bit parameter ].
   This parameter holds the Low 32 bits of the counter,
   while the following parameter holds the High 32 bits of the counter."
   ::= { ifPerfEntry 2 }

ifPerfHighCounterPart OBJECT-TYPE
   SYNTAX  Unsigned32
   MAX-ACCESS  read-only
   STATUS  current
   DESCRIPTION
   "This parameter holds the High 32 bits of the counter
   (see description in the above parameter)."
   ::= { ifPerfEntry 3 }

ifPerfHCCounter OBJECT-TYPE
   SYNTAX  Counter64
   MAX-ACCESS  read-only
   STATUS  current
   DESCRIPTION
   "This High Capacity counter holds whole 64 bits of the counter
    indicated by ifPerfCounterType (concatenates both counter parts
    ifPerfHighCounterPart&ifPerfLowCounterPart)
    This object can be supported only by agents using SNMPv2 or SNMPv3."
   ::= { ifPerfEntry 4 }


systemOam    OBJECT IDENTIFIER  ::=  { agnt 36 }

systemOamTable OBJECT-TYPE
	SYNTAX  SEQUENCE OF SystemOamEntry
    MAX-ACCESS  not-accessible
    STATUS  current
    DESCRIPTION
	"The OAM Configuration Table."
	::= { systemOam 1 }

systemOamEntry OBJECT-TYPE
    SYNTAX  SystemOamEntry
    MAX-ACCESS  not-accessible
    STATUS  current
    DESCRIPTION
    "An entry in the OAM table."
    INDEX   { systemOamCnfgIdx }
    ::= { systemOamTable 1 }

SystemOamEntry ::=
    SEQUENCE {
        systemOamCnfgIdx            Integer32,
        systemOamFrequency			Integer32,
		systemOamTimeoutCycles		Integer32,
		systemOamLinkCheck          INTEGER		
    }

systemOamCnfgIdx OBJECT-TYPE
    SYNTAX Integer32 (1..255)
    MAX-ACCESS not-accessible
    STATUS current
    DESCRIPTION
    "This attribute indicates the Idx of the Cnfg(1..255) being 
     accessed ; Idx of 255 relates to the TmpCnfg."
    ::= {  systemOamEntry 1}

systemOamFrequency OBJECT-TYPE
    SYNTAX  Integer32
    MAX-ACCESS  read-write
    STATUS  current
    DESCRIPTION
    "Time in sec. between 2 OAM packets."
    ::= { systemOamEntry 2 }

systemOamTimeoutCycles OBJECT-TYPE
    SYNTAX  Integer32
    MAX-ACCESS  read-write
    STATUS  current
    DESCRIPTION
    "No. of cycles the agent will send OAM packets without receiving a response
     from the remote device before declaring that the connection to the remote side
     is down - Time Out."
    ::= { systemOamEntry 3 }

systemOamLinkCheck
    OBJECT-TYPE
     SYNTAX  INTEGER
      {
       disable       (2),
       enable        (3)
      }
     MAX-ACCESS  read-write
     STATUS  current
     DESCRIPTION
     "This MIB object determines whether continuous connectivity Link checks will be
      performed by the device for uplinks.

      For Vmux-2100: enable (3) value can be set upon device installation.
      In this case, TDM Link Connectivity checks can be performed even before the user
      configures the Links of the device.If the value is enable (3) and there is
      no connection with the remote side, the Test LED will blink on the
      Main Board Module."
     ::= { systemOamEntry 4 }


systemOamDescrTable OBJECT-TYPE
	SYNTAX  SEQUENCE OF SystemOamDescrEntry
    MAX-ACCESS  not-accessible
    STATUS  current
    DESCRIPTION
	"The OAM Descriptors Configuration Table."
	::= { systemOam 2 }

systemOamDescrEntry OBJECT-TYPE
    SYNTAX  SystemOamDescrEntry
    MAX-ACCESS  not-accessible
    STATUS  current
    DESCRIPTION
    "An entry in the OAM table."
    INDEX   { systemOamDescrIdx }
    ::= { systemOamDescrTable 1 }

SystemOamDescrEntry ::=
    SEQUENCE {
        systemOamDescrIdx					Integer32,
		systemOamDescrRowStatus				RowStatus,
        systemOamDescrMode					INTEGER,
        systemOamDescrCCDirection			INTEGER,
		systemOamDescrLoopbackOperation		INTEGER,
		systemOamDescrLoopbackDestAddr		OCTET STRING,
        systemOamDescrXcCounter				Gauge32
		}

systemOamDescrIdx OBJECT-TYPE
    SYNTAX Integer32
    MAX-ACCESS not-accessible
    STATUS current
    DESCRIPTION
    "The OAM Descriptor Index."
    ::= { systemOamDescrEntry 1 }

systemOamDescrRowStatus OBJECT-TYPE
	SYNTAX      RowStatus
	MAX-ACCESS  read-create
	STATUS      current
	DESCRIPTION
	"Enables the user to create/delete entries in this table."
	::= { systemOamDescrEntry 2 }

systemOamDescrMode OBJECT-TYPE
	SYNTAX  INTEGER {
		intermediate(1),
		segmentTermination(2),
		endToEndTermination(3)
	}
	MAX-ACCESS  read-create
	STATUS  current
	DESCRIPTION
	"The OAM Mode of the Descriptor."
	::= { systemOamDescrEntry 3 }

systemOamDescrCCDirection OBJECT-TYPE
	SYNTAX  INTEGER {
		both  (2),
		none  (3),
		source(4),
		sink  (5)     
	} 
	MAX-ACCESS read-create
	STATUS current
	DESCRIPTION
	"OAM Continuity Check function mode.
	 both(2)  - Agent sends OAM CC cells and checks received OAM CC cells.
	 none(3) - Agent does not send and does not check received OAM CC cells.
	 source(4)- Agent sends OAM CC cells.
	 sink(5)  - Agent checks received OAM CC cells."
	::= { systemOamDescrEntry 4 }

systemOamDescrLoopbackOperation OBJECT-TYPE
	SYNTAX INTEGER {
		off	(2),
		on	(3)
	} 
	MAX-ACCESS read-create
 	STATUS current
	DESCRIPTION
	"The OAM Loopback function mode.
	 off(2) - Stop sending loopback OAM cells.
	 on(3) - Start loopback OAM cells."
	::= { systemOamDescrEntry 5 }	 

systemOamDescrLoopbackDestAddr OBJECT-TYPE
	SYNTAX OCTET STRING 
	MAX-ACCESS read-create
 	STATUS current
	DESCRIPTION
	"Loopback Destination Address."
	::= { systemOamDescrEntry 6 }

systemOamDescrXcCounter OBJECT-TYPE
	SYNTAX Gauge32 
	MAX-ACCESS read-only
 	STATUS current
	DESCRIPTION
	"The number of connections that use this OAM Descriptor."
	::= { systemOamDescrEntry 7 }

systemBfd    OBJECT IDENTIFIER  ::=  { systemOam 3 }


bfdSessXTable OBJECT-TYPE
    SYNTAX      SEQUENCE OF BfdSessXEntry
    MAX-ACCESS  not-accessible
    STATUS      current
    DESCRIPTION
        "A 'Pseodo-Augment' of the BFD Session table.

         It is not a 'real augment', as BFD Session table (bfdSessTable)
         is defined within an adopted draft (BFD-STD-R-MIB).

         BFD Session table includes a RowStatus attribute (bfdSessRowStatus),
         while current table is defined WITHOUT a RowStatus attribute.
         Therefore (and similar to an augment table),
         whenever bfdSessRowStatus is set, current table's entries
         should be updated accordingly."
    ::= { systemBfd 2 }

bfdSessXEntry OBJECT-TYPE
    SYNTAX      BfdSessXEntry
    MAX-ACCESS  not-accessible
    STATUS      current
    DESCRIPTION
       "An entry in the table."
    INDEX { bfdSessXIndex }
    ::= { bfdSessXTable 1 }

BfdSessXEntry ::= SEQUENCE {
    bfdSessXIndex               Unsigned32,
    bfdSessXStaticAssociated    INTEGER,
    bfdSessXRemoteDiag          BfdDiagTC,
    bfdSessXClearStatisticsCmd  INTEGER,
    bfdSessXDescription         SnmpAdminString 
 }

bfdSessXIndex OBJECT-TYPE
    SYNTAX      Unsigned32
    MAX-ACCESS  not-accessible
    STATUS      current
    DESCRIPTION
        "This object represents the BFD Session Index.
         Based on bfdSessIndex (from BFD-STD-R-MIB)."
    ::= { bfdSessXEntry 1 }

bfdSessXStaticAssociated OBJECT-TYPE
        SYNTAX      INTEGER {
            disable         (2),
            enable          (3)
            }
        MAX-ACCESS  read-write
        STATUS      current
        DESCRIPTION
                "This object determines whether BFD session (neighbor)
                runs in associated or unassociated mode.
                In associated mode, static-route state depends on
                the state of the BFD session.
                In unassociated mode, static-route state is not
                affected by the state of the BFD session.
                disable     (2) - associated mode is disabled
                enable      (3) - associated mode is enabled
                "
        ::= { bfdSessXEntry 5 }

bfdSessXRemoteDiag OBJECT-TYPE
        SYNTAX     BfdDiagTC
        MAX-ACCESS read-only
        STATUS     current
        DESCRIPTION
            "A diagnostic code specifying the remote system's reason
             for the last transition of the session from up(4)
             to some other state."
        ::= { bfdSessXEntry 6 }

bfdSessXClearStatisticsCmd OBJECT-TYPE
        SYNTAX  INTEGER
          {
            off(2),
            on (3)
          }
        MAX-ACCESS  read-write
        STATUS      current
        DESCRIPTION
            "Indicates a user command to clear all counters in row of
            specific BFD session."
        DEFVAL { off }
        ::= { bfdSessXEntry 7 }

bfdSessXDescription OBJECT-TYPE
        SYNTAX  SnmpAdminString
        MAX-ACCESS  read-write
        STATUS      current
        DESCRIPTION
            "BFD session description. By default the agent will set
            the value equal to bfdSessXIndex."
        ::= { bfdSessXEntry 9 }


agnDeviceView OBJECT-TYPE
    SYNTAX  INTEGER
    {
     oldLook       (2),
     newLook       (3),
     newLook2      (4),
     plastic       (5),
     metal         (6)
    }
    MAX-ACCESS  read-only
    STATUS current
    DESCRIPTION
    "This variable denotes the view of the device:
    Look: old look, new look or new look 2.
    Material: Plastic or Metal."
     ::= { agnt 37 }

bitMappingTable OBJECT-TYPE
      SYNTAX SEQUENCE OF BitMappingEntry
      MAX-ACCESS not-accessible
      STATUS current
      DESCRIPTION
      "This table maps bits of an octet string to an interface.
      For ACE-2002 this table is used to map bits of VLAN port lists
      to LAN VCC's. This table is the opposite view of the xcTable for
      xcBitMapping. It is used to ease the bit translation for the NMS."
      ::= { agnt 38 }

bitMappingEntry OBJECT-TYPE
      SYNTAX BitMappingEntry
      MAX-ACCESS not-accessible
      STATUS current
	DESCRIPTION  
	"Each entry in the table describes a correlation of a bit location to 
	an interface.
	For ACE-2002 - Upon creation of a new LAN VCC the agent will add an 
	entry to this table that will define the bit location for that VCC."
	INDEX { bitMappingLocation }
      ::= { bitMappingTable 1}

BitMappingEntry ::=
      SEQUENCE {
	  bitMappingLocation       Integer32,
      bitMappingIndex          Integer32
      }

bitMappingLocation OBJECT-TYPE
      SYNTAX  Integer32
      MAX-ACCESS  not-accessible
      STATUS  current
      DESCRIPTION
      "The bit location in an octet string."
      ::= { bitMappingEntry 1 }

bitMappingIndex OBJECT-TYPE
      SYNTAX  Integer32
      MAX-ACCESS  read-only
      STATUS  current
      DESCRIPTION
      "The interface index or any other index that should be mapped."
      ::= { bitMappingEntry 2 }

bitMappingView OBJECT-TYPE
      SYNTAX  OCTET STRING
      MAX-ACCESS  read-only
      STATUS  current
      DESCRIPTION
      "A view of the bitMappingTable in one object - each entry in the 
      biMappingTable will have the corresponding Bit of this object 
      (bitMappingLocation) = '1'.
      For ACE-2002 it is used to describe all the existing LAN VCC's
      So that the NMS can easily calculate which VCC's can be selected
      as members for a VLAN, instead of reading all the bitMapping Table."
      ::= { agnt 39 }

hostTable OBJECT-TYPE
    SYNTAX  SEQUENCE OF HostEntry
    MAX-ACCESS  not-accessible
    STATUS  current
    DESCRIPTION
    "Host interface table."
    ::= { agnt 40 }

hostEntry OBJECT-TYPE
    SYNTAX  HostEntry
    MAX-ACCESS  not-accessible
    STATUS  current
    DESCRIPTION
    "An entry in the Host Table.
    The hostParam1, hostParam2, and hostParam3 entries may 
    have different use in different applications."
    INDEX   { hostIndex } 
    ::= { hostTable 1 }

HostEntry ::=
   SEQUENCE {
   hostIndex			Integer32,
   hostIP	    		IpAddress,
   hostIPMask			IpAddress,
   hostDefaultNextHop	IpAddress,
   hostMode				Integer32,
   hostParam1			Integer32,
   hostParam2			Integer32,
   hostParam3			Integer32,
   hostRowStatus		RowStatus,
   hostVlanTagging		INTEGER,
   hostVlanId			Integer32,
   hostVlanPriority		Integer32
                 }


hostIndex OBJECT-TYPE
   SYNTAX  Integer32 
   MAX-ACCESS  not-accessible
   STATUS  current
   DESCRIPTION
   "The Host Table Index. This index can have the same value as Host No."
   ::= { hostEntry 1 }

hostIP OBJECT-TYPE
   SYNTAX  IpAddress 
   MAX-ACCESS  read-create
   STATUS  current
   DESCRIPTION
   "The host interface IP address."
   ::= { hostEntry 2 }

hostIPMask OBJECT-TYPE
   SYNTAX  IpAddress 
   MAX-ACCESS  read-create
   STATUS  current
   DESCRIPTION
   "The host interface subnet mask."
   ::= { hostEntry 3 }

hostDefaultNextHop OBJECT-TYPE
   SYNTAX  IpAddress 
   MAX-ACCESS  read-create
   STATUS  current
   DESCRIPTION
   "The host interface Default Next Hop address."
   ::= { hostEntry 4 }

hostMode OBJECT-TYPE
   SYNTAX  Integer32 
   MAX-ACCESS  read-create
   STATUS  current
   DESCRIPTION
   "This parameter represents the Host mode of operation.
   There can be different values for each application.
   For example:
   Not Applicable = 1."
   ::= { hostEntry 5 }

hostParam1 OBJECT-TYPE
   SYNTAX  Integer32 
   MAX-ACCESS  read-create
   STATUS  current
   DESCRIPTION
   "This parameter represents the first Host parameter.
   There can be different values for each application.
   For example:
   Not Applicable = 1."
   ::= { hostEntry 6 }

hostParam2 OBJECT-TYPE
   SYNTAX  Integer32 
   MAX-ACCESS  read-create
   STATUS  current
   DESCRIPTION
   "This parameter represents the 2nd Host parameter.
   There can be different values for each application."
   ::= { hostEntry 7 }

hostParam3 OBJECT-TYPE
   SYNTAX  Integer32 
   MAX-ACCESS  read-create
   STATUS  current
   DESCRIPTION
   "This parameter represents the 3nd Host parameter.
   There can be different values for each application."
   ::= { hostEntry 8 }

hostRowStatus OBJECT-TYPE
   SYNTAX  RowStatus 
   MAX-ACCESS  read-create
   STATUS  current
   DESCRIPTION
   "Creation/Deletion of rows in the table."
   ::= { hostEntry 9 }

hostVlanTagging OBJECT-TYPE
    SYNTAX  INTEGER 
    {
    notApplicable(1),
    untag		(2),
    tag	    	(3)
    }
    MAX-ACCESS  read-create
    STATUS  current
    DESCRIPTION
    "Host VLAN support (Tagging).
     untag - No support of VLAN Tagging.
     tag - 4 VLAN bytes will be added to the frame."
    ::= { hostEntry 10 }

hostVlanId OBJECT-TYPE
     SYNTAX  Integer32 
     MAX-ACCESS  read-create
     STATUS  current
     DESCRIPTION
     "Host VLAN ID."
     ::= { hostEntry 11 }
  
hostVlanPriority OBJECT-TYPE
     SYNTAX  Integer32 
     MAX-ACCESS  read-create
     STATUS  current
     DESCRIPTION
     "Host VLAN Frame priority."
     ::= { hostEntry 12 }


invNameXCTable OBJECT-TYPE
	SYNTAX  SEQUENCE OF InvNameXCEntry
	MAX-ACCESS  not-accessible
	STATUS  current
	DESCRIPTION
	"Inverse Name XC Table.
	 This table can be used to ease the search for a connection first index
	 by the connection name."
	::= { agnt 41 }

invNameXCEntry OBJECT-TYPE
	SYNTAX  InvNameXCEntry
	MAX-ACCESS  not-accessible
	STATUS  current
	DESCRIPTION
	"An entry in the table."
	INDEX   { IMPLIED invNameXC } 
	::= { invNameXCTable 1 }

InvNameXCEntry ::= SEQUENCE {
	invNameXC			SnmpAdminString,
	invNameXCType		OBJECT IDENTIFIER,
	invNameXCIndex		Integer32
	}

invNameXC OBJECT-TYPE
	SYNTAX  SnmpAdminString (SIZE (1..64)) 
	MAX-ACCESS  not-accessible
	STATUS  current
	DESCRIPTION
	"The unique Connection name,
	 associated to a Cross-Connection."
	::= { invNameXCEntry 1 }

invNameXCType OBJECT-TYPE
	SYNTAX  OBJECT IDENTIFIER 
	MAX-ACCESS  read-only
	STATUS  current
	DESCRIPTION
	"The OBJECT IDENTIFIER of the respective XC Table.
	 Examples:
	 
	 XC Table					invNameXCType
	 ---------------------------------------------------
	 atmVpCrossConnectTable		1.3.6.1.2.1.37.1.9
	 atmVcCrossConnectTable		1.3.6.1.2.1.37.1.11
	 atmfCESConfTable			1.3.6.1.4.1.353.5.2.2.1.1
	 ."
	::= { invNameXCEntry 2 }

invNameXCIndex OBJECT-TYPE
	SYNTAX  Integer32 
	MAX-ACCESS  read-only
	STATUS  current
	DESCRIPTION
	"The XC Table (invNameXCType) may include more than one index.
	 This object represents the value of the first XC Index."
	::= { invNameXCEntry 3 }


agnDeviceCapabilities OBJECT-TYPE
    SYNTAX  OCTET STRING
    MAX-ACCESS  read-only
    STATUS current
    DESCRIPTION
    "Indicates the optional capabilities that are implemented by this device
     and are manageable through this MIB.

     For each capability 1 BIT is allocated in each Octet starting from the LSB.
     If the value of the BIT = 1, the capability is Enabled.
     If the value of the BIT = 0, the capability is Disabled.
     For bit assignment, refer to device specification.
     Capabilities example:
     Router - BIT 0 (0000 0001 = 01 Hex = 1 Decimal).

     For ACE: 2nd octet (MSB) will represent the maximum number of intervals that
     the Agent can keep in its DB (same for all ports).

     For Vmux, this object describes agent's support of LBRAD coder feature:
     1 octet ; bit 0 (LSB).
     '1' - LBRAD feature is supported
     '0' - LBRAD feature is not supported.

     For some devices like Vmux, ASMi-54, RICi-4/8/16 this MIB object is used for licensing.
     More details on licensing can be found in device spec."
    ::= {agnt 42}


rowInfoTable OBJECT-TYPE
    SYNTAX  SEQUENCE OF RowInfoEntry
    MAX-ACCESS  not-accessible
    STATUS  current
    DESCRIPTION
    "This table holds information of other tables."
    ::= { agnt 43 }

rowInfoEntry OBJECT-TYPE
    SYNTAX  RowInfoEntry
    MAX-ACCESS  not-accessible
    STATUS  current
    DESCRIPTION
    "An entry in the table."
    INDEX   { rowInfoTableId }
    ::= { rowInfoTable 1 }

RowInfoEntry ::= SEQUENCE {
    rowInfoTableId      OBJECT IDENTIFIER,
    rowInfoCounter      Integer32,
    rowInfoIndexNext    Integer32,
    rowInfoMaxNoOfRows  Integer32 
 }

rowInfoTableId OBJECT-TYPE
    SYNTAX  OBJECT IDENTIFIER
    MAX-ACCESS  not-accessible
    STATUS  current
    DESCRIPTION
    "The OBJECT IDENTIFIER of the Table,
     which its information is held by this table (rowInfoTable).
     Examples:

     Table Name                 rowInfoTableId
     ---------------------------------------------------
     atmTrafficDescrParamTable  1.3.6.1.2.1.37.1.5
     atmVpCrossConnectTable     1.3.6.1.2.1.37.1.9
     atmVcCrossConnectTable     1.3.6.1.2.1.37.1.11
     atmfCESConfTable           1.3.6.1.4.1.353.5.2.2.1.1

     For OAM-CFM, additional indices will be used to indicate higher levels
     entity instance.
     e.g for MA table (dot1agCfmMaNetTable) and MIP table (ethIfOamCfmMip),
     additional index will indicate MD.

     For MEP table (IEEE8021-CFM-MIB.dot1agCfmMepTable)
     additional indices will indicate MD.MA.MEP_Direction
     (MEP_Direction - Down = 1, Up = 2)"
    ::= { rowInfoEntry 1 }

rowInfoCounter OBJECT-TYPE
    SYNTAX  Integer32
    MAX-ACCESS  read-only
    STATUS  current
    DESCRIPTION
    "The Number of rows in the table, indicated by rowInfoTableId."
    ::= { rowInfoEntry 2 }

rowInfoIndexNext OBJECT-TYPE
    SYNTAX  Integer32
    MAX-ACCESS  read-only
    STATUS  current
    DESCRIPTION
    "The First Free Index of the table, indicated by rowInfoTableId."
    ::= { rowInfoEntry 3 }

rowInfoMaxNoOfRows OBJECT-TYPE
    SYNTAX  Integer32
    MAX-ACCESS  read-only
    STATUS  current
    DESCRIPTION
    "The maximum possible number of rows in the table, indicated by rowInfoTableId."
    ::= { rowInfoEntry 4 }


agnStoreCmd OBJECT-TYPE
    SYNTAX  INTEGER
    {
     off                (2), --offOK
     inFlash            (3),
     asDefConfigFile    (4),
     offError           (5)  --offFailed
         }
    MAX-ACCESS  read-write
    STATUS current
    DESCRIPTION
    "Store command.
     inFlash(3)         = store the current Agent configuration in Flash memory.
     asDefConfigFile(4) = store the current Agent configuration as
                          Default Configuration file (e.g. 'DefConfig.cfg').
     Agent will perform the required command and change automatically
     the value of this object to off(2), except for the following case.
     When device supports CLI and the operation of copying the current configuration
     to Flash memory (or Default Configuration) is taking a long time,
     Agent will keep the value Set until the operation is finished.
     This way, by Getting this object, one can know that the device is in
     process of storage. Upon end of the process, the value will be changed
     by Agent, as follows:
     - off(2) - if storage operation was successful (OK)
     - offError(5) - if storage operation failed."
     ::= { agnt 44 }


agnFunctionTable OBJECT-TYPE
    SYNTAX  SEQUENCE OF AgnFunctionEntry
    MAX-ACCESS  not-accessible
    STATUS  current
    DESCRIPTION
    "This table is used in order to activate/deactivate device functions.
     The index indicates the function. Each function can be Enabled or Disabled."
    ::= { agnt 45 }

agnFunctionEntry OBJECT-TYPE
    SYNTAX  AgnFunctionEntry
    MAX-ACCESS  not-accessible
    STATUS  current
    DESCRIPTION
    "An entry in the table."
    INDEX   { agnFunction }
    ::= { agnFunctionTable 1 }

AgnFunctionEntry ::= SEQUENCE {
    agnFunction                 INTEGER,
    agnFunctionActivation       INTEGER,
    agnFunctionAttributes       OCTET STRING,
    agnFunctionVersion          Unsigned32 
 }

agnFunction     OBJECT-TYPE
    SYNTAX  INTEGER
    {
     routing                   (2),
     backup                    (3),
     alarmForwarding           (4),
     uplinkLoopDetect          (5),
     systemClock               (6),
     nps                       (7),
     ethOamCfm                 (8),
     fileTransfer              (9),
     netEq                     (10), -- Network Equalizer (for Voice Quality)
     ecan                      (11), -- Echo Canceler
     cli                       (12), -- Command Line Interface
     csm                       (13), -- Clock Selection model
     erp                       (14),
     eps                       (15),
     tdmPwProtect              (16),
     pathSdhSonetProtect       (17),
     aps                       (18),
     ethPortProtect            (19),
     tdmPortProtect            (20),
     tdmPW                     (21),
     fileSystem                (22),
     ssfp                      (23),
     ptp                       (24), -- 1588 Recovered clock
     copyFile                  (25),
     router                    (26),
     tbd                       (27), -- not in use
     faultManagement           (28),
     configChangeSync          (29), -- NE Configuration Change Support
     binaryDataRetrievalMethod (30), -- Binary Data Retrieval from device
     bridge                    (31),
     acl                       (32),
     ospf                      (33),
     bgp                       (34),
     bfd                       (35),
     performanceManagement     (36),
     ituSat                    (37), -- Y.1564  support
     genericPpp                (38), -- Generic PPP & PPPoE
     policer                   (39), -- Policer Profile
     lldp                      (40), -- LLDP
     twamp                     (41), -- TWAMP
     flow                      (42),
     vrrp                      (43), -- Virtual Router Redundancy Protocol
     l3Sat                     (44),
     portFlowMirroring         (45),
     ethPort                   (46), -- Ethernet Port
     dhcpL2Relay               (47), -- DHCP Layer 2 Relay
     nat                       (48), -- NAT 
     cellular                  (49)  -- Cellular 
     }
    MAX-ACCESS  not-accessible
    STATUS current
    DESCRIPTION
    "This MIB object indicates the function that will be enabled or disabled
     in the device.
     alarmForwarding= Fault Propagation (usually towards user port).
     For Vmux:
     routing (2) - enable/disable Router
     backup  (3) - enable/disable Backup between E1/T1/Serial Link and ETH.
     uplinkLoopDetect (5) - enable/disable Loop Detection on the TDM Uplink.
     systemClock (6) - enable/disable the System Clock.

     nps (7) - N+1 Protection Switching device physically connected to I/O
     modules in Gmux2000.

     ethOamCfm (8) - denotes that the device supports ETH OAM CFM  (802.1ag).
     The list of supported CFM attributes is specified in agnFunctionAttributes.
     Different from the other functions, the manager cannot activate the CFM.
     agnFunctionActivation is set only by the agent. A value of enable (3)
     denotes that the device supports ETH OAM CFM.

     fileTransfer (9) - denotes that the device supports file transfer functions
     and agnFunctionAttributes object which lists the supported functions.
     Similar to ETH OAM CFM, agnFunctionActivation is set only by the agent.
     A value of enable(3) denotes that the device supports file transfer functions
     and agnFunctionAttributes.

     erp (14) - Ethernet Ring Protection according to the G.8032 standard

     The general protection related capabilitites eps(15), tdmPwProtect(16),
      pathSdhSonetProtect(17), aps(18), ethPortProtect(19) and tdmPortProtect(20)
      are correlated to the definition of the ProtectClassType.

     eps (15) - Ethernet Protection Switching according to the G.8031 standard

     tdmPwProtect (16) - TDM PW protection

     pathSdhSonetProtect (17) - SDH/SONET VC Path Protection

     aps (18) - SONET (APS) or SDH (MSP) switching protection

     ethPortProtect (19) - Ethernet port protection

     tdmPortProtect (20)- TDM port protection

     tdmPw (21) - TDM PW functionality, for supported options see
      the agnFunctionAttributes below.

     fileSystem (22) - File System support

     ssfp (23)       - Smart SFP support

     acl (32)        - access control list (security)

     lldp (40)       - Link Layer Discovery Protocol

     twamp (41)      - Two Way Active Measurement Protocol

     flow (42)       - flow

     vrrp (43)       - Virtual Router Redundancy Protocol
     
     portFlowMirroring (45) - Port and flow mirroring 
     
     ethPort        (46)    - Ethernet port capabilities
     
     dhcpL2Relay    (47)    - DHCP Layer 2 Relay
     
     nat            (48)    - Network Address Translator/Translation 
     
     cellular       (49)    - Cellular 
    "
     ::= { agnFunctionEntry 1 }

agnFunctionActivation   OBJECT-TYPE
    SYNTAX  INTEGER
    {
     disable   (2),
     enable    (3)
         }
    MAX-ACCESS  read-write
    STATUS current
    DESCRIPTION
    "This MIB object indicates the activation of the current function."
     ::= { agnFunctionEntry 2 }

agnFunctionAttributes    OBJECT-TYPE
    SYNTAX   OCTET STRING
    MAX-ACCESS  read-only
    STATUS current
    DESCRIPTION
    "This MIB object indicates for each supported function
    its set of attributes.

    For ETH OAM-CFM: (agnFunction enumeration 8)
    Bit 0 = '1' denotes that the device supports C+S classification.
    Bit 1 = '1' denotes that the device supports port level binding.
    Bit 2 = '0' denotes that the device supports queueing for OAM frames.
    Bits 3-7 - reserved  (for future usage of Phase 1 features)

    The following are supported starting from OAM-CFM Phase 2 and up:
    Bit 8  = '1' Dest NE level is supported
    Bit 9  = '1' Port level MEP is supported
    Bit 10 = '1' Dynamic Remote MEP allocation
    Bit 11 = '1' Dynamic Service allocation
    Bit 12 = '1' Use identical VLAN ID in different MD levels
    Bit 13 = '1' Single-ended loss measurement
    Bit 14 = '1' Two-way delay measurement
    Bit 15 = '1' 10msec CCM interval is supported
    Bit 16 = '1' Use identical VLAN ID in multiple MEPs, which are members
                 of the same MA (different priority) -- NON STANDARD

    The following are supported starting from OAM-CFM phase 3 and up:

    Bit 17. Entu -
        ENTU includes Hardware Based Features:
        CCM Interval value: 3.3 msec, and
        Forwarding-Method (E-LAN, E-Line)
        (There is no specific bit for these items)

    Bit 18. Direction (up, down)
    Bit 19. Lmm-Dmm interval
    Bit 20. LBM data-tlv
    Bit 21. DMM data-tlv
    Bit 22. Loss traffic-type
    Bit 23. Measurement Bins. (Round Trip Delay counters only)
    Bit 24. ETH-AIS - Fault Propagation
    Bit 25. ETH-AIS - Alarm Suppression
    Bit 26. MIP none and explicit
    Bit 27. MIP Defer, Default
    Bit 28. Cross Connect Status
    Bit 29. Variable Duration statistics interval (pmIntervalTimeDuration is supported)

    Bit 30  MIP Tx Flow
    Bit 31  MIP Rx Flow

    Bit 32  MIP and MHF manual configuration
    Bit 33  MHF Single VLAN
    Bit 34  MHF Fixed CoS
    Bit 35  MHF Fixed Queue
    Bit 36  MHF Classification Profile
    Bit 37  MHF CoS Profile
    Bit 38  MHF Queue Profile
    Bit 39  MD Protocol Standard selection

    Bit 40  MEP Single VLAN
    Bit 41  MEP Fixed CoS
    Bit 42  MEP Fixed Queue
    Bit 43  MEP Classification Profile
    Bit 44  MEP CoS Profile
    Bit 45  MEP Queue Profile
    Bit 46  MEP Tx Flow
    Bit 47  MEP Rx Flow

    Bit 48    The device supports both MIP configuration modes (manual and auto)
               If this Bit is set to 0 -> The device supports only one configuration
               mode (see Bit 32 that indicates the configuration mode)
               If this Bit is set to 1 -> The device supports both configuration modes
               (bit 32 will indicates which mode has been selected)

    Bit 49     Agent Supports all objects indicating min/max Delay and min/max Delay Variations.

    Bit 50 MD Name & MD Format ('1' = not supported)
    Bit 51 MD MIP Policy ('1' = not supported)
    Bit 52 MA Name & MA Format ('1' = not supported)
    Bit 53 LBM,LTM and Dest NE - Remote MEP ID ('1' = not supported)

    Bit 54 ethOamSvcDayTable is supported instead of ethOamSvcTotalTable
    Bit 55 = '1' 100 msec CCM interval is supported . (for ETX-36)
    Bit 56 = '1' MEP is supported only for network port. (for ETX-36)

    Bit 57  = '1', All one way (Forward) Perfromance Measurements
    (Delay, Delay Variation) are supported.

    Bit 58 = '1' Multiple flows (unidirectional Rx and Tx, bidirectional) per MEP are supported.
             (ethOamMepFlowsTable is supported)


    Bit 59 = '1' -  For MD Name Format, ONLY 'None' and 'String' are supported.
                  (MD Name is supported)
    Bit 60 = '1' -  For MA Name Format, ONLY 'UINT' (UnsignedInt16) and 'String' are supported.
                  (MA Name is supported)
    Bit 61 = '1' - SLM supported
    Bit 62 = '1' - Availability per MEF36 supported (configuration and statistics)
    Bit 63 = '1' - CFM Alarm type configuration is supported (legacy or soam)
    Bit 64 = '1' - Configurable Interface Status TLV usage
    Bit 65 = '1' - Configurable Dest-Ne description
    Bit 66 = '1' - One Way delay variation supported ( forward/backward, bin profiles, statistics)
    Bit 67 = '1' - LBM multicast address supported
    Bit 68 = '1' - CCM statistics per MEP supported (Local/Remote, running, current and history intervals)
    Bit 69 = '1' - For MA Name Format, ONLY 'UINT' (UnsignedInt16), 'String' and 'ICC' are supported.
                   (MA Name is supported)
    Bit 70 = '1' - ETH-CSF indications for Remote MEP is supported.
    Bit 71 = '1' - Latching Loopback per MEF46 is supported.

    For File Transfer:   (agnFunction enumeration 9) (refer also to fileTransCmd)
    In each bit field, the value '1' denotes that the device supports the operation/behavior.
    Bit 0  - Configuration file is in text format -- moved to agnFunction=cli(12)
    Bit 1  - SW Download
    Bit 2  - Configuration Download
    Bit 3  - Configuration Upload
    Bit 4  - Additional SW Download
    Bit 5  - Statistics Upload
    Bit 6  - User File Download
    Bit 7  - User File Upload
    Bit 8  - SW Download and Reset
    Bit 9  - SW Upload
    Bit 10 - SW Download to Backup (therefore also Swap Main and Backup)
    Bit 11 - Boot Download
    Bit 12 - Boot Upload
    Bit 13 - SW Upload from Backup
    Bit 14 - License Download
    Bit 15 - Configuration Download to Default
    Bit 16 - Reset operation
    Bit 17 - Configuration Download to Active Configuration
    Bit 18 - Additional SW Download and Reset
    Bit 19 - The policy for Software Download is as follows:
             After download the NMS should send Reset to the device.
    Bit 20 - The policy for Software Download is as follows:
             After download the device performs a Reset by itself.
    Bit 21 - The policy for Configuration Download is as follows:
             After download the NMS should send Reboot command to the device.
    Bit 22 - The policy for Configuration Download is as follows:
             After download the device performs a Reset by itself.
    Bit 23 - The policy for Software Download is as follows:
             Like in Bit 20, except that the command sent in fileTransCmd is swDwnLoadAndReset(8).
    Bit 24 - The policy for Configuration Download is as follows:
             After Configuration download the device activates the configuration file and sends
             sanityCheckTrap with attached variable sysSSanityCheckStatus = ok(4) or warning(3).
    Bit 25 - The policy for Configuration Download is as follows:
             Like in Bit 22, except that the trap sent is
             sanityTrap with attached variable agnSSanityCheckStatus = ok(4) or warning(3)
    Bit 26 - Total Timeout (tftpTotalTimeOut) -- Not Applicable
    Bit 27 - Retry Timeout (tftpRetryTimeOut) -- Not Applicable
    Bit 28 - It is forbidden to send the device retries for Reset (after Download) operation.
    Bit 29 - Upload Factory Default Configuration file        -- Not Applicable
    Bit 30 - Download/Upload User Default Configuration file  -- Not Applicable
    Bit 31 - Download/Upload Startup Configuration file       -- Not Applicable
    Bit 32 - SFTP is supported.                               -- Not Applicable. Supported via agnCommonCapabilities
    Bit 33 - The policy for Configuration Download is as follows:
             Like in Bit 24, except no sanity trap is sent.

        For CLI:  (agnFunction enumeration 12)
    Bit 0  - Configuration file is in text format (replacing bit 0 of File Transfer)

        For CSM:  (agnFunction enumeration 13)
    Bit 0 - '1' Domain is supported as 'clock source'
    Bit 1 - '1' Station port exists in system
    Bit 2 - '1' RX port is supported as 'clock source'
    Bit 3 - '1' 'adaptive' is supported as 'clock source'
    Bit 4 - '1' '1588' is supported as 'clock source'
    Bit 5 - '1' Station-out port exists in system
    Bit 6 - '1' GPS is supported as 'clock source'
    Bit 7 - '1' E1/T1 is supported as 'clock source'    

        For ERP:  (agnFunction enumeration 14)
    Bit 0 - '1': ERP supported (STD G.8032). '0': ERP not supported
    Bit 1 - '0': Sub Ring supported.'1':Sub Ring not supported
    Bit 2 - '1': Internal Flows supported. '0': Internal Flows not supported
    Bit 3 - '1': multiple rings per physical port supported. '0': Multiple rings not supported
    Bit 4 - '1': Passthrough VLANs supported. '0':Passthrough VLANs not supported 
    Bit 5 - '1': color mapping also by P-bit. '0': Color mapping by P-bit not supported
    Bit 6 - '1': Passthrough VLAN IDs supported. '0':Passthrough VLAN IDs not supported 
    Bit 7 - '1': ERP STD G.8032v2 supported. '0': ERP STD G.8032v2 not supported

        For TDM PW   (agnFunction enumeration 21)
    Bit 0 - '1' CESoPSN TDM traffic supported
    Bit 1 - '1' SAToP TDM traffic supported
    Bit 2 - '1' TDM PW Connectivity current and Interval statistics is supported
            (pwPerfConnCurrentTable, pwPerfConnIntervalTable)


    For Smart SFP bit (agnFunction enumeration 23):
    Bit 0  N/A
    Bit 1  N/A
    Bit 2  This device supports Smart SFP type: miRIC-E1
    Bit 3  This device supports Smart SFP type: miRIC-T1
    Bit 4  This device supports Smart SFP type: miRIC-E3
    Bit 5  This device supports Smart SFP type: miRIC-T3
    Bit 6  This device supports Smart SFP type: miRICi-E1
    Bit 7  This device supports Smart SFP type: miRICi-T1
    Bit 8  This device supports Smart SFP type: miRICi-E3
    Bit 9  This device supports Smart SFP type: miRICi-T3
    Bit 10 This device supports Smart SFP type: miRICi-155
    Bit 11 This device supports Smart SFP type: miRICi-622
    Bit 12  This device supports Smart SFP type: miTOP-E1
    Bit 13  This device supports Smart SFP type: miTOP-E3
    Bit 14  This device supports Smart SFP type: miTOP-T1
    Bit 15  This device supports Smart SFP type: miTOP-T3
    Bit 16  This device supports Smart SFP type: sfp-VDSL-2W

    
For PTP (agnFunction enumeration 24)
    Bit 0 - '0' Slave is not supported. '1' Slave is supported.
    Bit 1 - '0' Master is not supported. '1' Master is supported.


For Copy File ( agnFunction enumeration 25)
    Bit 0 - Indicates if download and upload user file is supported.
    Bit 1 - Indicates if download a running configuration file.
    Bit 2 - Indicates if device performes reboot after install SW (set-active).
    Bit 3 - Indicates if device supports Rollback SW.
    Bit 4 - Indicates if device supports log files.
    Bit 5 - Indicates if device supports download statistics.
    Bit 6 - Indicates if device supports FileType value = otherType(2)
    Bit 7 - '1' Indicates that the device does not support rowInfoTableId


For Router  (agnFunction enumeration 26)
    Bit 0 - Indicates if device supports multiple instances.
    Bit 1 - '0': HW Router exists in device. '1': SW Router exists in device.
    Bit 2 - '0': DHCP Relay is not supported. '1': DHCP relay is supported.
    Bit 3 - '0': IP Forwarding (RtrIfCfgIpForwarding) is not supported. 
            '1': IP Forwarding is supported
    

For Fault Management (agnFunction enumeration 28):
    Bit 0  Indicates activeAlarmTable is supported
    Bit 1  Indicates alarmEventBriefLogTable (Summary Table) is supported
    Bit 2  Indicates alarmEventLogTable  (History Log) is supported
    Bit 3  Indicates alarmEventConfigTable and maskReportTable  (Severity and Masking Configuration) is supported
    Bit 4  Indicates alarmEventConfiguredTable is supported
    Bit 5  Indicates Alarm Led is Supported
    Bit 6  Indicates Alarm Output Relay is supported (alarmRelayOutputTable)
    Bit 7  Indicates Alarm Input Relay is supported (alarmRelayInputTable)
    Bit 8  Indicates Soaking configuration is supported (defectSoakTable)
    Bit 9  Indicates Popup alarm indications are supported.
    Bit 10 Indicates device has Slots
    Bit 11 Indicates Input Relay exists on chassis
    Bit 12 Indicates Input Relay(s) exist on slot(s)
    Bit 13 Indicates Output Relay exists on chassis
    Bit 14 Indicates Output Relay(s) exist on slot (s)
    Bit 15 Indicates Alarm Masking Statistics is supported
             (AlarmEventLogStatsType = activeAlarmsMasked(4))


For Bridge (agnFunction enumeration 31):
    Bit 0  Indicates support with Bridge Topology.
    Bit 1  '0':Vlan Mode=Aware only.'1':Vlan Mode=Aware and Unaware.
    Bit 2  '0': Forwarding Mode=Filter only.'1': Forwarding Mode=Filter and Transparent.
    Bit 3  '0': Bridge Port can be Bound to SVI. '1': Bridge Port cannot be Bound to SVI.
    Bit 4  '0': Bridge Port cannot be Bound to Phy Port. '1': Bridge Port can be Bound to Phy Port.
    Bit 5  '0': MAC Table is not displayed in Bridge GUI. '1': MAC Table displayed in Bridge GUI.
    Bit 6  '0': MAC Table displayed per Vlans. '1': MAC TAble not displayed per Vlan (unsorted).
    Bit 7  '0': Table radBridgePortVlanMemberTable not supported. '1': Table radBridgePortVlanMemberTable supported.
    Bit 8  '0': search MAC per MAC Criteria is not supported. '1': search MAC per MAC Criteria is supported.
    Bit 9  '0': search MAC per Vlan Criteria is not supported. '1': search MAC per Vlan Criteria is supported.
    Bit 10 '0': search MAC per Bridge Port Criteriais not supported. '1': search MAC per Bridge Port Criteria is supported.
    Bit 11 '0': RSTP is not supported '1': RSTP is supported.
    Bit 12 '0': MSTP is not supported '1': MSTP is supported.
    Bit 13 '0': MLDv2 snooping is not supported '1': MLDv2 snooping is supported.

    
For acl ( agnFunction enumeration 32):
    Bit 0   IPv4 ACL-type is supported,
    Bit 1   IPv6 ACL-type is supported,
    Bit 2   Management Entity bound to ACL is supported,
    Bit 3   Router Interface bound to ACL is supported,
    Bit 4   Inbound Direction bound to ACL is supported,
    Bit 5   Outbound Direction bound to ACL is supported,
    Bit 6   IP Protocol based ACL match is supported,
    Bit 7   UDP Protocol based ACL match is supported,
    Bit 8   TCP Protocol based ACL match is supported,
    Bit 9   ICMP Protocol based ACL match is supported.
    Bit 10  Port Range Support.
           '0' - only noOperator(1) is supported for xxxPortOp fields;
                 xxxPortRange field value must be equal to xxxPort field.
           '1' - only 'range (6)' is supported for xxxPortOp field; xxxportRange field must be >= xxxPort.


For Performance Management (agnFunction enumeration 36):
    Bit 0  '0':PM v3 Protocol not supported.'1':PM v3 Protocol supported.
    Bit 1  '0':PM File Schema not supported.'1':PM V3 File Schema supported.

    
For Y.1564 testing (agnFunction enumeration 37):
    Bit 0  - '1': generator supported.
    Bit 1  - '1': responder supported.
    Bit 2  - '1': unidirectional mode supported.
    Bit 3  - '1': bidirectional mode supported.
    Bit 4  - '1': color-aware supported.
    Bit 5  - '1': traffic policy supported.
    Bit 6  - '1': MAC swap functionality supported.
    Bit 7  - '1': EMIX supported.
    Bit 8  - '1': CBS/EBS tests supported.
    Bit 9  - '1': Internal MEP supported.
    Bit 10 - '1': E-LAN/E-Tree supported.
    Bit 11 - '1': E-LAN/E-Tree supported for internal MEP.
    Bit 12 - '1': configurable block or not block of user traffic. '0': user traffic is always blocked.
    Bit 13 - '1': jumbo frames supported.
    Bit 14 - '1': multiple SA MAC for LAG supported.
    Bit 15 - '1': automatic creation of CFM services and destNEs supported.
  
  
For Policer (agnFunction enumeration 39)
    Bit 0 - '0' Color Aware supported. '1' Color Aware not supported.
    Bit 1 - '0' Coupling Flag supported. '1' Coupling Flag is not supported.
    Bit 2 - '1' Envelope policer supported.

    
For LLDP (agnFunction enumeration 40)
    Bit 0 - '1' denotes that the device supports LLDP.

    
For TWAMP (agnFunction enumeration 41)
    Bit 0 - '1' denotes that the device supports TWAMP light Responder.
    Bit 1 - '1' denotes that the device supports TWAMP light Generator.
    Bit 2 - '1' denotes that the device supports TWAMP (full) Responder.
    Bit 3 - '1' denotes that the device supports TWAMP (full) Generator.
    Bit 4 - '1' denotes that the device supports icmpEcho Generator. 
    Bit 5 - '1' denotes that the device supports udpEcho Generator. 

    
For Flow (agnFunction enumeration 42)
    Bit 0 - '1' enhanced CoS mapping is supported (untagged, non-ip).
    Bit 1 - '1' multi-CoS flow counters are supported.
    Bit 2 - '0' denotes that the CIR & EIR shall always be set to the closest lower granular value - not configurable.
            '1' denotes that the CIR & EIR can be set to the closest lower or higher granular value - configurable.
    Bit 3 - '1' denotes support for flow type 'port classifier'.

    
For vrrp (agnFunction enumeration 43)
    Bit 0 - '1': VRRP version 2 is supported
    Bit 1 - '1': VRRP version 3 is supported.

    
For L3 SAT  (agnFunction enumeration 44)
    Bit 0 - '1': generator supported.
    Bit 1 - '1': responder supported.

    
For Port & Flow Mirroring  (agnFunction enumeration 45)
    Bit 0 - '1': VLAN list mirroring is supported.
    Bit 1 - '1': flow mirroring is supported.
    
    
For Ethernet Port  (agnFunction enumeration 46)
    Bit 0 - '1': Silent Start is supported.
    Bit 1 - '1': Fat Pipe is supported.
    Bit 2 - '1': Maximum two queue blocks are supported. 

    
For DHCP Layer 2 Relay  (agnFunction enumeration 47)
    Bit 0 - '1': DHCP Layer 2 Relay Snooping is supported.
    Bit 1 - '1': DHCP Layer 2 Relay option 82 is supported.
    Bit 2 - '1': Circuit ID for option 82 is supported.
    Bit 3 - '1': Remote ID for option 82 is supported.

    
For NAT  (agnFunction enumeration 48)
    Bit 0 - '1': Static NAT is supported.
    Bit 1 - '1': 'Hole Punching' is supported.
    Bit 2 - '1': NAPT/PAT/Overload is supported.
    Bit 3 - '1': Router Interface as inside global IP address is supported.

    
For Cellular  (agnFunction enumeration 49)
    Bit 0 - '1': Cellular Interface is supported.
"
     ::= { agnFunctionEntry 3 }


agnFunctionVersion     OBJECT-TYPE
    SYNTAX             Unsigned32
    MAX-ACCESS  read-only
    STATUS current
    DESCRIPTION
       "This variable is applicable whenever a function is implemented
        via a software package that resides in the NE.
        The value saved in this variable contains the package version as follows:
        The 4 MS bits represent the major version number
        The 4 next bits represent the minor version number
        The remaining 16 LS bits will be used for different 'flavors in a version.
        Example:
        0x02010003 represents package version 02.01 with feature subset #3.
       "
    ::= { agnFunctionEntry 4 }

agnManagerConfigPorts OBJECT-TYPE
    SYNTAX  Integer32 
    MAX-ACCESS  read-write
    STATUS  current
     DESCRIPTION
     "This variable defines from which port/s this manager can manage the device.
	  The value is a sum of 2**n, where n is a bit assigned to a certain port.
	  For RIC-E1 and ETX 102 the value will be according to the ports 
	  combination:
      Network = bit 0
      User= bit 1
  	  For Example: All = 3."
     ::= {agnt 46 }

agnEgressRateRange OBJECT-TYPE
    SYNTAX  INTEGER
    	{
	 unlimited   (1),
	 range1   (2),
	 range2   (3),
	 range3   (4),
	 range4   (5),
	 range5   (6),
     range6   (7),
     range7   (8)  
     	 	 }
    MAX-ACCESS  read-write
    STATUS  current
     DESCRIPTION
     "This variable defines the valid ranges of egress rate. 
      For example, for ETX 102:
	  range 1 (2)= 128KBPS - 8MBPS,
	  range 2 (3)= 256KBPS - 16MBPS,
	  range 3 (4)= 512KBPS - 32MBPS,
	  range 4 (5)= 1MBPS - 64MBPS,
	  range 5 (6)= 1.5MBPS - 80MBPS."
     ::= {agnt 47 }

agnNoOfCurrentConns OBJECT-TYPE
	SYNTAX  Integer32 
	MAX-ACCESS  read-only
	STATUS  current
	DESCRIPTION
	"This variable indicates the number of connections
	 currently configured for the agent."
	::= { agnt 48 }

agnIngressRateRange OBJECT-TYPE
    SYNTAX  INTEGER
    	{
	 unlimited   (1),
	 range1   (2),
	 range2   (3),
	 range3   (4),
	 range4   (5),
	 range5   (6),
     range6   (7),
     range7   (8)  
	 	 }
    MAX-ACCESS  read-write
    STATUS  current
     DESCRIPTION
     "This variable defines the valid ranges of ingress rate. 
      For example, for ETX 102:
	  range 1 (2)= 128KBPS - 8MBPS,
	  range 2 (3)= 256KBPS - 16MBPS,
	  range 3 (4)= 512KBPS - 32MBPS,
	  range 4 (5)= 1MBPS - 64MBPS,
	  range 5 (6)= 1.5MBPS - 80MBPS."
     ::= {agnt 49 }


alarmForwardingTable OBJECT-TYPE
    SYNTAX  SEQUENCE OF AlarmForwardingEntry
    MAX-ACCESS  not-accessible
    STATUS  current
    DESCRIPTION
    "The Alarm Forwarding Mechanism will be operated
     for this table entries."
   ::= { agnt 50 }

alarmForwardingEntry OBJECT-TYPE
    SYNTAX  AlarmForwardingEntry
    MAX-ACCESS  not-accessible
    STATUS  current
    DESCRIPTION
    "Each entry in this table is a pair of ports that
    the Alarm Forwarding Mechanism is determined for."
    INDEX   { alarmForwardingFailPort, alarmForwardingToPort }
    ::= { alarmForwardingTable 1 }

AlarmForwardingEntry ::= SEQUENCE {
    alarmForwardingFailPort          Integer32,
    alarmForwardingToPort          Integer32,
    alarmForwardingRowStatus          RowStatus,
    alarmForwardingRecoveryTime          Integer32,
     alarmForwardingGroupConditions	Integer32,
    alarmForwardingCause          AlarmForwardingCause,
     alarmForwardingRecoveryMode 	INTEGER,	  
     alarmForwardingRecoveryCommand 	INTEGER,
    alarmForwardingDelay 		Unsigned32,
    alarmForwardingDirection 		INTEGER,
    alarmForwardingAction          BITS,
    alarmForwardingActiveCause          AlarmForwardingCause,
    alarmForwardingDescr          SnmpAdminString,
    alarmForwardingPriorityDecrement          Unsigned32 
 }

alarmForwardingFailPort OBJECT-TYPE
    SYNTAX  Integer32 (0..2147483647)
    MAX-ACCESS  not-accessible
    STATUS  current
    DESCRIPTION
    "An Index of the port on which a fail occurs."
    ::= { alarmForwardingEntry 1}

alarmForwardingToPort OBJECT-TYPE
    SYNTAX  Integer32 (0..2147483647)
    MAX-ACCESS  not-accessible
    STATUS  current
    DESCRIPTION
    "An Index of the port that will be affected
    upon the failure of the alarmForwardingFailPort."
    ::= { alarmForwardingEntry 2}

alarmForwardingRowStatus OBJECT-TYPE
    SYNTAX  RowStatus
    MAX-ACCESS  read-create
    STATUS  current
    DESCRIPTION
    "Creation/ Deletion of rows in the table."
    ::= { alarmForwardingEntry 3}

alarmForwardingRecoveryTime OBJECT-TYPE
     SYNTAX  Integer32
     MAX-ACCESS  read-create
     STATUS  current
     DESCRIPTION
     "This parameter defines the maximum time (sec)
      the affected port will hold the down state."
      ::= { alarmForwardingEntry 4 }

alarmForwardingGroupConditions OBJECT-TYPE
	 SYNTAX  Integer32
     MAX-ACCESS  read-create
     STATUS  current
     DESCRIPTION
	 "This parameter is applicable when there is a group of interfaces 
	 in which a fault may occur, and one interface to which alarm is propagated (forwarded).
	 0 = All - Forwarding will take place only when all interfaces of the 
     same group are faulty.
	 1 = Single - Forwarding will take place when at least one (single)
     interface of the same group (any of them) is faulty.
	 n - forwarding will take place only when n (n < all) 
	 interfaces of the same group fail."
	 ::= { alarmForwardingEntry 5 }

alarmForwardingCause  OBJECT-TYPE
     SYNTAX   AlarmForwardingCause
     MAX-ACCESS  read-create
     STATUS  current
     DESCRIPTION
     "Bit map representing the cause upon which alarm forwarding will take place."
     DEFVAL { {} }
     ::= { alarmForwardingEntry 6 }

alarmForwardingRecoveryMode OBJECT-TYPE
     SYNTAX  INTEGER 
     {
  	    manual     (1),
	    automatic  (2)
     } 
     MAX-ACCESS  read-create
     STATUS  current
     DESCRIPTION
     "This parameter determines the Recovery Mode. 
     manual - The user should stop the alarm forwarding 
     by using the alarmForwardingRecoveryCommand.
     automatic - Alarm forwarding will be automatically 
     stopped upon alarmForwardingFailPort recovery."
     ::= { alarmForwardingEntry 7 }

alarmForwardingRecoveryCommand OBJECT-TYPE
     SYNTAX  INTEGER 
     {
 	   off   (2),
	   on    (3)
     } 
     MAX-ACCESS  read-create
     STATUS  current
     DESCRIPTION
     "This parameter is a command. It is applicable when 
     alarmForwardingRecoveryMode = manual.
     on - Will stop alarm forwarding. 
     After setting to 'On', the agent will set this parameter back to 'Off'."
     ::= { alarmForwardingEntry 8 }

alarmForwardingDelay OBJECT-TYPE
     SYNTAX  Unsigned32 
     MAX-ACCESS  read-create
     STATUS  current
     DESCRIPTION
     "This parameter determines the period of time (in seconds) the 
     alarm of the alarmForwardingFailPort should exist before 
     starting alarm forwarding."
     ::= { alarmForwardingEntry 9 }

alarmForwardingDirection OBJECT-TYPE
     SYNTAX  INTEGER 
     {
  	    unidirectional (1),
	    bidirectional  (2)
     } 
     MAX-ACCESS  read-create
     STATUS  current
     DESCRIPTION
     "This parameter determines the Direction of the Alarm Forwarding. 
     unidirectional - alarmForwardingFailPort affects the
                      alarmForwardingToPort.
     bidirectional - alarmForwardingFailPort affects the
                     alarmForwardingToPort AND vice-versa.
                     For such cases, this value will be selected, instead of 
                     entering an additional unidirectional entry
                     in the table, where the indexes are swapped."
     ::= { alarmForwardingEntry 10 }

alarmForwardingAction  OBJECT-TYPE
     SYNTAX   BITS
     {
       noAction              (0),
       interfaceDeactivation (1),  -- Deactivate the interface
       oamSignaling          (2),  -- Send OAM EFM signaling
       interfaceStatusTLV    (3),  -- Send OAM CFM interface status TLV
       oamCfmAis             (4),  -- Send OAM CFM AIS
       dhcpRestart           (5),  -- Renew DHCP lease
       vrrpPriorityDecrement (6),  -- Decrement VRRP priority
       shaperSwap            (7),  -- Apply shaper profile set in alarmForwardingActionElement
       policerSwap           (8),  -- Apply policer profile set in alarmForwardingActionElement
       oamCfmCsfClos         (9),  -- Send OAM CFM CSF (C-LOS state)
       reset                 (10), -- Reset an element (e.g. card)
       los                   (11), -- Activate LOS hardware signal on PHY
       txDisableSignal       (12), -- Activate Tx-disable hardware signal on PHY
       txFaultSignal         (13)  -- Activate Tx-fault hardware signal on PHY
     }
     MAX-ACCESS  read-create
     STATUS  current
     DESCRIPTION
         "Bit map representing actions to be taken on the entity set in alarmForwardingToPort,
          when alarm is propagated from the entity set in alarmForwardingFromPort.
          Bit 0 (noAction) has a special meaning: 
          - 0: The device should take all the actions whose bit are set to 1. 
            At least one bit of this object must be set to 1 if bit 0 is 0.
          - 1: The device should take no action, regardless of  the value of other
            bits of this object."
     ::= { alarmForwardingEntry 11 }

alarmForwardingActiveCause OBJECT-TYPE
     SYNTAX   AlarmForwardingCause
     MAX-ACCESS  read-only
     STATUS  current
     DESCRIPTION
     "Bit map representing the cause for the current active forwarding entry.
      When this forwarding entry is not active, the value will be: 0."
    ::= { alarmForwardingEntry 12 }

alarmForwardingDescr    OBJECT-TYPE
   SYNTAX       SnmpAdminString (SIZE (1..64))
   MAX-ACCESS   read-create
   STATUS       current
   DESCRIPTION
       "Description of the current forwarding entry.
        Default description will be: ' '
        "
    ::= { alarmForwardingEntry 13 }

alarmForwardingPriorityDecrement OBJECT-TYPE
    SYNTAX Unsigned32 (1..253)
    MAX-ACCESS read-create
    STATUS current
    DESCRIPTION
    "The amount by which to decrement the priority of the
     VRRP group the fault is propagated to.
     If this object is higher than the VRRP group priority,
     the priority will be decremented to 1."
    DEFVAL { 253 }
    ::= { alarmForwardingEntry 14 }


agnSwVersionSwapCmd OBJECT-TYPE
	SYNTAX  INTEGER
	{
	 off  (2),
	 mainAndBackup  (3)
	 	 }
	MAX-ACCESS  read-write
	STATUS current
	DESCRIPTION
	"SW switch command.
	 mainAndBackup (3) = Swap between Main SW and the backup one.
	 Agent will perform the required command and change automatically 
	 the value of this object to off(2)."
     ::= { agnt 51 }

-- agnClockSource OBJECT IDENTIFIER  ::=  { agnt 52 }

agnMaxNoOfConns OBJECT-TYPE
	SYNTAX  Integer32 
	MAX-ACCESS  read-only
	STATUS  current
	DESCRIPTION
	"This variable indicates the maximum number of connections
	 that can be configured for the agent."
	::= { agnt 53 }
 
-- lag   OBJECT IDENTIFIER  ::=  { agnt 54  }
-- see Lag.txt file


-- gfp   OBJECT IDENTIFIER  ::=  { agnt 55  }
-- see Gfp.txt file


--Group Table

agnGroupTable OBJECT-TYPE
    SYNTAX  SEQUENCE OF AgnGroupEntry
    MAX-ACCESS  not-accessible
    STATUS  current
    DESCRIPTION
    "A table that enables associating components to Group/s
     (or removing components of a group).
     The Group Idx can then be used in other tables (e.g alarmForwardingTable)."
    ::= {agnt 56}

agnGroupEntry OBJECT-TYPE
    SYNTAX  AgnGroupEntry
    MAX-ACCESS  not-accessible
    STATUS  current
    DESCRIPTION
    "An entry in the agnGroupTable."
     INDEX  { agnGroupCnfgIdx, agnGroupIdx, agnGroupComponentIdx }
    ::= { agnGroupTable 1 }

AgnGroupEntry ::= SEQUENCE {
    agnGroupCnfgIdx             Unsigned32,
    agnGroupIdx                 Unsigned32,
    agnGroupComponentIdx        Unsigned32,
    agnGroupRowStatus           RowStatus,
    agnGroupName                SnmpAdminString,
    agnGroupParam               Unsigned32,
    agnGroupStatus              Unsigned32,
    agnGroupStatus2             Unsigned32,
    agnGroupComponentString     SnmpAdminString,
    agnGroupComponentTDomain    TDomain,
    agnGroupComponentTAddress   TAddress 
 }

agnGroupCnfgIdx OBJECT-TYPE
    SYNTAX      Unsigned32 (1..255)
    MAX-ACCESS  not-accessible
    STATUS      current
    DESCRIPTION
     "This object indicates the Idx of the Cnfg(1..255) being
      accessed ; Idx of 255 relates to the TmpCnfg.
      For devices supporting more than one group type ,the value will indicate:
      1  Fault Propagation group.
      2  For Policer Aggregate group.
      3  For Voice Quality Monitoring (VQMON) or BW Control Bundles Group (Vmux Family).
      4  For Trap Synchronization."
    ::= { agnGroupEntry 1 }

agnGroupIdx OBJECT-TYPE
    SYNTAX      Unsigned32
    MAX-ACCESS  not-accessible
    STATUS      current
    DESCRIPTION
     "This object indicates a unique Group Index."
    ::= { agnGroupEntry 2 }

agnGroupComponentIdx  OBJECT-TYPE
    SYNTAX       Unsigned32
    MAX-ACCESS   not-accessible
    STATUS       current
    DESCRIPTION
    "This object indicates a unique Component Index that belongs to the
     Group defined by agnGroupIdx.

     When agnGroupCnfgIdx=2 (Policer Aggregate), when creating a new
     group the index will be 0xFFFF.
     Upon assigning a policer aggregate to a flow, a new entry is created
     with this item contains the flow ID.

     When agnGroupCnfgIdx=4 (Trap Synchronization),
     this object indicates a running Index of the trap destination.
     This running index MAY hold the following values:
     - For SNMPv1: index = mngID
     - For SNMPv3: index = running index of the snmpTargetAddrTAddress."
    ::= { agnGroupEntry 3 }

agnGroupRowStatus    OBJECT-TYPE
    SYNTAX      RowStatus
    MAX-ACCESS  read-create
    STATUS      current
    DESCRIPTION
    "This object enables user to create/delete entries of this table.
     destroy - If a Group is used in another table, Agent may not allow
     destroying the entry/ies that belong to this Group Index."
    ::= { agnGroupEntry 4 }

agnGroupName    OBJECT-TYPE
    SYNTAX      SnmpAdminString
    MAX-ACCESS  read-create
    STATUS      current
    DESCRIPTION
    "The name of the group. Device should check that this name is unique."
    ::= { agnGroupEntry 5 }

agnGroupParam   OBJECT-TYPE
    SYNTAX      Unsigned32
    MAX-ACCESS  read-create
    STATUS      current
    DESCRIPTION
    "When agnGroupCnfgIdx=2 (Policer Aggregate),this attribute contains the Policer Profile
     that is related to this Policer Aggregate group (bwProfileIndex from MEF-R.bwProfileTable) .
     O means that no policer profile is attached.
     When agnGroupCnfgIdx=3 (VQMON in Vmux family), this attribute contains the
     Voice Quality Monitoring Mean Opinion Score (MOS) Threshold. If the voice quality
     is reduced to a value below this threshold an alarm will be generated.
     Valid values in SNMP: 0 - 45. Actual values are 0 - 4.5.
     0 means that no alarm will be generated."
     ::= { agnGroupEntry 6 }

agnGroupStatus   OBJECT-TYPE
    SYNTAX      Unsigned32
    MAX-ACCESS  read-only
    STATUS      current
    DESCRIPTION
    "For Vmux family: When agnGroupCnfgIdx=3 (Vmux Bundles Group), this attribute contains the
     MAX Bandwidth (since device last reset) that was used in the Bundles Group.
     This attribute is used only for ETH bundles (Exit Port = NET or NET/USER). "
    ::= { agnGroupEntry 7 }

agnGroupStatus2   OBJECT-TYPE
    SYNTAX      Unsigned32
    MAX-ACCESS  read-only
    STATUS      current
    DESCRIPTION
    "For Vmux family: When agnGroupCnfgIdx=3 (Vmux Bundles Group), this attribute contains the
     Average Bandwidth (since device last reset) that was used in the Bundles Group.
     This attribute is used only for ETH bundles (Exit Port = NET or NET/USER). "
    ::= { agnGroupEntry 8 }

agnGroupComponentString   OBJECT-TYPE
    SYNTAX      SnmpAdminString
    MAX-ACCESS  read-create
    STATUS      current
    DESCRIPTION
    "This objects indicate a Component string.

     When agnGroupCnfgIdx=4 (Trap Synchronization),
     this object indicates the Name of the trap destination, where:
     - For SNMPv3: Name = snmpTargetAddrName (from SNMP-TARGET-MIB, RFC-3413)."
    ::= { agnGroupEntry 9 }

agnGroupComponentTDomain OBJECT-TYPE
    SYNTAX      TDomain
    MAX-ACCESS  read-create
    STATUS      current
    DESCRIPTION
    "This object indicates the type of Transport Service
     contained in agnGroupComponentTAddress."
    ::= { agnGroupEntry 10 }

agnGroupComponentTAddress OBJECT-TYPE
    SYNTAX      TAddress
    MAX-ACCESS  read-create
    STATUS      current
    DESCRIPTION
    "This object indicates the Component's Transport Service Address.
     The format of this address depends on agnGroupComponentTDomain value."
    ::= { agnGroupEntry 11 }


agnStatNoOfUploadedIntervals OBJECT-TYPE
    SYNTAX      Integer32
    MAX-ACCESS  read-only
    STATUS      current
    DESCRIPTION
    "This parameter indicates the Number of Intervals that were
     successfully collected and uploaded in the last statistics collection session."
       ::= { agnt 57 }

agnSyslog    OBJECT IDENTIFIER  ::=  { agnt 58 }

agnSyslogDeviceUdpPort OBJECT-TYPE
    SYNTAX      Unsigned32
    MAX-ACCESS  read-write
    STATUS      current
    DESCRIPTION
    "The UDP Port of the device, from which Syslog messages are sent.
     Default=514."
    ::= { agnSyslog 1 }

agnSyslogFacility OBJECT-TYPE
    SYNTAX      INTEGER
            {
-- (0)..(15) are reserved for Standard values + (16) is reserved for Local 0.
              local1          (17),
              local2          (18),
              local3          (19),
              local4          (20),
              local5          (21),
              local6          (22),
              local7          (23)
-- (99) is reserved for  'noMap' - indicating that the appropriate facility
--      will be provided by the application
            }
    MAX-ACCESS  read-write
    STATUS      current
    DESCRIPTION
    "A user defined SW module, task or function, from which Syslog messages are sent
     to the remote Server."
    ::= { agnSyslog 2 }

agnSyslogSeverityLevel OBJECT-TYPE
    SYNTAX      Integer32
    MAX-ACCESS  read-write
    STATUS      current
    DESCRIPTION
    "Device will send events equal or exceeding this severity level (configured by user).
         emergency  (0),  Emergency messages
         alert (1),              Critical alarms
         critical (2),     Major alarms
         error  (3),            Minor alarms
         warning (4),        Events
         notice (5),          Cleared alarms
         informational (6),  Informational messages
         debug (7)               Debug messages
    "
    DEFVAL {6}
    ::= { agnSyslog 3 }

agnSyslogCmd OBJECT-TYPE
    SYNTAX      INTEGER
        {
            off         (2),
            clearStats  (3)  -- clear statistics counters
        }
    MAX-ACCESS  read-write
    STATUS      current
    DESCRIPTION
        "This variable represents Syslog possible commands.
         After the Agent accepts a command, it will automatically change
         the value to off(2)."
    ::= { agnSyslog 4 }

agnNetworkInterfaceType OBJECT-TYPE
	SYNTAX  INTEGER
	{
	 notApplicable (1),
	 t1  (2),
	 t3  (3)
    }
	MAX-ACCESS  read-write
	STATUS current
	DESCRIPTION
	"This MIB object indicates the network interface type to be used
	 by the device.
	 It is used for devices that use only one network port type."
	::= { agnt 59 }

agnTrapDelay OBJECT-TYPE
    SYNTAX  Unsigned32
    MAX-ACCESS  read-write
    STATUS current
    DESCRIPTION
    "This variable enables the user to set a delay (in seconds) before a trap is sent.
     This delay will be used only for traps that need to be sent during device initialization.
     It is needed because the device connected to our device starts transmitting traps later.
     The delay starts from the end of the Boot process. The device will keep the init traps
     in the correct order, and cancel those which clear former ones in the list.
     After this init delay, traps will be sent without a delay."
        ::= { agnt 60 }


trapManagement  OBJECT IDENTIFIER ::= { agnt 61 }

trapMngVars     OBJECT IDENTIFIER ::= { trapManagement 1 }

trapState   OBJECT-TYPE
    SYNTAX  INTEGER
    {
        start   (2),
        end     (3)
    }
    MAX-ACCESS  accessible-for-notify
    STATUS     current
    DESCRIPTION
        "State of current trap (sent within a trap)."
    ::= { trapMngVars 1 }

trapSeqId   OBJECT-TYPE
    SYNTAX     Unsigned32
    MAX-ACCESS accessible-for-notify
    STATUS     current
    DESCRIPTION
        "Sequence ID of current trap (sent within a trap)."
    ::= { trapMngVars 2 }

alarmSync       OBJECT IDENTIFIER ::= { trapManagement 2 }

alarmSyncEvents	OBJECT IDENTIFIER ::= { alarmSync 0 }

hardSyncTrap  NOTIFICATION-TYPE
	OBJECTS       { trapState }
	STATUS		current
	DESCRIPTION     
		"This trap is sent whenever Hard Synchronization process starts or ends
		 (Hard Synchronization retrieves current status of Agent)."
     ::= { alarmSyncEvents 1 }

alarmSyncTable  OBJECT-TYPE
    SYNTAX      SEQUENCE OF AlarmSyncEntry
    MAX-ACCESS  not-accessible
    STATUS      current
    DESCRIPTION
        "This table includes Alarm Synchronization information
         for each Logical Group of managers."
    ::= { alarmSync 1 }

alarmSyncEntry  OBJECT-TYPE
    SYNTAX      AlarmSyncEntry
    MAX-ACCESS  not-accessible
    STATUS      current
    DESCRIPTION
        "An entry in the table."
    INDEX       { alarmSyncGroupId }
    ::= { alarmSyncTable 1 }

AlarmSyncEntry ::= SEQUENCE {
    alarmSyncGroupId                Unsigned32,
    alarmSyncLastSentSeqId          Counter32,
    alarmSyncCmd                    INTEGER,
    alarmSyncStartSeqId             Unsigned32,
    alarmSyncEndSeqId               Unsigned32 
 }

alarmSyncGroupId    OBJECT-TYPE
    SYNTAX      Unsigned32
    MAX-ACCESS  not-accessible
    STATUS      current
    DESCRIPTION
        "A unique Logical Group ID,
         which represents a group of managers."
    ::= { alarmSyncEntry 1 }

alarmSyncLastSentSeqId  OBJECT-TYPE
    SYNTAX      Counter32
    MAX-ACCESS  read-only
    STATUS      current
    DESCRIPTION
        "Last Sequence ID of trap that is sent
         to this Logical Group of managers."
    ::= { alarmSyncEntry 2 }

alarmSyncCmd    OBJECT-TYPE
    SYNTAX  INTEGER
    {
        off         (1),
        softSync    (2),
        hardSync    (3)
    }
    MAX-ACCESS  read-write
    STATUS     current
    DESCRIPTION
        "Initates an Alarm Synchronization request
         for this Logical Group of managers.

         softSync(2) - sends Soft Synchronization request,
                       in order to synchronize missing traps from Agent.
         hardSync(3) - sends Hard Synchronization request,
                       in order to synchronize current alarms of Agent.

         After an Alarm Synchronization process is completed,
         Agent will automatically change this value to off(1).
         "
    ::= { alarmSyncEntry 3 }

alarmSyncStartSeqId OBJECT-TYPE
    SYNTAX     Unsigned32
    MAX-ACCESS read-write
    STATUS     current
    DESCRIPTION
         "First Sequence ID of Soft Synchronization request
          for this Logical Group of managers.

          Soft Synchronization request is sent for a range of Sequence IDs.
          This object represents the first Sequence ID of this range."
    ::= { alarmSyncEntry 4 }

alarmSyncEndSeqId   OBJECT-TYPE
    SYNTAX     Unsigned32
    MAX-ACCESS read-write
    STATUS     current
    DESCRIPTION
         "Last Sequence ID of Soft Synchronization request
          for this Logical Group of managers.

          Soft Synchronization request is sent for a range of Sequence IDs.
          This object represents the last Sequence ID of this range."
    ::= { alarmSyncEntry 5 }

agnStringToIndexTable OBJECT-TYPE
    SYNTAX  SEQUENCE OF AgnStringToIndexEntry
    MAX-ACCESS  not-accessible
    STATUS  current
    DESCRIPTION
    "This table holds the conversions of tables from unique String
     to numeric index."
    ::= {agnt 62}

agnStringToIndexEntry OBJECT-TYPE
    SYNTAX  AgnStringToIndexEntry
    MAX-ACCESS  not-accessible
    STATUS  current
    DESCRIPTION
    "An entry in the table."
    INDEX   { agnStringToIndexTableId,IMPLIED agnStringToIndexUserName }
    ::= { agnStringToIndexTable 1 }

AgnStringToIndexEntry ::= SEQUENCE {
    agnStringToIndexTableId           OBJECT IDENTIFIER,
    agnStringToIndexUserName          SnmpAdminString,
    agnStringToIndexTableIndex        Unsigned32 
 }

agnStringToIndexTableId OBJECT-TYPE
    SYNTAX  OBJECT IDENTIFIER
    MAX-ACCESS  not-accessible
    STATUS  current
    DESCRIPTION
    "The OBJECT IDENTIFIER of the Table, having as index numeric values.
     In this table, the value of agnStringToIndexUserName is an attribute."
    ::= { agnStringToIndexEntry 1 }

agnStringToIndexUserName OBJECT-TYPE
    SYNTAX  SnmpAdminString(SIZE (1..64))
    MAX-ACCESS  not-accessible
    STATUS  current
    DESCRIPTION
    "This object indicates a unique name used by agnStringToIndexTableId,
     although it is not it's index."
    ::= { agnStringToIndexEntry 2 }

agnStringToIndexTableIndex OBJECT-TYPE
    SYNTAX  Unsigned32
    MAX-ACCESS  read-only
    STATUS  current
    DESCRIPTION
    "The numeric Index of agnStringToIndexTableId."
    ::= { agnStringToIndexEntry 3 }

agnRowPointerTable OBJECT-TYPE
    SYNTAX  SEQUENCE OF AgnRowPointerEntry
    MAX-ACCESS  not-accessible
    STATUS  current
    DESCRIPTION
    "This table holds information about a specific entry in a table.
     For example, number of usages of this row."
    ::= { agnt 63 }

agnRowPointerEntry OBJECT-TYPE
    SYNTAX  AgnRowPointerEntry
    MAX-ACCESS  not-accessible
    STATUS  current
    DESCRIPTION
    "An entry in the table."
    INDEX   {agnRowPointerIndex }
    ::= { agnRowPointerTable 1 }

AgnRowPointerEntry ::= SEQUENCE {
    agnRowPointerIndex             OBJECT IDENTIFIER,
    agnRowPointerNoOfUsages        Unsigned32 
 }

agnRowPointerIndex   OBJECT-TYPE
    SYNTAX  OBJECT IDENTIFIER
    MAX-ACCESS  not-accessible
    STATUS  current
    DESCRIPTION
    "The OBJECT IDENTIFIER of an entry in a table."
    ::= { agnRowPointerEntry 1 }

agnRowPointerNoOfUsages  OBJECT-TYPE
    SYNTAX  Unsigned32
    MAX-ACCESS  read-only
    STATUS  current
    DESCRIPTION
    "The number of usages of specific entry in a table, which is
     pointed by agnRowPointerIndex.Usually, when the value of this counter is greater
     than 0,the entry cannot be removed."
    ::= { agnRowPointerEntry 2 }


agnConfigVersion OBJECT-TYPE
    SYNTAX      SnmpAdminString
    MAX-ACCESS  read-only
    STATUS      current
    DESCRIPTION
        "ASCII string of the Configuration Version."
    ::= { agnt 64 }


agnResources  OBJECT IDENTIFIER ::= { agnt 65 }

-- Agn Memory Buffer Table


agnMemoryBufferTable OBJECT-TYPE
    SYNTAX  SEQUENCE OF AgnMemoryBufferEntry
    MAX-ACCESS  not-accessible
    STATUS  current
    DESCRIPTION
    "This table holds information about system memory buffers."
     ::= {agnResources 1 }

agnMemoryBufferEntry OBJECT-TYPE
    SYNTAX  AgnMemoryBufferEntry
    MAX-ACCESS  not-accessible
    STATUS  current
    DESCRIPTION
    "An entry in the table."
    INDEX   {agnMemoryBufferPoolIndex }
    ::= { agnMemoryBufferTable 1 }

AgnMemoryBufferEntry ::= SEQUENCE {
    agnMemoryBufferPoolIndex    Unsigned32,
    agnMemoryBufferName         SnmpAdminString,
    agnMemoryBufferTotalNum     Unsigned32,
    agnMemoryBufferFree         Unsigned32,
    agnMemoryBufferSize         Unsigned32,
    agnMemoryBufferAllocErrors  Unsigned32,
    agnMemoryBufferFreeErrors   Unsigned32 
 }

agnMemoryBufferPoolIndex   OBJECT-TYPE
    SYNTAX      Unsigned32
    MAX-ACCESS  not-accessible
    STATUS  current
    DESCRIPTION
    "This object defines a buffer pool index."
    ::= {agnMemoryBufferEntry 1 }

agnMemoryBufferName   OBJECT-TYPE
    SYNTAX      SnmpAdminString
    MAX-ACCESS  read-only
    STATUS  current
    DESCRIPTION
    "This object defines the name of the specific pool."
    ::= {agnMemoryBufferEntry 2 }

agnMemoryBufferTotalNum OBJECT-TYPE
     SYNTAX          Unsigned32
     MAX-ACCESS      read-only
     STATUS          current
     DESCRIPTION
     "The total number of buffers in the specific pool."
     ::= {agnMemoryBufferEntry 3 }

agnMemoryBufferFree OBJECT-TYPE
      SYNTAX          Unsigned32
      MAX-ACCESS      read-only
      STATUS          current
      DESCRIPTION
      "The number of free buffers in the specific pool."
      ::= {agnMemoryBufferEntry 4}

agnMemoryBufferSize OBJECT-TYPE
      SYNTAX          Unsigned32
      MAX-ACCESS      read-only
      STATUS          current
      DESCRIPTION
      "The size (in Bytes) of each buffer of this pool."
      ::= {agnMemoryBufferEntry 5}

agnMemoryBufferAllocErrors OBJECT-TYPE
      SYNTAX          Unsigned32
      MAX-ACCESS      read-only
      STATUS          current
      DESCRIPTION
      "Number of errors occurred when trying to return buffer to this pool."
      ::= {agnMemoryBufferEntry 6}

agnMemoryBufferFreeErrors OBJECT-TYPE
      SYNTAX          Unsigned32
      MAX-ACCESS      read-only
      STATUS          current
      DESCRIPTION
      "Number of errors occurred when trying to get buffer
       from this pool. "
      ::= {agnMemoryBufferEntry 7}

-- Agn Cpu Utilization Table

agnCpuUtilizationTable OBJECT-TYPE
    SYNTAX  SEQUENCE OF AgnCpuUtilizationEntry
    MAX-ACCESS  not-accessible
    STATUS  current
    DESCRIPTION
    "This table holds information about CPU utilization per task."
     ::= {agnResources 2 }

agnCpuUtilizationEntry OBJECT-TYPE
    SYNTAX  AgnCpuUtilizationEntry
    MAX-ACCESS  not-accessible
    STATUS  current
    DESCRIPTION
    "An entry in the table."
    INDEX   {agnCpuUtilizationCpuIdx, agnCpuUtilizationTaskIdx }
    ::= { agnCpuUtilizationTable 1 }

AgnCpuUtilizationEntry ::= SEQUENCE {
    agnCpuUtilizationCpuIdx     Integer32,
    agnCpuUtilizationTaskIdx    Unsigned32,
    agnCpuUtilizationCurrent    Unsigned32,
    agnCpuUtilizationMin        Unsigned32,
    agnCpuUtilizationMax        Unsigned32,
    agnCpuUtilizationClear      INTEGER,
    agnCpuUtilizationAverage    Unsigned32 
 }

agnCpuUtilizationCpuIdx   OBJECT-TYPE
    SYNTAX      Integer32 (1..2147483647)
    MAX-ACCESS  not-accessible
    STATUS  current
    DESCRIPTION
    "This object defines the CPU index that is monitored.
     If only one CPU exists,the value will always be 1."
    ::= {agnCpuUtilizationEntry 1 }

agnCpuUtilizationTaskIdx   OBJECT-TYPE
    SYNTAX      Unsigned32
    MAX-ACCESS  not-accessible
    STATUS  current
    DESCRIPTION
    "This object defines the task index that is monitored .
     When it equals to 2^32-1 ,it represents all the monitored tasks
     in the system."
    ::= {agnCpuUtilizationEntry 2 }

agnCpuUtilizationCurrent OBJECT-TYPE
     SYNTAX          Unsigned32
     MAX-ACCESS      read-only
     STATUS          current
     DESCRIPTION
     "Current CPU usage of a specific task in %.
      When agnCpuUtilizationTaskIdx equals to 2^32-1,
      it holds the current CPU utilization for all tasks."
      ::= {agnCpuUtilizationEntry 3 }

agnCpuUtilizationMin OBJECT-TYPE
      SYNTAX          Unsigned32
      MAX-ACCESS      read-only
      STATUS          current
      DESCRIPTION
      "Minimum CPU usage of a specific task in % from the last
      reset that has been executed ,for example, by using
      agnCpuUtilizationClear command or systemReset.
      When agnCpuUtilizationTaskIdx equals to 2^32-1,
      it holds the minimum CPU utilization for all tasks."
      ::= {agnCpuUtilizationEntry 4}

agnCpuUtilizationMax OBJECT-TYPE
      SYNTAX          Unsigned32
      MAX-ACCESS  read-only
      STATUS          current
      DESCRIPTION
      "Maximum CPU usage of a specific task in % from the last
      reset that has been executed ,for example, by using
      agnCpuUtilizationClear command or systemReset.
      When agnCpuUtilizationTaskIdx equals to 2^32-1,
      it holds the maximum CPU utilization for all tasks."
      ::= { agnCpuUtilizationEntry 5 }

agnCpuUtilizationClear OBJECT-TYPE
       SYNTAX  INTEGER
         {
       off (2),
       on  (3)
         }
       MAX-ACCESS  read-write
       STATUS          current
       DESCRIPTION
      "Reset action of the CPU utilization counters(except agnCpuUtilizationCurrent).
       After setting the command to 'on' , the device returns it to 'off'
       automatically after completing the clearing action"
       ::= { agnCpuUtilizationEntry 6 }

agnCpuUtilizationAverage OBJECT-TYPE
      SYNTAX          Unsigned32
      MAX-ACCESS      read-only
      STATUS          current
      DESCRIPTION
      "Average CPU usage of a specific task in % from the last
      reset that has been executed ,for example, by using
      agnCpuUtilizationClear command or systemReset.
      When agnCpuUtilizationTaskIdx equals to 2^32-1,
      it holds the average CPU utilization for all tasks."
      ::= { agnCpuUtilizationEntry 7 }


--******************
-- Agent Disk Table
--******************

agnDiskResourcesTable OBJECT-TYPE
    SYNTAX SEQUENCE OF AgnDiskResourcesEntry
    MAX-ACCESS  not-accessible
    STATUS      current
    DESCRIPTION
            "This table holds information about device disk(s)."
    ::= { agnResources 3 }

agnDiskResourcesEntry OBJECT-TYPE
    SYNTAX      AgnDiskResourcesEntry
    MAX-ACCESS  not-accessible
    STATUS      current
    DESCRIPTION
            "An entry in the table."
    INDEX       { agnDiskIdx }
    ::= { agnDiskResourcesTable 1 }

AgnDiskResourcesEntry ::= SEQUENCE {
    agnDiskIdx              Unsigned32,
    agnDiskTotalSpace       Unsigned32,
    agnDiskAvailableSpace   Unsigned32 
 }

agnDiskIdx OBJECT-TYPE
    SYNTAX      Unsigned32
    MAX-ACCESS  not-accessible
    STATUS      current
    DESCRIPTION
            "The disk index. The index is equals to 1, even device uses
            more than one disk."
    ::= { agnDiskResourcesEntry 1 }

agnDiskTotalSpace OBJECT-TYPE
    SYNTAX      Unsigned32
    MAX-ACCESS  read-only
    STATUS      current
    DESCRIPTION
            "Total disk space in kbytes. If the device uses more
            than one disk the object shall contain the minimal value."
    ::= { agnDiskResourcesEntry 2 }

agnDiskAvailableSpace OBJECT-TYPE
    SYNTAX      Unsigned32
    MAX-ACCESS  read-only
    STATUS      current
    DESCRIPTION
            "Available disk space in kbytes. If the device uses more
            than one disk the object shall contain the minimal value."
    ::= { agnDiskResourcesEntry 3 }


--***********************
-- System Resources Table
--***********************

systemResourcesTable OBJECT-TYPE
    SYNTAX SEQUENCE OF SystemResourcesEntry
    MAX-ACCESS  not-accessible
    STATUS      current
    DESCRIPTION
        "This table provides information on system resources."
    ::= { agnResources 4 }

systemResourcesEntry OBJECT-TYPE
    SYNTAX      SystemResourcesEntry
    MAX-ACCESS  not-accessible
    STATUS      current
    DESCRIPTION
        "This table has a single row entry and provides
         information related to system resources."
    INDEX   { systemResourceId }
    ::= { systemResourcesTable 1 }

SystemResourcesEntry ::= SEQUENCE {
    systemResourceId              Unsigned32,
    systemResourceLastError       INTEGER 
 }

systemResourceId OBJECT-TYPE
    SYNTAX      Unsigned32
    MAX-ACCESS  not-accessible
    STATUS      current
    DESCRIPTION
        "systemResourceId = 1."
    ::= { systemResourcesEntry 1 }

systemResourceLastError OBJECT-TYPE
    SYNTAX      INTEGER
    {
     notApplicable   (1),
     arpTableOverfow (2),
     ipv6NeighborTableOverflow (3)
    }
    MAX-ACCESS  read-only
    STATUS      current
    DESCRIPTION
        "Resource Last Error."
    ::= { systemResourcesEntry 2 }


--***********************
-- Memory Resources Table
--***********************

memoryUsageTable  OBJECT-TYPE
    SYNTAX SEQUENCE OF MemoryUsageEntry
    MAX-ACCESS not-accessible
    STATUS     current
    DESCRIPTION
    "This table monitors memory usage of various elements of the agent."
    ::=  { agnResources 5 }

memoryUsageEntry OBJECT-TYPE
    SYNTAX     MemoryUsageEntry
    MAX-ACCESS not-accessible
    STATUS     current
    DESCRIPTION
    "Each row contains memory usage-related parameters of one memory pool.
     Rows are added and removed by the agent
     and the information they contain is read-only."
    INDEX { memoryUsageEntityId, memoryUsagePoolId }
      ::= { memoryUsageTable 1 }

MemoryUsageEntry ::= SEQUENCE {
    memoryUsageEntityId                        Unsigned32,
    memoryUsagePoolId                          Unsigned32,
    memoryUsagePoolName                        SnmpAdminString,
    memoryUsageTotal                           Gauge32,
    memoryUsageFree                            Gauge32,
    memoryUsageApplicAllocCounter              Counter32,
    memoryUsageApplicFreeCounter               Counter32,
    memoryUsageApplicMaxUsed                   Gauge32,
    memoryUsageApplicAllocSize                 Counter64,
    memoryUsageApplicFreedSize                 Counter64 
 }

memoryUsageEntityId OBJECT-TYPE
    SYNTAX     Unsigned32
    MAX-ACCESS not-accessible
    STATUS     current
    DESCRIPTION
    "A numeric value representing the entity the row contains information on.
     If this is a slot, the same values as in  the SlotType TC are used.

     The special value of 0xffffffff represents the device itself."
    ::= { memoryUsageEntry 1 }

memoryUsagePoolId OBJECT-TYPE
    SYNTAX     Unsigned32
    MAX-ACCESS not-accessible
    STATUS     current
    DESCRIPTION
    "An ID that identifies the memory pool the row contains information on.
     If an entity contains multiple pools, they are represented in separate
     rows with the same memoryUsageEntityId and different memoryUsagePoolId.

     The special value of 0xffffffff represents the device itself."
    ::= { memoryUsageEntry 2 }

memoryUsagePoolName OBJECT-TYPE
    SYNTAX     SnmpAdminString
    MAX-ACCESS read-only
    STATUS     current
    DESCRIPTION
    "A human-readable description of the memory pool."
    ::= { memoryUsageEntry 3 }

memoryUsageTotal OBJECT-TYPE
    SYNTAX     Gauge32
    UNITS      "kilobytes"
    MAX-ACCESS read-only
    STATUS     current
    DESCRIPTION
    "Total amount of memory (in KBytes) allocated to the pool.
     This is equivalent to the sum of used and free memory."
    ::= { memoryUsageEntry 4 }

memoryUsageFree OBJECT-TYPE
    SYNTAX     Gauge32
    UNITS      "kilobytes"
    MAX-ACCESS read-only
    STATUS  current
    DESCRIPTION
    "Amount of memory (in KBytes) allocated to the pool, but not used."
    ::= { memoryUsageEntry 5 }

memoryUsageApplicAllocCounter OBJECT-TYPE
    SYNTAX     Counter32
    MAX-ACCESS read-only
    STATUS     current
    DESCRIPTION
    "Number of times the pool asked the OS application for memory allocation."
    ::= { memoryUsageEntry 6 }

memoryUsageApplicFreeCounter OBJECT-TYPE
    SYNTAX     Counter32
    MAX-ACCESS read-only
    STATUS     current
    DESCRIPTION
    "Number of times the pool freed memory to the OS application."
    ::= { memoryUsageEntry 7 }

memoryUsageApplicMaxUsed OBJECT-TYPE
    SYNTAX     Gauge32
    UNITS      "kilobytes"
    MAX-ACCESS read-only
    STATUS     current
    DESCRIPTION
    "Highest amount of memory (in KBytes) ever used by the pool."
    ::= { memoryUsageEntry 8 }

memoryUsageApplicAllocSize OBJECT-TYPE
    SYNTAX     Counter64
    UNITS      "bytes"
    MAX-ACCESS read-only
    STATUS     current
    DESCRIPTION
    "Sum of memory allocations (in Bytes) the pool has ever received."
    ::= { memoryUsageEntry 9 }

memoryUsageApplicFreedSize OBJECT-TYPE
    SYNTAX     Counter64
    UNITS      "bytes"
    MAX-ACCESS read-only
    STATUS     current
    DESCRIPTION
    "Sum of memory allocations (in Bytes) the pool has ever freed."
    ::= { memoryUsageEntry 10 }

    

-- Entity Convert Index Table

entityConvertIndexTable OBJECT-TYPE
    SYNTAX  SEQUENCE OF EntityConvertIndexEntry
    MAX-ACCESS  not-accessible
    STATUS  current
    DESCRIPTION
    "This table holds information about converted indexes of entities that
     have more than one index. The original indexes can be each, up to Unsigned32 value,
     though the total number of entities in the device is less than Unsigned32.
     These indexes are converted to a single index, in order to use it in MIB tables that require
     one unique index."
     ::= {agnt 66 }

entityConvertIndexEntry OBJECT-TYPE
    SYNTAX  EntityConvertIndexEntry
    MAX-ACCESS  not-accessible
    STATUS  current
    DESCRIPTION
    "An entry in the table."
    INDEX   {entityConvertEntityType, entityConvertIndex }
    ::= { entityConvertIndexTable 1 }

EntityConvertIndexEntry ::= SEQUENCE {
    entityConvertEntityType     RadEntityType,
    entityConvertIndex          Unsigned32,
    entityConvertRowStatus      RowStatus,
    entityConvertParam1         Unsigned32,
    entityConvertParam2         Unsigned32,
    entityConvertParam3         Unsigned32,
    entityConvertParam4         Unsigned32,
    entityConvertParam5         Unsigned32 
 }

entityConvertEntityType OBJECT-TYPE
      SYNTAX  RadEntityType
      MAX-ACCESS  not-accessible
      STATUS  current
      DESCRIPTION
      "This object defines the type of entity that its indexes are
       converted to one index using this table."
      ::= { entityConvertIndexEntry 1 }

entityConvertIndex OBJECT-TYPE
    SYNTAX      Unsigned32
    MAX-ACCESS  not-accessible
    STATUS      current
    DESCRIPTION
     "The converted index. For each device, the valid range of the converted index should not
      conflict with ifIndex values of the device's interfaces . "
    ::= { entityConvertIndexEntry 2}

entityConvertRowStatus  OBJECT-TYPE
    SYNTAX       RowStatus
    MAX-ACCESS   read-create
    STATUS       current
    DESCRIPTION
    "This object enables to create/delete entries of this table."
    ::= { entityConvertIndexEntry 3}

entityConvertParam1    OBJECT-TYPE
    SYNTAX      Unsigned32
    MAX-ACCESS  read-create
    STATUS      current
    DESCRIPTION
    "First original index of the entity."
    ::= { entityConvertIndexEntry 4}

entityConvertParam2    OBJECT-TYPE
    SYNTAX      Unsigned32
    MAX-ACCESS  read-create
    STATUS      current
    DESCRIPTION
    "Second original index of the entity."
    ::= { entityConvertIndexEntry 5}

entityConvertParam3   OBJECT-TYPE
    SYNTAX      Unsigned32
    MAX-ACCESS  read-create
    STATUS      current
    DESCRIPTION
    "Third original index of the entity."
    ::= { entityConvertIndexEntry 6}

entityConvertParam4   OBJECT-TYPE
    SYNTAX      Unsigned32
    MAX-ACCESS  read-create
    STATUS      current
    DESCRIPTION
    "Forth original index of the entity."
    ::= { entityConvertIndexEntry 7}

entityConvertParam5   OBJECT-TYPE
    SYNTAX      Unsigned32
    MAX-ACCESS  read-create
    STATUS      current
    DESCRIPTION
    "Fifth original index of the entity."
    ::= { entityConvertIndexEntry 8}


agnFiles        OBJECT IDENTIFIER ::= { agnt 67 }

-- File System Table


fileSystemTable OBJECT-TYPE
    SYNTAX      SEQUENCE OF FileSystemEntry
    MAX-ACCESS  not-accessible
    STATUS      current
    DESCRIPTION
        "The File System Table."
    ::= { agnFiles 1 }

fileSystemEntry OBJECT-TYPE
    SYNTAX      FileSystemEntry
    MAX-ACCESS  not-accessible
    STATUS      current
    DESCRIPTION
        "An entry in the File System Table."
    INDEX       { fileSystemPath, fileSystemObjType, IMPLIED fileSystemObjName }
    ::= { fileSystemTable 1 }

FileSystemEntry ::= SEQUENCE {
    fileSystemPath                     SnmpAdminString,
    fileSystemObjType                  FileType,
    fileSystemObjName                  SnmpAdminString,
    fileSystemRowStatus                RowStatus,
    fileSystemSignatureBoot            Integer32,
    fileSystemSignatureTime            Integer32,
    fileSystemLastUpdateTime           DateAndTime,
    fileSystemLastUpdateBootSignature  Integer32,
    fileSystemLastUpdateTimeSignature  Integer32,
    fileSystemFileSize                 Unsigned32,
    fileSystemValidIndication          BITS 
 }

fileSystemPath OBJECT-TYPE
    SYNTAX      SnmpAdminString
    MAX-ACCESS  not-accessible
    STATUS      current
    DESCRIPTION
    "This object represents the path to the location of the file.
    The length of the path is limited to 64 octets."
    ::= { fileSystemEntry 1 }

fileSystemObjType OBJECT-TYPE
    SYNTAX      FileType
    MAX-ACCESS  not-accessible
    STATUS      current
    DESCRIPTION
        "This object represents the Object's Type."
    ::= { fileSystemEntry 2 }

fileSystemObjName OBJECT-TYPE
    SYNTAX      SnmpAdminString (SIZE (1..255))
    MAX-ACCESS  not-accessible
    STATUS      current
    DESCRIPTION
    "This object represents the name of the file.
    The length of the name is limited to 32 octets."
    ::= { fileSystemEntry 3 }

fileSystemRowStatus OBJECT-TYPE
    SYNTAX      RowStatus
    MAX-ACCESS  read-create
    STATUS      current
    DESCRIPTION
        "This object enables the user to create/delete entries in this table."
    ::= { fileSystemEntry 4 }

fileSystemSignatureBoot OBJECT-TYPE
    SYNTAX      Integer32
    MAX-ACCESS  read-only
    STATUS current
    DESCRIPTION
       "The value saved in this variable is:
        If the copied file is from the NE's file system it is the value
        of fileSystemSignatureBoot of the copied file.
        Otherwise (the copied file is external), it is the value
        of snmpEngineBoot at the time when copy operation is completed.

        For Running configuration file:
            The variable is also updated with the device's
            snmpEngineBoot whenever the Running Configuration file is changed (by user).
            After reboot, the value is copied from fileSystemSignatureBoot of the file copied
            to the Running configuration (e.g. startup-config, rollback-config,
            user-default-config, or factory-default-config).

        For Factory Default configuration file:
            The variable denotes the value of snmpEngineBoot
            when the file was uploaded to the NE.
        "
    ::=  { fileSystemEntry 5 }

fileSystemSignatureTime OBJECT-TYPE
    SYNTAX  Integer32
    MAX-ACCESS  read-only
    STATUS current
    DESCRIPTION
       "Measurement units: Seconds.
        The value saved in this variable is the value
        of fileSystemSignatureTime of the copied file.

        For Running configuration file:
            The variable is also updated with the device's
            snmpEngineTime whenever the Running Configuration file is changed (by user).
            After reboot, the value is copied from fileSystemSignatureTime of the file copied
            to the Running configuration (e.g. startup-config, rollback-config,
            user-default-config, or factory-default-config).

        For Factory Default configuration file:
            The variable denotes the value of snmpEngineTime
            when the file was uploaded to the NE.
        "
    ::=  { fileSystemEntry 6 }



fileSystemLastUpdateTime OBJECT-TYPE
    SYNTAX      DateAndTime
    MAX-ACCESS  read-only
    STATUS      current
    DESCRIPTION
    "If the NE does not support a real-time clock, or,
     if from any other reason the UTC time is not known,
     this variable must be set to zero (eight octets with the value 0 in each).
     Otherwise, this variable represents the UTC time
     when the file has been last updated, as recorded by the NE."
    ::= { fileSystemEntry 7 }


fileSystemLastUpdateBootSignature OBJECT-TYPE
    SYNTAX      Integer32
    MAX-ACCESS  read-only
    STATUS      current
    DESCRIPTION
    "The variable denotes the value of snmpEngineBoots when the file has been updated.
    "
    ::= { fileSystemEntry 8 }

fileSystemLastUpdateTimeSignature OBJECT-TYPE
    SYNTAX      Integer32
    MAX-ACCESS  read-only
    STATUS      current
    DESCRIPTION
    "Units: seconds.
     The variable denotes the value of snmpEngineTime when the file has been updated.
    "
    ::= { fileSystemEntry 9 }


 fileSystemFileSize OBJECT-TYPE
    SYNTAX      Unsigned32
    MAX-ACCESS  read-only
    STATUS      current
    DESCRIPTION
    "File size in bytes."
    ::= { fileSystemEntry 10 }


fileSystemValidIndication OBJECT-TYPE
    SYNTAX      BITS {
        runningError           (0),
        invalidHeader          (1),
        confirmNotReceived     (2),
        fileNotExist           (3),
        loadFailure            (4),
        crcError               (5),
        locked                 (6),
        readOnly               (7),
        copyInProgress         (8),
        packCorrupted          (9),
        migrationFailed       (10),
        migrationErrors       (11),
        fileInUse             (12),
        previousInUse         (13),
        standbyCopyInProgress (14),
        mirroringFailure      (15),
        fileOverflow          (16)
        }
    MAX-ACCESS  read-only
    STATUS      current
    DESCRIPTION
        "The variable indicates if the file is valid, or, specifies
        invalidity reason.
        Each bit indicate a status or possible error that occurred:
        runningError           (0) - an error occurred while executing
                                    the file.
        invalidHeader          (1) - header checking failed.
        confirmNotReceived     (2) - confirmation rejected by user or
                                    confirmation time has expired.
        fileNotExist           (3) - file does not exist.
        loadFailure            (4) - loading file has been failed for
                                    three successive times.
        crcError               (5) - CRC error in file.
        locked                 (6) - denotes that currently the file
                                    cannot be modified.
        readOnly               (7) - file cannot be deleted or modified
        copyInProgress         (8) - file copy operation is in progress
        packCorrupted          (9) - SW Pack is corrupted e.g. due to
                                    device flash error.
        migrationFailed       (10) - file migration failed (example: migration from binary to text failed)
        migrationErrors       (11) - file migration was completed but file has errors
        fileInUse             (12) - current file is in use
        previousInUse         (13) - current file is used as previous
        standbyCopyInProgress (14) - issued during copy to standby card
        mirroringFailure      (15) - file failed to be copied to standby card
        fileOverflow          (16) - file has reached its maximum capability
        "
    ::= { fileSystemEntry 11 }



fileChangeStatus OBJECT-TYPE
    SYNTAX  BITS
    {
       startupConfigError   (0), -- either startup configuration file does not exist, or is corrupted
       startupConfigChanged (1), -- startup configuration file has been changed
                                 -- since last time it equaled Running configuration file
       runningConfigChanged (2)  -- running configuration file has been changed
                                 -- since last time it equaled Startup configuration file
    }
    MAX-ACCESS  read-only
    STATUS current
    DESCRIPTION
       "This variable indicates changes in configuration files.
        Indication exists when a value of '1' exists in the corresponding bit.
       "
    ::= { agnFiles 2 }


configLoadTable OBJECT-TYPE
    SYNTAX      SEQUENCE OF ConfigLoadEntry
    MAX-ACCESS  not-accessible
    STATUS      current
    DESCRIPTION
        "The purpose of this table is to gather the parameters used in
         the process of loading configuration files to the NE.
        "
    ::= { agnFiles 3 }

configLoadEntry OBJECT-TYPE
    SYNTAX      ConfigLoadEntry
    MAX-ACCESS  not-accessible
    STATUS      current
    DESCRIPTION
        "An entry in the Config Load Table."
    INDEX       { configLoadIndex }
    ::= { configLoadTable 1 }

ConfigLoadEntry ::= SEQUENCE {
    configLoadIndex                       Unsigned32,
    configLoadConfirmReq                  INTEGER,
    configLoadConfirmConf                 INTEGER,
    configLoadConfirmTimer                Unsigned32,
    configLoadRollbackFilePath            SnmpAdminString,
    configLoadRollbackFileName            SnmpAdminString,
    configLoadErrorPolicy                 INTEGER,
    configLoadObjType                     FileType,
    configLoadZtcStartupConfigVersion     SnmpAdminString 
 }

configLoadIndex   OBJECT-TYPE
        SYNTAX             Unsigned32
        MAX-ACCESS        not-accessible
        STATUS            current
        DESCRIPTION
                "An index in the Config Load Table.
                "
        ::= { configLoadEntry 1 }

configLoadConfirmReq    OBJECT-TYPE
    SYNTAX        INTEGER
    {
      off  (2),
      on   (3)
    }
    MAX-ACCESS   read-write
    STATUS current
    DESCRIPTION
    "This variable denotes if after next reboot startup-config
     requires manager confirmation.
     After reboot the agent must set the value to off (2).
    "
    DEFVAL {2}
    ::= { configLoadEntry 2 }

configLoadConfirmConf OBJECT-TYPE
    SYNTAX  INTEGER {
        off      (2),    -- Off OK
        pending  (3),
        offError (5)     -- Off Error
        }
    MAX-ACCESS  read-write
    STATUS      current
    DESCRIPTION
            "This variable is used for confirming startup-config.
            It is applicable only when configLoadConfirmReq is set to
            on(3). If reboot is completed and startup-config is properly
            loaded the agent sets the value to pending(3) and starts a
            timer for a period defined at configLoadConfirmTimer.
            Confirmation is gained when the manager sets the value to
            off(2) within timeout. If after reboot the value of the
            variable equals pending(3), namely, the device has rebooted
            without confirmation, startup-config is considered invalid.
            If the manager fails to confirm startup-config, the agent
            will set the value to offError(5). The manager can poll this
            variable in order to determine if the command was executed
            successfully (pending(3)) or not (offError(5)).

            The values pending (3) and offError(5) may be set only by
            the agent."
    DEFVAL {2}
    ::= { configLoadEntry 3 }

configLoadConfirmTimer  OBJECT-TYPE
    SYNTAX         Unsigned32
    MAX-ACCESS     read-write
    STATUS         current
    DESCRIPTION
    "This variable denotes the time in seconds to wait for confirmation (after reboot).
     It is applicable only when configLoadConfirmReq is set to on(3).
    "
    DEFVAL {300}
    ::= { configLoadEntry 4 }

configLoadRollbackFilePath  OBJECT-TYPE
    SYNTAX          SnmpAdminString
    MAX-ACCESS      read-write
    STATUS          current
    DESCRIPTION
    "This variable denotes the path of the file to be copied to rollback-config file
     when configLoadConfirmReq is set to on(3).
    "
    ::= { configLoadEntry 5 }

configLoadRollbackFileName  OBJECT-TYPE
    SYNTAX          SnmpAdminString
    MAX-ACCESS      read-write
    STATUS          current
    DESCRIPTION
    "This variable denotes the name of the file to be copied to rollback-config file
     when configLoadConfirmReq is set to on(3).
    "
    ::= { configLoadEntry 6 }

configLoadErrorPolicy    OBJECT-TYPE
    SYNTAX          INTEGER
    {
       stop   (1),
       reject (2),
       ignore (3)
    }
    MAX-ACCESS      read-write
    STATUS          current
    DESCRIPTION
    "This variable denotes the policy to be carried out
     in case that an error has occurred while loading or executing the file:
       stop   (1) - stop upon first encountered error in the file.
       reject (2) - reject and mark the file as invalid.
       ignore (3) - load or execute the whole file, regardless of errors.
    "
    DEFVAL {3}
    ::= { configLoadEntry 7 }

configLoadObjType   OBJECT-TYPE
        SYNTAX            FileType
        MAX-ACCESS        read-only
        STATUS            current
        DESCRIPTION
        "This variable denotes the configuration file that was loaded after reboot.
         The value saved is the file type, as defined in fileSystemObjType.
        "
        ::= { configLoadEntry 8 }

configLoadZtcStartupConfigVersion   OBJECT-TYPE
        SYNTAX            SnmpAdminString
        MAX-ACCESS        read-only
        STATUS            current
        DESCRIPTION
        "This variable denotes the version of last startup config file loaded by
         Zero Touch Configuration mechanism."
        ::= { configLoadEntry 9 }


-- RAD General SW Pack Handling is defined in SwPackHndl.txt
-- swPack OBJECT IDENTIFIER ::= { agnFiles 4 }


agnErrorMessageTable OBJECT-TYPE
    SYNTAX  SEQUENCE OF AgnErrorMessageEntry
    MAX-ACCESS  not-accessible
    STATUS  current
    DESCRIPTION
    "This table holds Agent error messages,caused by last SNMP Set operation/s.
    For each SNMP Set fail response,Agent will report a relevant error message."
     ::= {agnt 68 }

agnErrorMessageEntry OBJECT-TYPE
    SYNTAX  AgnErrorMessageEntry
    MAX-ACCESS  not-accessible
    STATUS  current
    DESCRIPTION
    "An entry in the table."
    INDEX   {agnErrorMessageSeqId }
    ::= { agnErrorMessageTable 1 }

AgnErrorMessageEntry ::= SEQUENCE {
    agnErrorMessageSeqId                  Unsigned32,
    agnErrorMessage                       SnmpAdminString 
 }

agnErrorMessageSeqId   OBJECT-TYPE
    SYNTAX      Unsigned32
    MAX-ACCESS  not-accessible
    STATUS  current
    DESCRIPTION
    "This object is the Sequence ID of the response PDU
     (Set Response PDU that announced the SNMP failure), or any other message
     ID that will be generated by Agent.
     For first implementation, only one message will be stored at a time ,
     and every new message will overwrite the older one, so that the message
     will be always of last SNMP Set fail."
    ::= {agnErrorMessageEntry 1 }

agnErrorMessage   OBJECT-TYPE
    SYNTAX      SnmpAdminString
    MAX-ACCESS  read-only
    STATUS  current
    DESCRIPTION
    "This object defines the string of the error message."
    ::= {agnErrorMessageEntry 2 }

agnCapabilities     OBJECT IDENTIFIER ::= { agnt 70 }

agnCommonCapabilities    OBJECT-TYPE
    SYNTAX  BITS
    {
     snmpV3                    (0),
     cli                       (1),
     trapSynchronization       (2),
     sshServer                 (3),
     oamCfm                    (4),
     oamEfm                    (5),
     lag                       (6),
     sntp                      (7),
     sftpClient                (8),
     tftpClient                (9),
     entityMib                 (10),
     mlppp                     (11),
     telnet                    (12),
     csm                       (13),
     erp                       (14),
     eps                       (15),
     tdmPwProtect              (16),
     pathSdhSonetProtect       (17),
     aps                       (18),
     ethPortProtect            (19),
     tdmPortProtect            (20),
     tdmPW                     (21),
     fileSystem                (22),
     ssfp                      (23),
     ptp                       (24), -- 1588 Recovered clock
     copyFile                  (25),
     router                    (26),
     fileTransfer              (27),
     faultManagement           (28),
     configChangeSync          (29), -- NE Configuration Change Support
     binaryDataRetrievalMethod (30), -- Binary Data Retrieval from device
     bridge                    (31),
     acl                       (32),
     ospf                      (33),
     bgp                       (34),
     bfd                       (35),
     performanceManagement     (36),
     ituSat                    (37), -- Y.1564  support
     genericPpp                (38), -- Generic PPP & PPPoE
     policer                   (39),
     lldp                      (40),
     twamp                     (41), -- TWAMP
     flow                      (42), -- not used here, but defined due to compiler error: Named bits must be numbered contiguously.
     vrrp                      (43), -- Virtual Router Redundancy Protocol
     ntp                       (44), -- Network Time Protocol
     l3Sat                     (45),
     security8021x             (46),
     inServicePing             (47), -- Layer 2 Ping
     macSec                    (48),
     portFlowMirroring         (49),
     ethPort                   (50),
     dhcpL2Relay               (51)
   }
     MAX-ACCESS  read-only
     STATUS  current
     DESCRIPTION
     "This object indicates common capabilities that this Agent can support.
      These capabilities may not be active (reasons may be for example,
      lack of relevant HW, lack of License, or being disabled by user).
      For each BIT: '1' means that this feature is supported.
      Generally, these capabilities are required for map/net applications.
      The general protection related capabilitites eps(15), tdmPwProtect(16),
      pathSdhSonetProtect(17), aps(18), ethPortProtect(19) and tdmPortProtect(20)
      are correlated to the definition of the ProtectClassType.
     "
     ::=  {agnCapabilities 1}

agnCommonFeatureAvailability    OBJECT-TYPE
    SYNTAX  BITS
    {
     snmpV3                    (0),
     cli                       (1),
     trapSynchronization       (2),
     sshServer                 (3),
     oamCfm                    (4),
     oamEfm                    (5),
     lag                       (6),
     sntp                      (7),
     sftpClient                (8),
     tftpClient                (9),
     entityMib                 (10),
     mlppp                     (11),
     telnet                    (12),
     csm                       (13),
     erp                       (14),
     eps                       (15),
     tdmPwProtect              (16),
     pathSdhSonetProtect       (17),
     aps                       (18),
     ethPortProtect            (19),
     tdmPortProtect            (20),
     tdmPW                     (21),
     fileSystem                (22),
     ssfp                      (23),
     ptp                       (24), -- 1588 Recovered clock
     copyFile                  (25),
     router                    (26),
     fileTransfer              (27),
     faultManagement           (28),
     configChangeSync          (29), -- NE Configuration Change Support
     binaryDataRetrievalMethod (30), -- Binary Data Retrieval from device
     bridge                    (31),
     acl                       (32),
     ospf                      (33),
     bgp                       (34),
     bfd                       (35),
     performanceManagement     (36),
     ituSat                    (37), -- Y.1564  support
     genericPpp                (38), -- Generic PPP & PPPoE
     policer                   (39),
     lldp                      (40),
     twamp                     (41), -- TWAMP
     flow                      (42), -- not used here, but defined due to compiler error: Named bits must be numbered contiguously.
     vrrp                      (43), -- Virtual Router Redundancy Protocol
     ntp                       (44), -- Network Time Protocol
     l3Sat                     (45),
     security8021x             (46),
     inServicePing             (47), -- Layer 2 Ping
     macSec                    (48),
     portFlowMirroring         (49),
     ethPort                   (50),
     dhcpL2Relay               (51)
    }
     MAX-ACCESS  read-only
     STATUS  current
     DESCRIPTION
     "This object denotes for each feature that is supported by the NE
      (denoted in agnCommonCapabilities) if it is available (enabled, license valid etc).
      The purpose of this variable is to enable a map application to get the information
      it needs in a single PDU: Feature is supported (agnCommonCapabilities),
      and is available (this variable).
      For each BIT: '1' means that this feature is available.
      The general protection related capabilitites eps(15), tdmPwProtect(16),
      pathSdhSonetProtect(17), aps(18), ethPortProtect(19) and tdmPortProtect(20)
      are correlated to the definition of the ProtectClassType.
     "
     ::=  {agnCapabilities 2}



--services OBJECT IDENTIFIER ::= { radGen 3}  See services.txt

radTransport OBJECT IDENTIFIER ::= { radGen 4}
--RAD transport tree
radTransportDomains  OBJECT IDENTIFIER ::= { radTransport 1}

radTransportDomainSnmpEfmOam OBJECT-IDENTITY
   STATUS  current
   DESCRIPTION
   "The SNMP over EFM OAM transport domain.  The corresponding
    transport address is of type RadTransportAddressEfmOam for
    EFM OAM addresses (port)."
   ::= { radTransportDomains 1 }



agnThreshold        OBJECT IDENTIFIER ::= { agnt 71 }

--  agn Threshold Table

agnThresholdTable OBJECT-TYPE
      SYNTAX SEQUENCE OF AgnThresholdEntry
      MAX-ACCESS not-accessible
      STATUS current
      DESCRIPTION
      "The list of card/device agent Threshold."
      ::= { agnThreshold 1 }

agnThresholdEntry OBJECT-TYPE
      SYNTAX AgnThresholdEntry
      MAX-ACCESS not-accessible
      STATUS current
      DESCRIPTION
      "Threshold table is used to define any type of threshold, like temperature or power."
      INDEX { agnThresholdIdx }
      ::= { agnThresholdTable 1}

AgnThresholdEntry ::= SEQUENCE {
    agnThresholdIdx            INTEGER,
    agnThresholdUom            INTEGER,
    agnThresholdMin            Integer32,
    agnThresholdMax            Integer32,
    agnThresholdHysteresis     Integer32,
    agnThresholdCurrent        Integer32 
 }


agnThresholdIdx OBJECT-TYPE
      SYNTAX  INTEGER
       {
       critical                  (1),
       steadyState               (2),
        powerOn                   (3),
        systemPower               (4)
       }
      MAX-ACCESS  not-accessible
      STATUS  current
      DESCRIPTION
      "This object defines the index of the Threshold Table.
       For temperature objects,
       the device shall support steadyState (2) threshold.
       For system power-in the index should be systemPower(4).
       "
      ::= { agnThresholdEntry 1}

agnThresholdUom OBJECT-TYPE
      SYNTAX  INTEGER
       {
       celsius            (1),
       fahrenheit         (2),
       milliVolt          (3)
       }
      MAX-ACCESS  read-write
      STATUS  current
      DESCRIPTION
      "This object defines the Unit Of Measure like
       Celsius, Fahrenheit, Millivolt etcetera.
       For temperature threshold, the device shall work internally in Celsius and
       make the necessary conversion if the user configuration is in Fahrenheit.
       "
      ::= { agnThresholdEntry 2}


agnThresholdMin OBJECT-TYPE
  SYNTAX  Integer32
  MAX-ACCESS  read-write
  STATUS  current
  DESCRIPTION
  "This object define the Minimum threshold "
    ::= { agnThresholdEntry 3 }

agnThresholdMax OBJECT-TYPE
  SYNTAX  Integer32
  MAX-ACCESS  read-write
  STATUS  current
  DESCRIPTION
  "This object define the Maximum threshold"
    ::= { agnThresholdEntry 4 }

agnThresholdHysteresis OBJECT-TYPE
  SYNTAX  Integer32
  MAX-ACCESS  read-write
  STATUS  current
  DESCRIPTION
  "This object defines a range value of a state transition around a
   Minimum or Maximum threshold.
    Upon threshold crossing, an Alarm will be sent Once
    if the current value variation is retained
    inside the hysteresis range.
    "
    ::= { agnThresholdEntry 5 }

agnThresholdCurrent OBJECT-TYPE
  SYNTAX  Integer32
  MAX-ACCESS  read-only
  STATUS  current
  DESCRIPTION
  "This object define the current Actual value"
    ::= { agnThresholdEntry 6}

--  RAD Protection Mechanism
agnProtection       OBJECT IDENTIFIER ::= { agnt 72 }
-- see file Protection.txt

--  RAD Licensing
agnLicense OBJECT IDENTIFIER ::= { agnt 73 }
-- see file License.txt

-- RAD Performance Management
agnPerformanceManagement OBJECT IDENTIFIER ::= { agnt 74 }
-- see file pm.txt

--  NE (Network Element) Configuration Change (Sync between NMS and Device)
agnConfigChange OBJECT IDENTIFIER ::= { agnt 75 }
-- see file ConfigChange.txt


agnLldp     OBJECT IDENTIFIER ::= { agnt 76 }

agnLldpTable OBJECT-TYPE
      SYNTAX SEQUENCE OF AgnLldpEntry
      MAX-ACCESS not-accessible
      STATUS current
    DESCRIPTION  "LLDP table. Contains scalars that operate at device level."
    ::=  {agnLldp 1}

agnLldpEntry OBJECT-TYPE
      SYNTAX AgnLldpEntry
      MAX-ACCESS not-accessible
      STATUS current
      DESCRIPTION
      "An entry in the LLDP table."
      INDEX {lldpIndex }
      ::= { agnLldpTable 1}

AgnLldpEntry ::= SEQUENCE {
    lldpIndex           Unsigned32,
    lldpAdminStatus     INTEGER,
    lldpSysBridgeType   INTEGER 
 }

lldpIndex         OBJECT-TYPE
      SYNTAX  Unsigned32
      MAX-ACCESS  not-accessible
      STATUS  current
      DESCRIPTION
      "A dummy index. Has a fixed value of 1."
      ::= { agnLldpEntry 1}

lldpAdminStatus     OBJECT-TYPE
     SYNTAX INTEGER {
     disable (1),
     enable  (2)
     }
     MAX-ACCESS read-write
     STATUS current
     DESCRIPTION
      "Enable or Disable the LLDP status."
      ::= { agnLldpEntry 2}

lldpSysBridgeType   OBJECT-TYPE
     SYNTAX INTEGER {
     nearestBridge   (1),
     customerBridge  (2),
     nonTpmrBridge   (3)
     }
     MAX-ACCESS read-write
     STATUS current
     DESCRIPTION
      "The bridge type of the system. The LLDP protocol frames,
      matched the defined by this parameter bridge type, will be
      forwarded to the LLDP control process, that is peered.
      All unmatched LLDP frames will be handled as regular L2CP frames "
      ::= { agnLldpEntry 3}


agnPanelType OBJECT-TYPE
    SYNTAX      Unsigned32
    MAX-ACCESS  read-only
    STATUS      current
    DESCRIPTION
    "This object identify the device panel.
    For ETX-36:
    Panel number        agnPanelType
    k-32-41-00-m483     483
    k-32-41-00-m484     484
    k-32-41-00-m488     488
    42.11.10.17         17.00
    42.11.10.17.01      17.01
    42.11.10.17.02      17.02."
    ::= {agnt 78}

-- agnt 80  see Sniffer.MIB  RAD-Sniffer-MIB
     
agnScalarObjects OBJECT IDENTIFIER ::= { agnt 81 }

agnDscp OBJECT-TYPE
    SYNTAX       Unsigned32 (0..63)
    MAX-ACCESS   read-write
    STATUS       current
    DESCRIPTION
        "The DSCP value of any management applications traffic generated by the device."
        DEFVAL  { 0 }
    ::= { agnScalarObjects 1 }
    
schedControl  OBJECT IDENTIFIER ::= { systemTiming 8 }


schedDeleteFinishedCmd OBJECT-TYPE
    SYNTAX  INTEGER {
       off (2),
       on  (3)
    }
    MAX-ACCESS  read-write
    STATUS  current
    DESCRIPTION
    "When this object is set to on(3), the agent removes all schedTable entries
     whose schedOperStatus == finished(3).
     Upon completion, this object automatically transitions to off(2)."
    DEFVAL { off }
    ::= { schedControl 1 }

schedClearLogCmd OBJECT-TYPE
    SYNTAX  INTEGER {
       off (2),
       on  (3)
    }
    MAX-ACCESS  read-write
    STATUS  current
    DESCRIPTION
    "When this object is set to on(3), the agent clears the scheduler log file.
     Upon completion, this object automatically transitions to off(2)."
    DEFVAL { off }
    ::= { schedControl 2 }


systemDateTime  OBJECT IDENTIFIER ::= { systemTiming 9 } -- System date and time management

systemLastTimeChangeOffset OBJECT-TYPE
    SYNTAX  Integer32
    UNITS "seconds"
    MAX-ACCESS  read-only
    STATUS  current
    DESCRIPTION
    "This object contains the number of seconds by which
     the system local time was moved during the most recent time change."
    ::= { systemDateTime 1 }

systemLastTimeChangeReason OBJECT-TYPE
    SYNTAX  INTEGER {
        unknown (1),
        userCommand (2),
        ntp (3),
        summerTimeStart (4),
        summerTimeEnd (5)
    }
    MAX-ACCESS  read-only
    STATUS  current
    DESCRIPTION
    "This object specifies the trigger of the most recent system local time change."
    ::= { systemDateTime 2 }


-- SYSTEM TRAPS

--NOTIFICATIONS

systemsEvents OBJECT-IDENTITY
     STATUS  current
     DESCRIPTION
     "The events for RAD products."
     ::= { systems 0 }

tftpStatusChangeTrap  NOTIFICATION-TYPE
     OBJECTS       { tftpStatus }
     STATUS current
     DESCRIPTION     
     "This trap is sent whenever the status of tftp changed."
     ::= { systemsEvents 1 }

agnStatusChangeTrap  NOTIFICATION-TYPE
	OBJECTS		{agnIndication }
    STATUS current
	DESCRIPTION
	"This trap is sent whenever the state of the entity the agent is
	 responsible for changed.
	 TDM devices will send agnTestStatus variable to indicate the current test status."
	::= { systemsEvents 2 }

prtStatusChangeTrap  NOTIFICATION-TYPE
    STATUS current
	DESCRIPTION
	"This trap is sent whenever the state of a port changed.
	 Attached, will be parameter/s that indicate the new port status.
	 The attached variables will be specified in the specifications
	 of the products supporting this trap."
	::= { systemsEvents 3 }

swdlStatusResult	    NOTIFICATION-TYPE
	OBJECTS			{swdlStatusFileName}
    STATUS  current
	DESCRIPTION
	"This notification is sent when Software Down Load is finished.
	 The attached object indicates the File Name."
	::= { systemsEvents 4 }

intSwdlSlotFileMismatch	    NOTIFICATION-TYPE
	OBJECTS			{intSwdlFileName}
    STATUS  current
	DESCRIPTION
	"This notification is sent when the card in the chosen slot doesn't match 
	 the chosen file.
	 The attached object indicates the File Name."
	::= { systemsEvents 5 }

agnCounterChange  NOTIFICATION-TYPE
    STATUS  current
	DESCRIPTION
	"This notification is sent when the value of a specific Counter is changed.
	 Agent can send as attached object the updated Counter.
	 For details about this Counter and attached object, see spec of the relevant
	 application."
	::= { systemsEvents 6 }

prtClkSrcChangeTrap NOTIFICATION-TYPE
      STATUS  current
      DESCRIPTION
	  "This trap is sent upon any port clock change."
    ::= { systemsEvents 7 }

moduleFailTrap NOTIFICATION-TYPE
      STATUS  current
      DESCRIPTION
	  "This trap is sent upon a module failure."
    ::= { systemsEvents 8 }
	
moduleInitFailTrap NOTIFICATION-TYPE
    STATUS current
      DESCRIPTION
	  "This trap is sent upon a module initialization failure."
	::= { systemsEvents 9 }

clkSrcChangeTrap NOTIFICATION-TYPE
      STATUS  current
      DESCRIPTION
	  "This trap is sent upon any change in Clock Source."
    ::= { systemsEvents 10 }

agnUploadDataTrap  NOTIFICATION-TYPE
     STATUS current
     DESCRIPTION     
     "This trap is sent upon an upload data session termination.
     For more details see product specification."
     ::= { systemsEvents 11 }

enrollmentTrap  NOTIFICATION-TYPE
     STATUS current
     DESCRIPTION     
     "This trap is a periodically trap, which sent to manager 
     untill Agent get any response (Get or Set) from this manager."
     ::= { systemsEvents 12 }

agnPowerFailureTrap  NOTIFICATION-TYPE
     STATUS current
     DESCRIPTION     
     "This trap is sent upon power failure. It is applicable for 
     the following devices:
     1. Devices having one PS unit, which sense the failure in advance,
        and still have time to send this trap before it goes off.
     2. Devices having 2 PS units and send this trap in order to notify a
        failure in one of the units."
     ::= { systemsEvents 13 }

agnFanFailureTrap  NOTIFICATION-TYPE
     STATUS current
     DESCRIPTION     
     "This trap is sent upon fan failure/recovery."
 	 ::= { systemsEvents 14 }

agnSystemParameterChangeTrap   NOTIFICATION-TYPE
	OBJECTS			{systemParameter}
    STATUS  current
	DESCRIPTION
	"This trap is sent upon any change of the systemParameter value."
	 ::= { systemsEvents 15 }

 
-- CONFIG DATABASE CHECKSUM ERROR  
agnConfigDBChecksumError  NOTIFICATION-TYPE
      OBJECTS			{alarmSeverity}
      STATUS  current
      DESCRIPTION
      "This trap indicates that the database currently
      stored in the non-volatile memory of the device is corrupted"	
      ::= { systemsEvents 16 }

-- ALARM BUFFER OVERFLOW
agnAlarmBufferOverflow  NOTIFICATION-TYPE		
      OBJECTS {alarmSeverity}
      STATUS  current
      DESCRIPTION
      "This trap indicates that the quantity of 
      alarm messages which have been written 
      in the alarm buffer, since the last clear command,
      exceeds predefined threshold. (Buffer size) 
      The new alarms are overwriting the oldest alarms 
      (the first alarms written in the buffer).
      For LA-110,threshold value is 200 alarms."
      ::= { systemsEvents 17 }

-- ALARM BUFFER CLEAR	
agnAlarmBufferClear NOTIFICATION-TYPE		
      OBJECTS {alarmSeverity}
      STATUS  current
      DESCRIPTION
      "This trap indicates that 
       alarm buffer has been cleared."	
      ::= { systemsEvents 18 }


-- PARAMETER CHANGES IN DB DUE TO UPGRADE PROCESS	
agnParametersValueChanged NOTIFICATION-TYPE		
      OBJECTS {alarmSeverity}
      STATUS  current
      DESCRIPTION
      "This trap indicates that due to software upgrade, 
       some of the parameters are assigned new values"	
      ::= { systemsEvents 19 }

-- (SHDSL) INTERFACE SW VERSION INCOMPATIBLE WITH HW	
agnDriverSwMismatch NOTIFICATION-TYPE		
      OBJECTS {alarmSeverity,ifAlias}
      STATUS  current
      DESCRIPTION
      "There is mismatch between the SW driver and 
       the HW of the device uplink interface."	
      ::= { systemsEvents 20 }

-- DEVICE SYNCHRONIZED ON LESS THAN CONFIGURED BANDWIDTH
agnActualLowRate NOTIFICATION-TYPE		
      OBJECTS {alarmSeverity}
      STATUS  current
      DESCRIPTION
      "The main link is synchronized 
       at a rate lower than expected."	
      ::= { systemsEvents 21 }

xModemFileTransferStatusTrap  NOTIFICATION-TYPE
     OBJECTS       { trapVal }
     STATUS current
     DESCRIPTION     
     "This trap is sent in the following cases:
      - When an xModem File Transfer Session begins. In this case,
        the trapVal.1 string sent will be: 'Start'.
      - When an xModem File Transfer Session ends. In this case,
        the trapVal.1 string sent will be one of the following,
        according to the way the session ended :
        - 'End: OK'
        - 'End: Failed'   "
     ::= { systemsEvents 22 }

agnStationClkFailureTrap  NOTIFICATION-TYPE
     STATUS current
     DESCRIPTION     
     "This trap is sent upon Station Clock failure."
     ::= { systemsEvents 23 }

successfulLogin  NOTIFICATION-TYPE
     STATUS current
     DESCRIPTION     
     "This trap is sent when a user performed successful Login via 
      Terminal/Telnet/Web. This trap is used when the device is located
      at End-User's premises while management is at Service Provider's 
      premises."
     ::= { systemsEvents 24 }

failedLogin  NOTIFICATION-TYPE
     STATUS current
     DESCRIPTION     
     "This trap is sent when a user tried to Login via Terminal/Telnet/Web
      and failed. This trap is used when the device is located
      at End-User's premises while management is at Service Provider's 
      premises."
     ::= { systemsEvents 25 }

modlChangeTrap  NOTIFICATION-TYPE
     STATUS current
     DESCRIPTION     
     "This trap is sent whenever a module is inserted or removed.
      The trap should include the new module type (e.g. modlParamType)."
     ::= { systemsEvents 26 }

licenseUpdateTrap  NOTIFICATION-TYPE
     STATUS current
     DESCRIPTION     
     "This trap is sent whenever a license is successfully downloaded
      or whenever a license's demo duration is expired."
     ::= { systemsEvents 27 }

agnClkSrcStateChangeTrap  NOTIFICATION-TYPE
     OBJECTS       { agnClkSrcPortState }
     STATUS	current
     DESCRIPTION     
	 "The trap is sent upon change in Recovery Clock State."
     ::= { systemsEvents 28 }

agnSelfTestResultChangeTrap NOTIFICATION-TYPE
	 STATUS  current
 	 DESCRIPTION
	 "The trap is sent upon each change in the result of a Self State operation."
	 ::= { systemsEvents 29 }

agnCurrClkStateChangeTrap NOTIFICATION-TYPE
     OBJECTS       { agnCurrClkState }
     STATUS	current
     DESCRIPTION     
	 "The trap is sent upon change in the state of the current (active) clock,
	  when it is a Recovery Clock." 
     ::= { systemsEvents 30 }

agnClkSrcFrequencyAlarmTrap  NOTIFICATION-TYPE
     STATUS	current
     DESCRIPTION     
	 "The trap is sent upon Recovered Clock Frequency alarm."
     ::= { systemsEvents 31 }

prtLoopDetectTrap NOTIFICATION-TYPE
	STATUS current
	DESCRIPTION
	"This trap is sent upon Loop Detect (On/Off) on a certain port."
	::= { systemsEvents 32 }


-----------------------------------
-- System Common Trap Definitions
-----------------------------------

--      RESERVED      ::= { systemsEvents 40 }

--SYSTEM DEVICE TEMPERATURE ORA

systemDeviceTemperatureOra   NOTIFICATION-TYPE
	OBJECTS { alarmEventLogSourceName, alarmEventLogAlarmOrEventId, alarmEventLogDescription, 
     alarmEventLogSeverity, alarmEventLogDateAndTime, alarmEventReason, 
     sysName, agnThresholdCurrent, agnThresholdMin, 
     agnThresholdMax, agnThresholdUom } 
      STATUS  current
      DESCRIPTION
      "This trap indicates that Device Temprature is
      above or below range.
      "
      ::= { systemsEvents 41 }

-- SYSTEM SOFTWARE INSTALL START
--  { systemsEvents 42 } Moved to SwPackHndl.txt

-- SYSTEM SOFTWARE INSTALL END
--  { systemsEvents 43 } Moved to SwPackHndl.txt

-- RESERVED
--      ::= { systemsEvents 44}

--SYSTEM ALTERNATE CONFIGURATION LOADED

systemAlternateConfigLoaded  NOTIFICATION-TYPE
	OBJECTS { alarmEventLogSourceName, alarmEventLogAlarmOrEventId, alarmEventLogDescription, 
     alarmEventLogSeverity, alarmEventLogDateAndTime, alarmEventReason, 
     sysName, configLoadObjType } 
      STATUS  current
      DESCRIPTION
      "This trap indicates that one of the following files:
      factory-default-config,
      rollback-config,
      user-default-config
      or other file
      was loaded as running-config.

      Note that this notification should be sent only
      if running-config is not startup-config
      "
      ::= { systemsEvents 45}

--SYSTEM CONFIGURATION SANITY

systemConfigurationSanity    NOTIFICATION-TYPE
	OBJECTS { alarmEventLogSourceName, alarmEventLogAlarmOrEventId, alarmEventLogDescription, 
     alarmEventLogSeverity, alarmEventLogDateAndTime, alarmEventReason, 
     sysName, fileSystemValidIndication, configLoadErrorPolicy } 
      STATUS  current
      DESCRIPTION
      " This notification MUST be sent if error has occurred while loading a configuration file.
      It MUST only be sent once per file and only if the error policy is either 'ignore' or 'stop' "
      ::= { systemsEvents 47}

--   ::= {systemsEvents 48} reserved

systemDyingGasp         NOTIFICATION-TYPE
	OBJECTS { alarmEventLogSourceName, alarmEventLogAlarmOrEventId, alarmEventLogDescription, 
     alarmEventLogSeverity, alarmEventLogDateAndTime, alarmEventReason, 
     sysName, entPhysicalDescr } 
      STATUS  current
      DESCRIPTION
      "This Trap Indicates power Dying Gasp"
      ::= { systemsEvents 49}

systemDyingGaspRecovery          NOTIFICATION-TYPE
	OBJECTS { alarmEventLogSourceName, alarmEventLogAlarmOrEventId, alarmEventLogDescription, 
     alarmEventLogSeverity, alarmEventLogDateAndTime, alarmEventReason, 
     sysName } 
      STATUS  current
      DESCRIPTION
      "This Trap Indicates power Dying Gasp Recovery"
      ::= { systemsEvents 50}


systemTraceMsgFatalError              NOTIFICATION-TYPE
	OBJECTS { alarmEventLogSourceName, alarmEventLogAlarmOrEventId, alarmEventLogDescription, 
     alarmEventLogSeverity, alarmEventLogDateAndTime, alarmEventReason, 
     sysName, resetInformationFileName, resetInformationLineNumber } 
      STATUS  current
      DESCRIPTION
      "This Trap indicates that a critical error has occured in the device.
       A corresponding message was added to the Trace Log Buffer."
      ::= { systemsEvents 51}

systemTraceMsgException              NOTIFICATION-TYPE
	OBJECTS { alarmEventLogSourceName, alarmEventLogAlarmOrEventId, alarmEventLogDescription, 
     alarmEventLogSeverity, alarmEventLogDateAndTime, alarmEventReason, 
     sysName, resetInformationPC, resetInformationExceptionCause } 
      STATUS  current
      DESCRIPTION
      "This Trap indicates that an error has occured in the device.
       A corresponding message was added to the Trace Log Buffer."
      ::= { systemsEvents 52}

systemDeviceStartup                     NOTIFICATION-TYPE
	OBJECTS { alarmEventLogSourceName, alarmEventLogAlarmOrEventId, alarmEventLogDescription, 
     alarmEventLogSeverity, alarmEventLogDateAndTime, alarmEventReason, 
     sysName, resetInformationLastReset } 
      STATUS  current
      DESCRIPTION
      "This Trap indicates that warm start or cold start of the device has occurred."
      ::= { systemsEvents 55 }
--  Reserved  ::= { systemsEvents 56 }

--systemConfigurationMismatch       NOTIFICATION-TYPE
--      OBJECTS  {alarmEventLogSourceName, alarmEventLogAlarmOrEventId,
--      alarmEventLogDescription, alarmEventLogSeverity,
--     alarmEventLogDateAndTime, alarmEventReason,
--      sysName,entPhysicalDescr,entPhysicalXConfigMismatchReason}
--      STATUS  current
--      DESCRIPTION
--      "This Trap indicates that a configuration error exists in the system level."
--      ::= { systemsEvents 57 }

systemHardwareFailure       NOTIFICATION-TYPE
	OBJECTS { alarmEventLogSourceName, alarmEventLogAlarmOrEventId, alarmEventLogDescription, 
     alarmEventLogSeverity, alarmEventLogDateAndTime, alarmEventReason, 
     sysName, entPhysicalDescr } 
      STATUS  current
      DESCRIPTION
      "This Trap indicates that a Hardware Failure has occured."
      ::= { systemsEvents 58 }

--      ::= { systemsEvents 61} exists in SwPackHndl.txt
--      ::= { systemsEvents 62} exists in SwPackHndl.txt

systemStartupConfigUnconfirmed   NOTIFICATION-TYPE
	OBJECTS { alarmEventLogSourceName, alarmEventLogAlarmOrEventId, alarmEventLogDescription, 
     alarmEventLogSeverity, alarmEventLogDateAndTime, alarmEventReason, 
     sysName } 
      STATUS  current
      DESCRIPTION
      "This Trap is sent during SW installation, if the user asked for a startup configuration
       confirmation and the device didn't receive a confirmation from the user.
       If the user didn't ask for confirmation - this trap will not be sent.
      "
      ::= { systemsEvents 63 }

fanFailure       NOTIFICATION-TYPE
	OBJECTS { alarmEventLogSourceName, alarmEventLogAlarmOrEventId, alarmEventLogDescription, 
     alarmEventLogSeverity, alarmEventLogDateAndTime, alarmEventReason, 
     entPhysicalAlias } 
      STATUS  current
      DESCRIPTION
      "This Trap indicates that there is a failure on the current fan."
      ::= { systemsEvents 64 }

--      ::= { systemsEvents 65 }


-- ***********************
-- systemFeConfigurationMismatch        NOTIFICATION-TYPE
--      OBJECTS  {alarmEventLogSourceName, alarmEventLogAlarmOrEventId,
--      alarmEventLogDescription, alarmEventLogSeverity,
--      alarmEventLogDateAndTime, alarmEventReason,
--      sysName,entPhysicalDescr,entPhysicalXConfigMismatchReason}
--      STATUS  current
--      DESCRIPTION
--      "This Trap indicates that a Configuration Mismatch error exists in the system level in the Far End."
--      ::= { systemsEvents 66 }






   systemSuccessfulLogin           NOTIFICATION-TYPE
	OBJECTS { alarmEventLogSourceName, alarmEventLogAlarmOrEventId, alarmEventLogDescription, 
     alarmEventLogSeverity, alarmEventLogDateAndTime, alarmEventReason, 
     sysName, deviceAccessUserName, deviceAccessIpAddress, 
     deviceAccessMethod, deviceAccessAuthenticationMethod, deviceAccessSessionId } 
         STATUS  current
         DESCRIPTION
         "This Trap indicates that a successful login occurred."
         ::= { systemsEvents 70 }

   systemFailedLogin              NOTIFICATION-TYPE
	OBJECTS { alarmEventLogSourceName, alarmEventLogAlarmOrEventId, alarmEventLogDescription, 
     alarmEventLogSeverity, alarmEventLogDateAndTime, alarmEventReason, 
     sysName, deviceAccessUserName, deviceAccessIpAddress, 
     deviceAccessMethod, deviceAccessAuthenticationMethod, deviceAccessLoginStatus } 
         STATUS  current
         DESCRIPTION
         "This Trap indicates that an unsuccessful login occurred."
         ::= { systemsEvents 71 }

   systemLogout   NOTIFICATION-TYPE
	OBJECTS { alarmEventLogSourceName, alarmEventLogAlarmOrEventId, alarmEventLogDescription, 
     alarmEventLogSeverity, alarmEventLogDateAndTime, alarmEventReason, 
     sysName, deviceAccessUserName, deviceAccessIpAddress, 
     deviceAccessMethod, deviceAccessAuthenticationMethod, deviceAccessSessionId, 
     deviceAccessLogoutStatus } 
         STATUS  current
         DESCRIPTION
         "This Trap indicates that logout was performed from the device. "
         ::= { systemsEvents 72 }

systemTrapHardSyncStart           NOTIFICATION-TYPE
	OBJECTS { alarmEventLogSourceName, alarmEventLogAlarmOrEventId, alarmEventLogDescription, 
     alarmEventLogSeverity, alarmEventLogDateAndTime, alarmEventReason, 
     sysName } 
      STATUS  current
      DESCRIPTION
      "This Trap indicates that hard trap synchronization process between the device
       and NMS has started."
      ::= { systemsEvents 77}

systemTrapHardSyncEnd           NOTIFICATION-TYPE
	OBJECTS { alarmEventLogSourceName, alarmEventLogAlarmOrEventId, alarmEventLogDescription, 
     alarmEventLogSeverity, alarmEventLogDateAndTime, alarmEventReason, 
     sysName } 
      STATUS  current
      DESCRIPTION
      "This Trap indicates that hard trap synchronization process between the device
       and NMS has ended."
      ::= { systemsEvents 78}


-- { systemsEvents 79-81 } exist in ConfigChange.txt

systemUserReset           NOTIFICATION-TYPE
	OBJECTS { alarmEventLogSourceName, alarmEventLogAlarmOrEventId, alarmEventLogDescription, 
     alarmEventLogSeverity, alarmEventLogDateAndTime, alarmEventReason, 
     sysName, resetInformationReason } 
      STATUS  current
      DESCRIPTION
      "This Trap Indicates that the user reset the device."
      ::= { systemsEvents 82}

-- FAULT PROPAGATION
faultPropagation  NOTIFICATION-TYPE
	OBJECTS { alarmEventLogSourceName, alarmEventLogAlarmOrEventId, alarmEventLogDescription, 
     alarmEventLogSeverity, alarmEventLogDateAndTime, alarmEventReason, 
     alarmForwardingDescr, alarmForwardingAction, alarmForwardingActiveCause } 
      STATUS  current
      DESCRIPTION
      "This trap indicates that an interface/port/card received fault propagation.
      "
      ::= { systemsEvents 87}




-- systemsEvents 89 exists in radAcl.txt

systemResourceOverflow      NOTIFICATION-TYPE
	OBJECTS { alarmEventLogSourceName, alarmEventLogAlarmOrEventId, alarmEventLogDescription, 
     alarmEventLogSeverity, alarmEventLogDateAndTime, alarmEventReason, 
     sysName, systemResourceLastError } 
      STATUS  current
      DESCRIPTION
      "This notification is sent when a system resource overflows."
      ::= { systemsEvents 90}

systemRemoteTerminalStarted      NOTIFICATION-TYPE
	OBJECTS { alarmEventLogSourceName, alarmEventLogAlarmOrEventId, alarmEventLogDescription, 
     alarmEventLogSeverity, alarmEventLogDateAndTime, alarmEventReason, 
     sysName, deviceAccessUserName, deviceAccessIpAddress, 
     deviceAccessMethod, deviceAccessSessionId, deviceAccessRemoteIpAddress, 
     deviceAccessRemoteTerminal } 
      STATUS  current
      DESCRIPTION
      "This notification is sent when remote terminal to a virtual engine starts."
      ::= { systemsEvents 91}

systemRemoteTerminalEnded      NOTIFICATION-TYPE
	OBJECTS { alarmEventLogSourceName, alarmEventLogAlarmOrEventId, alarmEventLogDescription, 
     alarmEventLogSeverity, alarmEventLogDateAndTime, alarmEventReason, 
     sysName, deviceAccessUserName, deviceAccessIpAddress, 
     deviceAccessMethod, deviceAccessRemoteIpAddress, deviceAccessRemoteTerminal } 
      STATUS  current
      DESCRIPTION
      "This notification is sent when remote terminal to a virtual engine is terminated,
      either by a user or by an inactivity timeout."
      ::= { systemsEvents 92}

systemNtpAccuracyOutOfLimit      NOTIFICATION-TYPE
	OBJECTS { alarmEventLogSourceName, alarmEventLogAlarmOrEventId, alarmEventLogDescription, 
     alarmEventLogSeverity, alarmEventLogDateAndTime, alarmEventReason, 
     sysName, systemNtpLockingStatus } 
      STATUS  current
      DESCRIPTION
      "This alarm notification is sent when NTP client accuracy becomes 'out of limit'."
      ::= { systemsEvents 93}

systemSummerTimeStarted  NOTIFICATION-TYPE
	OBJECTS { alarmEventLogSourceName, alarmEventLogAlarmOrEventId, alarmEventLogDescription, 
     alarmEventLogSeverity, alarmEventLogDateAndTime, alarmEventReason, 
     sysName } 
    STATUS  deprecated
    DESCRIPTION
    "This event is sent when the agent enters summer time.
     The event was obsoleted by systemTimeChanged."
    ::= { systemsEvents 95 }


systemSummerTimeEnded  NOTIFICATION-TYPE
	OBJECTS { alarmEventLogSourceName, alarmEventLogAlarmOrEventId, alarmEventLogDescription, 
     alarmEventLogSeverity, alarmEventLogDateAndTime, alarmEventReason, 
     sysName } 
    STATUS  deprecated
    DESCRIPTION
    "This event is sent when the agent exits summer time.
     The event was obsoleted by systemTimeChanged."
    ::= { systemsEvents 96 }

systemFileOverflow NOTIFICATION-TYPE
	OBJECTS { alarmEventLogSourceName, alarmEventLogAlarmOrEventId, alarmEventLogDescription, 
     alarmEventLogSeverity, alarmEventLogDateAndTime, alarmEventReason, 
     sysName, fileSystemValidIndication } 
    STATUS  current
    DESCRIPTION
    "This event is sent if a file reaches its maximum size.
     The file name can be inferred from the
     indices of the fileSystemValidIndication attached variable."
    ::= { systemsEvents 97 }

systemTimeChanged  NOTIFICATION-TYPE
	OBJECTS { alarmEventLogSourceName, alarmEventLogAlarmOrEventId, alarmEventLogDescription, 
     alarmEventLogSeverity, alarmEventLogDateAndTime, alarmEventReason, 
     sysName, systemLastTimeChangeOffset, systemLastTimeChangeReason } 
    STATUS  current
    DESCRIPTION
    "This event is sent when the system local time changes."
    ::= { systemsEvents 98 }
    
systemTimeSourceChanged  NOTIFICATION-TYPE
	OBJECTS { alarmEventLogSourceName, alarmEventLogAlarmOrEventId, alarmEventLogDescription, 
     alarmEventLogSeverity, alarmEventLogDateAndTime, alarmEventReason, 
     sysName, systemNtpCurrentSource } 
    STATUS  current
    DESCRIPTION
    "This event is sent when the source providing time for the system changes."
    ::= { systemsEvents 99 }

-- Serial port disabled
systemSerialPortDisabled NOTIFICATION-TYPE
	OBJECTS { alarmEventLogSourceName, alarmEventLogAlarmOrEventId, alarmEventLogDescription, 
     alarmEventLogSeverity, alarmEventLogDateAndTime, alarmEventReason, 
     sysName } 
    STATUS current
    DESCRIPTION
    "This trap is sent if the serial port is disabled."
    ::= { systemsEvents 100 }

-- Serial port enabled
systemSerialPortEnabled NOTIFICATION-TYPE
	OBJECTS { alarmEventLogSourceName, alarmEventLogAlarmOrEventId, alarmEventLogDescription, 
     alarmEventLogSeverity, alarmEventLogDateAndTime, alarmEventReason, 
     sysName } 
    STATUS current
    DESCRIPTION
    "This trap is sent if the serial port is enabled."
    ::= { systemsEvents 101 }

-- Factory default button activated
systemFactoryDefaultButtonPushed NOTIFICATION-TYPE
	OBJECTS { alarmEventLogSourceName, alarmEventLogAlarmOrEventId, alarmEventLogDescription, 
     alarmEventLogSeverity, alarmEventLogDateAndTime, alarmEventReason, 
     sysName } 
    STATUS current
    DESCRIPTION
    "This trap is sent if the factory default button has been pressed 
     for five seconds, triggering the factory-default command."
    ::= { systemsEvents 102 }

--SFP REMOVED
sfpRemoved NOTIFICATION-TYPE
	OBJECTS { alarmEventLogSourceName, alarmEventLogAlarmOrEventId, alarmEventLogDescription, 
     alarmEventLogSeverity, alarmEventLogDateAndTime, alarmEventReason, 
     ifAlias } 
      STATUS  current
      DESCRIPTION
      "This trap indicates SFP not installed
      "
      ::= { sfpEvents 3}

deviceAccessTable             OBJECT-TYPE
    SYNTAX      SEQUENCE OF DeviceAccessEntry
    MAX-ACCESS  not-accessible
    STATUS      current
    DESCRIPTION
        "This table trace tdevice access attempts  "
    ::= {  agnAccess 6 }

deviceAccessEntry OBJECT-TYPE
    SYNTAX      DeviceAccessEntry
    MAX-ACCESS  not-accessible
    STATUS      current
    DESCRIPTION  "This table  ."
    INDEX {  deviceAccessIndex}
    ::= { deviceAccessTable  1 }

DeviceAccessEntry ::= SEQUENCE {
    deviceAccessIndex                   Unsigned32,
    deviceAccessLoginTime               DateAndTime,
    deviceAccessLoginStatus             INTEGER,
    deviceAccessUserName                SnmpAdminString,
    deviceAccessIpAddressType           InetAddressType,
    deviceAccessIpAddress               InetAddress,
    deviceAccessMethod                  INTEGER,
    deviceAccessAuthenticationMethod    INTEGER,
    deviceAccessSessionId               Unsigned32,
    deviceAccessLogoutTime              DateAndTime,
    deviceAccessLogoutStatus            INTEGER,
    deviceAccessRemoteTerminal          INTEGER,
    deviceAccessRemoteIpAddressType     InetAddressType,
    deviceAccessRemoteIpAddress         InetAddress,
    deviceAccessRemoteLoginTime         DateAndTime 
 }

deviceAccessIndex   OBJECT-TYPE
    SYNTAX          Unsigned32
    MAX-ACCESS      not-accessible
    STATUS          current
    DESCRIPTION  "running index"
    ::= { deviceAccessEntry  1 }

deviceAccessLoginTime   OBJECT-TYPE
    SYNTAX          DateAndTime
    MAX-ACCESS      read-only
    STATUS          current
    DESCRIPTION
    "The date and time that the user tried to login.
     Always in UTC format."
    ::= { deviceAccessEntry  2 }

deviceAccessLoginStatus   OBJECT-TYPE
    SYNTAX          INTEGER
    {
    success             (1),
    maxSessionExceeded  (2),
    wrongUser           (3),
    wrongPassword       (4),
    authenticationServerUnavailable (5)
    }
    MAX-ACCESS      read-only
    STATUS          current
    DESCRIPTION
    "Login attempt Status"
    ::= { deviceAccessEntry 3}

deviceAccessUserName     OBJECT-TYPE
    SYNTAX          SnmpAdminString
    MAX-ACCESS      read-only
    STATUS          current
    DESCRIPTION
    "Login attempt User Name"
    ::= { deviceAccessEntry 4}

deviceAccessIpAddressType OBJECT-TYPE
    SYNTAX          InetAddressType
    MAX-ACCESS      read-only
    STATUS          current
    DESCRIPTION
    "Type of the IP Address designated by deviceAccessIpAddress"
    ::= { deviceAccessEntry 5}

deviceAccessIpAddress OBJECT-TYPE
    SYNTAX          InetAddress
    MAX-ACCESS      read-only
    STATUS          current
    DESCRIPTION
        "the IP Address of the user
        (the value will be 0 if the
        deviceAccessMethod = localTerminal(1)
        "
    ::= { deviceAccessEntry 6}

deviceAccessMethod   OBJECT-TYPE
    SYNTAX          INTEGER
    {
    localTerminal   (1),
    telnet          (2),
    ssh             (3),
    http            (4),
    https           (5),
    ssl             (6)
    }
    MAX-ACCESS      read-only
    STATUS          current
    DESCRIPTION
    "Method used to access the device"
    ::= { deviceAccessEntry 7}

deviceAccessAuthenticationMethod    OBJECT-TYPE
    SYNTAX          INTEGER
    {
    local       (1),
    radius      (2),
    tacacsPlus  (3),
    notApplicable (255)
    }
    MAX-ACCESS      read-only
    STATUS          current
    DESCRIPTION
    "The method used to authenticate a logged-in user.
     notApplicable is used if the login session is rejected
     due to lack of resources, before the authentication stage"
    ::= { deviceAccessEntry 8}

deviceAccessSessionId  OBJECT-TYPE
    SYNTAX          Unsigned32
    MAX-ACCESS      read-only
    STATUS          current
    DESCRIPTION
    " The session ID. If login attempt failed,
      the value will be 0xFFFFFFFF"
    ::= { deviceAccessEntry 9}

deviceAccessLogoutTime  OBJECT-TYPE
    SYNTAX          DateAndTime
    MAX-ACCESS      read-only
    STATUS          current
    DESCRIPTION
    " The date and time that the session ended.
      This information will be filled only if the login succeed.
      Always in UTC format"
    ::= { deviceAccessEntry 10}

deviceAccessLogoutStatus    OBJECT-TYPE
    SYNTAX          INTEGER
    {
    userLogoff                 (1),
    inactivityTimeout     (2),
    awaitingLogout       (3) ,  -- the login session is activated yet and awaiting to be logged out.
    userLoginChanged  (4),  -- the initial user login has been changed to another user
    notApplicable          (5)   -- not applicable
    }
    MAX-ACCESS      read-only
    STATUS          current
    DESCRIPTION
    "The status and reason of logout"
    ::= { deviceAccessEntry 11}

deviceAccessRemoteTerminal    OBJECT-TYPE
    SYNTAX          INTEGER
    {
    inactive       (1),
    serialInternal (101),
    telnet         (102),
    ssh            (103)
    }
    MAX-ACCESS      read-only
    STATUS          current
    DESCRIPTION
    "The state of a remote session, which may be
     opened from the CLI session reperesented by this raw:
     inactive(1)- No active remote session
     serialInternal(101) - Active internal serial remote session (e.g. x86)
     telnet(102) - Active telnet remote session
     ssh(103) - Active SSH remote session"
    ::= { deviceAccessEntry 13}

deviceAccessRemoteIpAddressType OBJECT-TYPE
    SYNTAX          InetAddressType
    MAX-ACCESS      read-only
    STATUS          current
    DESCRIPTION
    "If a remote IP (i.e. not over serial connection) session was opened
     from the CLI session represented by this entry, this object holds
     the type of the destination IP address of that session.
     Otherwise, it returns unknown(0)."
    ::= { deviceAccessEntry 14}

deviceAccessRemoteIpAddress OBJECT-TYPE
    SYNTAX          InetAddress
    MAX-ACCESS      read-only
    STATUS          current
    DESCRIPTION
    "If a remote IP (i.e. not over serial connection) session was opened
     from the CLI session represented by this entry, this object holds
     the destination IP address of that session.
     Otherwise, it is a zero-length string."
    ::= { deviceAccessEntry 15}

deviceAccessRemoteLoginTime OBJECT-TYPE
    SYNTAX          DateAndTime
    MAX-ACCESS      read-only
    STATUS          current
    DESCRIPTION
    "Date and time (UTC) at which the user cnnected to a remote terminal."
    ::= { deviceAccessEntry  16 }

    -- ****************************************************************



--
-- File: FaultMng.txt
--
-- Fault Management Module
--
fmObjects OBJECT IDENTIFIER ::= { radGen 5 }

alarmEventConfig       OBJECT IDENTIFIER ::= { fmObjects 1 }   -- Node for configuration and Active Alarms
alarmEventLog          OBJECT IDENTIFIER ::= { fmObjects 2 }   -- Node for Log
alarmEventStatistics   OBJECT IDENTIFIER ::= { fmObjects 3 }   -- Node for statistics


-- Textual Conventions

SourceId  ::= TEXTUAL-CONVENTION
    STATUS current
    DESCRIPTION
            "A unique identifier for a source."
    SYNTAX   Unsigned32

--
-- Alarm and Event Source
--
  AlarmEventSourceType ::= TEXTUAL-CONVENTION
    STATUS current
    DESCRIPTION
        "A unique Source Type for alarm and for event."
    SYNTAX  INTEGER {
        security           (10000),
        system             (20000),
        fan                (20100),
        powerSupply        (20200),
        systemFe           (20300),  -- System Far End
        alarmInput         (20400),
        abm                (20600),  -- Available Bandwidth Monitoring
        clock              (30000),
        stationClock       (30100),  -- Input Port of the External Clock Source (Building Integrated Timing System)
        ptpRecovered       (30200),  -- IEEE 1588 Slave
        clockDomain        (30300),
        ptpRecoveredMaster (30400),  -- IEEE 1588 Slave's Master
        clockDomainSource  (30500),
        ptpdistributed     (30600),  -- IEEE 1588 Master
        gnss               (30700),  -- GNSS (Clock source from Global Navigation Satellite System, e.g. GPS)
        g82751Recovered    (30800),  -- G.8275.1 Recovered (Slave) Clock
        g82751Master       (31000),  -- G.8275.1 Master Clock
        card               (40000),
        smartSfp           (40100),
        eth                (50000),  -- ETH (10/100/1000)
        ethFe              (50100),  -- ETH Far End
        intEth             (50200),  -- Internal Ethernet for VE (Virtual Engine) device
        xVirtualPort       (50300),  -- 802.1X virtual port
        mngEth             (50400),  -- Management Ethernet 
        muxEthTdm          (60000),  -- Optical uplinks in Optimux device, MP, LRS.
        muxEthTdmFe        (61000),
        dsl                (70000),
        vdsl               (70100),
        shdsl              (70200),
        adsl               (70300),
        pcs                (70400),
        shdslFe            (70500),  -- SHDSL Far End
        vdsl2              (70600),
        bri                (80000),  -- ISDN
        briFe              (80100),  -- BRI Far End
        voice              (90000),  -- Voice
        sdhSonet           (100000),
        vcVt               (100100), -- Low  order Virtual Container
        path               (100200), -- High order Virtual Container
        ds1                (110000),
        ds1Opt             (111000), -- DS1 optical, C37.94
        e1                 (110100),
        t1                 (110200),
        j1                 (110300),
        e1i                (110400), -- Internal E1
        t1i                (110500),
        j1i                (110600),
        e1Fe               (110700), -- Far End E1 (over ETH)
        t1Fe               (110800), -- Far End T1 (over ETH)
        j1Fe               (110900), -- Far End J1 (over ETH)
        ds3                (120000),
        e3                 (120100),
        t3                 (120200),
        ds0Bundle          (120300), 
        ds0G703            (120400),
        vcg                (130000), -- Virtual Concatination Group
        atm                (140000),
        atmPort            (140100),
        atmVp              (140200),
        atmVc              (140300),
        serial             (150000),
        serialBundle       (150100), -- LS-12 card in MP: D channel
        serialFe           (150200),
        ima                (160000),
        bridge             (170000),
        bridgePort         (170100),
        logicalMac         (180000),
        ces                (190000),
        etpPort            (200000),
        etp                (200100),
        flow               (210000),
        svi                (220000),
        gfp                (230000), -- Generic Framing Procedure
        hdlc               (240000),
        lag                (250000),
        mpls               (260000),
        oam                (270000),
        oamEfm             (270100),
        oamCfmMep          (270200),
        oamCfmService      (270300),
        oamCfmDestNe       (270400),
        oamCnode           (270500),
        oamCfmRMep         (270600),
        ppp                (280000),
        mlppp              (280100),
        protection         (290000),
        aps                (290100), -- Sonet Linear Automatic Protection Switching (RFC3498)
        eps                (290200), -- Ethernet Protection Switching (G.8031)
        erp                (290300), -- Ethernet Ring Protection (G.8032)
        protectionMain     (290400),
        protectionIo       (290500),
        protectionVcPath   (290600),
        protectionTdm      (290700),
        protectionEth      (290800),
        protectionPw       (290900),
        protectionTdmMux   (291000),
        erpPort            (291100),
        router             (300000),
        routerInterface    (300100),
        ospf               (300200),
        ospfNeighbor       (300300),
        ospfInterface      (300400),
        bgp                (300600), -- Boarder Gateway Protocol
        ipBfd              (300800), -- IP-BFD Protocol
        twampSession       (300900),
        twampPeer          (301000),
        twampResponder     (301100),
        tunnel             (301200),
        pw                 (310000), -- Pseudowire
        cmdChannel         (320000), -- Teleprotection (tp) Cmd Channel
        cmdIn              (320100), -- Teleprotection (tp) Cmd In
        cmdOut             (320200), -- Teleprotection (tp) Cmd Out
        cellular           (320300)  -- Cellular
     }


AlarmEventId ::= TEXTUAL-CONVENTION
    STATUS current
    DESCRIPTION
            "A unique identifier for alarms and events."
    SYNTAX  INTEGER {
    ---===============================================================
    --                             ALARM ID         ALARM NAME        |
    --=================================================================

       systemLicenseInvalid             (20001), -- license_invalid

       systemDeviceTemperatureOra       (20002), -- device_temperature_ora

       systemEmergencyLicenseActive     (20003), -- emergency_license_active
       systemConfigurationMismatch      (20004), -- configuration_mismatch
       systemHardwareFailure            (20005), -- hardware_failure_fe
       systemInterfaceMismatch          (20006), -- interface_mismatch
       systemNoInterface                (20007), -- no_interface
       systemSwPackCorrupted            (20008), -- sw_pack_corrupted,
       systemTraceMsgProtoMemAllocErr   (20009), -- trace_msg_proto_mem_alloc_err
       systemPmProcessDisabled          (20010), -- pm_process_disabled
       systemMainCardsSync              (20011), -- main_cards_sync
       systemSourceClockFailure         (20012), -- source_clock_failure
       systemNtpAccuracyOutOfLimit      (20013), -- ntp_accuracy_out_of_limit
       systemLowMemory                  (20014), -- low_memory
       systemCriticalLowMemory          (20015), -- critical_low_memory


       systemPoePowerDeliveryExceeded   (20016), -- Poe Power Delivery Exceeded
       systemNewSwFromBootMismatch      (20017), -- new_sw_from_boot_mismatch      
--     systemDhcpIpLeaseFailure         (20040), DHCP_IP_LEASE_FAILURE

       fanFailure                       (20101), -- fan_failure

       powerDeliveryFailure             (20201), -- power_delivery_failure
       powerInOra                       (20202), -- power_in_ora
       powerInLow                       (20203), -- power_in_low


       alarmInput                       (20401), -- alarm_input


       stationClockAis                  (30102), -- ais
       stationClockLof                  (30103), -- lof
       stationClockLos                  (30104), -- los

       ptpRecoveredNoPtpMaster              (30201), -- no_ptp_master
       ptpRecoveredInvalidFreqAccuracy      (30202), -- invalid_frequency_accuracy
       ptpRecoveredInvalidTimeAccuracy      (30203), -- invalid_time_accuracy
       ptpRecoveredDisqualifiedMaster       (30204), -- disqualified_master

       clockDomainSystemClockUnlock              (30301), -- system_clock_unlock
       clockDomainStationClockQlLow              (30302), -- station_clock_ql_low
       clockDomainStationClockUnlock             (30303), -- station_clock_unlock

       ptpRecoveredMasterSyncFailure             (30401), -- sync_failure
       ptpRecoveredMasterAnnounceFailure         (30402), -- announce_failure
       ptpRecoveredMasterDelayResponseFailure    (30403), -- delay_response_failure

       clockDomainSourceFailure                  (30501), -- source_clock_failure

       ptpMasterUnavailableTod                   (30601),  -- unavailable_tod
       ptpMasterUnavailable1pps                  (30602),  -- unavailable_1pps
       ptpMasterSlavesLimitReached               (30603),  -- slaves_limit_reached

       gnssNotLocked                             (30702), -- not_locked
       gnssHardwareFailure                       (30703), -- hardware_failure

       g82751RecoveredNoMaster                   (30801), -- no_master
       g82751RecoveredFreqOutOfSpec              (30802), -- frequency_accuracy_out_of_specification
       g82751RecoveredTimeOutOfSpec              (30803), -- Time_accuracy_out_of_specification
       g82751RecoveredDisqualMaster              (30804), -- Master_disqualified

       g82751RecoveredSyncFail                   (30805), -- sync_failure
       g82751RecoveredAnnounceFail               (30806), -- announce_failure
       g82751RecoveredDelayRespFail              (30807), -- delay_response_failure

       cardHwFailure                             (40001), -- hardware_failure
       cardMismatch                              (40002), -- card_mismatch
       cardProvisionFailure                      (40003), -- card_provision_failure
       cardUnsupportedSw                         (40004), -- unsupported_software
       cardUnsupportedHw                         (40005), -- unsupported_hardware
       cardImproperRemoval                       (40006), -- card_improper_removal
       cardTemperatureOra                        (40007), -- card_temperature_ora
       cardNoResponse                            (40008), -- card_no_response
       cardInitFailure                           (40009), -- card_initialization_failure
       cardConfigurationMismatch                 (40010), -- configuration_mismatch
       cardLoading                               (40011), -- card_loading
       cardUserInitiatedSwitchover               (40012), -- user_initiated_switchover
       cardFaultPropagation                      (40013), -- fault_propagation 

       smartSfpMismatch                          (40101), -- smart_sfp_mismatch

       ethSfpNoResponse                          (50001), -- sfp_no_response
       ethSfpMismatch                            (50002), -- sfp_mismatch
       ethLos                                    (50003), -- los
       ethSfpRemoved                             (50004), -- sfp_removed
       ethSfpTemperatureOra                      (50005), -- sfp_temperature_ora
       ethSfpOprOra                              (50006), -- sfp_opr_ora
       ethFaultPropagation                       (50007), -- fault_propagation
       ethAutoNegotiationFailure                 (50008), -- auto_negotiation_failure
       ethLfs                                    (50009), -- lfs
       ethSilentStartNoRx                        (50010), -- silent_start_no_rx
       ethDot1xSupplicantAuthFailed              (50011), -- dot1x_supplicant_auth_failed

       ethOamEfmLinkDown                         (50012), -- oam_efm_link_down
       ethOamEfmLinkFaultIndication              (50013), -- oam_efm_link_fault
       ethOamEfmFeLinkFaultIndication            (50014), -- oam_efm_link_fault_fe
       ethOamEfmCriticalLinkIndication           (50015), -- oam_efm_critical_link
       ethOamEfmFeCriticalLinkIndication         (50016), -- oam_efm_critical_link_fe
       ethOamEfmDyingGaspIndication              (50017), -- oam_efm_dying_gasp
       ethOamEfmFeDyingGaspIndication            (50018), -- oam_efm_dying_gasp_fe
       ethPoePoweredDeviceDisabled               (50019), -- Poe Powered Device Disabled
       ethLagLacpDown                            (50020), -- lag_lacp_down
       ethLagLacpLoopDetected                    (50021), -- lag_lacp_loop_detected
       ethLagLacpChurn                           (50022), -- lag_lacp_churn
       ethMacsecJoinCaFailed                     (50023), -- macsec_join_ca_failed     
       ethFatPipeRateExceededBwp                 (50024), -- fat_pipe_rate_exceeded_bwp        

       muxEthTdmLof                              (60001), -- lof
       muxEthTdmLos                              (60002), -- los
       muxEthFaultPropagation                    (60003), -- fault_propagation
       -- RESERVED
       muxEthTdmRemoteConnectionFailure          (60005), -- remote_connection_failure
       muxEthTdmLoopDetection                    (60006), -- loop_detection
       muxEthTdmAis                              (60007), -- ais
       muxEthTdmSfpMismatch                      (60008), -- sfp_mismatch
       muxEthTdmSfpRemoved                       (60009), -- sfp_removed
       muxEthTdmSfpTemperatureOra                (60010), -- sfp_temperature_ora
       muxEthTdmSfpOprOra                        (60011), -- sfp_opr_ora

       shdslPowerFeedingOverCurrent             (70201), -- shdsl_power_feeding_over_current
       shdslInitializationFailure               (70202), -- shdsl_initialization_failure
       shdslConfigMismatch                      (70203), -- shdsl_configuration_mismatch
       shdslManagementLinkDown                  (70204), -- management_link_down
       shdslLoopAttenOra                        (70214), -- loop_attenuation_ora
       shdslSnrMarginOra                        (70216), -- snr_margin_ora
       shdslLosw                                (70218), -- losw
       shdslExcessiveCrcError                   (70220), -- excessive_crc_error

       shdslLinkDown                            (70222), -- link_down

       pcsLinkDown                              (70401), -- pcs Link Down
       pcsOamEfmLinkDown                        (70402), -- oam_efm_link_down
       pcsOamEfmLinkFaultIndication             (70403), -- oam_efm_link_fault
       pcsOamEfmFeLinkFaultIndication           (70404), -- oam_efm_link_fault_fe
       pcsOamEfmCriticalLinkIndication          (70405), -- oam_efm_critical_link
       pcsOamEfmFeCriticalLinkIndication        (70406), -- oam_efm_critical_link_fe
       pcsOamEfmDyingGaspIndication             (70407), -- oam_efm_dying_gasp
       pcsOamEfmFeDyingGaspIndication           (70408), -- oam_efm_dying_gasp_fe
       pcsFaultPropagation                      (70409), -- fault_propagation
       vdsl2LinkDown                            (70601), -- link_down
       voiceHwFailure                           (90001), -- hardware_failure

       sdhSonetSfpNoResponse                    (100001), -- sfp_no_response
       sdhSonetSfpMismatch                      (100002), -- sfp_mismatch
       sdhSonetLof                              (100003), -- lof
       sdhSonetRfi                              (100004), -- rfi_line
       sdhSonetLos                              (100005), -- los
       sdhSonetSfpRemoved                       (100006), -- sfp_removed
       sdhSonetSfpTemperatOra                   (100007), -- sfp_temperature_ora
       sdhSonetSfpOprOra                        (100008), -- sfp_opr_ora
       sdhSonetAisLine                          (100009), -- ais-line
       sdhSonetTimLine                          (100010), -- tim-line
       sdhSonetSdLine                           (100011), -- sd-line
       sdhSonetEedLine                          (100012), -- eed-line
       sdhSonetFaultPropagation                 (100013), -- fault_propagation
       sdhSonetManagementLinkDown               (100014), -- management_link_down
       sdhSonetApsProtectionByteFailure         (100016), -- aps_protection_byte_failure
       sdhSonetApsChannelMismatch               (100017), -- aps_channel_mismatch
       sdhSonetApsModeMismatch                  (100018), -- aps_mode_mismatch
       sdhSonetApsProtectionLineFailureFe       (100019), -- aps_fe_protection_line_failure
       sdhSonetLicenseMismatch                  (100020), -- license_mismatch
       sdhSonetApsInvalidMode                   (100021), -- APS mode mismatch
       vcVtAisVc                                (100101), -- ais-vcvt
       vcVtLomfVc                               (100102), -- lomf-vcvt
       vcVtUnequipVc                            (100103), -- uneq-vcvt
       vcVtTimVc                                (100104), -- tim-vcvt
       vcVtPlmVc                                (100105), -- plm-vcvt
       vcVtLopVc                                (100106), -- lop-vcvt
       vcVtSdVc                                 (100107), -- sd-vcvt
       vcVtEedVc                                (100108), -- eed-vcvt
       vcVtRfiVc                                (100109), -- rfi-vcvt
       vcVtHg1Ais                               (100110), -- vc Vt Hg 1 Ais
       vcVtHg1Lof                               (100111), -- vc Vt Hg 1 Lof
       vcVtHg1Rfi                               (100112), -- vcVtHg1Rfi
       vcVtHg2Ais                               (100113), -- vcVtHg2Ais
       vcVtHg2Lof                               (100114), -- vcVtHg2Lof
       vcVtHg2Rfi                               (100115), -- vcVtHg2Rfi
       vcVtHg3Ais                               (100116), -- vcVtHg3Ais
       vcVtHg3Lof                               (100117), -- vcVtHg3Lof
       vcVtHg3Rfi                               (100118), -- vcVtHg3Rfi
       vcVtHg4Ais                               (100119), -- vcVtHg4Ais
       vcVtHg4Lof                               (100120), -- vcVtHg4Lof
       vcVtHg4Rfi                               (100121), -- vcVtHg4Rfi
       vcVtUserInitiatedSwitchover              (100122), -- user_initiated_switchover

       pathAisPath                              (100201), -- ais-path
       pathLomfPath                             (100202), -- lomf-path
       pathUnequipPath                          (100203), -- uneq-path
       pathTimPath                              (100204), -- tim-path
       pathPlmPath                              (100205), -- plm-path
       pathLopPath                              (100206), -- lop-path
       pathSdPath                               (100207), -- sd-path
       pathEedPath                              (100208), -- eed-path
       pathRfiPath                              (100209), -- rfi-path
       pathUserInitiatedSwitchover              (100210), -- user_initiated_switchover

       e1t1UserInitiatedSwitchover              (110101), -- user_initiated_switchover     
       e1t1ManagementLinkDown                   (110102), -- management_link_down
       e1t1ExcessiveBpv                         (110103), -- excessive_bpv
       e1t1ExcessiveErrorRatio                  (110104), -- excessive_error_ratio
       e1t1Ais                                  (110105), -- ais
       e1t1Lof                                  (110106), -- lof
       e1t1Rai                                  (110107), -- rai
       e1t1Lomf                                 (110108), -- lomf

       e1t1Los                                  (110110), -- los
       e1t1Ds1RingClockFailure                  (110111), -- ds1_ring_clock_failure
       e1t1Ds1RingDirectionMismatch             (110112), -- ds1_ring_direction_mismatch
       e1t1FaultPropagation                     (110113), -- fault_propagation

       ds1OptOpticalReceiverLos                 (111001), -- optical_receiver_los
       ds1OptDs1Lof                             (111002), -- ds1_lof
       ds1OptC3794Lof                           (111003), -- c37.94_lof
       ds1OptDs1Rai                             (111004), -- ds1_rai
       ds1OptFaultPropagation                   (111005), -- fault_propagation
       ds1OptManagementLinkDown                 (111006), -- management_link_down
       ds1OptAis                                (111007), -- ais
       ds1OptExcessiveBpv                       (111008), -- excessive_bpv     

       e3t3Rai                                  (120101), -- rai
       e3t3Ais                                  (120102), -- ais
       e3t3Lof                                  (120103), -- lof
       e3t3Los                                  (120104), -- los
       e3t3UserInitiatedSwitchover              (120105), -- user_initiated_switchover

       ds0BundleLof                             (120301), -- lof
       ds0BundleRdi                             (120302), -- rdi
       ds0BundleOutOfService                    (120303), -- out_of_service
       ds0BundleRemoteForce                     (120304), -- remote_force
       
       ds0G703Los                               (120401), -- los
       ds0G703FaultPropagation                  (120402), -- fault_propagation
       ds0G703OutOfSequence                     (120403), -- out_of_sequence 
       
       vcgMinimumMembers                        (130001), -- minimum_members_tca
       vcgFaultPropagation                      (130002), -- fault_propagation
       vcgDifferentialDelayExceeded             (130003), -- Differential delay exceeded
       vcgLoa                                   (130004), -- Loss Of Alignment (LOA)
       vcgLoopDetection                         (130005), -- Loop Detection

       serialHwFail                             (150001), -- hardware_failure
       serialLof                                (150002), -- lof
       serialRai                                (150003), -- rai
       serialNoRts                              (150004), -- no_rts
       -- RESERVED
       serialRs232RateMismatch                  (150006), -- rs232_rate_mismatch
       serialFaultPropagation                   (150007), -- fault_propagation

       serialLos                                (150009),

       serialBundleLof                          (150101), -- lof
       serialBundleRai                          (150102), -- rai
       serialBundleFaultPropagation             (150103), -- fault_propagation

       logicalMacOamEfmLinkDown                 (180001), -- oam_efm_link_down
       logicalMacOamEfmLinkFaultIndication      (180002), -- oam_efm_link_fault
       logicalMacOamEfmFeLinkFaultIndication    (180003), -- oam_efm_link_fault_fe
       logicalMacOamEfmCriticalLinkIndication   (180004), -- oam_efm_critical_link
       logicalMacOamEfmFeCriticalLinkIndication (180005), -- oam_efm_critical_link_fe
       logicalMacOamEfmDyingGaspIndication      (180006), -- oam_efm_dying_gasp
       logicalMacOamEfmFeDyingGaspIndication    (180007), -- oam_efm_dying_gasp_fe
       logicalMacFaultPropagation               (180008), -- fault_propagation

       etpPortDown                              (200001), -- etp_port_down
       etpEpsConfigurationMismatch              (200101), -- eps configuration mismatch
       
       flowFaultPropagation                     (210001), -- fault_propagation

       gfpLof                                   (230001), -- lof
       gfpCsf                                   (230002), -- csf
       gfpRxTrailFailure                        (230003), -- rx_trail_failure
       gfpFaultPropagation                      (230004), -- fault_propagation

       hdlcRxTrailFailure                       (240001), -- rx_trail_failure
       hdlcFaultPropagation                     (240002), -- fault_propagation

       lagLacpDown                              (250001), -- lacp_down, DEPRECATED, replaced by ethLagLacpDown
       lagLacpLoopDetection                     (250002), -- lacp_loop_detection, DEPRECATED, replaced by ethLagLacpLoopDetected
       lagLacpChurn                             (250003), -- lacp_churn, DEPRECATED, replaced by ethLagLacpChurn
       lagMinimumMembers                        (250004), -- lag_minimum_members, DEPRECATED
       lagFailed                                (250005), -- lag_failure_Indication
       lagFaultPropagation                      (250006), -- fault_propagation

       oamCfmMepAis                             (270201), -- ais
       oamCfmMepLck                             (270202), -- lck
       oamCfmMepMismatch                        (270203), -- mismatch
       oamCfmMepDefXconCCM                      (270204), -- defXconCCM
       oamCfmMepDefErrorCCM                     (270205), -- defErrorCCM

       oamCfmRmepLoc                            (270601), -- loc
       oamCfmRmepRdi                            (270602), -- rdi
       oamCfmRmepDefRemoteCCM                   (270603), -- defRemoteCCM
       oamCfmRmepDefRDICCM                      (270604), -- defRDICCM
       oamCfmRmepDefMACstatus                   (270605), -- defMACstatus

       pppLcpFailure                            (280001), -- lcp_failure
       pppBcpFailure                            (280002), -- bcp_failure
       pppLoopDetection                         (280003), -- loop_detection

       mlpppBcpFailure                          (280101), -- bcp_failure
       mlpppFaultPropagation                    (280102), -- fault_propagation

       epsConfigMismatch                        (290201), -- configuration_mismatch DEPRECATED

       erpStateProtected                        (290301), -- erp_state_protected

       routerNatMappingTableFull                (300001), -- nat_mapping_table_full
       
       routerInterfaceDhcpClientNoLease         (300101), -- dhcp_client_no_lease
       ospfGracefulRestart                      (300201), -- ospf_graceful_restart

       ospfNeighborStateChange                  (300302), -- ospf_neighbor_state_change
       ospfInterfaceStateChange                 (300401), -- ospf_interface_state_change
       ospfInterfaceConfigError                 (300402), -- ospf_interface_config_error
       bgpSessionFailure                        (300601), -- session_failure
       bgpTcpSessionAuthFailure                 (300602), -- tcp_session_auth_failure
       ipBfdDetectionTimeExpired                (300801), -- detection_time_expired
       twampSessionUnavailable                  (300901), -- twamp_session_unavailable
       twampSessionForwardUnavailable           (300902), -- twamp_session_forward_unavailable
       twampSessionBackwardUnavailable          (300903), -- twamp_session_backward_unavailable
       
       twampPeerTodAccuracyOutOfLimit           (301001), -- twamp_peer_tod_acc_out_of_limit
       
       tunnelDown                               (301201), -- tunnel_down
       tunnelNhrpRegistrationNoReply            (301202), -- nhrp_registration_no_reply
       tunnelNhrpRegistrationNak                (301203), -- nhrp_registration_nak

       pwConfigMismatch                         (310001), -- pw_configuration_mismatch
       pwOamFailure                             (310002), -- pw_oam_failure
       pwRdi                                    (310003), -- rdi
       pwRxFailure                              (310004), -- rx_failure
--     RESERVED                                 (310005),
       pwFaultPropagation                       (310006), -- fault_propagation
--    RESERVED                                  (310007)
       pwRxFailureFe                            (310008), -- rx_failure far end
       pwRdiFe                                  (310009), -- rdi far end

-- teleprotection
       cmdChannelLof                            (320001), -- Cmd Channel LOF
       cmdChannelRai                            (320002), -- Cmd Channel RAI
       cmdChannelAddressMismatch                (320003), -- Cmd Channel Address Mismatch
       cmdChannelOutOfService                   (320004), -- Cmd Channel Out of Service

       cmdInActive                              (320101), -- Command input active

       cmdOutActive                             (320201), -- Command output active
       
       cellularIfDown                           (320301), -- cellular_interface_down

                                                      --  EVENTS --
       ------------------------------------------------------------------
       --                           EVENT ID         EVENT NAME         |
       ------------------------------------------------------------------


       systemSwInstallStart                 (1020001), -- sw_install_start
       systemSwInstallEnd                   (1020002), -- sw_install_end
       systemDownloadEnd                    (1020003), -- download_end
       systemUserReset                      (1020004), -- user_reset
       systemAlternativeConfLoaded          (1020005), -- alternate_configuration_loaded
       systemConfMigration                  (1020006), -- configuration_migration
       systemConfSanity                     (1020007), -- configuration_sanity
       systemTrapHardSyncStart              (1020008),
       systemTrapHardSyncEnd                (1020009),
       systemPmSpaceOverflow                (1020010), -- pm_space_overflow
       systemResourceOverflow               (1020011), -- resource_overflow
       systemDyingGasp                      (1020012), -- dying_gasp
       systemDyingGaspRecovery              (1020013), -- dying_gasp_recovery
       systemTraceMsgFatalError             (1020014), -- trace_msg_fatal_error
       systemTraceMsgException              (1020015), -- trace_msg_exception
       systemTraceMsgSwWatchdogReset        (1020016), -- trace_msg_sw_watchdog_reset
       systemBackupConfigurationLoaded      (1020017), -- backup_configuration_loaded
       systemDeviceStartup                  (1020018), -- device_startup
       systemItuSatTestStart                (1020019), -- Y.1564 Test Start
       systemItuSatConfigurationTestEnd     (1020020), -- Y.1564 Test Configuration End
       systemItuSatPerformanceTestEnd       (1020021), -- Y.1564 Test Performance End
       systemSuccessfulLogin                (1020022), -- successful_login
       systemFailedLogin                    (1020023), -- failed_login
       systemLogout                         (1020024), -- user_logout
       systemRfc2544TestStart               (1020025), -- rfc2544 test start
       systemRfc2544TestEnd                 (1020026), -- rfc2544
       systemAclLogging                     (1020027),
       systemStartupConfigUnconfirmed       (1020028), -- startup_config_unconfirmed
       systemActiveSoftwareChanged          (1020029), -- Active Software Changed
       systemRunningConfigSaved             (1020030), -- Running Config Saved
       systemItuSatResponderActivated       (1020031), -- Y.1564 Responder Activated
       systemItuSatResponderDeactivated     (1020032), -- Y.1564 Responder Deactivated
       systemSummerTimeStarted              (1020033), -- summer_time_started
       systemSummerTimeEnded                (1020034), -- summer_time_ended


       systemCfmSoamRxPacketDropped         (1020035), -- CFM SOAM Rx Packet dropped
       systemRemoteTerminalStarted          (1020036), -- remote_terminal_started
       systemRemoteTerminalEnded            (1020037), -- remote_terminal_ended
       systemLicenseEnabled                 (1020038), -- license_enabled
       systemLicenseDisabled                (1020039), -- license_disabled
       systemLicenseViolation               (1020040), -- license_violation
       systemLicenseFilesIncompatible       (1020041), -- license_files_incompatible
       systemLicenseInstallEnd              (1020042), -- license_install_end
       systemLicenseAboutToExpire           (1020043), -- license_about_to_expire
       systemLicenseExpired                 (1020044), -- license_expired
       systemL3SatTestStart                 (1020045), -- L3 SAT test start
       systemL3SatConfigurationTestEnd      (1020046), -- L3 SAT configuration test end
       systemL3SatPerformanceTestEnd        (1020047), -- L3 SAT performance test end
       systemL3SatResponderActivated        (1020048), -- L3 SAT Responder Activated
       systemL3SatResponderDeactivated      (1020049), -- L3 SAT Responder Deactivated

       systemAbmTestStart                   (1020050), -- abm_test_started
       systemAbmTestEnd                     (1020051), -- abm_test_ended
       systemL3SatPreliminaryTestFailed     (1020052), -- l3sat_preliminary_test_failed
       systemFileOverflow                   (1020053), -- file_overflow
       systemTimeChanged                    (1020054), -- time_changed
       systemTimeSourceChanged              (1020055), -- time_source_changed
       systemSerialPortDisabled             (1020056), -- serial_port_disabled
       systemSerialPortEnabled              (1020057), -- serial_port_enabled
       systemFactoryDefaultButtonPushed     (1020058), -- factory_default_button_pushed
       systemPcRpcapSessionStarted          (1020060), -- pc_rpcap_session_started
       systemPcRpcapSessionEnded            (1020061), -- pc_rpcap_session_ended
       systemPcRpcapRequestRejected         (1020062), -- pc_rpcap_session_rejected
       
       ptpRecoveredPtpStateChange           (1030201), -- ptp_state_change
       ptpRecoveredSevereFrequencyCondition (1030202), -- severe_frequency_condition
       ptpRecoveredSevereTimeCondition      (1030203), -- severe_time_condition
       ptpRecoveredMasterSwitchover         (1030204), -- master_switchover
       ptpRecoveredTimeStateChange          (1030205), -- ptp_time_state_change

       clockDomainSystemSourceClockChange   (1030301), -- system_source_clock_change
       clockDomainStationSourceClockChange  (1030302), -- station_source_clock_change

       ptpRecoveredMasterUnicastNegotiationFailue (1030401),  -- unicast_negotiation_failue

       ptpMasterGrantedServiceAborted       (1030601), -- granted_service_aborted
       ptpMasterSlaveRequestDenied          (1030602), -- slave_request_denied
       g82751RecoveredFreqStateChange       (1030801), -- G.8275.1 Slave Frequency state changed
       g82751RecoveredTimeStateChange       (1030802), -- G.8275.1 Slave Time state changed
       g82751RecoveredRxClkClsChange        (1030803), -- G.8275.1 Slave Rx clock class change
       g82751RecoveredSlavePortChange       (1030804), -- G.8275.1 Slave Port change
       g82751RecoveredGMChange              (1030805), -- G.8275.1 Slave Grandmaster change
       g82751MasterTxClkClassChange         (1031001), -- G.8275.1 Master Tx clock class change
       cardReset                            (1040001), -- card_reset
       cardSwitchover                       (1040002), -- card_switchover
       cardProtectionCommand                (1040003), -- Card Protection command
       cardPluggedIn                        (1040004), -- card_plugged_in
       cardPluggedOut                       (1040005), -- card_plugged_out
       cardTraceMsgFatalError               (1040006), -- trace_msg_fatal_error
        cardTraceMsgException               (1040007), -- trace_msg_exception
        cardTraceMsgSwWatchdogReset         (1040008), -- trace_msg_sw_watchdog_reset
       cardFanOperModeChanged               (1040009), -- fan_oper_mode_changed
       ethSfpOptOra                         (1050001), -- sfp_opt_ora
       ethSfpOptOraOff                      (1050002), -- sfp_opt_ora_off
       ethSfpLbcOra                         (1050003), -- sfp_lbc_ora
       ethSfpLbcOraOff                      (1050004), -- sfp_lbc_ora_off
       ethOamEfmRemoteLoopback              (1050005), -- oam_efm_remote_loopback
       ethOamEfmRemoteLoopbackOff           (1050006), -- oam_efm_remote_loopback_off
       ethPortSwitchover                    (1050007), -- port_switchover
       ethPoePoweredDeviceConnected         (1050008), -- Poe Powered Device Connected
       ethPoePoweredDeviceRemoved           (1050009), -- Poe Powered Device Removed
       ethProtectionCommand                 (1050010), -- Ethernet Protection command

       ethLoopback                          (1050011), -- Ethernet Loopback Started
       ethLoopbackOff                       (1050012), -- Ethernet Loopback Ended

       ethDot1xSuppAuthorized               (1050024), -- dot1x_supp_authorized
       ethDot1xSuppUnauthorized             (1050025), -- dot1x_supp_unauthorized
       ethDot1xAuthSuppAuthorized           (1050026), -- dot1x_auth_supp_authorized
       ethDot1xAuthSuppUnauthorized         (1050027), -- dot1x_auth_supp_unauthorized
       
       ethMacsecTxScCreated                 (1050013), -- macsec_tx_sc_created
       ethMacsecRxScCreated                 (1050014), -- macsec_rx_sc_created
       ethMacsecRxScDeleted                 (1050015), -- macsec_rx_sc_deleted
       ethMacsecKeyServerElected            (1050016), -- macsec_key_server_elected
       ethMacsecMembershipRejected          (1050017), -- macsec_membership_rejected
       ethMacsecSaNotInUseDiscarded         (1050018), -- macsec_sa_not_in_use_discarded
       ethMacsecLateFrameDiscarded          (1050019), -- macsec_late_frame_discarded
       ethMacsecInvalidFrameDiscarded       (1050020), -- macsec_invalid_frame_discarded
       ethMacsecNoSecTagDiscarded           (1050021), -- macsec_no_sec_tag_discarded
       ethMacsecBadSecTagDiscarded          (1050022), -- macsec_bad_sec_tag_discarded
       ethMacsecUnknownSciDiscarded         (1050023), -- macsec_unknown_sci_discarded
       
       muxEthTdmSfpOptOra                   (1060001), -- sfp_opt_ora
       muxEthTdmSfpOptOraOff                (1060002), -- sfp_opt_ora_off

       shdslLoopback                        (1070204), -- loopback
       shdslLoopbackOff                     (1070205), -- loopback_off

       pcsOamEfmRemoteLoopback              (1070401), -- oam_efm_remote_loopback
       pcsOamEfmRemoteLoopbackOff           (1070402), -- oam_efm_remote_loopback_off
       
       briLoopback                          (1080001), -- loopback
       briLoopbackOff                       (1080002), -- loopback_off


       sdhSonetSfpOptOra                    (1100001), -- sfp_opt_ora
       sdhSonetSfpLbcOra                    (1100002), -- sfp_lbc_ora
       sdhSonetEsSectionTca                 (1100003), -- es_section_tca
       sdhSonetSesSectionTca                (1100004), -- ses_section_tca
       sdhSonetSefsSectionTca               (1100005), -- sefs_section_tca
       sdhSonetCvSectionTca                 (1100006), -- cv_section_tca
       sdhSonetEsLineTca                    (1100007), -- es_line_tca
       sdhSonetSesLineTca                   (1100008), -- ses_line_tca
       sdhSonetCvLineTca                    (1100009), -- cv_line_tca
       sdhSonetUasLineTca                   (1100010), -- uas_line_tca
       sdhSonetEsLineTcaFe                  (1100011), -- es_line_tca_fe
       sdhSonetSesLineTcaFe                 (1100012), -- ses_line_tca_fe
       sdhSonetCvLineTcaFe                  (1100013), -- cv_line_tca_fe
       sdhSonetUasLineTcaFe                 (1100014), -- uas_line_tca_fe
       sdhSonetPortSwitchOver               (1100015), -- uas_line_tca_fe
       --     RESERVED
       sdhSonetSfpOptOraOff                 (1100017), -- sfp_opt_ora_off
       sdhSonetSfpLbcOraOff                 (1100018), -- sfp_lbc_ora_off
       sdhSonetLoopback                     (1100019), -- loopback
       sdhSonetLoopbackOff                  (1100020), -- loopback_off
       sdhSonetApsCompatibleCommand         (1100021), -- APS compatible mode protection command
       sdhSonetApsOptimizedCommand          (1100022), -- APS optimized mode protection command

       vcVtEsVcVtTca                        (1100101), -- es_vcvt_tca
       vcVtSesVcVtTca                       (1100102), -- ses_vcvt_tca
       vcVtCvVcVtTca                        (1100103), -- cv_vcvt_tca
       vcVtUasVcVtTca                       (1100104), -- uas_vcvt_tca
       vcVtEsVcVtTcaFe                      (1100105), -- es_vcvt_tca_fe
       vcVtSesVcVtTcaFe                     (1100106), -- ses_vcvt_tca_fe
       vcVtCvVcVtTcaFe                      (1100107), -- cv_vcvt_tca_fe
       vcVtUasVcVtTcaFe                     (1100108), -- uas_vcvt_tca_fe

       pathEsPathTca                        (1100201), -- es_path_tca
       pathSesPathTca                       (1100202), -- ses_path_tca
       pathCvPathTca                        (1100203), -- cv_path_tca
       pathUasPathTca                       (1100204), -- uas_path_tca
       pathEsPathTcaFe                      (1100205), -- es_path_tca_fe
       pathSesPathTcaFe                     (1100206), -- ses_path_tca_fe
       pathCvPathTcaFe                      (1100207), -- cv_path_tca_fe
       pathUasPathTcaFe                     (1100208), -- uas_path_tca_fe

       e1t1FrameSlip                        (1110101), -- frame_slip
       e1t1Bpv                              (1110102), -- bpv
       e1t1CrcError                         (1110103), -- crc_error
       e1t1Loopback                         (1110104), -- loopback
       e1t1LoopbackOff                      (1110105), -- loopback_off
       e1t1EsLineTca                        (1110106), -- es_line_tca
       e1t1CvPathTca                        (1110107), -- cv_path_tca
       e1t1EsPathTca                        (1110108), -- es_path_tca
       e1t1SesPathTca                       (1110109), -- ses_path_tca
       e1t1SefsPathTca                      (1110110), -- sefs_path_tca
       e1t1CssPathTca                       (1110111), -- css_path_tca
       e1t1UasPathTca                       (1110112), -- uas_path_tca
       e1t1PortSwitchover                   (1110113), -- port_switchover
       
       ds1OptFrameSlip                      (1111001), -- frame_slip
       ds1OptBpv                            (1111002), -- bpv
       ds1OptCrcError                       (1111003), -- crc_error
       ds1OptLoopback                       (1111004), -- loopback
       ds1OptLoopbackOff                    (1111005), -- loopback_off
       ds1OptEsLineTca                      (1111006), -- es_line_tca
       ds1OptCvPathTca                      (1111007), -- cv_path_tca
       ds1OptEsPathTca                      (1111008), -- es_path_tca
       ds1OptSesPathTca                     (1111009), -- ses_path_tca
       ds1OptSefsPathTca                    (1111010), -- sefs_path_tca
       ds1OptCssPathTca                     (1111011), -- css_path_tca
       ds1OptUasPathTca                     (1111012), -- uas_path_tca
       ds1OptPortSwitchover                 (1111013), -- port_switchover      

       e3t3Loopback                         (1120101), -- loopback
       e3t3LoopbackOff                      (1120102), -- loopback off
       
       ds0G703Loopback                      (1120401), -- loopback
       ds0G703LoopbackOff                   (1120402), -- loopback_off

       serialBufferSlip                     (1150001), -- buffer_slip

       bridgeSpanningTreeNewRoot            (1170001), -- spanning_tree_new_root
       bridgeSpanningTreeTopologyChange     (1170002), -- spanning_tree_topology_change
       bridgeMstpNewRoot                    (1170003), -- mstp_new_root
       bridgeMstpTopologyChange             (1170004), -- mstp_topology_change
       bridgeMldSnoopingUnsupportedIp       (1170005), -- mld_snooping_unsupported_ip
       bridgeMldSnoopingDuplicateIp         (1170006), -- mld_snooping_duplicate_ip
       
       logicalMacOamEfmRemoteLoopback       (1180001), -- oam_efm_remote_loopback
       logicalMacOamEfmRemoteLoopbackOff    (1180002), -- oam_efm_remote_loopback_off
       
       etpEpsPortSwitchover                 (1200101), -- EPS port switchover

       ds0BundlePortSwitchover              (1120301), -- port_switchover
       
       lagSubGroupSwitchover                (1250001), -- sub_group_switchover
       lagFailure                           (1250002), -- lag_failure, DEPRECATED, replaced by lagFailureInd

       oamCfmDestNeDelayTca                 (1270401), -- delay_tca
       oamCfmDestNeDelayTcaOff              (1270402), -- delay_tca_off
       oamCfmDestNeDelayVarTca              (1270403), -- delay_var_tca
       oamCfmDestNeDelayVarTcaOff           (1270404), -- delay_var_tca_off
       oamCfmDestNeLossRatioTca             (1270405), -- loss_ratio_tca
       oamCfmDestNeLossRatioTcaOff          (1270406), -- loss_ratio_tca_off
       oamCfmDestNeLossRatioTcaFe           (1270407), -- loss_ratio_tca_fe
       oamCfmDestNeLossRatioTcaFeOff        (1270408), -- loss_ratio_tca_fe_off
       oamCfmDestNeUnavailableRatioTca      (1270409), -- unavailable_ratio_tca
       oamCfmDestNeUnavailableRatioTcaOff   (1270410), -- unavailable_ratio_tca_off
       oamCfmDestNeUnavailableRatioTcaFe    (1270411), -- unavailable_ratio_tca_fe
       oamCfmDestNeUnavailableRatioTcaFeOff (1270412), -- unavailable_ratio_tca_fe_off

       epsPortSwitchOver                    (1290201), -- port_switch_over DEPRECATED

       erpWtrStart                          (1290301), -- erp_wtr_start

       erpPortStateChange                   (1291101), -- erp_port_state_change

       routerNatPortRangeExhaustion         (1300001), -- nat_port_range_exhaustion
       
       routerInterfaceDhcpLeaseObtained     (1300102), -- dhcp_lease_obtained
       routerInterfaceDhcpAdressConflict    (1300103), -- dhcp_address_conflict
       ospfNeighborGracefulRestart          (1300301), -- ospf_neighbor_graceful_restart
       
       twampSessionLossRatioTca             (1300901), -- twamp_session_loss_ratio_tca
       twampSessionDelayTca                 (1300902), -- twamp_session_delay_tca
       twampSessionDelayVarTca              (1300903), -- twamp_session_delay_var_tca
       twampSessionForwardLossRatioTca      (1300904), -- twamp_session_forward_loss_ratio_tca
       twampSessionForwardDelayTca          (1300905), -- twamp_session_forward_delay_tca
       twampSessionForwardDelayVarTca       (1300906), -- twamp_session_forward_delay_var_tca
       twampSessionBackwardLossRatioTca     (1300907), -- twamp_session_backward_loss_ratio_tca
       twampSessionBackwardDelayTca         (1300908), -- twamp_session_backward_delay_tca
       twampSessionBackwardDelayVarTca      (1300909), -- twamp_session_backward_delay_var_tca
       twampSessionRequestRejected          (1300910), -- twamp_session_request_rejected
       
       twampPeerTestStarted                 (1301001), -- twamp_peer_test_started
       twampPeerTestStopped                 (1301002), -- twamp_peer_test_stopped
       twampPeerConnectionRejected          (1301003), -- twamp_peer_connection_rejected
       twampPeerTestActivationRejected      (1301004), -- twamp_test_activation_rejected

       twampResponderConnectionExpired      (1301101), -- responder_connection_expired
       twampResponderSessionExpired         (1301102), -- responder_session_expired

       pwSwitchOver                         (1310001), -- pw_switchover
       pwJitterBufferOverflow               (1310002), -- pw_jitter_buffer_overflow
       pwJitterBufferUnderflow              (1310003), -- pw_jitter_buffer_underflow
       pwOamDelayTca                        (1310004), -- pw_oam_delay_tca
       pwOamDelayTcaOff                     (1310005), -- pw_oam_delay_tca_off

       bgpSessionPrefixOverflow             (1300601), -- session_prefix_overflow
       ipBfdNeighborShutdown                (1300801), -- neighbor_shutdown
       ipBfdNeighborAddressChange           (1300802), -- neighbor_address_change
       
       cmdChannelCrcError                   (1320001), -- Channel CRC Error
       cmdChannelTxDelayChange              (1320002), -- Transmission delay changed
       cmdChannelPortSwitchover             (1320003), -- Port switchover
       
       cellularIfRssiTca                    (1320301), -- rssi_tca
       cellularIfRssiTcaOff                 (1320302), -- rssi_tca_off   

                               --  ALARMS AND EVENTS --
       ------------------------------------------------------------------
       --                         ALARM/EVENT ID                        |
       ------------------------------------------------------------------

      allAlarmsAndEvents         (2147483647), -- 0x7FFFFFFF for all Alarms and Events
      allAlarms                  (2147483646), -- 0x7FFFFFFE for all Alarms
      allEvents                  (2147483645)  -- 0x7FFFFFFD for all Events
     }



AlarmSeverity ::= TEXTUAL-CONVENTION
    STATUS current
    DESCRIPTION
            "Alarm severity values according to ITU Recommendation X.733,
            'Information Technology - Open Systems Interconnection -
            System Management: Alarm Reporting Function', 1992.
            "
    SYNTAX  INTEGER   {
      cleared       (1),
--    indeterminate (2),
      critical      (3),
      major         (4),
      minor         (5),
      warning       (6)   -- used to denote an event
    }

AlarmEventMasking  ::= TEXTUAL-CONVENTION
    STATUS current
    DESCRIPTION
            "Mask(if the bit is '1') and unmask('0') different methods of reporting
             of alarms and events.
             log(0)- Masking/unmasking sending of the history log, active alarm and SYSLOG.
             snmpTrap(1)- Masking/unmasking sending of SNMP notifications.
             ledRelay(2)- Masking/unmasking activation of alarms LED and relay.
             popup(3)- Masking/unmasking CLI popup messages.
             vtyPopup (4)- Masking/unmasking CLI remote terminal popup messages.
            "
    SYNTAX  BITS {
        log         (0),
        snmpTrap    (1),
        ledRelay    (2),
        popUp       (3),
        vtyPopup    (4)
    }


AlarmProperties  ::= TEXTUAL-CONVENTION
    STATUS current
    DESCRIPTION
            "This textual convention shows the properties of the current Alarm.

             maskInLog(0) - when this bit value is set to '1' the alarm that exists in the
             log table will not be displayed to the user.
             "
    SYNTAX  BITS {
        maskInlog      (0)
    }


AlarmReason  ::= TEXTUAL-CONVENTION
    STATUS current
    DESCRIPTION
        "This textual convention shows the reason for generating alarm or event:
         alarmResolved    (1) - Alarm is cleared because the condition causing it has been resolved.
         userInitiated    (2) - Alarm raising or clearing, or event was initiated by a user command.
         alarmSuppression (3) - Alarm is cleared because a root-cause alarm has suppressed it, or
                                raised after a root-cause alarm was cleared.
         alarmRebuild     (4) - Generated due to active alarms rebuild action
         notApplicable  (255) - Reason is irrelevant or unknown.
            "
    SYNTAX  INTEGER {
        alarmResolved    (1),
        userInitiated    (2),
        alarmSuppression (3),
        alarmRebuild     (4),
        notApplicable    (255)
}


--
-- Alarm and Event Statistics Type
--
AlarmEventLogStatsType ::= TEXTUAL-CONVENTION
    STATUS current
    DESCRIPTION
            "Type of Statistics. The Statistics can be from the Active Alarms or from the Log ."
    SYNTAX  INTEGER {
       activeAlarms         (1), -- All Active Alarms
       briefLog             (2), -- Brief log statistics
       briefLogSinceAck     (3), -- Brief log statistics since last acknowledge
       activeAlarmsMasked   (4)  -- Masked Active Alarms
     }

--
-- Alarm and Event Attribute Table
--

alarmEventAttrTable OBJECT-TYPE
   SYNTAX      SEQUENCE OF AlarmEventAttrEntry
   MAX-ACCESS  not-accessible
   STATUS      current
   DESCRIPTION
       "A table that lists the set of Attributes per possible alarm and event."
   ::= { alarmEventConfig 1 }

alarmEventAttrEntry OBJECT-TYPE
   SYNTAX      AlarmEventAttrEntry
   MAX-ACCESS  not-accessible
   STATUS      current
   DESCRIPTION
       "An entry appears in this table for each possible alarm and event.
        This table MUST be persistent upon system reboot."
   INDEX  { alarmEventAttrIndex, alarmEventAttrSourceType }
   ::= { alarmEventAttrTable 1 }

AlarmEventAttrEntry ::= SEQUENCE {
    alarmEventAttrIndex                      AlarmEventId,
    alarmEventAttrSourceType                 AlarmEventSourceType,
    alarmEventAttrName                       SnmpAdminString,
    alarmEventAttrDescription                SnmpAdminString,
    alarmEventAttrDefaultSeverity            AlarmSeverity,
    alarmEventAttrDefaultMasking             AlarmEventMasking,
    alarmEventAttrThresholdSupport           INTEGER,
    alarmEventAttrAssociatedNotification     OBJECT IDENTIFIER 
 }

alarmEventAttrIndex      OBJECT-TYPE
   SYNTAX      AlarmEventId
   MAX-ACCESS  not-accessible
   STATUS      current
   DESCRIPTION
   "The table index unique identifier of the alarm or the event."
   ::= { alarmEventAttrEntry 1 }

alarmEventAttrSourceType    OBJECT-TYPE
   SYNTAX      AlarmEventSourceType
   MAX-ACCESS  not-accessible
   STATUS      current
   DESCRIPTION
         "This is the Source Type of alarm or event.
         "
   ::= { alarmEventAttrEntry 2 }


alarmEventAttrName    OBJECT-TYPE
   SYNTAX       SnmpAdminString (SIZE (1..32))
   MAX-ACCESS   read-only
   STATUS       current
   DESCRIPTION
       "A name of up to 32 characters."
    ::= { alarmEventAttrEntry 3 }


alarmEventAttrDescription    OBJECT-TYPE
   SYNTAX       SnmpAdminString (SIZE (1..80))
   MAX-ACCESS   read-only
   STATUS       current
   DESCRIPTION
       "The description of the current alarm or event as ASCII string.
        The details of the formatted description string is defined
        in the user-manual document.
       "
        ::= { alarmEventAttrEntry 4 }


alarmEventAttrDefaultSeverity     OBJECT-TYPE
   SYNTAX       AlarmSeverity
   MAX-ACCESS   read-only
   STATUS       current
   DESCRIPTION
       "This variable applies for alarms only.
        It denotes the default severity assigned to the alarm.
       "
   ::= { alarmEventAttrEntry 5 }


 alarmEventAttrDefaultMasking     OBJECT-TYPE
   SYNTAX       AlarmEventMasking
   MAX-ACCESS   read-only
   STATUS       current
   DESCRIPTION
       "This variable applies for alarms only.
        It denotes the default masking assigned to the alarm.
       "
   ::= { alarmEventAttrEntry 6 }


alarmEventAttrThresholdSupport  OBJECT-TYPE
    SYNTAX  INTEGER {
      no     (2),
      yes    (3)
      }
    MAX-ACCESS  read-only
    STATUS  current
    DESCRIPTION
       "This variable denotes whether a threshold is supported in the current Event.
       "
     ::= { alarmEventAttrEntry 7 }

alarmEventAttrAssociatedNotification   OBJECT-TYPE
   SYNTAX       OBJECT IDENTIFIER
   MAX-ACCESS   read-only
   STATUS       current
   DESCRIPTION
       "The NOTIFICATION-TYPE object identifier of the alarm or event.
        If there is no notification associated
        with this alarm, the value of this object MUST be '0.0'.
       "
--   DEFVAL { 0.0 }
   ::= { alarmEventAttrEntry 8 }


--
-- Active Alarm Table --
--

activeAlarmTable OBJECT-TYPE
   SYNTAX      SEQUENCE OF ActiveAlarmEntry
   MAX-ACCESS  not-accessible
   STATUS      current
   DESCRIPTION
       "A table of Active Alarms entries."
   ::= { alarmEventConfig 2 }

activeAlarmEntry OBJECT-TYPE
   SYNTAX      ActiveAlarmEntry
   MAX-ACCESS  not-accessible
   STATUS      current
   DESCRIPTION
       "Entries appear in this table when alarms are raised.
        They are removed when the alarm is cleared.
       "
   INDEX  { activeAlarmSourceId, activeAlarmIndex }
   ::= { activeAlarmTable 1 }

ActiveAlarmEntry ::= SEQUENCE {
    activeAlarmSourceId              SourceId,
    activeAlarmIndex                 Unsigned32,
    activeAlarmDateAndTime           DateAndTime,
    activeAlarmId                    AlarmEventId,
    activeAlarmDescription           SnmpAdminString,
    activeAlarmSourceType            AlarmEventSourceType,
    activeAlarmSeverity              AlarmSeverity,
    activeAlarmMasking               AlarmEventMasking,
    activeAlarmSourceName            SnmpAdminString 
 }


activeAlarmSourceId    OBJECT-TYPE
   SYNTAX      SourceId
   MAX-ACCESS  not-accessible
   STATUS      current
   DESCRIPTION
      "This object identifies the specific managed object that caused the alarm.
      "
   ::= { activeAlarmEntry 1 }

activeAlarmIndex    OBJECT-TYPE
   SYNTAX       Unsigned32
   MAX-ACCESS  not-accessible
   STATUS      current
   DESCRIPTION
       "This is a global running index.
       "
   ::= { activeAlarmEntry 2 }

activeAlarmDateAndTime OBJECT-TYPE
   SYNTAX      DateAndTime
   MAX-ACCESS  read-only
   STATUS      current
   DESCRIPTION
       "This variable denotes the date in which the alarm has been raised.
        If the NE implements a real-time clock, this variable MUST hold the UTC time.
        If the NE does not support a real-time clock, or,
        if from any other reason the UTC time is unknown, this variable will hold
        the relative date and time since the last reboot (computed from sysUpTime)."
   ::= { activeAlarmEntry 3 }

activeAlarmId      OBJECT-TYPE
   SYNTAX      AlarmEventId
   MAX-ACCESS  read-only
   STATUS      current
   DESCRIPTION
      "This object identifies the ID of the raised alarm.
      "
   ::= { activeAlarmEntry 4 }

activeAlarmDescription      OBJECT-TYPE
   SYNTAX      SnmpAdminString  (SIZE (1..80))
   MAX-ACCESS  read-only
   STATUS      current
   DESCRIPTION
      "ASCII String specifiying the details of the Active Alarm."
   ::= { activeAlarmEntry 5 }

 activeAlarmSourceType    OBJECT-TYPE
   SYNTAX      AlarmEventSourceType
   MAX-ACCESS  read-only
   STATUS      current
   DESCRIPTION
         "This is the Source Type of the active alarm.
         "
   ::= { activeAlarmEntry 6 }

activeAlarmSeverity    OBJECT-TYPE
   SYNTAX      AlarmSeverity
   MAX-ACCESS  read-only
   STATUS      current
   DESCRIPTION
      "This object identifies the severity of the raised alarm.
       Notes:
       1. The severity of the alarm in the Active Alarm table may be different from the
          severity configured in AlarmEventConfigTable due to severity escalation or deescalation
          which may be performed by the NE as a consequent of internal events.
       2. A trap will be sent when the alarm is raised or cleared (if not masked).
          This MIB object will be attached to the trap.
          For alarms that are cleared, the value will be cleared (1).
          After the trap is sent with a cleared (1) value, the device will immediately remove
          the alarm and the cleared alarm from this table.
      "
   ::= { activeAlarmEntry 7 }

activeAlarmMasking   OBJECT-TYPE
      SYNTAX        AlarmEventMasking
      MAX-ACCESS    read-only
      STATUS        current
      DESCRIPTION
         "This object identifies the alarm and event masking on various reporting means.
         "
      ::= { activeAlarmEntry 8 }

activeAlarmSourceName   OBJECT-TYPE
      SYNTAX        SnmpAdminString (SIZE (1..32))
      MAX-ACCESS    read-only
      STATUS        current
      DESCRIPTION
         "ASCII String specifying the name of the source referenced by alarmEventLogSourceId.
          The syntax will be similar to CLI.
          Example: E1 2/4
          where E1 is the source type, 2 is the slot number, 4 is the port number.
          The general formula is as follows:
          <Source Type> <Slot number>/<Port number>
          Source Type is defined in: AlarmEventSourceType.
          For types that have 2 words like Serial Bundle, the 1st letter of each word will be capitalized.
          For abbreviations we shall have all capitals. Examples: OAM EFM.
          CL cards will be: cl-a, cl-b. Main cards will be: main-a, main-b

          For SDH over E1 for example with Slots we shall have the same syntax as in CLI.
          Example: E1  1/2/3  means:  slot=1/port SDH=2/port E1=3

          About the slot numbers, these will be the logical numbers of the slots according to
          whatever is written on the device panel. For example, if an IO card is in slot IO-5
          on the panel, '5' will be displayed for the slot.
         "
      ::= { activeAlarmEntry 9 }


--
-- Rebuilding Active Alarms --
--

activeAlarmRebuild OBJECT-TYPE
      SYNTAX INTEGER {
        off(2),
        activate (3),
        activateWithTraps (4)
      }
      MAX-ACCESS read-write
      STATUS current
      DESCRIPTION
          "When the manager sets the value of this variable to activate (3),
          the application recollects all the active alarms from I/O cards or other entities
          and sets the value of this variable to off(2). This command is useful, for example:
          if there was a switch between main and redundant cards and the user wants to recollect
          the alarms that were missed during the switch.

          When activateWithTraps (4) is set, same operation as activate (3) is performed with an additional
          operation: Device will send raising traps for all active alarms.
          "
       ::= { alarmEventConfig 3 }


--
-- Alarms and Events Configuration Table --
--
alarmEventConfigTable  OBJECT-TYPE
      SYNTAX  SEQUENCE OF AlarmEventConfigEntry
      MAX-ACCESS  not-accessible
      STATUS  current
      DESCRIPTION
         "This table enables user defined policy per specific Source ID of an alarm or event."
  ::= { alarmEventConfig 4 }

alarmEventConfigEntry  OBJECT-TYPE
      SYNTAX      AlarmEventConfigEntry
      MAX-ACCESS  not-accessible
      STATUS  current
      DESCRIPTION
         "Entry containing user configuration for a specific alarm or event."
      INDEX { alarmEventConfigId, alarmEventConfigSourceType,
               alarmEventConfigSourceId }
      ::= { alarmEventConfigTable 1 }

AlarmEventConfigEntry ::= SEQUENCE {
    alarmEventConfigId          AlarmEventId,
    alarmEventConfigSourceType  AlarmEventSourceType,
    alarmEventConfigSourceId    SourceId,
    alarmEventConfigSeverity    AlarmSeverity,
    alarmEventConfigMasking     AlarmEventMasking,
    alarmEventConfigRowStatus   RowStatus,
    alarmEventConfigSourceName  SnmpAdminString 
 }

alarmEventConfigId      OBJECT-TYPE
      SYNTAX       AlarmEventId
      MAX-ACCESS   not-accessible
      STATUS       current
      DESCRIPTION
         "Alarm and Event ID.
          Note: In order to apply a policy for all alarms/events on current source ID
          or source type, this object should be set to the following according to
          Textual Convention:
          Value of allAlarmsAndEvents: For all Alarms and Events.
          Value of allAlarms: For all Alarms.
          Value of allEvents: For all Events.
          "
   ::= { alarmEventConfigEntry 1 }


alarmEventConfigSourceType    OBJECT-TYPE
   SYNTAX      AlarmEventSourceType
   MAX-ACCESS  not-accessible
   STATUS      current
   DESCRIPTION
         "This is the Source Type of alarm or event.
         "
   ::= { alarmEventConfigEntry 2 }

alarmEventConfigSourceId  OBJECT-TYPE
      SYNTAX       SourceId
      MAX-ACCESS   not-accessible
      STATUS       current
      DESCRIPTION
         "Source ID. This object identifies the specific managed object that causes the alarm.
          Note: In order to apply a policy to all Source IDs of the same Source Type,
          the fields in the SourceId that hold the instance number should be set to zero.
          "
   ::= { alarmEventConfigEntry 3 }


alarmEventConfigSeverity  OBJECT-TYPE
      SYNTAX       AlarmSeverity
      MAX-ACCESS   read-create
      STATUS        current
      DESCRIPTION
         "For alarms: values will be one of: critical (3), major (4), minor (5).
          For events: value must be warning (6).
          "
      ::= { alarmEventConfigEntry 4 }

alarmEventConfigMasking   OBJECT-TYPE
      SYNTAX        AlarmEventMasking
      MAX-ACCESS    read-create
      STATUS        current
      DESCRIPTION
         "This variable enables alarm and event masking on various reporting means.
         "
      ::= { alarmEventConfigEntry 5 }

alarmEventConfigRowStatus   OBJECT-TYPE
      SYNTAX        RowStatus
      MAX-ACCESS    read-create
      STATUS        current
      DESCRIPTION
         "Enable rows creation/deletion.
          This is used for managed objects that are dynamically created or removed.
          "
      ::= { alarmEventConfigEntry 6 }



alarmEventConfigSourceName   OBJECT-TYPE
      SYNTAX        SnmpAdminString             (SIZE (1..32))
      MAX-ACCESS    read-only
                  STATUS        current
      DESCRIPTION
         "ASCII String specifying the name of the source referenced by alarmEventLogSourceId.
           The syntax will be similar to CLI.
          Example: E1 2/4
          where E1 is the source type, 2 is the slot number, 4 is the port number.
          The general formula is as follows:
            <Source Type> <Slot number>/<Port number>
            Source Type is defined in: AlarmEventSourceType.
            For types that have 2 words like Serial Bundle, the 1st letter of each word will be capitalized.
          For abbreviations we shall have all capitals. Examples: OAM EFM.
            CL cards will be: cl-a, cl-b. Main cards will be: main-a, main-b

          For SDH over E1 for example with Slots we shall have the same syntax as in CLI.
          Example: E1  1/2/3  means:  slot=1/port SDH=2/port E1=3

          About the slot numbers, these will be the logical numbers of the slots according to
          whatever is written on the device panel. For example, if an IO card is in slot IO-5
          on the panel, '5' will be displayed for the slot.  "
                  ::= { alarmEventConfigEntry 7 }

--
-- Clearing Alarms and Events Log Tables --
--
alarmEventLogClear OBJECT-TYPE
      SYNTAX INTEGER {
        off(2),
        clearAll(3),
        clearLog (4),
        clearBriefLog (5),
        clearActivityLog (6)
      }
      MAX-ACCESS read-write
      STATUS current
      DESCRIPTION
          "Setting the variable to clearAll(3) removes all entries from all the log tables.
           Setting the variable to clearLog (4) removes all entries from the alarmEventLogTable.
           Setting the variable to clearBriefLog (5) removes all entries in the alarmEventBriefLogTable.
           Setting the variable to clearActivityLog (6) removes all entries in the alarmActivityLogTable.
           After any clear operation, the device will immediately set the variable to off(2).
           "
      ::= { alarmEventConfig 5 }

--
-- Alarms and Events Log Table --
--
alarmEventLogTable  OBJECT-TYPE
      SYNTAX  SEQUENCE OF AlarmEventLogEntry
      MAX-ACCESS  not-accessible
      STATUS  current
      DESCRIPTION
         "A table that holds a record of all raised alarms, cleared alarms and events that occurred.
          This table has limited number of rows, hence, is implemented as a cyclic table."
  ::= { alarmEventLog 1 }

alarmEventLogEntry  OBJECT-TYPE
      SYNTAX      AlarmEventLogEntry
      MAX-ACCESS  not-accessible
      STATUS  current
      DESCRIPTION
         "Each entry in the table holds either a raised alarm,
          either a cleared alarm, or, an event.
         "
      INDEX  { alarmEventLogIndex }
      ::= { alarmEventLogTable 1 }

AlarmEventLogEntry ::= SEQUENCE {
    alarmEventLogIndex            Unsigned32,
    alarmEventLogDateAndTime      DateAndTime,
    alarmEventLogAlarmOrEventId   AlarmEventId,
    alarmEventLogDescription      SnmpAdminString,
    alarmEventLogSourceId         SourceId,
    alarmEventLogSourceType       AlarmEventSourceType,
    alarmEventLogSeverity         AlarmSeverity,
    alarmEventProperties          AlarmProperties,
    alarmEventReason              AlarmReason,
    alarmEventLogSourceName       SnmpAdminString 
 }

alarmEventLogIndex     OBJECT-TYPE
      SYNTAX        Unsigned32
      MAX-ACCESS  not-accessible
      STATUS  current
      DESCRIPTION
         "The table running index."
      ::= { alarmEventLogEntry 1 }

alarmEventLogDateAndTime   OBJECT-TYPE
      SYNTAX        DateAndTime
      MAX-ACCESS    read-only
      STATUS        current
      DESCRIPTION
         "This variable denotes the time in which the alarm or the event occurred.
          If the NE implements a real-time clock, this variable MUST hold the UTC time.
          If the NE does not support a real-time clock, or,
          if from any other reason the UTC time is not known, this variable will hold
          the relative date and time since last reboot (computed from sysUpTime).
         "
      ::= { alarmEventLogEntry 2 }

alarmEventLogAlarmOrEventId  OBJECT-TYPE
      SYNTAX        AlarmEventId
      MAX-ACCESS    read-only
      STATUS        current
      DESCRIPTION
         "This object identifies the ID of the alarm or the event."
      ::= { alarmEventLogEntry 3 }

 alarmEventLogDescription  OBJECT-TYPE
      SYNTAX        SnmpAdminString (SIZE (1..255))
      MAX-ACCESS    read-only
      STATUS        current
      DESCRIPTION
       "The description of the alarm or event.
       "
      ::= { alarmEventLogEntry 4 }

alarmEventLogSourceId     OBJECT-TYPE
      SYNTAX        SourceId
      MAX-ACCESS    read-only
      STATUS        current
      DESCRIPTION
         "This object identifies the specific managed object that caused the alarm."
      ::= { alarmEventLogEntry 5 }

 alarmEventLogSourceType     OBJECT-TYPE
      SYNTAX        AlarmEventSourceType
      MAX-ACCESS    read-only
      STATUS  current
      DESCRIPTION
         "Alarm or Event Source Type."
      ::= { alarmEventLogEntry 6 }

alarmEventLogSeverity       OBJECT-TYPE
      SYNTAX        AlarmSeverity
      MAX-ACCESS    read-only
      STATUS        current
      DESCRIPTION
         "For raised alarms this object denotes the specific alarm severity;
          For cleared alarms its value is always clear(1).
          For events the value of this object is always warning(6).
         "
      ::= { alarmEventLogEntry 7 }

alarmEventProperties       OBJECT-TYPE
      SYNTAX        AlarmProperties
      MAX-ACCESS    read-only
      STATUS        current
      DESCRIPTION
         "This object is relevant for alarms only.
          It shows whether the alarm will be displayed.
          When the bit of maskInlog is '1' this alarm will not be displayed to the user.
         "
      ::= { alarmEventLogEntry 8 }

alarmEventReason       OBJECT-TYPE
      SYNTAX        AlarmReason
      MAX-ACCESS    read-only
      STATUS        current
      DESCRIPTION
         "This object is relevant for alarms only.
          It shows the reason for clearing the alarm.
         "
      ::= { alarmEventLogEntry 9 }

alarmEventLogSourceName  OBJECT-TYPE
      SYNTAX        SnmpAdminString (SIZE (1..32))
      MAX-ACCESS    read-only
      STATUS        current
      DESCRIPTION
         "This object identifies the alarm or event source name defined as an ASCII string.
         For detailed description see object activeAlarmSourceName.
         "
      ::= { alarmEventLogEntry 10 }


--
--   Alarm and Event Log Acknowledgement Table
--
alarmEventLogAckTable OBJECT-TYPE
      SYNTAX  SEQUENCE OF AlarmEventLogAckEntry
      MAX-ACCESS  not-accessible
      STATUS  current
      DESCRIPTION
         "This table enables acknowledging log table entries.
          The acknowledgement is in sense of display; it serves as a filter by time:
          when the manager issues an acknowledgement command,
          the acknowledgement time is saved by the application.
          From that time, only entries that have date and time later than the
          acknowledgement time will be displayed.
          Notes:
          Entries are not removed and not marked in any other way.
          It shall always be possible to display all the log table entries.
         "
  ::= { alarmEventLog 2 }

alarmEventLogAckEntry OBJECT-TYPE
      SYNTAX  AlarmEventLogAckEntry
      MAX-ACCESS  not-accessible
      STATUS  current
      DESCRIPTION
         "The acknowledgment function is implemented in a table
          for possible future required flexibility, such as having
          more than one acknowledge time.
         "
      INDEX   { alarmEventLogAckIndex }
      ::=  { alarmEventLogAckTable 1 }

AlarmEventLogAckEntry ::= SEQUENCE {
    alarmEventLogAckIndex   Unsigned32,
    alarmEventLogAckCmd     INTEGER,
    alarmEventLogAckTime    DateAndTime 
 }

alarmEventLogAckIndex OBJECT-TYPE
      SYNTAX      Unsigned32
      MAX-ACCESS  not-accessible
      STATUS  current
      DESCRIPTION
         " The index of the table represents to which log file the acknowledge refers:
           alarmEventLogAckIndex = 1: Log File   (alarmEventLogTable)
           alarmEventLogAckIndex = 2: Brief Log  (alarmEventBriefLogTable)
           alarmEventLogAckIndex = 3: Acitivity Log (alarmActivityLogTable)
         "
      ::= { alarmEventLogAckEntry 1 }

alarmEventLogAckCmd   OBJECT-TYPE
      SYNTAX      INTEGER
      {
        off(2),
        on(3)
      }
      MAX-ACCESS  read-write
      STATUS  current
      DESCRIPTION
         "When the manager sets the value of this variable to on (3),
          the device saves the date and time to AlarmEventLogAckTime,
          and sets the value of this variable to off(2).
         "
      ::= { alarmEventLogAckEntry 2 }

alarmEventLogAckTime  OBJECT-TYPE
      SYNTAX      DateAndTime
      MAX-ACCESS  read-only
      STATUS  current
      DESCRIPTION
         "This variable denotes the date and time when alarmEventLogAckCmd
          was last set to any value different than off(2).
         "
      ::= { alarmEventLogAckEntry 3 }

--
-- Masking Report Types by Severity --
--

maskReportTable  OBJECT-TYPE
      SYNTAX  SEQUENCE OF MaskReportEntry
      MAX-ACCESS  not-accessible
      STATUS  current
      DESCRIPTION
         "This table enables masking alarms on various reporting means.
         "
  ::= { alarmEventConfig 6 }

maskReportEntry  OBJECT-TYPE
      SYNTAX  MaskReportEntry
      MAX-ACCESS  not-accessible
      STATUS  current
      DESCRIPTION
         "Each entry in this table contains a masking severity per reporting means.
          The masking policy for a higher severity level enforces the policy
          for all lower severity levels.

          For example: if sending SNMP notifications is masked for Major severity
          then SNMP notifications will be masked also for Minor severity."
      INDEX   { maskReportType }
      ::= {  maskReportTable 1 }

MaskReportEntry ::= SEQUENCE {
    maskReportType            INTEGER,
    maskReportSeverity        INTEGER 
 }

maskReportType  OBJECT-TYPE
    SYNTAX  INTEGER {
        log      (1),
        snmpTrap (2),
        ledRelay (3),
        popUp  (4),
        vtyPopUp (5) --CLI remote terminal popup messages
    }
      MAX-ACCESS  not-accessible
      STATUS  current
      DESCRIPTION
        " This variable enables alarm and event masking on various reporting means.
          Note that the Textual Convention is not used here.
          Reason: Some bit Combinations are not allowed and require special dependency checks."
      ::= { maskReportEntry 1 }

maskReportSeverity      OBJECT-TYPE
      SYNTAX            INTEGER {
      critical (3),
      major    (4),
      minor    (5),
      warning  (6),
      noMask   (255)
      }
      MAX-ACCESS        read-write
      STATUS  current
      DESCRIPTION
        " This object MUST be one of the following values that are defined in the
          TC AlarmSeverity:
          critical(3)
          major(4)
          minor(5)
          warning (6)

          or
          noMask (255) value that is used to remove the mask.
         "
      ::= { maskReportEntry 2 }


--
-- Minimum Severity for turning on the Alarm LED --
--
alarmLedMinSeverity OBJECT-TYPE
      SYNTAX AlarmSeverity
      MAX-ACCESS read-write
      STATUS current
      DESCRIPTION
          "This scalar is relevant only for devices with only one Alarm LED.
           It enables configuration of the minimum alarm severity upon which to turn on the alarm led.
           Legal values are: critical(3), major(4), minor(5)."
       ::= { alarmEventConfig 7 }


--
-- Convert Alarm or Event Name to its ID --
--

alarmEventConvertNameToIdTable OBJECT-TYPE
   SYNTAX      SEQUENCE OF AlarmEventConvertNameToIdEntry
   MAX-ACCESS  not-accessible
   STATUS      current
   DESCRIPTION
       "A table that Converts the Name of an alarm or event to its ID."
   ::= { alarmEventConfig 8 }

alarmEventConvertNameToIdEntry OBJECT-TYPE
   SYNTAX      AlarmEventConvertNameToIdEntry
   MAX-ACCESS  not-accessible
   STATUS      current
   DESCRIPTION
       "An entry appears in this table for each possible alarm and event.
        This table MUST be persistent upon system reboot."
   INDEX  { alarmEventConvertName, alarmEventConvertSourceType}
   ::= { alarmEventConvertNameToIdTable 1 }

AlarmEventConvertNameToIdEntry ::= SEQUENCE {
    alarmEventConvertName                    SnmpAdminString,
    alarmEventConvertSourceType              AlarmEventSourceType,
    alarmEventConvertId                      AlarmEventId 
 }

alarmEventConvertName    OBJECT-TYPE
   SYNTAX       SnmpAdminString (SIZE (1..30))
   MAX-ACCESS   read-only
   STATUS       current
   DESCRIPTION
       "A name of up to 30 characters."
    ::= { alarmEventConvertNameToIdEntry 1 }

 alarmEventConvertSourceType    OBJECT-TYPE
   SYNTAX      AlarmEventSourceType
   MAX-ACCESS  not-accessible
   STATUS      current
   DESCRIPTION
         "This is the Source Type of alarm or event.
         "
   ::= { alarmEventConvertNameToIdEntry 2 }

alarmEventConvertId      OBJECT-TYPE
   SYNTAX      AlarmEventId
   MAX-ACCESS  not-accessible
   STATUS      current
   DESCRIPTION
       "The table index unique identifier of the alarm or the event."
   ::= { alarmEventConvertNameToIdEntry 3 }


--
-- Alarm Relay Input Table --
--
alarmRelayInputTable  OBJECT-TYPE
      SYNTAX  SEQUENCE OF AlarmRelayInputEntry
      MAX-ACCESS  not-accessible
      STATUS  current
      DESCRIPTION
         "This table enables configuration and status of Alarm Input Relay Cards or chassis.
          Examples for input relays: temperature sensor or alert system.
          "
  ::= { alarmEventConfig 9 }

alarmRelayInputEntry  OBJECT-TYPE
      SYNTAX      AlarmRelayInputEntry
      MAX-ACCESS  not-accessible
      STATUS  current
      DESCRIPTION
         "Entry containing user configuration for a specific alarm Input Relay."
      INDEX { alarmRelayInputRelayIndex }
            ::= { alarmRelayInputTable 1 }

AlarmRelayInputEntry ::= SEQUENCE {
    alarmRelayInputRelayIndex   Unsigned32,
    alarmRelayInputDescription  SnmpAdminString,
    alarmRelayInputActiveState  INTEGER,
    alarmRelayInputOperState    INTEGER 
 }

alarmRelayInputRelayIndex      OBJECT-TYPE
      SYNTAX       Unsigned32
      MAX-ACCESS   not-accessible
      STATUS       current
      DESCRIPTION
         "This object is the index of the Alarm Relay.
           Values: 1- critical, 2- major, 3- minor according to alarm severity.
           For devices that have only one alarm output the value
           will be one (1).
           For devices with alarms on a slot, the index will be:
           (1000*slot number)+ alarm relay severity number."
   ::= { alarmRelayInputEntry 1 }

 alarmRelayInputDescription  OBJECT-TYPE
      SYNTAX       SnmpAdminString  (SIZE (1..80))
      MAX-ACCESS   read-write
      STATUS       current
      DESCRIPTION
       "The Descriptions of the alarm relay.
        The default descriptions will be one of: Alarm Input 1, Alarm Input 2,
        Alarm Input 3, Alarm Input 4 etc.
        according to the number of connected relay.
        "
   ::= { alarmRelayInputEntry 2 }

alarmRelayInputActiveState      OBJECT-TYPE
      SYNTAX       INTEGER {
        high     (1),
        low      (2),
        none     (3)
    }
      MAX-ACCESS   read-write
      STATUS       current
      DESCRIPTION
         "This object shows the Active State voltage.
          The value of none (3) means that the Alarm Input is inactive.
          Default state of alarm input is none (3).
         "
   ::= { alarmRelayInputEntry 3 }

alarmRelayInputOperState      OBJECT-TYPE
      SYNTAX       INTEGER {
        active   (1),
        inActive (2)
        }
      MAX-ACCESS   read-only
      STATUS       current
      DESCRIPTION
         "This object shows the operational state of the alarm relay.
         "
   ::= { alarmRelayInputEntry 4 }


alarmRelayOutputTable  OBJECT-TYPE
      SYNTAX  SEQUENCE OF AlarmRelayOutputEntry
      MAX-ACCESS  not-accessible
      STATUS  current
      DESCRIPTION
         "This table enables configuration of Alarm Output Relay Cards or chassis.
          Example for output relay: alarm siren.
         "
  ::= { alarmEventConfig 10 }

alarmRelayOutputEntry  OBJECT-TYPE
      SYNTAX      AlarmRelayOutputEntry
      MAX-ACCESS  not-accessible
      STATUS  current
      DESCRIPTION
         "Entry containing user configuration and status for a specific alarm Output Relay."
      INDEX { alarmRelayOutputRelayIndex }
            ::= { alarmRelayOutputTable 1 }

AlarmRelayOutputEntry ::= SEQUENCE {
    alarmRelayOutputRelayIndex   Unsigned32,
    alarmRelayOutputEnergized    INTEGER,
    alarmRelayOutputOperState    INTEGER,
    alarmRelayOutputCmd          INTEGER 
 }

alarmRelayOutputRelayIndex      OBJECT-TYPE
      SYNTAX       Unsigned32
      MAX-ACCESS   not-accessible
      STATUS       current
      DESCRIPTION
         "This object is the index of the Alarm Relay.
          Values: 1- critical, 2- major, 3- minor according to alarm severity.
          For devices with alarms on a slot, the index will be:
          (1000*slot number)+ alarm relay severity number.
         "
   ::= { alarmRelayOutputEntry 1 }

alarmRelayOutputEnergized      OBJECT-TYPE
      SYNTAX       INTEGER {
        no     (2),
        yes    (3)
        }
      MAX-ACCESS   read-write
      STATUS       current
      DESCRIPTION
         "This object shows whether the relay transports electricity permanently (energized)
         or just when the alarm is activated (deEnergized).
         Default value for critical alarm relay on chassis will be: energized (1).
         For other severities, the default is:  deEnergized (2).
         "
   ::= { alarmRelayOutputEntry 2 }

alarmRelayOutputOperState      OBJECT-TYPE
      SYNTAX       INTEGER {
        active   (1),
        inActive (2)
        }
      MAX-ACCESS   read-only
      STATUS       current
      DESCRIPTION
         "This object shows the operational state of the alarm relay.
         "
   ::= { alarmRelayOutputEntry 3 }

alarmRelayOutputCmd OBJECT-TYPE
      SYNTAX  INTEGER
       {
       off(2),
       cutOffOn (3)
       }
       MAX-ACCESS  read-write
      STATUS  current
      DESCRIPTION
      "Setting this object to cutOffOn, will suppress the alarm output
       as long as it is not triggered again.
      Upon completion, the value will automatically change to off(2)."
    DEFVAL  { off }
::= { alarmRelayOutputEntry 4 }



alarmBindToRelayTable  OBJECT-TYPE
      SYNTAX  SEQUENCE OF AlarmBindToRelayEntry
      MAX-ACCESS  not-accessible
      STATUS  current
      DESCRIPTION
         "This table enables binding alarms to the alarm output relays."
  ::= { alarmEventConfig 11 }

alarmBindToRelayEntry  OBJECT-TYPE
      SYNTAX      AlarmBindToRelayEntry
      MAX-ACCESS  not-accessible
      STATUS  current
      DESCRIPTION
         "Entry containing the binding of alarms to the alarm output relays."
      INDEX { alarmBindToRelayIndex }
            ::= { alarmBindToRelayTable 1 }

AlarmBindToRelayEntry ::= SEQUENCE {
    alarmBindToRelayIndex           SourceId,
    alarmBindToRelayRowStatus       RowStatus,
    alarmBindToRelaySourceType      AlarmEventSourceType,
    alarmBindToRelaySourceId        SourceId,
    alarmBindToRelayAlarmId         AlarmEventId 
 }

alarmBindToRelayIndex      OBJECT-TYPE
      SYNTAX       SourceId
      MAX-ACCESS   not-accessible
      STATUS       current
      DESCRIPTION
         "This object is the index of the Alarm Output Relay.
          Values: 1- critical, 2- major, 3- minor according to alarm severity.
          For devices with alarms on a slot, the index will be:
          (1000*slot number)+ alarm relay severity number.
         "
   ::= { alarmBindToRelayEntry 1 }

alarmBindToRelayRowStatus   OBJECT-TYPE
      SYNTAX        RowStatus
      MAX-ACCESS    read-create
      STATUS        current
      DESCRIPTION
         "Enable rows creation/deletion.
          This is used for managed objects that are dynamically created or removed.
          "
   ::= { alarmBindToRelayEntry 2 }

alarmBindToRelaySourceType    OBJECT-TYPE
   SYNTAX      AlarmEventSourceType
   MAX-ACCESS  read-create
   STATUS      current
   DESCRIPTION
         "This is the Source Type of alarm or event that will be bound to the alarm relay.
         "
   ::= { alarmBindToRelayEntry 3 }

alarmBindToRelaySourceId  OBJECT-TYPE
      SYNTAX       SourceId
      MAX-ACCESS   read-create
      STATUS       current
      DESCRIPTION
         "Source ID (port, card etc.) that causes the alarm and will be bound to the alarm relay.
          Note: In order to bind all Source IDs of the same Source Type,
          this object should be set to zero.
          "
   ::= { alarmBindToRelayEntry 4 }

alarmBindToRelayAlarmId      OBJECT-TYPE
      SYNTAX       AlarmEventId
      MAX-ACCESS   read-create
      STATUS       current
      DESCRIPTION
         "Alarm or Event ID that will be bound to the alarm relay.
         "
   ::= { alarmBindToRelayEntry 5 }


--
-- Defect Soak Interval Table --
--

defectSoakTable OBJECT-TYPE
   SYNTAX      SEQUENCE OF DefectSoakEntry
   MAX-ACCESS  not-accessible
   STATUS      current
   DESCRIPTION
       "A table that defines the Defect Soaking and Clearing time periods."
   ::= { alarmEventConfig 12 }

defectSoakEntry OBJECT-TYPE
   SYNTAX      DefectSoakEntry
   MAX-ACCESS  not-accessible
   STATUS      current
   DESCRIPTION
       "An entry appears in this table for each technology."
   INDEX  { defectSoakTechnology }
   ::= { defectSoakTable 1 }

DefectSoakEntry ::= SEQUENCE {
    defectSoakTechnology         INTEGER,
    defectSoakInterval           Integer32,
    defectSoakClearInterval      Integer32 
 }

defectSoakTechnology      OBJECT-TYPE
   SYNTAX      INTEGER (1..1)
   MAX-ACCESS  not-accessible
   STATUS      current
   DESCRIPTION
   "The value will be a dummy value and equal to 1.
    "
   ::= { defectSoakEntry 1 }

defectSoakInterval    OBJECT-TYPE
      SYNTAX      Integer32
      UNITS       "milliseconds"
      MAX-ACCESS  read-write
      STATUS      current
      DESCRIPTION
          "The time in milliseconds since a defect occurs until an alarm is raised.
          "
   ::= { defectSoakEntry 2 }

defectSoakClearInterval    OBJECT-TYPE
      SYNTAX      Integer32
      UNITS       "milliseconds"
      MAX-ACCESS  read-write
      STATUS      current
      DESCRIPTION
         "The time in milliseconds since a defect is resolved until the alarm is cleared.
          "
   ::= { defectSoakEntry 3 }


--
-- Alarms and Events Configuration Table  per Instance --
--
alarmEventConfiguredTable OBJECT-TYPE
   SYNTAX      SEQUENCE OF AlarmEventConfiguredEntry
   MAX-ACCESS  not-accessible
   STATUS      current
   DESCRIPTION
       "A table of entities configuration mask & severity.
       This tables reflects per each existing or configured instance alarm severity and masking,
       according to RO alarmEventAttrTable and entries configured in alarmEventConfigTable     "
  ::= { alarmEventConfig 13 }

alarmEventConfiguredEntry OBJECT-TYPE
   SYNTAX      AlarmEventConfiguredEntry
   MAX-ACCESS  not-accessible
   STATUS      current
   DESCRIPTION
       "For all existing entities supporting fault management
         there is an entry in this table holding the mask & severity configured. "

   INDEX  { alarmEventConfiguredSourceType, alarmEventConfiguredSourceId,
                  alarmEventConfiguredId }
   ::= { alarmEventConfiguredTable 1 }

AlarmEventConfiguredEntry ::= SEQUENCE {
    alarmEventConfiguredSourceType        AlarmEventSourceType,
    alarmEventConfiguredSourceId          SourceId,
    alarmEventConfiguredId                AlarmEventId,
    alarmEventConfiguredSeverity          AlarmSeverity,
    alarmEventConfiguredMasking           AlarmEventMasking 
 }


alarmEventConfiguredSourceType   OBJECT-TYPE
  SYNTAX      AlarmEventSourceType
  MAX-ACCESS  not-accessible
  STATUS      current
  DESCRIPTION
        "This is the Source Type of the active alarm.
        "
  ::= { alarmEventConfiguredEntry 1 }

alarmEventConfiguredSourceId    OBJECT-TYPE
   SYNTAX      SourceId
   MAX-ACCESS  not-accessible
   STATUS      current
   DESCRIPTION
      "This object identifies the specific managed object that caused the alarm.
      "
   ::= { alarmEventConfiguredEntry 2 }

alarmEventConfiguredId      OBJECT-TYPE
   SYNTAX      AlarmEventId
   MAX-ACCESS  not-accessible
   STATUS      current
   DESCRIPTION
      "This object identifies the ID of the raised alarm.
      "
   ::= { alarmEventConfiguredEntry 3 }

alarmEventConfiguredSeverity    OBJECT-TYPE
   SYNTAX      AlarmSeverity
   MAX-ACCESS  read-only
   STATUS      current
   DESCRIPTION
      "This object identifies the severity of the raised alarm.
       Note that the severity of the alarm in the Active Alarm table may be different from the
       severity configured in the AlarmEventConfigTable due to severity escalation or deescalation
       which may be performed by the NE as a consequent of internal events.
      "
   ::= { alarmEventConfiguredEntry 4 }

alarmEventConfiguredMasking   OBJECT-TYPE
      SYNTAX        AlarmEventMasking
      MAX-ACCESS    read-only
      STATUS        current
      DESCRIPTION
         "This object identifies the alarm and event masking on various reporting means.
         "
      ::= { alarmEventConfiguredEntry 5 }


alarmEventLogFileTimestampType OBJECT-TYPE
      SYNTAX INTEGER {
          utc(2),
          localTime(3)
      }
      MAX-ACCESS read-write
      STATUS current
      DESCRIPTION
          "This object reflects the type of event and alarm timestamps in the log file
          (which may be uploaded).
           utc (2):       UTC timestamps are used
           localTime (3): Timestamps are in the device local time (taking into account its
                          time zone and daylight saving time)
          "
      DEFVAL  { utc }
      ::= { alarmEventConfig 14 }



--
--   Alarm Log Statistics
--
      alarmEventBriefLogTable  OBJECT-TYPE
      SYNTAX  SEQUENCE OF AlarmEventBriefLogEntry
      MAX-ACCESS  not-accessible
      STATUS  current
      DESCRIPTION
         "This table holds the alarm log statistics information.
         "
  ::= { alarmEventStatistics 1 }

alarmEventBriefLogEntry OBJECT-TYPE
      SYNTAX  AlarmEventBriefLogEntry
      MAX-ACCESS  not-accessible
      STATUS  current
      DESCRIPTION
         "Statistics on the alarm log."
      INDEX   { alarmEventBriefLogSourceType, alarmEventBriefLogSourceId, alarmEventBriefLogAlarmId }

  ::= {  alarmEventBriefLogTable 1 }

AlarmEventBriefLogEntry ::= SEQUENCE {
    alarmEventBriefLogSourceType             AlarmEventSourceType,
    alarmEventBriefLogSourceId               SourceId,
    alarmEventBriefLogAlarmId                AlarmEventId,
    alarmEventBriefLogAlarmSeverity          AlarmSeverity,
    alarmEventBriefLogTotalRaised            Counter32,
    alarmEventBriefLogTotalRaisedSinceAck    Counter32,
    alarmEventBriefLogLastRaisedTime         DateAndTime,
    alarmEventBriefLogLastRaisedTimeSinceAck DateAndTime,
    alarmEventBriefLogLastClearedTime        DateAndTime,
    alarmEventBriefLogLastClearedTimeSinceAck DateAndTime,
    alarmEventBriefLogSourceName                       SnmpAdminString 
 }

alarmEventBriefLogSourceType    OBJECT-TYPE
      SYNTAX      AlarmEventSourceType
      MAX-ACCESS  not-accessible
      STATUS  current
      DESCRIPTION
         "Alarm or Event Source Type.
         "
     ::= { alarmEventBriefLogEntry 1 }

alarmEventBriefLogSourceId    OBJECT-TYPE
      SYNTAX      SourceId
      MAX-ACCESS  not-accessible
      STATUS  current
      DESCRIPTION
         "This index identifies the specific managed object that caused the alarm.
         "
     ::= { alarmEventBriefLogEntry 2 }

alarmEventBriefLogAlarmId         OBJECT-TYPE
      SYNTAX      AlarmEventId
      MAX-ACCESS  not-accessible
      STATUS  current
      DESCRIPTION
         "This index identifies the ID of the raised alarm.
         "
     ::= { alarmEventBriefLogEntry 3 }

alarmEventBriefLogAlarmSeverity    OBJECT-TYPE
   SYNTAX      AlarmSeverity
   MAX-ACCESS  read-only
   STATUS      current
   DESCRIPTION
      "This object identifies the severity of the raised alarm.
      "
      ::= { alarmEventBriefLogEntry 4 }

alarmEventBriefLogTotalRaised   OBJECT-TYPE
      SYNTAX        Counter32
      MAX-ACCESS    read-only
      STATUS        current
      DESCRIPTION
      "This objects denotes how many times the alarm was raised since last reboot.
      "
     ::= { alarmEventBriefLogEntry 5 }

alarmEventBriefLogTotalRaisedSinceAck   OBJECT-TYPE
      SYNTAX        Counter32
      MAX-ACCESS    read-only
      STATUS        current
      DESCRIPTION
      "This objects denotes how many times the alarm was raised since last acknowledge.
      "
     ::= { alarmEventBriefLogEntry 6 }

alarmEventBriefLogLastRaisedTime   OBJECT-TYPE
      SYNTAX        DateAndTime
      MAX-ACCESS    read-only
      STATUS        current
      DESCRIPTION
      "This object denotes the date and time that the alarm was last raised.
      "
     ::= { alarmEventBriefLogEntry 7 }

alarmEventBriefLogLastRaisedTimeSinceAck   OBJECT-TYPE
      SYNTAX        DateAndTime
      MAX-ACCESS    read-only
      STATUS        current
      DESCRIPTION
      "This object denotes the date and time that the alarm was last raised since acknowledged.
      "
     ::= { alarmEventBriefLogEntry 8 }

alarmEventBriefLogLastClearedTime   OBJECT-TYPE
      SYNTAX        DateAndTime
      MAX-ACCESS    read-only
      STATUS        current
      DESCRIPTION
      "This object denotes the date and time that the alarms was last cleared.
      "
     ::= { alarmEventBriefLogEntry 9 }

alarmEventBriefLogLastClearedTimeSinceAck   OBJECT-TYPE
      SYNTAX        DateAndTime
      MAX-ACCESS    read-only
      STATUS        current
      DESCRIPTION
      "This object denotes the date and time that the alarms was last cleared since acknowledged.
      "
     ::= { alarmEventBriefLogEntry 10 }

alarmEventBriefLogSourceName  OBJECT-TYPE
      SYNTAX        SnmpAdminString (SIZE (1..32))
      MAX-ACCESS    read-only
      STATUS        current
      DESCRIPTION
         "This object identifies the alarm or event source name defined as an ASCII string.
         For detailed description see object activeAlarmSourceName.
         "
      ::= { alarmEventBriefLogEntry 11 }


--
-- Alarm and Event Statistics
--

alarmEventStatsTable  OBJECT-TYPE
      SYNTAX  SEQUENCE OF AlarmEventStatsEntry
      MAX-ACCESS  not-accessible
      STATUS  current
      DESCRIPTION
         "This table holds Alarms and Events statistics information.
         This information summarizes the Total number of Critical, Major, Minor Alarms
         and number of Total events for Active Alarms or in the Log.
         "
  ::= { alarmEventStatistics 2 }


alarmEventStatsEntry OBJECT-TYPE
      SYNTAX  AlarmEventStatsEntry
      MAX-ACCESS  not-accessible
      STATUS  current
      DESCRIPTION
         "Statistics entry for the alarms and events."
      INDEX   { alarmEventStatsType }

  ::= {  alarmEventStatsTable 1 }

AlarmEventStatsEntry ::= SEQUENCE {
    alarmEventStatsType              AlarmEventLogStatsType,
    alarmEventStatsTotalCritical     Gauge32,
    alarmEventStatsTotalMajor        Gauge32,
    alarmEventStatsTotalMinor        Gauge32,
    alarmEventStatsTotalEvents       Gauge32 
 }


alarmEventStatsType    OBJECT-TYPE
      SYNTAX        AlarmEventLogStatsType
      MAX-ACCESS    not-accessible
      STATUS        current
      DESCRIPTION
         "This index shows the Type of Statistics.
          It can be from the Active Alarms or from the Log .
         "
  ::= { alarmEventStatsEntry 1 }

alarmEventStatsTotalCritical  OBJECT-TYPE
      SYNTAX        Gauge32
      MAX-ACCESS    read-only
      STATUS        current
      DESCRIPTION
         "This variable counts the total number of raised alarms
          with severity Critical.
         "
  ::= { alarmEventStatsEntry 2 }

alarmEventStatsTotalMajor  OBJECT-TYPE
      SYNTAX        Gauge32
      MAX-ACCESS    read-only
      STATUS        current
      DESCRIPTION
         "This variable counts the total number of raised alarms
          with severity Major.
         "
  ::= { alarmEventStatsEntry 3 }

alarmEventStatsTotalMinor  OBJECT-TYPE
      SYNTAX        Gauge32
      MAX-ACCESS    read-only
      STATUS        current
      DESCRIPTION
         "This variable counts the total number of raised alarms
          with severity Minor.
         "
  ::= { alarmEventStatsEntry 4 }

 alarmEventStatsTotalEvents  OBJECT-TYPE
      SYNTAX        Gauge32
      MAX-ACCESS    read-only
      STATUS        current
      DESCRIPTION
         "This variable counts the total number of events."
  ::= { alarmEventStatsEntry 5 }

 
-- ------------------------------------------------------------------ --
-- Banner Table
-- ------------------------------------------------------------------ --
 
bannerTable OBJECT-TYPE
    SYNTAX     SEQUENCE OF BannerEntry
    MAX-ACCESS not-accessible
    STATUS     current
    DESCRIPTION
        "This table contains banners the CLI displays."
     ::= { agnAccess 11 }
 
bannerEntry OBJECT-TYPE
    SYNTAX     BannerEntry
    MAX-ACCESS not-accessible
    STATUS     current
    DESCRIPTION
        "Each entry contains up to 250 characters of a banner, 
         identified by bannerType.
         If a banner contains more than 250 characters it spans
         multiple entries, indexed by bannerLineNumber."
    INDEX { bannerType, bannerLineNumber }
    ::= { bannerTable 1 } 

BannerEntry ::= SEQUENCE {
    bannerType        INTEGER,
    bannerLineNumber  Unsigned32,
    bannerRowStatus   RowStatus,
    bannerText        SnmpAdminString 
 }
 
bannerType OBJECT-TYPE
    SYNTAX INTEGER {
        preLogin  (1),
        postLogin (2)
    }
    MAX-ACCESS not-accessible
    STATUS current
    DESCRIPTION
        "Banner type."
    ::= { bannerEntry 1 }
 
bannerLineNumber OBJECT-TYPE
    SYNTAX     Unsigned32
    MAX-ACCESS not-accessible
    STATUS     current
    DESCRIPTION
        "Banner line number."
    ::= { bannerEntry 2 }
 
bannerRowStatus OBJECT-TYPE
    SYNTAX     RowStatus
    MAX-ACCESS read-create
    STATUS     current
    DESCRIPTION
        "Create and delete rows in this table.
         Only createAndGo and destroy are supported."
    ::= { bannerEntry 3 }
 
bannerText OBJECT-TYPE
    SYNTAX      SnmpAdminString (SIZE(1..250))
    MAX-ACCESS  read-create
    STATUS      current
    DESCRIPTION
        "Banner text."
    ::= { bannerEntry 4 }
    
    
END

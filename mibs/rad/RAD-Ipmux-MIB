RAD-Ipmux-MIB DEFINITIONS ::= BEGIN


-- It is RAD's intent to encourage the widespread use of
-- this Specification in connection with the management of
-- RAD products. RAD grants vendors, end-users,
-- and other interested parties a non-exclusive license to
-- use this Specification in connection with the management
-- of RAD products.

-- This Specification is supplied "as is," and RAD makes
-- no warranty, either express or implied, as to the use,
-- operation, condition, or performance of the Specification.


IMPORTS

       ifAlias     FROM  IF-MIB
       Integer32, Counter32, IpAddress, 
       Unsigned32, OBJECT-TYPE, MODULE-IDENTITY, 
       NOTIFICATION-TYPE     FROM  SNMPv2-SMI
       atmInterfaceAlarmStatus     FROM  RAD-NtePrtCo-MIB
       RowStatus, MacAddress     FROM  SNMPv2-TC
       diverseIfWanGen, radSysWanEvents     FROM  RAD-SMI-MIB
       agnLed     FROM  RAD-GEN-MIB; 


    ip2If MODULE-IDENTITY
		LAST-UPDATED "201502191802Z"  -- February 19, 2015
        ORGANIZATION "RAD Data Communications Ltd."
        CONTACT-INFO
        "System Department

         Email:  mibs@rad.com
         Postal: RAD Data Communications Ltd.
                 24 Raoul Wallenberg St.
                 Tel-Aviv 6971920
                 Israel

         Phone:  +972-3-645-5421
         Fax:    +972-3-760-7844"
         DESCRIPTION
            "IPMUX MIB."
	::= { diverseIfWanGen 7 }


ip2IfTable OBJECT-TYPE
       SYNTAX  SEQUENCE OF Ip2IfEntry
       MAX-ACCESS  not-accessible
       STATUS  current
       DESCRIPTION
       "Channels Configuration Table."
       ::= { ip2If 1 }

ip2IfEntry OBJECT-TYPE
       SYNTAX Ip2IfEntry
       MAX-ACCESS not-accessible
       STATUS current
       DESCRIPTION
          "Application layer configuration per link"
       INDEX   { ip2IfChannelIndex }
       ::= { ip2IfTable 1 }

Ip2IfEntry ::= SEQUENCE {
    ip2IfChannelIndex             Integer32,
    ip2IfRowStatus                 RowStatus,
         ip2IfOperStatus	    INTEGER,
         ip2IfAdminStatus	    INTEGER,
         ip2IfDestAddr		    IpAddress,
         ip2IfNextHop		    IpAddress,
         ip2IfDestPort		    Integer32,
         ip2IfMacAddr		    MacAddress,
         ip2IfJitterBuffer	    Integer32,
		 ip2IfTos			    Integer32,
		 ip2IfTDMBytesInFrame   Integer32,
		 ip2IfVlanSupport       INTEGER,
		 ip2IfVlanIdentifier    Integer32,
		 ip2IfVlanFramePriority Integer32,
		 ip2IfExitPort          INTEGER,
		 ip2IfVoiceOos			OCTET STRING,
		 ip2IfDataOos			OCTET STRING,
		 ip2IfBundleUsage 		Integer32,
		 ip2IfOAM				OCTET STRING,
		 ip2IfTDMoIpMode		INTEGER,
		 ip2IfTimeElapsed		Integer32,
		 ip2IfValidIntervals    Integer32,
		 ip2IfFarEndType        INTEGER,
		 ip2IfRdnState			INTEGER,
		 ip2IfSourceAddr		IpAddress,
		 ip2IfBandWidth 		Integer32,
		 ip2IfMeasuredSilence   Integer32,
		 ip2IfPayloadType		INTEGER,
		 ip2IfProtocolVersion	INTEGER,
         ip2IfTdmBackUpNextHop  IpAddress,	
		 ip2IfOosTxEnable		INTEGER,		 
		 ip2IfConnCheckPktFrequency Integer32,
         ip2IfConnPktTimeOutCycles  Integer32,
		 ip2IfMfRelay			    INTEGER,
		 ip2IfTxGain			    Integer32,
		 ip2IfSuperTandem			INTEGER,
		 ip2IfSrcPort				Integer32,
     	 ip2IfModemCalls            INTEGER,
         ip2IfMinPulseWidth         Integer32,
		 ip2IfMinPowerLevel         Integer32,
		 ip2IfEchoCanceler          INTEGER,
		 ip2IfCodingLaw             INTEGER,
		 ip2IfCustomToneDetect      INTEGER,
		 ip2IfCallerIdDelay	        Integer32,
		 ip2IfConnectivityMode      INTEGER,
		 ip2IfClockSourceEnable		INTEGER,
		 ip2IfNetworkType			INTEGER,
		 ip2IfMplsRxLabelEnable		INTEGER,
		 ip2IfMplsRxLabel			Integer32,
		 ip2IfMplsTxLabelEnable		INTEGER,
		 ip2IfMplsTxLabel			Integer32,
		 ip2IfMplsTxExpBits			Integer32,
		 ip2IfMfcSpoofing           INTEGER,
		 ip2IfToneAckInterval       Integer32,
		 ip2IfNextHopType 			INTEGER,
 		 ip2IfNoiseLevelForVAD      INTEGER,
		 ip2IfClockPreferences		INTEGER,
		 ip2IfConnectionMode		INTEGER,
		 ip2IfRingBack              INTEGER,
		 ip2IfReversePolarity       INTEGER,
		 ip2IfPulseMeter            INTEGER,
		 ip2IfPulseMeterFreq        INTEGER,
		 ip2IfPulseMeterPeriod      Integer32,
		 ip2IfOnHookDetect          INTEGER,
		 ip2IfComfortNoiseGen       INTEGER,
		 ip2IfExitChannel			Integer32,
		 ip2IfMaxVBDModemCalls		Integer32,
		 ip2IfMaxRelayModemCalls	Integer32,
		 ip2IfCustomToneFrequency	INTEGER,
		 ip2IfVadMethod             INTEGER,
		 ip2IfRxGain                Integer32,
		 ip2IfCallerIDType          INTEGER,
		 ip2IfPeerAddrType 			INTEGER,		 
		 ip2IfVbdRate               INTEGER,
		 ip2IfDtmfDetection         INTEGER,
		 ip2IfNlpCutoffLevel        Unsigned32,
		 ip2IfDtdErlRatioCutoffQ3   Unsigned32,
		 ip2IfCASRedundancy         INTEGER,
		 ip2IfBundleSensitivity     INTEGER,
		 ip2IfOAMBundleIdent        INTEGER,
		 ip2IfMaxTxQueue			Unsigned32,
		 ip2IfMaxGprsTxQueue		Unsigned32,
		 ip2IfV23HD                 INTEGER,
		 ip2IfModemProtocolMode		OCTET STRING,
		 ip2IfCdisCngDetectionTime  Unsigned32,
		 ip2IfSuperTandemBitMask	OCTET STRING,
		 ip2IfVbdSwitchbackTime     Unsigned32,
		 ip2IfCallerIdTxGain		Integer32,
		 ip2IfCallerIdRxGain		Integer32,
		 ip2IfUdpMuxMethod			INTEGER,
		 ip2IfCallerIdDetection		INTEGER,
		 ip2IfWap					INTEGER,
		 ip2IfSignalingOos          INTEGER
 }

ip2IfChannelIndex OBJECT-TYPE
    SYNTAX  Integer32
    MAX-ACCESS  read-only
    STATUS  current
    DESCRIPTION
    "The channel index, which is actualy the bundle ID."
    ::= { ip2IfEntry 1 }

ip2IfRowStatus OBJECT-TYPE
    SYNTAX  RowStatus
    MAX-ACCESS  read-create
    STATUS  current
    DESCRIPTION
    "This parameter allows NMS to create/delete entries of this table."
    ::= { ip2IfEntry 2 }


ip2IfOperStatus OBJECT-TYPE
    SYNTAX       INTEGER {
    down		(2),
    up	        (3),
    disabled    (4),
    remoteFail  (5),
    localFail	(6),
	unavailable (7),
	validationFail  (8),
	standby		(9),
	tdmFail	   (10),
	hwMismatch (11)
    }
    MAX-ACCESS    read-only
    STATUS        current
    DESCRIPTION
    "The actual link status.
    remoteFail - No Rx.
    localFail  - No Tx.
    unavailable - No echo replay or replay with invalid code or when connection is in Test state.
    valiodationFail - Connection is in not valid state.
    standby - offline (can be in pre-sync mode).
    tdmFail - oper status is down cause of failure in the tdm.
    hwMismatch - the bundle exists on a card that is not installed or has a different
                 type than the programmed card."
    ::= { ip2IfEntry 3 }

ip2IfAdminStatus OBJECT-TYPE
    SYNTAX       INTEGER {
    down		(2),
    up	    (3)
    }
    MAX-ACCESS    read-create
    STATUS        current
    DESCRIPTION
    "The desired state of the link."
    ::= { ip2IfEntry 4 }

ip2IfDestAddr OBJECT-TYPE
    SYNTAX  IpAddress 
    MAX-ACCESS  read-create
    STATUS  current
    DESCRIPTION
    "The destination IP address."
    ::= { ip2IfEntry 5 }

ip2IfNextHop OBJECT-TYPE
    SYNTAX  IpAddress 
    MAX-ACCESS  read-create
    STATUS  current
    DESCRIPTION
    "The next hop to which the frame should be sent.
     Default value - 0.0.0.0. 
     Upon setting the default value the frame is sent 
     to the default Gateway."
    ::= { ip2IfEntry 6 }

ip2IfDestPort OBJECT-TYPE
    SYNTAX  Integer32 
    MAX-ACCESS  read-create
    STATUS  current
    DESCRIPTION
    "The destination Bundle at the far-end device."
    ::= { ip2IfEntry 7 }
  
ip2IfMacAddr OBJECT-TYPE
    SYNTAX  MacAddress
    MAX-ACCESS  read-create
    STATUS  current
    DESCRIPTION
    "The Destination MAC address of the next hop or 
     destination station."
    ::= { ip2IfEntry 8 }

ip2IfJitterBuffer OBJECT-TYPE
    SYNTAX  Integer32 
    MAX-ACCESS  read-create
    STATUS  current
    DESCRIPTION
    "The maximum cell arrival jitter in 10 usec that the 
     reassembly process will tolerate in the cell stream, 
     without producing errors on the CBR service interface.
          
     For KM2100:
     KML.11 - The range that will be used is 3...300 msec
     in steps of 1 msec.
     
     For Vmux:
     The range that will be used is 20...100 msec
     in steps of 10 msec."
    ::= { ip2IfEntry 9 }

ip2IfTos OBJECT-TYPE
    SYNTAX  Integer32 
    MAX-ACCESS  read-create
    STATUS  current
    DESCRIPTION
    "The TOS (Type of Service) value: 0..255.

     In Vmux-2100/110 devices versions 3.1 and up, in Vmux-210 and in Vmux-4x0:
     LSB   8 bits - 00 00 00 XX will be used for Signaling packets TOS.                    
     Next  8 bits - 00 00 XX 00 will be used for Media packets TOS.
	 Next 16 bits - will be 0.
				    XX = Hex values: 0..FF
     For mixed packets, TOS of Media Packets will be used.
     Signaling packets are for example: Keep alive packets and ABCD signaling bits.
     Media packets are for example: voice, fax, HDLC, payload packets."
    ::= { ip2IfEntry 10 }

ip2IfTDMBytesInFrame OBJECT-TYPE
    SYNTAX  Integer32 
    MAX-ACCESS  read-create
    STATUS  current
    DESCRIPTION
    "The number of TDM bytes to be placed in a single IP 
     frame payload.
     For ip2IfTDMoIpMode = cesOverPsn this parameter indicates
     the number of IP frames, calculated as: 1440/<Number of Timeslots>."
    ::= { ip2IfEntry 11 }

ip2IfVlanSupport OBJECT-TYPE
    SYNTAX       INTEGER {
    no		(2),
    yes	    (3)
    }
    MAX-ACCESS  read-create
    STATUS  current
    DESCRIPTION
    "VLAN support (Tagging).
     no - No support to VLAN.
     yes - 4 VLAN bytes will be added to the frame."
    ::= { ip2IfEntry 12}

ip2IfVlanIdentifier OBJECT-TYPE
     SYNTAX  Integer32 
     MAX-ACCESS  read-create
     STATUS  current
     DESCRIPTION
     "VLAN ID."
     ::= { ip2IfEntry 13 }
  
ip2IfVlanFramePriority OBJECT-TYPE
     SYNTAX  Integer32 
     MAX-ACCESS  read-create
     STATUS  current
     DESCRIPTION
     "VLAN Frame priority."
     ::= { ip2IfEntry 14 }

ip2IfExitPort  OBJECT-TYPE
     SYNTAX  INTEGER
      {
       notApplicable (1),
       ext1          (2), -- Vmux 2100 slot 1 port 1  or Gmux2000 GbE Slot 6, Port 1
       ext2          (3), -- Vmux 2100 slot 1 port 2  or Gmux2000 GbE Slot 6, Port 2
       auto          (4),
	   card2Ext1	 (5), -- Vmux 2100 slot 2 port 1 or Gmux2000 GbE Slot 8, Port 1
	   card2Ext2	 (6), -- Vmux 2100 slot 2 port 2 or Gmux2000 GbE Slot 6, Port 2
       ext5          (7), -- Vmux-110/210/2100 ETH-NET
       ext7          (8), -- Vmux-110/210 Serial Link
       ext6 		 (9), -- Vmux-110/210 E1/T1 Link, Vmux-2100 E1/T1 Link A   
	   prt17		(10), -- GMUX VMX/Vmux 2100 slot 1 port 3
	   prt18		(11), -- GMUX VMX/Vmux 2100 slot 1 port 4
	   prt19	    (12), -- GMUX VMX/Vmux 2100 slot 2 port 3
	   prt20        (13), -- GMUX VMX/Vmux 2100 slot 2 port 4
	   prtE1T1B     (14), -- Vmux 2100 E1/T1 Link B
       prtEthUser   (15), -- Vmux 2100/110/210 ETH-User
	   card3Ext1    (16), -- Vmux-2100 Slot 3 port 1
       card3Ext2    (17), -- Vmux-2100 Slot 3 port 2 
       card3Ext3    (18), -- Vmux-2100 Slot 3 port 3
       card3Ext4    (19), -- Vmux-2100 Slot 3 port 4
       card4Ext1    (20), -- Vmux-2100 Slot 4 port 1
       card4Ext2    (21), -- Vmux-2100 Slot 4 port 2
       card4Ext3    (22), -- Vmux-2100 Slot 4 port 3
       card4Ext4    (23), -- Vmux-2100 Slot 4 port 4
	   card1Ext3	(24), -- Gmux2000 GbE/8 Slot 6, Port 3
	   card1Ext4	(25), -- Gmux2000 GbE/8 Slot 6, Port 4
	   card1Ext5	(26), -- Gmux2000 GbE/8 Slot 6, Port 5
	   card1Ext6	(27), -- Gmux2000 GbE/8 Slot 6, Port 6
	   card1Ext7	(28), -- Gmux2000 GbE/8 Slot 6, Port 7
	   card1Ext8	(29), -- Gmux2000 GbE/8 Slot 6, Port 8
	   card2Ext3	(30), -- Gmux2000 GbE/8 Slot 8, Port 3
	   card2Ext4	(31), -- Gmux2000 GbE/8 Slot 8, Port 4
	   card2Ext5	(32), -- Gmux2000 GbE/8 Slot 8, Port 5
	   card2Ext6	(33), -- Gmux2000 GbE/8 Slot 8, Port 6
	   card2Ext7	(34), -- Gmux2000 GbE/8 Slot 8, Port 7
	   card2Ext8	(35)  -- Gmux2000 GbE/8 Slot 8, Port 8
     }
     MAX-ACCESS  read-create
     STATUS  current
     DESCRIPTION
     "This object determines to which external port the traffic
      will be sent.
      auto - the device will decide automatically the exit port.
      If there is an option for Tx via more than one ETH card then use ext1 (1) and ext2(2) 
      for ETH card #1 (ex. LAN1 or Ggabit-ETH1) and use card2Ext1(5) and card2Ext2(6) for 
      card #2 (ex. LAN1 or Ggabit-ETH1).
      In Vmux-110/210 ext5 is used for ETH-NET, ext 6 is used for E1/T1 link and ext7 is 
      used for Serial Link.
      In Vmux-2100 Main Board: ext 5 is used for ETH-NET, ext 6 is used for E1/T1 link A, 
      prtE1T1B is used for E1/T1 link B and prtEthUser is used for ETH-User.       
      prt17(10) - prt20(13) values were added in order to support Gmux2000 VMX Card."
      ::= { ip2IfEntry 15 }

ip2IfVoiceOos  OBJECT-TYPE
     SYNTAX  OCTET STRING 
     MAX-ACCESS  read-create
     STATUS  current
     DESCRIPTION
     "Voice Out-Of-Service code. Valid range: (0 - FF HEX).
      For agents that do not support this feature, the value will 
      always be 0."
     ::= { ip2IfEntry 16 }

ip2IfDataOos  OBJECT-TYPE
     SYNTAX  OCTET STRING 
     MAX-ACCESS  read-create
     STATUS  current
     DESCRIPTION
     "Data Out-Of-Service code. Valid range: (0 - FF HEX).
      For agents that do not support this feature, the value will
      always be 0."
     ::= { ip2IfEntry 17 }

ip2IfBundleUsage OBJECT-TYPE
    SYNTAX  Integer32 
    MAX-ACCESS  read-only
    STATUS  current
    DESCRIPTION
    "The Bundle Resource usage in Kbps."
    ::= { ip2IfEntry 18 }

ip2IfOAM  OBJECT-TYPE
     SYNTAX  OCTET STRING 
     MAX-ACCESS  read-create
     STATUS  current
     DESCRIPTION
     "This parameter determine the OAM configuration.
      The LSB (Bit 0 the most right one) is used for OAM connectivity. 
      Values: 0 = disable, 1= enable."
    ::= { ip2IfEntry 19 }

ip2IfTDMoIpMode OBJECT-TYPE
    SYNTAX  INTEGER {
    notApplicable     (1),
    static		      (2),
	dynamicLES        (3),
	dynamicCAS        (4),
	cesOverIp	      (5),
	voiceOverMpls     (6),
	hdlc		      (7),
	voIpComprHeader   (8),
	voMplsComprHeader (9),
	satop             (10),
	cesOverPsn        (11),
	hdlcOverPsn       (12)
    }
    MAX-ACCESS    read-create
    STATUS        current
    DESCRIPTION
    "The TDMoIP Mode configuration. Static- means TS can Tx any time.
     dynamicLES - means TS can Tx only when line is enabled according to LES protocol.
     dynamicCAS - means TS can Tx only when line is enabled according to CAS protocol.
     cesOverIp - use for information that this bundle is used for CES Over IP.
     voiceOverMpls - Voice over Multi Protocol Label Switching.
	 hdlc - High Level Data Link.
	 voIpComprHeader - indicates proprietary compressed IP header packets.
	 voMplsComprHeader - indicates proprietary compressed MPLS header packets."
    ::= { ip2IfEntry 20 }


ip2IfTimeElapsed OBJECT-TYPE
     SYNTAX  Integer32 (0..899)
     MAX-ACCESS  read-only
     STATUS  current
     DESCRIPTION
     "The number of seconds that have elapsed since
      the beginning of the  current error-measurement period.
      If, for some reason, such as an adjustment in the 
      system's time-of-day clock, the current interval exceeds
      the maximum	value, the agent will return the maximum value."
     ::= {ip2IfEntry 21 }

ip2IfValidIntervals OBJECT-TYPE
     SYNTAX  Integer32 (0..96)
     MAX-ACCESS  read-only
     STATUS  current
     DESCRIPTION
     "The number of previous intervals for which data was collected.  
      The value will be	96 unless the interface was brought online within
      the last 24 hours, in which case the value will be
      the number of complete 15 minute intervals since the
      interface has been online. "
     ::= {ip2IfEntry 22 }

ip2IfFarEndType  OBJECT-TYPE
     SYNTAX  INTEGER
      {
       notApplicable (1),
       e1            (2),
       t1Esf         (3),
       t1D4          (4),
       fxs           (5),
	   serialLink 	 (6),
	   t1Unframed	 (7)
      }
     MAX-ACCESS  read-create
     STATUS  current
     DESCRIPTION
     "This object defines the type of the Far-End device.
      This data is important for signaling and DS0 format.
      
      For Vmux: e1  (2) value is used for a PBX in the Far End.
                fxs (5) is used for Phone.
                Other values are not used. "
     ::= { ip2IfEntry 23 }

ip2IfRdnState  OBJECT-TYPE
     SYNTAX  INTEGER
      {
       notApplicable (1),
       none          (2),
       primary       (3),
       secondary     (4)
      }
     MAX-ACCESS  read-only
     STATUS  current
     DESCRIPTION
     "This object defines the role this bundle plays in the redundancy scheme:
     none(2) - means this bundle is not part of redundancy pair.
     primary/ secondary - means this bundle is not part of redundancy pair,
     and that is the primary bundle or the secondary bunle. "
     ::= { ip2IfEntry 24 }

ip2IfSourceAddr OBJECT-TYPE
     SYNTAX  IpAddress 
     MAX-ACCESS  read-create
     STATUS  current
     DESCRIPTION
     "Source IP Address of the bundle."     	  
	  ::= {ip2IfEntry 25 }

ip2IfBandWidth OBJECT-TYPE
    SYNTAX  Integer32 
    MAX-ACCESS  read-create
    STATUS  current
    DESCRIPTION
    "Defines the Bandwidth of the bundle.

     For TDM bundles - it is the Number of Time Slots  in The Bundle.
     - For T1 the value will be: 1..24
     - For E1 the value will be: 1..31
     - For T3 the value will be: 1..84
     - For E3 the value will be: 1..63
     
     This parameter is required for devices like Emux where the bandwidth of
     the bundles is unknown. The bundles that are received should be transmitted
     without any change in the bandwidth. It is the user's responsibility to
     enter the correct bandwidth.
     
     For Ethernet bundles - it is the bandwidth, measured in Kbps."
     ::= {ip2IfEntry 26 }

ip2IfMeasuredSilence  OBJECT-TYPE
     SYNTAX  Integer32     
     MAX-ACCESS  read-only
     STATUS  current
     DESCRIPTION
     "This object shows the percentage of Silence that was measured by the device
      for the current bundle in the transmitted payload.
      Relevant values: 0..100, 255.
      Default value is 50.
      0 means that there is no silence on the line.
      100 means that there is only silence. In this case, there might be no traffic.
      255 - value for not applicable or unknown."      
     ::= { ip2IfEntry 27 }

ip2IfPayloadType  OBJECT-TYPE
     SYNTAX  INTEGER
      {
       notApplicable (1),
       data          (2),
       voice         (3),
       voiceAndCas   (4)
      }
     MAX-ACCESS  read-create
     STATUS  current
     DESCRIPTION
     "This object defines the TDMoIP payload type."
     ::= { ip2IfEntry 28 }

ip2IfProtocolVersion  OBJECT-TYPE
     SYNTAX  INTEGER
      {
       notApplicable (1),
       v1   (2),
       v2   (3)  
      }
     MAX-ACCESS  read-create
     STATUS  current
     DESCRIPTION
     "This object defines the TDMoIP protocol Version."
     ::= { ip2IfEntry 29 }

ip2IfTdmBackUpNextHop OBJECT-TYPE
    SYNTAX  IpAddress 
    MAX-ACCESS  read-create
    STATUS  current
    DESCRIPTION
    "Defines the TDM bundle default router in case there was a switch from the Primary Link
     (for example an ETH port) to a TDM backup Link like E1, T1 or Serial Link.
     This parameter is relevant only when a Backup Link is configured.
     When a Backup Link is not configured the value will be: 0.0.0.0"
    ::= { ip2IfEntry 30 }

ip2IfOosTxEnable  OBJECT-TYPE
     SYNTAX  INTEGER
      {
       notApplicable 	(1),
       disable  		(2),
       enable    		(3)
             }
     MAX-ACCESS  read-create
     STATUS  current
     DESCRIPTION
     "This object defines whether OOS will be Transmitted.
	 Note that for IPmux1000 the Lbit is always sent,
	 but the OOS will be sent according to user selection in this parameter."
     ::= { ip2IfEntry 31 }

ip2IfConnCheckPktFrequency   OBJECT-TYPE
     SYNTAX  Integer32     
     MAX-ACCESS  read-create
     STATUS  current
     DESCRIPTION
     "Time in sec. between 2 Bundle Connectivity Check packets.
      Valid values: 0..60. 0 = Not Applicable."      
      ::= { ip2IfEntry 32 }

ip2IfConnPktTimeOutCycles      OBJECT-TYPE
     SYNTAX  Integer32     
     MAX-ACCESS  read-create
     STATUS  current
     DESCRIPTION
    "No. of cycles the agent will send Bundle Connectivity packets without receiving
     a response from the remote device before declaring that the bundle connection
     to the remote side is down - Time Out.
     Valid values: 0..5. 0 = Not Applicable."    
     ::= { ip2IfEntry 33 }

ip2IfMfRelay                  OBJECT-TYPE
     SYNTAX  INTEGER
      {
       notApplicable (1),
       disable       (2),
       enable        (3)
      }
     MAX-ACCESS  read-create
     STATUS  current
     DESCRIPTION
    "Multi Frequency Signaling Detection."    
     ::= { ip2IfEntry 34 }

ip2IfTxGain                  OBJECT-TYPE
     SYNTAX  Integer32
     MAX-ACCESS  read-create
     STATUS  current
     DESCRIPTION
    "Transmit gain in dBm."    
     ::= { ip2IfEntry 35 }

ip2IfSuperTandem             OBJECT-TYPE
     SYNTAX  INTEGER
      {
       notApplicable (1),
       disable       (2),
       enable        (3)
      }
     MAX-ACCESS  read-create
     STATUS  current
     DESCRIPTION
    "The Super Tandem feature provides end to end compression over multiple hops,
     solving the double compression problem detected in Voice compressing systems.
     The Super Tandem allows transmission of compressed voice between a few
     Vmux 2100 hubs, and eliminates the need to decompress an recompress it over
     each voice card and PBX, thus improving voice quality and reducing delay."    
     ::= { ip2IfEntry 36 }

ip2IfSrcPort OBJECT-TYPE
    SYNTAX  Integer32 
    MAX-ACCESS  read-create
    STATUS  current
    DESCRIPTION
    "The source Bundle at the local device, 
    this parameter used for cases where there is no match 
    between ip2IfChannelIndex and the Source Bundle ID."
    ::= { ip2IfEntry 37 }

   ip2IfModemCalls             OBJECT-TYPE
     SYNTAX  INTEGER
      {
       disable       (2),
       enable        (3),
	   relay         (4)
      }
     MAX-ACCESS  read-create
     STATUS  current
     DESCRIPTION
     "This MIB object shows whether Modem Calls are enabled via the bundle.
      relay option (3) means that the bundle will send to the network only
      modulated data."
     ::= { ip2IfEntry 38 }
 					 
   ip2IfMinPulseWidth  OBJECT-TYPE
      SYNTAX  Integer32                   
      MAX-ACCESS  read-create
      STATUS  current
      DESCRIPTION
      "Indicates the minimum width in milliseconds of the MF (Multi Frequency)
       tone transmitted by the switch.
       Valid values: 45-300 msec.
       notApplicable=0."
       ::= { ip2IfEntry 39 } 

   ip2IfMinPowerLevel  OBJECT-TYPE
      SYNTAX  Integer32                   
      MAX-ACCESS  read-create
      STATUS  current
      DESCRIPTION
       "Indicates the minimum power level in dBm of the MF (Multi Frequency)
        tone transmitted by the switch.
        Valid values: -1...-35 dBm."
        ::= { ip2IfEntry 40 }

ip2IfEchoCanceler             OBJECT-TYPE
     SYNTAX  INTEGER
        {
          off    (2),
          on     (3)
       }
      MAX-ACCESS  read-create
      STATUS  current
      DESCRIPTION
      "Echo canceler activation."
     ::= { ip2IfEntry 41 }

ip2IfCodingLaw OBJECT-TYPE
      SYNTAX  INTEGER
       {
          aLAW    (1),
          uLAW    (2)
       }
      MAX-ACCESS  read-create
      STATUS  current
      DESCRIPTION
      "This attribute indicates the Method/Law for decoding/encoding the voice
       information.
       aLaw(1) is the standard Law for E1 links.
       uLaw(2) is the standard Law for T1 links."
       ::= { ip2IfEntry 42 }
  
ip2IfCustomToneDetect             OBJECT-TYPE
     SYNTAX  INTEGER
      {
       disable       (2),
       enable        (3)
      }
     MAX-ACCESS  read-create
     STATUS  current
     DESCRIPTION
     "Custom Tone Detection (COT) is a Control operation of a 2Khz tone detector.
	  This tone is sent between PBX devices in order to check that the line status
	  is OK. When the COT is enabled the device will not compress/decompress the tone.
	  In this case, if the tone is initiated by the local PBX, the Device runs
	  a 2Khz detector tone and once detected by the Remote Device, if the COT is enabled
	  in the Remote Device, the Remote Device will generate a 2khz tone to the remote PBX."
	  ::= { ip2IfEntry 43 }

 ip2IfCallerIdDelay      OBJECT-TYPE
     SYNTAX  Integer32
     MAX-ACCESS  read-create
     STATUS  current
     DESCRIPTION
     "Time in msec between CLID (Caller ID) signal detection on the line and CLID
      signal transmission. The CLID must be sent between ringing signals and the value
      of the delay is used for synchronizing the CLID transmission with the ringing
      signals transmission.
      
      Valid values: 0 - 3000 msec."
	  ::= { ip2IfEntry 44 }

 ip2IfConnectivityMode    OBJECT-TYPE
     SYNTAX  INTEGER
      {
       ping       (2),
       oam        (3)
       }
     MAX-ACCESS  read-create
     STATUS  current
     DESCRIPTION
     "This MIB object shows whether to send Pings or OAM frames over the bundle."
      ::= { ip2IfEntry 45 }

ip2IfClockSourceEnable    OBJECT-TYPE
     SYNTAX  INTEGER
      {
       notApplicable 	(1),
       disable  		(2),
       enable    		(3)
       }
     MAX-ACCESS  read-create
     STATUS  current
     DESCRIPTION
     "This MIB object defines whether this bundle can be a clock source."
      ::= { ip2IfEntry 46 }

ip2IfNetworkType   OBJECT-TYPE
      SYNTAX   INTEGER
    {
     notApplicable 	(1),
     ip  			(2),
     mplsEth    	(3),
	 mac			(4),
	 ipComprHeader   (5),
	 mplsComprHeader (6),
	 udp			 (7)
     }
   MAX-ACCESS  read-create
   STATUS  current
   DESCRIPTION
   "This MIB object defines the network over which the 
   Bundle PSN (Packet Switching Network)is transported.
   In Gmux2000:
   ipComprHeader indicates proprietary compressed IP header packets.
   mplsComprHeader indicates proprietary compressed MPLS header packets." 
       ::= { ip2IfEntry 47}

ip2IfMplsRxLabelEnable   OBJECT-TYPE
      SYNTAX   INTEGER
    {
     notApplicable 	(1),
     disable  		(2),
     enable    		(3)
     }
   MAX-ACCESS  read-create
   STATUS  current
   DESCRIPTION
   "This MIB object defines whether there is user defined 
    inner (Rx.) label for this Bundle."
       ::= { ip2IfEntry 48}

ip2IfMplsRxLabel 	  OBJECT-TYPE
   SYNTAX         Integer32
   MAX-ACCESS     read-create
   STATUS         current
   DESCRIPTION
    "This MIB object defines the MPLS Rx. Label for this Bundle."
    ::= { ip2IfEntry 49}

ip2IfMplsTxLabelEnable   OBJECT-TYPE
      SYNTAX   INTEGER
    {
     notApplicable 	(1),
     disable  		(2),
     enable    		(3)
     }
   MAX-ACCESS  read-create
   STATUS  current
   DESCRIPTION
   "This MIB object defines whether there is user defined 
    outer (Tx.) label for this Bundle."
       ::= { ip2IfEntry 50}

ip2IfMplsTxLabel 	  OBJECT-TYPE
   SYNTAX         Integer32
   MAX-ACCESS     read-create
   STATUS         current
   DESCRIPTION
    "This MIB object defines the MPLS Tx. Label for this Bundle."
    ::= { ip2IfEntry 51}

ip2IfMplsTxExpBits	  OBJECT-TYPE
   SYNTAX         Integer32	 (0..7)
   MAX-ACCESS     read-create
   STATUS         current
   DESCRIPTION
    "The MPLS Network priority (EXP bits) used for this bundle."
    ::= { ip2IfEntry 52}

ip2IfMfcSpoofing		 OBJECT-TYPE
      SYNTAX   INTEGER
    {
     notApplicable 	(1),
     disable  		(2),
     enable    		(3)
     }
   MAX-ACCESS  read-create
   STATUS  current
   DESCRIPTION
   "This MIB object defines whether the MFC (Multi Frequency Compelled) protocol
    spoofing will exist in the bundle. When the MFC Spoofing is used, the Local
    and Remote PBXs will send MFC Signaling to each other. The Vmuxes between
    the PBXs will send proprietary signaling to each other. They will however
    create and send MFC tones to their local PBX. The PBXs will not know that
    the actual signaling was not sent from a PBX but from a Vmux."
    ::= { ip2IfEntry 53}

ip2IfToneAckInterval  OBJECT-TYPE
   SYNTAX         Integer32 
   MAX-ACCESS     read-create
   STATUS         current
   DESCRIPTION
   "Time Interval in milli seconds from the time a Vmux sends tone/s to a local PBX until
    it receives an acknowledgement from this PBX.
    Valid values: 60...400 in steps of 20."
    ::= { ip2IfEntry 54}

ip2IfNextHopType   OBJECT-TYPE
      SYNTAX   INTEGER
    {
     notApplicable 	(1),
     ipAddress		(2),
     macAddress    	(3)
     }
   MAX-ACCESS  read-create
   STATUS  current
   DESCRIPTION
   "This MIB object defines the Bundle next Hop Address Type." 
       ::= { ip2IfEntry 55}

ip2IfNoiseLevelForVAD   OBJECT-TYPE
   SYNTAX  INTEGER
   {       
    low          (2),
    high         (3),
	off			 (4)
   }
   MAX-ACCESS  read-create
   STATUS  current
   DESCRIPTION
   "This object defines the Level of Noise on the line,
    the Voice Activation Detector (VAD) will have to handle."
   ::= { ip2IfEntry 56}

ip2IfClockPreferences   OBJECT-TYPE
   SYNTAX  INTEGER
   {       
    accurateness          (2),
    constantDelay         (3)
   }
   MAX-ACCESS  read-create
   STATUS  current
   DESCRIPTION
   "The Clock preferences:
   accurateness (2) = Accurate clock is more important than Constant Delay.
   constantDelay (3)= Constant Delay is more important than Accurate clock ."
   ::= { ip2IfEntry 57}

ip2IfConnectionMode   OBJECT-TYPE
   SYNTAX  INTEGER
   {       
    tdmOIpCe         (2),
    tdmOIpCv         (3)
   }
   MAX-ACCESS  read-create
   STATUS  current
   DESCRIPTION
   "The Connection Mode:
   tdmOIpCe (2) = TDMOiP (CE) = Circuit Emulation.
   tdmOIpCv (3)= TDMOiP (CV) = Compressed Voice."
   ::= {ip2IfEntry 58}

 ip2IfRingBack   OBJECT-TYPE
   SYNTAX  INTEGER
   {       
    disable         (2),
    enable          (3)
   }
   MAX-ACCESS  read-create
   STATUS  current
   DESCRIPTION
   "Enables or disable Ring Back."
   ::= {ip2IfEntry 59}

 ip2IfReversePolarity   OBJECT-TYPE
   SYNTAX  INTEGER
   {       
     disable         (2),
     enable          (3)   
   }
   MAX-ACCESS  read-create
   STATUS  current
   DESCRIPTION
   "Enables or disable Reverse polarity synthesis."
   ::= {ip2IfEntry 60}

 ip2IfPulseMeter   OBJECT-TYPE
   SYNTAX  INTEGER
   {       
    disable         (2),
    enable          (3)
   }
   MAX-ACCESS  read-create
   STATUS  current
   DESCRIPTION
   "Enables or disable Pulse metering synthesis."
   ::= {ip2IfEntry 61}

    ip2IfPulseMeterFreq   OBJECT-TYPE
   SYNTAX  INTEGER
   {       
    rate12Khz        (2),
    rate16Khz        (3)
   }
   MAX-ACCESS  read-create
   STATUS  current
   DESCRIPTION
   "Frequency of synthesized pulse metering for this bundle."
   ::= {ip2IfEntry 62}

    ip2IfPulseMeterPeriod   OBJECT-TYPE
   SYNTAX  Integer32
   MAX-ACCESS  read-create
   STATUS  current
   DESCRIPTION
   "Duration of synthesized pulse metering. current values are: 100-250."
   ::= {ip2IfEntry 63}

    ip2IfOnHookDetect   OBJECT-TYPE
   SYNTAX  INTEGER
   {       
    disable        (2),
    enable       (3)
   }
   MAX-ACCESS  read-create
   STATUS  current
   DESCRIPTION
   "Enables or disable immediate reaction to On-Hook bits from network in Ringing."
   ::= {ip2IfEntry 64}

ip2IfComfortNoiseGen   OBJECT-TYPE  
   SYNTAX  INTEGER
   {       
    disable      (2),
    enable       (3)
   }
   MAX-ACCESS  read-create
   STATUS  current
   DESCRIPTION
   "Enable or disable Comfort Noise Generation (CNG).
    When this parameter is enabled and no voice payload exists on the line for some
    time period during the call (moments of silence), the device will generate a soft   
    background noise which assures the user that the connection is still alive (CNG).
    
    When this parameter is disabled and no voice payload exists on the line,
    absolute silence will be heard (Comfort Noise will not be generated)."
   ::= {ip2IfEntry 65}

ip2IfExitChannel   OBJECT-TYPE
   SYNTAX  Integer32
   MAX-ACCESS  read-create
   STATUS  current
   DESCRIPTION
   "The channelized bundle that the voice bundle exits through.
   In Gmux2000 it is the ifIndex of the Channelized Bundle (sub-channel) 
   that the Voice Bundle exits through. The ifIndex contains 
   the Slot+Prt+Channelized Bundle No."
   ::= {ip2IfEntry 66}

ip2IfMaxVBDModemCalls   OBJECT-TYPE
   SYNTAX  Integer32
   MAX-ACCESS  read-create
   STATUS  current
   DESCRIPTION
   "Maximum VBD modem calls for this bundle."
   ::= {ip2IfEntry 67}

ip2IfMaxRelayModemCalls   OBJECT-TYPE
   SYNTAX  Integer32
   MAX-ACCESS  read-create
   STATUS  current
   DESCRIPTION
   "Maximum Relay modem calls for this bundle."
   ::= {ip2IfEntry 68}

ip2IfCustomToneFrequency          OBJECT-TYPE
     SYNTAX  INTEGER
      {
      notApplicable   (1),
      f1780Hz         (2),
      f2000Hz         (3),
      f1780Plus2000Hz (4)
      }
     MAX-ACCESS  read-create
     STATUS  current
     DESCRIPTION
     "This is the frequency of the Custom Tone that is sent between PBXs in order
      to check that the line status is OK. When the Custom Tone Detection is enabled
      the device will not compress/decompress this tone. The custom tone that is received
      from the local PBX will be sent to the remote PBX with the same frequency it was received.

      When the Custom Tone Frequency is f1780Plus2000Hz (4), the device will not  
      compress/decompress any tone with frequencies of 1780Hz or 2000 Hz."
      ::= { ip2IfEntry 69 }

ip2IfVadMethod   OBJECT-TYPE  
    SYNTAX  INTEGER
    {       
     proprietary      (2),
     internalITUT   (3)
    }
    MAX-ACCESS  read-create
    STATUS  current
    DESCRIPTION
    "Voice Activity Detection (VAD) method.
    proprietary    (2) - non standard VAD based only on power measurement.
                          It is very sensitive to background noise.
    internalITUT (3) - standard ITU-T VAD. It is a robust method."    
    ::= {ip2IfEntry 70}

ip2IfRxGain      OBJECT-TYPE
    SYNTAX  Integer32
    MAX-ACCESS  read-create
    STATUS  current
    DESCRIPTION
    "Receive gain in dBm."    
    ::= { ip2IfEntry 71 }

ip2IfCallerIDType   OBJECT-TYPE  
    SYNTAX  INTEGER
    {       
     bellcoreType1 (2),
     v23           (3)
    }
    MAX-ACCESS  read-create
    STATUS  current
    DESCRIPTION
    "Caller ID Type used by the DSP for this bundle.
     Bellcore type is used by the American method.
     V.23     type is used by the European method."    
    ::= {ip2IfEntry 72}


ip2IfPeerAddrType   OBJECT-TYPE
      SYNTAX   INTEGER
    {
     notApplicable 	(1),
     ipAddress		(2),
     macAddress    	(3)
     }
   MAX-ACCESS  read-create
   STATUS  current
   DESCRIPTION
   "This MIB object defines the peer Address Type." 
       ::= { ip2IfEntry 73}

ip2IfVbdRate   OBJECT-TYPE  
    SYNTAX  INTEGER
    {   
     r64KbpsIn5msecIntervalsG711(2),
     r64KbpsIn10msecIntervalsG711(3),
     r32KbpsG726(4),
     r24KbpsG726(5)     
    }
    MAX-ACCESS  read-create
    STATUS  current
    DESCRIPTION
    "Voice Band Data (VBD) rate for this bundle."    
    ::= {ip2IfEntry 74}

ip2IfDtmfDetection    OBJECT-TYPE
    SYNTAX  INTEGER
    {
     notApplicable 	(1),
     disable  		(2),
     enable    		(3)
    }
    MAX-ACCESS  read-create
    STATUS  current
    DESCRIPTION
    "Enable/Disable DTMF (Dual Tone Multi Frequency) detectors for this bundle."
    ::= { ip2IfEntry 75 }

ip2IfNlpCutoffLevel    OBJECT-TYPE
     SYNTAX  Unsigned32 
     MAX-ACCESS  read-create
     STATUS  current
     DESCRIPTION
     "Non Linear Processor (NLP) Cutoff Level for this bundle.
      This parameter is used by the echo canceller.
      It is the maximum absolute linear PCM amplitude of the near-end signal that will
      cause the NLP module to be active and to mute low level residual echo & noisy
      surroundings."    
   ::= { ip2IfEntry 76 }

ip2IfDtdErlRatioCutoffQ3    OBJECT-TYPE
     SYNTAX  Unsigned32 
     MAX-ACCESS  read-create
     STATUS  current
     DESCRIPTION
     "The DTD ERL cutoff level is used in order to determine whether the near-end is talking
      or not. This parameter is used by the echo canceller when echo exists and there is
      voice with low volume on the line.
      DTD means Double Talk Detection.
      ERL means Echo Return Loss. It  is the power difference [dB] between the far-end signal
      to the echo returned.
      The cutoff level is calculated for the value entering Q.3.
      This value will be divided by 2^3=8 in order to get the linear ratio."       
     ::= { ip2IfEntry 77 }

ip2IfCASRedundancy    OBJECT-TYPE
    SYNTAX  INTEGER
    {
     notApplicable 	(1),
     disable  		(2),
     enable    		(3)
    }
    MAX-ACCESS  read-create
    STATUS  current
    DESCRIPTION
    "Enable/Disable CAS signaling redundancy.
     This parameter is useful when there are problems with the network and applicable
     only for CAS signaling: E1-MF (G.732S) or E1-CRC-MF (G.732SCRC ).
     
     enable (3) - means that each packet containing CAS signaling will be triplicated
                  into 3 packets.
     disable (2)- No redundancy will exist. Only 1 packet containing CAS will be
                  transmitted."
    ::= { ip2IfEntry 78 }

ip2IfBundleSensitivity 	OBJECT-TYPE
    SYNTAX  INTEGER
    {
     delaySensitive	(2),
     dataSensitive	(3)
    }
    MAX-ACCESS  read-create
    STATUS  current
    DESCRIPTION
    "Denotes if the bundle is sensitive to delay in the network,
     or is sensitive to data errors in the network.
	 Voice bundles are sensitive to delay;
	 Non-voice bundles are sensitive to data errors."
    ::= { ip2IfEntry 79 }

ip2IfOAMBundleIdent 	OBJECT-TYPE
    SYNTAX  INTEGER
    {
     bundleNumber  (2),
     vccvCtrlWord  (3)
    }
    MAX-ACCESS  read-create
    STATUS  current
    DESCRIPTION
    "Denotes if an OAM bundle is identified according to the Bundle Number (0x3fff),
     or according to the value of the first nibble in the VCCV control word sent in the frame.
	 controlWord - applicable only when ip2IfProtocolVersion = v2(2).
	 When ip2IfProtocolVersion = v1(1), only bundleNumber is applicable."
    ::= { ip2IfEntry 80 }

ip2IfMaxTxQueue OBJECT-TYPE
	SYNTAX		Unsigned32 
	MAX-ACCESS	read-create
	STATUS		current
	DESCRIPTION
	"Max Tx Queue buffer size, measured in msec (milliseconds).

	 Low buffer size may cause the buffer to overflow and discard packets
	 in case of burst of packets on the network.
	 
	 High buffer size allows to store this burst and not lose packets."
	::= { ip2IfEntry 81 }

ip2IfMaxGprsTxQueue OBJECT-TYPE
	SYNTAX		Unsigned32 
	MAX-ACCESS	read-create
	STATUS		current
	DESCRIPTION
	"Max GPRS Tx Queue buffer size, measured in msec (milliseconds).       

	 Low buffer size may cause the buffer to overflow and discard packets
	 in case of burst of packets on the network.
	 
	 High buffer size allows to store this burst and not lose packets."
	::= { ip2IfEntry 82 }

ip2IfV23HD    OBJECT-TYPE
    SYNTAX  INTEGER
    {
     notApplicable 	(1),
     disable  		(2),
     enable    		(3)
    }
    MAX-ACCESS  read-create
    STATUS  current
    DESCRIPTION
    "This parameter shows whether V.23 Half Duplex Modem Protocol is enabled
     on the bundle."
    ::= { ip2IfEntry 83 }

ip2IfModemProtocolMode  OBJECT-TYPE
    SYNTAX  OCTET STRING
    MAX-ACCESS  read-create
    STATUS  current
    DESCRIPTION
    "This octet string contains the mode of each Modem Protocol used on the bundle.
     For each protocol one octet will be used. 
     
     Octet #1 will be used for V.22 Protocol.
     Octet #2, #3, #4... are reserved for future protocols.

     Octet #1 values:
     0 - Not Applicable
     1 - VBD:   Voice Band Data.
     2 - Relay: Pulse Code Modulated (PCM) data is sent via the bundle.
       
     For V.22: This MIB object is relevant only when ip2IfModemCalls = relay (4)."     
     ::= { ip2IfEntry 84 }

ip2IfCdisCngDetectionTime  OBJECT-TYPE
	SYNTAX	Unsigned32 
	MAX-ACCESS	read-create
	STATUS	current
	DESCRIPTION
	"When working with CDIS (Call DIScrimination method) or CNG (Comfort Noise Generation):
       The time in msec that the device will detect 1100Hz & 2100Hz signals
       on the line before switching to modem or fax.
       For Vmux: the values will be in steps of 10 msec."
	::= { ip2IfEntry 85 }

ip2IfSuperTandemBitMask OBJECT-TYPE
    SYNTAX  OCTET STRING
    MAX-ACCESS  read-create
    STATUS  current
    DESCRIPTION
    "This MIB object enables controlling the Time Slot/Channel rate.
     Valid values: 1 - FF HEX
     Each BIT represents 1/8 of the TS.
     Example:
     7E (0111 1110) means that 6/8 of the TS (the center ones) are masked and data will
     be Tx/Rx only through them.    
     This MIB object is relevant only when Super Tandem is enabled."
    ::= { ip2IfEntry 86 }

ip2IfVbdSwitchbackTime  OBJECT-TYPE
	SYNTAX	Unsigned32 
	MAX-ACCESS	read-create
	STATUS	current
	DESCRIPTION
	"Time in msec required for the DSP to switch back from VBD (Voice Band Data) to Voice.
       For Vmux: the values will be in steps of 30 msec. 
    "
	::= { ip2IfEntry 87 }


ip2IfCallerIdTxGain                  OBJECT-TYPE
     SYNTAX  Integer32
     MAX-ACCESS  read-create
     STATUS  current
     DESCRIPTION
     "The gain value in dBm units used for transmitting the Caller ID signal on the bundle.
     "    
     ::= { ip2IfEntry 88 }


ip2IfCallerIdRxGain      OBJECT-TYPE
    SYNTAX  Integer32
    MAX-ACCESS  read-create
    STATUS  current
    DESCRIPTION
    "The gain value in dBm units of the Caller ID signal received on the bundle."    
    ::= { ip2IfEntry 89 }

ip2IfUdpMuxMethod	  OBJECT-TYPE
    SYNTAX 		INTEGER
	{
	    srcPort  (2),
		destPort (3)
	}
    MAX-ACCESS  read-create
    STATUS  current
    DESCRIPTION
    "This parameter determines according to which field the multiplexing is made:
    srcPort (2) - multiplexing according to the UDP Source Port (Dest=0x085e).
	    This should be the default value, for backwards compatibility.
	destPort (3) - multiplexing according to the UDP Destination Port 
	   (standard multiplexing). 
	   
	 The UDP Source and Destination ports' range is determined according to 
	 ip2IfUdpMuxMethod value:
	 For srcPort (2) the range is 1-7000
	 For destPort (3) the range is 49152-65535."    
    ::= { ip2IfEntry 90 }

ip2IfCallerIdDetection    OBJECT-TYPE
    SYNTAX  INTEGER
    {
     notApplicable 	(1),
     disable  		(2),
     enable    		(3)
    }
    MAX-ACCESS  read-create
    STATUS  current
    DESCRIPTION
    "Enable/Disable Caller ID Detection for this bundle."
    ::= { ip2IfEntry 91 }

ip2IfWap    OBJECT-TYPE
    SYNTAX  INTEGER
    {
     notApplicable 	(1),
     disable  		(2),
     enable    		(3)
    }
    MAX-ACCESS  read-create
    STATUS  current
    DESCRIPTION
    "Enable/Disable WAP (Wireless Application Protocol) for this bundle.
     WAP allows users to access the internet from wireless devices."
    ::= { ip2IfEntry 92 }


ip2IfSignalingOos     OBJECT-TYPE
    SYNTAX  INTEGER
       {
        notApplicable  (1),
        forcedIdle     (3),
        forcedBusy     (4)
       }
      MAX-ACCESS  read-create
      STATUS  current
      DESCRIPTION
      "Out of Service code sent on signaling TimeSlot."
      ::= {ip2IfEntry 93}


ip2IfTDMFrameBytes OBJECT-TYPE
       SYNTAX  Integer32 
       MAX-ACCESS  read-write
       STATUS  current
       DESCRIPTION
       "The number of TDM bytes to be placed in a single IP 
       frame payload."
       ::= { ip2If 2 }

ip2IfTosValue OBJECT-TYPE
       SYNTAX  Integer32 
       MAX-ACCESS  read-write
       STATUS  current
       DESCRIPTION
       "The TOS value to write in the IP frame."
       ::= { ip2If 3 }
  
ip2IfVlanTagging OBJECT-TYPE
       SYNTAX INTEGER {
       no		(1),
       yes	    (2)
       }
       MAX-ACCESS  read-write
       STATUS  current
       DESCRIPTION
       "VLAN support.
       no - No support to VLAN.
       yes - 4 VLAN bytes will be added to the frame."
       ::= { ip2If 4 }

ip2IfVlanID OBJECT-TYPE
       SYNTAX  Integer32 
       MAX-ACCESS  read-write
       STATUS  current
       DESCRIPTION
       "VLAN ID."
       ::= { ip2If 5 }
  
ip2IfVlanPriority OBJECT-TYPE
       SYNTAX  Integer32 
       MAX-ACCESS  read-write
       STATUS  current
       DESCRIPTION
       "Frame priority."
       ::= { ip2If 6 }


-- ip2If Statistics table  

ip2IfStatTable OBJECT-TYPE
       SYNTAX  SEQUENCE OF Ip2IfStatEntry
       MAX-ACCESS  not-accessible
       STATUS  current
       DESCRIPTION
       "Channels (Bundles) Statistics Table."
       ::= { ip2If 7 }
  
ip2IfStatEntry OBJECT-TYPE
       SYNTAX Ip2IfStatEntry
       MAX-ACCESS not-accessible
       STATUS current
       DESCRIPTION
       "IP Statistics per bundle"
       INDEX   { ip2IfStatChIndex }
       ::= { ip2IfStatTable 1 }

Ip2IfStatEntry ::=
         SEQUENCE {
         ip2IfStatChIndex	       Integer32,
         ip2IfStatSeqErrors        Integer32,
         ip2IfStatBufUnderflows    Integer32,
         ip2IfStatBufOverflows     Integer32,
		 ip2IfStatTxOnTimeInterval Counter32,
		 ip2IfStatTxOnMaxSize      Counter32,
		 ip2IfStatRxSignaling      Counter32,
		 ip2IfStatRxVoice          Counter32,
		 ip2IfStatRxHdlc           Counter32,
		 ip2IfStatTxSignaling      Counter32,
		 ip2IfStatTxVoice          Counter32,
		 ip2IfStatTxHdlc           Counter32,
		 ip2IfStatRdnFlip		   Counter32,
		 ip2IfFarEndTdmStatus	   Integer32,
		 ip2IfStatPsnTxFrames		   Counter32,
		 ip2IfStatPsnRxFrames		   Counter32,
		 ip2IfStatMinJittBufLevel	   Unsigned32,
		 ip2IfStatMaxJittBufLevel	   Unsigned32,
		 ip2IfStatRecommendedJittBufSize  Unsigned32,
		 ip2IfStatPsnSeqErrors		  Counter32,
		 ip2IfStatPsnReorderFrames 	  Counter32,
		 ip2IfStatMinRoundTripDelay	  Unsigned32,
		 ip2IfStatMaxRoundTripDelay	  Unsigned32,
		 ip2IfStatAvrRoundTripDelay	  Unsigned32,
		 ip2IfStatFrameTrackDupDrop	   Counter32,
         ip2IfStatFrameTrackMissing	   Counter32,
         ip2IfStatFrameTrackLongSerMiss  Integer32,
		 ip2IfStatTxMeasuredSilence      Integer32,
		 ip2IfStatRxMeasuredSilence      Integer32,
		 ip2IfStatHdlcCrcErr			 Counter32,
		 ip2IfStatHdlcAlignErr			 Counter32,
		 ip2IfStatHdlcOversize			 Counter32,
		 ip2IfStatHdlcUndersize			 Counter32,
		 ip2IfStatHdlcAbort				 Counter32,
		 ip2IfStatRxCorrectFrames        Counter32,
		 ip2IfStatHdlcErroredFrames      Counter32
          }
  
ip2IfStatChIndex OBJECT-TYPE
    SYNTAX  		Integer32 
    MAX-ACCESS  read-only
    STATUS  current
    DESCRIPTION
    "The channel index, which is actualy the bundle ID."
    ::= { ip2IfStatEntry 1 }

ip2IfStatSeqErrors      OBJECT-TYPE
    SYNTAX        Integer32
    MAX-ACCESS        read-only
    STATUS        current
    DESCRIPTION
    "Number of events that the sequence number of an incoming Frame
     causes a transition from the 'sync' state to
     the 'out of sequence' state."
     ::= { ip2IfStatEntry 2 }

ip2IfStatBufUnderflows      OBJECT-TYPE
    SYNTAX        Integer32
    MAX-ACCESS    read-only
    STATUS        current
    DESCRIPTION
    "Number of events that the buffer underflows. This records the count of the
     number of events the Receive (Eth to TDM) buffer underflows. In the
     case of a continuous underflow caused by a loss of Frame
     flow, a single buffer underflow should be counted."
    ::= { ip2IfStatEntry 3 }

ip2IfStatBufOverflows      OBJECT-TYPE
    SYNTAX        Integer32
    MAX-ACCESS        read-only
    STATUS        current
    DESCRIPTION
    "Number of events that the buffer overflows. This records the count of the
     number of events the Receive (Eth to TDM) buffer overflows."
    ::= { ip2IfStatEntry 4 }
  
ip2IfStatTxOnTimeInterval      OBJECT-TYPE
    SYNTAX        Counter32
    MAX-ACCESS    read-only
    STATUS        current
    DESCRIPTION
    "Number of frames that were transmitted due to time interval elapse.
     The user can choose to Tx the Frame when it reaches the Max size
     or when the packetizing time interval elapses.
     The packetizing time interval is the interval in msec that it takes
     to build a Max. size frame."
    ::= { ip2IfStatEntry 5 }

ip2IfStatTxOnMaxSize      OBJECT-TYPE
    SYNTAX        Counter32
    MAX-ACCESS    read-only
    STATUS        current		
    DESCRIPTION
    "Number of frames that were transmitted due to reaching max.
     frame size. The user can choose to Tx the Frame when it reaches the
     Max size or when the packetizing time interval elapses."
    ::= { ip2IfStatEntry 6 }

ip2IfStatRxSignaling      OBJECT-TYPE
    SYNTAX        Counter32
    MAX-ACCESS    read-only
    STATUS        current		
    DESCRIPTION
    "Number of signaling frames that were received."
    ::= { ip2IfStatEntry 7 }

ip2IfStatRxVoice          OBJECT-TYPE
    SYNTAX        Counter32
    MAX-ACCESS    read-only
    STATUS        current		
    DESCRIPTION
    "Number of voice frames that were received."
    ::= { ip2IfStatEntry 8 }

ip2IfStatRxHdlc           OBJECT-TYPE
    SYNTAX        Counter32
    MAX-ACCESS    read-only
    STATUS        current		
    DESCRIPTION
    "Number of HDLC frames that were received."
    ::= { ip2IfStatEntry 9 }

ip2IfStatTxSignaling      OBJECT-TYPE
    SYNTAX        Counter32
    MAX-ACCESS    read-only
    STATUS        current		
    DESCRIPTION
    "Number of signaling frames that were transmitted."
    ::= { ip2IfStatEntry 10 }

ip2IfStatTxVoice          OBJECT-TYPE
    SYNTAX        Counter32
    MAX-ACCESS    read-only
    STATUS        current		
    DESCRIPTION
    "Number of voice frames that were transmitted."
    ::= { ip2IfStatEntry 11 }

ip2IfStatTxHdlc           OBJECT-TYPE
    SYNTAX        Counter32
    MAX-ACCESS    read-only
    STATUS        current		
    DESCRIPTION
    "Number of HDLC frames that were transmitted."
    ::= { ip2IfStatEntry 12 }

ip2IfStatRdnFlip          OBJECT-TYPE
    SYNTAX        Counter32
    MAX-ACCESS    read-only
    STATUS        current		
    DESCRIPTION
    "Number of redundancy flips occured.
    This parameter counts only flips from this bundle to the other bundle
    in the redundancy couple."
    ::= { ip2IfStatEntry 13 }

ip2IfFarEndTdmStatus OBJECT-TYPE
     SYNTAX  Integer32 (1..6)
     MAX-ACCESS  read-only
     STATUS  current
     DESCRIPTION
     "This variable indicates the Status of the Far-End TDM Line.  
     It contains failure state information.  
     The variable is a bit map represented as a sum, therefore, it
     can represent multiple failures simultaneously.  
     The farEndTdmNoDefect must be set if and only if no other flag is set.

     The various bit positions are:
        1   farEndTdmNoDefect
        2   farEndTdmAIS	   Alarm Indication Signal
        4   farEndTdmRDI	   Remote Defect Indication"
    ::= { ip2IfStatEntry 14 }

ip2IfStatPsnTxFrames           OBJECT-TYPE
    SYNTAX        Counter32
    MAX-ACCESS    read-only
    STATUS        current		
    DESCRIPTION
    "Number of frames that were transmitted to PSN."
    ::= { ip2IfStatEntry 15 }

ip2IfStatPsnRxFrames           OBJECT-TYPE
    SYNTAX        Counter32
    MAX-ACCESS    read-only
    STATUS        current		
    DESCRIPTION
    "Number of frames that were recieved from PSN."
    ::= { ip2IfStatEntry 16 }

ip2IfStatMinJittBufLevel      OBJECT-TYPE
    SYNTAX        Unsigned32
    MAX-ACCESS    read-only
    STATUS        current
    DESCRIPTION
    "The Minimum jitter buffer level (in msec)."
    ::= { ip2IfStatEntry 17 }

ip2IfStatMaxJittBufLevel      OBJECT-TYPE
    SYNTAX        Unsigned32
    MAX-ACCESS    read-only
    STATUS        current
    DESCRIPTION
    "The Maximum jitter buffer level (in msec)."
    ::= { ip2IfStatEntry 18 }

ip2IfStatRecommendedJittBufSize      OBJECT-TYPE
    SYNTAX        Unsigned32
    MAX-ACCESS    read-only
    STATUS        current
    DESCRIPTION
    "The Recommended jitter buffer Size (in msec).
     0= not applicable."
    ::= { ip2IfStatEntry 19 }

ip2IfStatPsnSeqErrors      OBJECT-TYPE
    SYNTAX        Counter32
    MAX-ACCESS    read-only
    STATUS        current
    DESCRIPTION
    "Number of times that the sequence number of an incoming Frame
     indicates Loss of Frame or Out of order occured in PSN."
     ::= { ip2IfStatEntry 20 }

ip2IfStatPsnReorderFrames      OBJECT-TYPE
    SYNTAX        Counter32
    MAX-ACCESS    read-only
    STATUS        current
    DESCRIPTION
    "Number of times that Frames had been reordered in PSN."
     ::= { ip2IfStatEntry 21 }

ip2IfStatMinRoundTripDelay      OBJECT-TYPE
    SYNTAX        Unsigned32
    MAX-ACCESS    read-only
    STATUS        current
    DESCRIPTION
    "The minimum Round Trip delay (in msec).
     0= not applicable."
    ::= { ip2IfStatEntry 22}

ip2IfStatMaxRoundTripDelay      OBJECT-TYPE
    SYNTAX        Unsigned32
    MAX-ACCESS    read-only
    STATUS        current
    DESCRIPTION
    "The maximum Round Trip delay (in msec).
     0= not applicable."
    ::= { ip2IfStatEntry 23 }

ip2IfStatAvrRoundTripDelay      OBJECT-TYPE
    SYNTAX        Unsigned32
    MAX-ACCESS    read-only
    STATUS        current
    DESCRIPTION
    "The avarage Round Trip delay (in msec).
     0= not applicable."
    ::= { ip2IfStatEntry 24 }

ip2IfStatFrameTrackDupDrop      OBJECT-TYPE
    SYNTAX        Counter32
    MAX-ACCESS    read-only
    STATUS        current
    DESCRIPTION
    "The number of packets dropped due to being duplicated.
     (duplicated packet means a packet that has the same sequential
      number as a packet being received previously)."
    ::= { ip2IfStatEntry 25 }

ip2IfStatFrameTrackMissing      OBJECT-TYPE
    SYNTAX        Counter32
    MAX-ACCESS    read-only
    STATUS        current
    DESCRIPTION
    "The number of packets that are missing.
     (Missing packet means an expected packet- according to the current sequential
      number - that was not received)."
    ::= { ip2IfStatEntry 26 }

ip2IfStatFrameTrackLongSerMiss   OBJECT-TYPE
    SYNTAX        Integer32
    MAX-ACCESS    read-only
    STATUS        current
    DESCRIPTION
"The longest series of consecutive missing sequential numbers.
    Missing sequential numbers represent missing packets that was
    expected to be received successively."
    ::= { ip2IfStatEntry 27 }


ip2IfStatTxMeasuredSilence  OBJECT-TYPE
     SYNTAX  Integer32     
     MAX-ACCESS  read-only
     STATUS  current
     DESCRIPTION
     "This object shows the percentage of Silence that was measured by the device
      for the current bundle in the transmitted payload.
      Relevant values: 0..100, 255.
      Default value is 50.
      0 means that there is no silence on the line.
      100 means that there is only silence. In this case, there might be no traffic.
      255 - value for not applicable or unknown."      
     ::= { ip2IfStatEntry 28 }
							
ip2IfStatRxMeasuredSilence  OBJECT-TYPE
     SYNTAX  Integer32     
     MAX-ACCESS  read-only
     STATUS  current
     DESCRIPTION
     "This object shows the percentage of Silence that was measured by the device
      for the current bundle in the received payload.
      Relevant values: 0..100, 255.
      Default value is 50.
      0 means that there is no silence on the line.
      100 means that there is only silence. In this case, there might be no traffic.
      255 - value for not applicable or unknown."      
     ::= { ip2IfStatEntry 29 }

ip2IfStatHdlcCrcErr	  OBJECT-TYPE
     SYNTAX  Counter32     
     MAX-ACCESS  read-only
     STATUS  current
     DESCRIPTION
     "This counter indicates the number of received HDLC frames 
     with CRC errors."      
     ::= { ip2IfStatEntry 30 }

ip2IfStatHdlcAlignErr	  OBJECT-TYPE
     SYNTAX  Counter32     
     MAX-ACCESS  read-only
     STATUS  current
     DESCRIPTION
     "This counter indicates the number of received HDLC frames 
     with alignment errors."      
     ::= { ip2IfStatEntry 31 }

ip2IfStatHdlcOversize	  OBJECT-TYPE
     SYNTAX  Counter32     
     MAX-ACCESS  read-only
     STATUS  current
     DESCRIPTION
     "This counter indicates the number of received HDLC frames 
     longer than 1470."      
     ::= { ip2IfStatEntry 32 }

ip2IfStatHdlcUndersize	  OBJECT-TYPE
     SYNTAX  Counter32     
     MAX-ACCESS  read-only
     STATUS  current
     DESCRIPTION
     "This counter indicates the number of received HDLC frames 
     shorter than 4."      
     ::= { ip2IfStatEntry 33 }

ip2IfStatHdlcAbort	  OBJECT-TYPE
     SYNTAX  Counter32     
     MAX-ACCESS  read-only
     STATUS  current
     DESCRIPTION
     "This counter indicates the number of received HDLC frames 
     with abort indication."      
     ::= { ip2IfStatEntry 34 }

ip2IfStatRxCorrectFrames  OBJECT-TYPE
     SYNTAX  Counter32     
     MAX-ACCESS  read-only
     STATUS  current
     DESCRIPTION
     "Number of received correct frames."      
     ::= { ip2IfStatEntry 35 }

ip2IfStatHdlcErroredFrames  OBJECT-TYPE
     SYNTAX  Counter32
     MAX-ACCESS  read-only
     STATUS  current
     DESCRIPTION
     "Number of received errored HDLC frames."      
     ::= { ip2IfStatEntry 36 }


							
ip2IfRateLimit OBJECT-TYPE
       SYNTAX  Integer32 
       MAX-ACCESS  read-write
       STATUS  current
       DESCRIPTION
       "The maximum rate permitted to transfer via the network portin Mbps."
       ::= { ip2If 8 }


-- ip2If Port table  

ip2IfPortTable OBJECT-TYPE
       SYNTAX  SEQUENCE OF Ip2IfPortEntry
       MAX-ACCESS  not-accessible
       STATUS  current
       DESCRIPTION
               "Port  Table."
       ::= { ip2If 9 }
  
ip2IfPortEntry OBJECT-TYPE
       SYNTAX Ip2IfPortEntry
       MAX-ACCESS not-accessible
       STATUS current
       DESCRIPTION
          "Application layer configuration per Port"
       INDEX   { ip2IfPortIndex }
       ::= { ip2IfPortTable 1 }

Ip2IfPortEntry ::=
         SEQUENCE {
         ip2IfPortIndex	    		Integer32,
         ip2IfPortUsage		    	Integer32,
		 ip2IfPortMask				INTEGER,
		 ip2IfPortTotalThroughput	Integer32
         	}
  
ip2IfPortIndex OBJECT-TYPE
    SYNTAX  Integer32 
    MAX-ACCESS  read-only
    STATUS  current
    DESCRIPTION
    "The Port index, which is actualy the ifIndex."
    ::= { ip2IfPortEntry 1 }

ip2IfPortUsage OBJECT-TYPE
    SYNTAX  Integer32 
    MAX-ACCESS  read-only
    STATUS  current
    DESCRIPTION
    "This parameter indicates the usage of the port (percents)."
    ::= { ip2IfPortEntry 2 }


ip2IfPortMask OBJECT-TYPE
       SYNTAX INTEGER {
       notApplicable	(1),
       dontMask  	    (2),
	   mask 			(3)
       }
       MAX-ACCESS  read-write
       STATUS  current
       DESCRIPTION
       "This parameter defines whether Agent will mask port's alarms and statistics or not."
	 ::= {  ip2IfPortEntry 3 }


ip2IfPortTotalThroughput OBJECT-TYPE
    SYNTAX  Integer32 
    MAX-ACCESS  read-only
    STATUS  current
    DESCRIPTION
    "This parameter indicates the total Throughput of the port in bps."
    ::= { ip2IfPortEntry 4 }


-- ip2If Current Statistics table  

ip2IfCurrentStatTable OBJECT-TYPE
       SYNTAX  SEQUENCE OF Ip2IfCurrentStatEntry
       MAX-ACCESS  not-accessible
       STATUS  current
       DESCRIPTION
       "Channels (Bundles) Current Statistics Table."
       ::= { ip2If 10 }
  
ip2IfCurrentStatEntry OBJECT-TYPE
       SYNTAX Ip2IfCurrentStatEntry
       MAX-ACCESS not-accessible
       STATUS current
       DESCRIPTION
       "IP Current Statistics per bundle"
       INDEX   { ip2IfChannelIndex }
       ::= { ip2IfCurrentStatTable 1 }

Ip2IfCurrentStatEntry ::=
         SEQUENCE {
         ip2IfCurrentStatSeqErrors         Counter32,
         ip2IfCurrentStatBufUnderflows     Counter32,
         ip2IfCurrentStatBufOverflows      Counter32,
		 ip2IfCurrentStatMaxDelayVar       Integer32,
		 ip2IfCurrentStatMinJittBufLevel   Unsigned32,
		 ip2IfCurrentStatMaxJittBufLevel   Unsigned32,
		 ip2IfCurrentStatTxErrFrameSec     Counter32
		 		 		 }

ip2IfCurrentStatSeqErrors      OBJECT-TYPE
    SYNTAX        Counter32
    MAX-ACCESS        read-only
    STATUS        current
    DESCRIPTION
    "Number of seconds that the sequence number of an incoming Frame
     causes a transition from the 'sync' state to
     the 'out of sequence' state in the current interval."
     ::= { ip2IfCurrentStatEntry 1 }

ip2IfCurrentStatBufUnderflows      OBJECT-TYPE
    SYNTAX        Counter32
    MAX-ACCESS    read-only
    STATUS        current
    DESCRIPTION
    "Number of seconds that the buffer underflows in the current interval. 
     This records the count of the number of seconds the Receive 
     (Eth to TDM) buffer underflows in the current interval. In the
     case of a continuous underflow caused by a loss of Frame
     flow, a single buffer underflow should be counted."
    ::= { ip2IfCurrentStatEntry 2 }

ip2IfCurrentStatBufOverflows      OBJECT-TYPE
    SYNTAX        Counter32
    MAX-ACCESS        read-only
    STATUS        current
    DESCRIPTION
    "Number of seconds that the buffer overflows in the current interval. 
     This records the count of the number of seonds the Receive 
     (Eth to TDM) buffer overflows in the current interval."
    ::= { ip2IfCurrentStatEntry 3 }

ip2IfCurrentStatMaxDelayVar      OBJECT-TYPE
    SYNTAX        Integer32
    MAX-ACCESS        read-only
    STATUS        current
    DESCRIPTION
    "The maximum deviation from the center of the buffer (in msec) for the current interval."
    ::= { ip2IfCurrentStatEntry 4 }

ip2IfCurrentStatMinJittBufLevel      OBJECT-TYPE
    SYNTAX        Unsigned32
    MAX-ACCESS    read-only
    STATUS        current
    DESCRIPTION
    "The Minimum jitter buffer level (in msec) for the current interval."
    ::= { ip2IfCurrentStatEntry 5 }

ip2IfCurrentStatMaxJittBufLevel      OBJECT-TYPE
    SYNTAX        Unsigned32
    MAX-ACCESS    read-only
    STATUS        current
    DESCRIPTION
    "The Maximum jitter buffer level (in msec) for the current interval."
    ::= { ip2IfCurrentStatEntry 6 }
  
ip2IfCurrentStatTxErrFrameSec    OBJECT-TYPE
    SYNTAX        Counter32
    MAX-ACCESS    read-only
    STATUS        current
    DESCRIPTION
    "The number of seconds in which errored frames were transmitted during the current interval.
     The error may be one of the following:
     CRC error, Alignment error, Oversized frame, Undersized frame, Aborted frame."
    ::= { ip2IfCurrentStatEntry 7 }

-- ip2If Interval Statistics table  

ip2IfIntervalStatTable OBJECT-TYPE
       SYNTAX  SEQUENCE OF Ip2IfIntervalStatEntry
       MAX-ACCESS  not-accessible
       STATUS  current
       DESCRIPTION
       "Channels (Bundles) Interval Statistics Table."
       ::= { ip2If 11 }
  
ip2IfIntervalStatEntry OBJECT-TYPE
       SYNTAX Ip2IfIntervalStatEntry
       MAX-ACCESS not-accessible
       STATUS current
       DESCRIPTION
       "IP Interval Statistics per bundle"
       INDEX   { ip2IfChannelIndex, ip2IfIntervalStatIndex }
       ::= { ip2IfIntervalStatTable 1 }

Ip2IfIntervalStatEntry ::=
         SEQUENCE {
         ip2IfIntervalStatIndex	       	   Integer32,
         ip2IfIntervalStatSeqErrors        Counter32,
         ip2IfIntervalStatBufUnderflows    Counter32,
         ip2IfIntervalStatBufOverflows     Counter32,
		 ip2IfIntervalStatMaxDelayVar      Integer32,
		 ip2IfIntervalStatMinJittBufLevel  Unsigned32,
		 ip2IfIntervalStatMaxJittBufLevel  Unsigned32,
		 ip2IfIntervalStatTxErrFrameSec    Counter32		
		 }

ip2IfIntervalStatIndex OBJECT-TYPE
    SYNTAX  		Integer32 
    MAX-ACCESS  read-only
    STATUS  current
    DESCRIPTION
    "The Interval index, which is actualy the Interval number."
    ::= { ip2IfIntervalStatEntry 1 }

ip2IfIntervalStatSeqErrors      OBJECT-TYPE
    SYNTAX        Counter32
    MAX-ACCESS        read-only
    STATUS        current
    DESCRIPTION
    "Number of seconds that the sequence number of an incoming Frame
     causes a transition from the 'sync' state to
     the 'out of sequence' state in the selected interval."
     ::= { ip2IfIntervalStatEntry 2 }

ip2IfIntervalStatBufUnderflows      OBJECT-TYPE
    SYNTAX        Counter32
    MAX-ACCESS    read-only
    STATUS        current
    DESCRIPTION
    "Number of seconds that the buffer underflows in the selected interval. 
     This records the count of the number of seconds the Receive 
     (Eth to TDM) buffer underflows in the selected interval. In the
     case of a continuous underflow caused by a loss of Frame
     flow, a single buffer underflow should be counted."
    ::= { ip2IfIntervalStatEntry 3 }

ip2IfIntervalStatBufOverflows      OBJECT-TYPE
    SYNTAX        Counter32
    MAX-ACCESS        read-only
    STATUS        current
    DESCRIPTION
    "Number of seconds that the buffer overflows in the selected interval. 
     This records the count of the number of seconds the Receive 
     (Eth to TDM) buffer overflows in the selected interval."
    ::= { ip2IfIntervalStatEntry 4 }

ip2IfIntervalStatMaxDelayVar      OBJECT-TYPE
    SYNTAX        Integer32
    MAX-ACCESS        read-only
    STATUS        current
    DESCRIPTION
    "The maximum size of the buffer (in 10's of usec) in the selected interval.
     For some devices (e.g. MP-4100) units are usec."
    ::= { ip2IfIntervalStatEntry 5 }

ip2IfIntervalStatMinJittBufLevel      OBJECT-TYPE
    SYNTAX        Unsigned32
    MAX-ACCESS    read-only
    STATUS        current
    DESCRIPTION
    "The Minimum jitter buffer level (in msec) for the selected interval.
     For some devices (e.g. MP-4100) units are usec."
    ::= { ip2IfIntervalStatEntry 6 }

ip2IfIntervalStatMaxJittBufLevel      OBJECT-TYPE
    SYNTAX        Unsigned32
    MAX-ACCESS    read-only
    STATUS        current
    DESCRIPTION
    "The Maximum jitter buffer level (in msec) for the selected interval.
     For some devices (e.g. MP-4100) units are usec."
    ::= { ip2IfIntervalStatEntry 7 }
								 
ip2IfIntervalStatTxErrFrameSec   OBJECT-TYPE
    SYNTAX        Counter32		
    MAX-ACCESS    read-only
    STATUS        current
    DESCRIPTION
    "The number of seconds in which errored frames were transmitted during the selected interval.
     The error may be one of the following:
     CRC error, Alignment error, Oversized frame, Undersized frame, Aborted frame."
    ::= { ip2IfIntervalStatEntry 8 }


ip2IfLogEvents			OBJECT-TYPE
     SYNTAX INTEGER {
       notApplicable	(1),
       all		  	    (2),
       oneMinStep		(3)
     }
     MAX-ACCESS  read-write
     STATUS  current
     DESCRIPTION
     "This parameter defines whether all Jitter Buffer and Sequence Number events
      will enter to Log File,
      or enter those events to Log file in one minute steps."
     ::= {  ip2If 12}


ip2IfEthSwitchMode			OBJECT-TYPE
     SYNTAX INTEGER {
       notApplicable	(1),
       unTagged	  	    (2),
       tagged			(3)
     }
     MAX-ACCESS  read-write
     STATUS  current
     DESCRIPTION
     "This parameter defines whether Eth Switch is in VLAN Tagged mode."
     ::= {  ip2If 13}



--Traps
 
--The numbers 1-4 are used by Imx.txt



--The numbers 5-6 are used by IpmuxAtmTraps.txt

alarmStatusTrap NOTIFICATION-TYPE
  OBJECTS  {atmInterfaceAlarmStatus}
  STATUS  current
  DESCRIPTION
      "The trap is sent whenever there is a transition from a no alarm
       state to a state with at least one active alarm."
  ::= { radSysWanEvents 5 }

systemTrap NOTIFICATION-TYPE
  OBJECTS  { atmNteEventType, agnLed, alarmSeverity }  
  STATUS  current
  DESCRIPTION
      "This trap alerts of major problems in the device."
  ::= { radSysWanEvents 6 }

alarmLOS NOTIFICATION-TYPE
      OBJECTS  { alarmSeverity, alarmState, ifAlias }  
      STATUS  current
      DESCRIPTION
	  "This trap indicates Loss Of Signal."
      ::= { radSysWanEvents 7 }

alarmLOF NOTIFICATION-TYPE
      OBJECTS  { alarmSeverity, alarmState, ifAlias }  
      STATUS  current
      DESCRIPTION
	  "This trap indicates Loss Of Frame."
      ::= { radSysWanEvents 8 }

channelOperStatusTrap NOTIFICATION-TYPE
      OBJECTS  { ip2IfOperStatus }  
      STATUS  current
      DESCRIPTION
	  "This trap is sent upon any change in one or more channels."
      ::= { radSysWanEvents 9 }

alarmAIS NOTIFICATION-TYPE
      OBJECTS  { alarmSeverity, alarmState, ifAlias }  
      STATUS  current
      DESCRIPTION
	  "This trap indicates AIS."
      ::= { radSysWanEvents 10 }

alarmRDI NOTIFICATION-TYPE
      OBJECTS  { alarmSeverity, alarmState, ifAlias }  
      STATUS  current
      DESCRIPTION
	  "This trap indicates RDI."
      ::= { radSysWanEvents 11 }

alarmFEBE NOTIFICATION-TYPE
      OBJECTS  { alarmSeverity, alarmState, ifAlias }  
      STATUS  current
      DESCRIPTION
	  "This trap indicates FEBE."
      ::= { radSysWanEvents 12 }

localConnStatusTrap NOTIFICATION-TYPE
      OBJECTS  { alarmSeverity, alarmState, ifAlias }  
      STATUS  current
      DESCRIPTION
	  "This trap is sent upon a change in Local connectivity
	   of Bundle connection."
      ::= { radSysWanEvents 13 }

remoteConnStatusTrap NOTIFICATION-TYPE
      OBJECTS  { alarmSeverity, alarmState, ifAlias }  
      STATUS  current
      DESCRIPTION
	  "This trap is sent upon a change in Remote connectivity
	   of Bundle connection."
      ::= { radSysWanEvents 14 }

bundleConnectionStatusTrap NOTIFICATION-TYPE
      OBJECTS  { ifAlias, ip2IfOperStatus }  
      STATUS  current
      DESCRIPTION
	  "This trap is sent upon any change in the connectivity status 
	   of a Bundle (ip2IfOperStatus).
	   The ifAlias index is the ifIndex of the bundle that its status has been changed."
      ::= { radSysWanEvents 15 }


END

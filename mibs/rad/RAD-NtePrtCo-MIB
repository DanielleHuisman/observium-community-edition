RAD-NtePrtCo-MIB DEFINITIONS ::= BEGIN


-- It is RAD's intent to encourage the widespread use of
-- this Specification in connection with the management of
-- RAD products. RAD grants vendors, end-users,
-- and other interested parties a non-exclusive license to
-- use this Specification in connection with the management
-- of RAD products.

-- This Specification is supplied "as is," and RAD makes
-- no warranty, either express or implied, as to the use,
-- operation, condition, or performance of the Specification.


IMPORTS

atmVplVpi , atmVclVpi, atmVclVci     FROM 	ATM-MIB
ifIndex		                    FROM 	IF-MIB
Integer32, OBJECT-TYPE, MODULE-IDENTITY,
OBJECT-IDENTITY	,Unsigned32     FROM 	SNMPv2-SMI
DateAndTime, DisplayString		FROM 	SNMPv2-TC
rad                             FROM RAD-SMI-MIB;


	radAtm MODULE-IDENTITY
		LAST-UPDATED "201502191804Z"  -- February 19, 2015
        ORGANIZATION "RAD Data Communications Ltd."
        CONTACT-INFO
        "System Department

         Email:  mibs@rad.com
         Postal: RAD Data Communications Ltd.
                 24 Raoul Wallenberg St.
                 Tel-Aviv 6971920
                 Israel

         Phone:  +972-3-645-5421
         Fax:    +972-3-760-7844"
         DESCRIPTION
            "ATM NTE MIB."
	::= { rad 12 }


atmNte              OBJECT IDENTIFIER ::= { radAtm 3 }
atmNtePrt		    OBJECT IDENTIFIER ::= { atmNte 2 }
atmNtePrtConfig		OBJECT IDENTIFIER ::= { atmNtePrt 1 }

atmNteEvents OBJECT-IDENTITY
     STATUS  current
     DESCRIPTION
     "The events for RAD ATM products."
     ::= { atmNte 0 }

atmNteConfIfTable OBJECT-TYPE
              SYNTAX  SEQUENCE OF AtmNteConfIfEntry
              MAX-ACCESS  not-accessible
              STATUS  current
              DESCRIPTION
              "The Physical interface configuration table."
              ::= { atmNtePrtConfig 1 }

          atmNteConfIfEntry OBJECT-TYPE
              SYNTAX  AtmNteConfIfEntry
              MAX-ACCESS  not-accessible
              STATUS  current
              DESCRIPTION
              "An entry in the Physical interface configuration table.
               The ifIndex is of the lowest physical layer."
              INDEX   { ifIndex}
              ::= { atmNteConfIfTable 1 }

          AtmNteConfIfEntry ::=
              SEQUENCE {
				atmConfIfTransmitClk
				      INTEGER,
				atmConfIfLoopback
				      INTEGER,
				atmConfIfFrameType
				      INTEGER,
				atmConfIfCardType
				      INTEGER,
				atmConfAtmIfVpiVciLimit
				      INTEGER,
				atmConfIfHwFeatures
				      INTEGER,
				atmConfIfOutputRate
				      Integer32,
				atmConfIfInputRate
				      Integer32,
				atmConfAlarmForwarding
				      INTEGER,
				atmConfIfAllocatedBw
					  Integer32,
				atmConfIfLowerVpi
					  Integer32,
				atmConfIfOamMode
					  INTEGER,
				atmConfIfOamFailureInd
					  INTEGER
                 }

          atmConfIfTransmitClk OBJECT-TYPE
              SYNTAX  INTEGER { internal(2), external(3), loopback(4), adaptive(5) }
              MAX-ACCESS  read-write
              STATUS  current
              DESCRIPTION
              "The transmit clock of the port."
              ::= { atmNteConfIfEntry 1 }

          atmConfIfLoopback OBJECT-TYPE
              SYNTAX  INTEGER { internal(2), external(3), disable(4) }
              MAX-ACCESS  read-write
              STATUS  current
              DESCRIPTION
              "Interface Loopback."
              ::= { atmNteConfIfEntry 2 }

          atmConfIfFrameType OBJECT-TYPE
              SYNTAX  INTEGER {
              other        (1),
              sonet        (2),
			  sdh          (3),
			  direct       (4),
			  plcpInternal (5),
			  plcpExternal (6),
			  e3           (7),
			  ethCrcTrans  (8),
			  ethCrcNotTrans          (9),
	          directNoScrmbling       (10),
	          plcpInternalNoScrmbling (11),
	          plcpExternalNoScrmbling (12)
	          }
              MAX-ACCESS  read-write
              STATUS  current
              DESCRIPTION
              "The frame type. Valid values for a 155M interface:
               sonet(2), sdh(3). Valid values for a T3 interface:
               direct(4), plcpInternal(5), plcpExternal(6),
               directNoScrmbling(10), plcpInternalNoScrmbling(11),
               plcpExternalNoScrmbling(12). Valid values for Ethernet
               interface: ethCrcTrans (8), ethCrcNotTrans(9).
               (DS1 interfaces frame type is specified in the DSX1 mib)."
              ::= { atmNteConfIfEntry 3 }

          atmConfIfCardType OBJECT-TYPE
              SYNTAX  INTEGER {
		      notApplicable(1),
		      sc13m-155(2),
		      st13s-155(3),
		      st13l-155(4),
		      utp-155(5),
		      cx-bnc-155(6),
		      e3(7),
		      t3(8),
			  e1(9),
		      e1-ltu(10),
		      fc13l-155(11),
		      fc13lh-155(12),
		      fc15lh-155(13),
		      fc13l-e3(14),
	          fc13lh-e3(15),
		      fc15lh-e3(16),
		      fc13l-t3(17),
		      fc13lh-t3(18),
		      fc15lh-t3(19)
              }
         	  MAX-ACCESS  read-only
         	  STATUS  deprecated
         	  DESCRIPTION
         	          "The card type."
         	  ::= { atmNteConfIfEntry 4 }

         	  atmConfAtmIfVpiVciLimit OBJECT-TYPE
         	  SYNTAX  INTEGER {
         	  bits15(2),
			  bits17(3)
			   }
         	  MAX-ACCESS  read-only
         	  STATUS  current
         	  DESCRIPTION
         	  "The limit on the sum of the VPI+VCI bits for this interface."
         	  ::= { atmNteConfIfEntry 5 }

              atmConfIfHwFeatures  OBJECT-TYPE
              SYNTAX  INTEGER {
              disable(1),
			  enable(2)
			  }
              MAX-ACCESS  read-write
              STATUS  current
              DESCRIPTION
              "HW features command."
              ::= { atmNteConfIfEntry 6 }

              atmConfIfOutputRate  OBJECT-TYPE
              SYNTAX  Integer32
              MAX-ACCESS  read-write
              STATUS  current
              DESCRIPTION
              "This parameter indicates the output rate in cells/sec, which is
              supported per port. Successfully setting this parameter
              is dependent on all other ports values calculations,
              which are described in the NMS SRS."
              ::= { atmNteConfIfEntry 7 }

              atmConfIfInputRate  OBJECT-TYPE
              SYNTAX  Integer32
              MAX-ACCESS  read-write
              STATUS  current
              DESCRIPTION
              "This parameter indicates the input rate in cells/sec, which is
              supported per port. Successfully setting this parameter
              is dependent on all other ports values calculations,
              which are described in the NMS SRS."
              ::= { atmNteConfIfEntry 8 }

          atmConfAlarmForwarding OBJECT-TYPE
              SYNTAX  INTEGER { disable(2), enable(3) }
              MAX-ACCESS  read-write
              STATUS  current
              DESCRIPTION
              "Enables Path AIS Alarm forwarding upon a failure detection. The
			  following might be considered as a failure: LOS, LOF, LOC, SLM,
			  LOP, Path AIS and Line AIS.

              disable(2) -  will not forward an alarm upon a failure on this port.

              enable(3) - will forward an alarm upon a failure on this port."
              ::= { atmNteConfIfEntry 9 }

		  atmConfIfAllocatedBw OBJECT-TYPE
			  SYNTAX  Integer32
    		  MAX-ACCESS read-only
			  STATUS current
			  DESCRIPTION
			  	"Total VC Bandwidth Allocation."
			  ::= { atmNteConfIfEntry 10 }

		  atmConfIfLowerVpi OBJECT-TYPE
    		  SYNTAX  Integer32
 		      MAX-ACCESS  read-write
		      STATUS  current
		      DESCRIPTION
			    "The Lower possible VPI."
			  ::= { atmNteConfIfEntry 11 }

		  atmConfIfOamMode OBJECT-TYPE
    		  SYNTAX  INTEGER {
              		--	intermediate(1),
              		segmentTermination(2),
              		endToEndTermination(3)
			  		-- vpEndToEndVcSegment(4)
              	}
 		      MAX-ACCESS  read-write
		      STATUS  current
		      DESCRIPTION
			    "OAM support Mode, which determines the
			     interface's location in a segment wise."
			  ::= { atmNteConfIfEntry 12 }

	atmConfIfOamFailureInd OBJECT-TYPE
             SYNTAX INTEGER {
             		disabled  (2),
             		ais       (3),
             		rdi       (4),
             		aisAndRdi (5)
             		}
             MAX-ACCESS read-write
             STATUS     current
             DESCRIPTION
             "This object allows user to define the type of indication
               (if any) that will be created upon a LB cell failure,
               for all VCs on which OAM loopback traffic is activated.
                    disabled(2) - no indication will be created.
                    ais(3) - will cause Tx of AIS.
                    rdi(4) - will cause Tx of RDI.
                    aisAndRdi(5) - will cause Tx of AIS & RDI.
    	  For LA-110, indication will be sent only
    	  for VCs with atmConfVcLoopbackFailureInd <> disabled"
             ::= {atmNteConfIfEntry 13}


atmNteAlarmIfTable OBJECT-TYPE
              SYNTAX  SEQUENCE OF AtmNteAlarmIfEntry
              MAX-ACCESS  not-accessible
              STATUS  current
              DESCRIPTION
                      "The interface Alarm table."
              ::= { atmNtePrtConfig 2 }

          atmNteAlarmIfEntry OBJECT-TYPE
              SYNTAX  AtmNteAlarmIfEntry
              MAX-ACCESS  not-accessible
              STATUS  current
              DESCRIPTION
                      "An entry in the interface Alarm table."
              INDEX   { ifIndex}
              ::= { atmNteAlarmIfTable 1 }

          AtmNteAlarmIfEntry ::=
              SEQUENCE {
				atmInterfaceActiveAlarms
				      Integer32,
				atmThresholdSectionBIP
				      Integer32,
				atmThresholdLineBIP
				      Integer32,
				atmThresholdLineFEBE
				      Integer32,
				atmThresholdPathBIP
				      Integer32,
				atmThresholdPathFEBE
				      Integer32,
				atmThresholdErroredCells
				      Integer32,
				atmThresholdLostCells
				      Integer32,
				atmThresholdMisinsertedCells
				      Integer32,
			    atmInterfaceAlarmStatus
				      INTEGER,
                atmInterfaceMaskAlarms
				      Integer32
              }

          atmInterfaceActiveAlarms OBJECT-TYPE
              SYNTAX  Integer32
              MAX-ACCESS  read-only
              STATUS  current
              DESCRIPTION
                      "A Bit String of the active alarms on this interface.
					   An up bit (1) means there is an active alarm of this
					   type. A down bit (0) means there is no such alarm.
                       The meaning of the bits is as follows:
                       1 - LOS
                       2 - LOF
                       3 - Line AIS (SONET)/ PLCP LOF (DS3)
                       4 - LOP
                       5 - Path AIS
                       6 - SLM
                       7 - LCD
                       8 - Line RDI  (SONET)/ PLCP Yellow (DS3)
                       9 - Path RDI  (SONET)/ RDI (DS3)
					   10 - Section BIP (SONET)/ P1/P2 (DS3) > Threshold
					   11 -	Line BIP (SONET)/ PLCP BIP (DS3) > Threshold
					   12 - Line FEBE (SONET)/ PLCP FEBE (DS3) > Threshold
					   13 - Path BIP > Threshold
					   14 - Path FEBE > Threshold
					   15 - HW Failure
                       "
              ::= { atmNteAlarmIfEntry 1 }

          atmThresholdSectionBIP OBJECT-TYPE
              SYNTAX  Integer32
              MAX-ACCESS  read-write
              STATUS  current
              DESCRIPTION
                      "When Section BIPs are greater than this threshold,
	an active alarm is raised. N/A for ds3/e3 interface."
              ::= { atmNteAlarmIfEntry 2 }

          atmThresholdLineBIP OBJECT-TYPE
              SYNTAX  Integer32
              MAX-ACCESS  read-write
              STATUS  current
              DESCRIPTION
                      "When Line BIPs are greater than this threshold,
	an active alarm is raised. N/A for ds3/e3 interface."
              ::= { atmNteAlarmIfEntry 3 }

          atmThresholdLineFEBE OBJECT-TYPE
              SYNTAX  Integer32
              MAX-ACCESS  read-write
              STATUS  current
              DESCRIPTION
                      "When Line FEBEs are greater than this threshold,
	an active alarm is raised. N/A for ds3/e3 interface."
              ::= { atmNteAlarmIfEntry 4 }

          atmThresholdPathBIP OBJECT-TYPE
              SYNTAX  Integer32
              MAX-ACCESS  read-write
              STATUS  current
              DESCRIPTION
                      "When Path BIPs are greater than this threshold,
					   an active alarm is raised."
              ::= { atmNteAlarmIfEntry 5 }

          atmThresholdPathFEBE OBJECT-TYPE
              SYNTAX  Integer32
              MAX-ACCESS  read-write
              STATUS  current
              DESCRIPTION
                      "When Path FEBEs are greater than this threshold,
					   an active alarm is raised."
              ::= { atmNteAlarmIfEntry 6 }

          atmThresholdErroredCells OBJECT-TYPE
              SYNTAX  Integer32
              MAX-ACCESS  read-write
              STATUS  current
              DESCRIPTION
                      "When Errored Cells are greater than this threshold,
					   an active alarm is raised."
              ::= { atmNteAlarmIfEntry 7 }

          atmThresholdLostCells OBJECT-TYPE
              SYNTAX  Integer32
              MAX-ACCESS  read-write
              STATUS  current
              DESCRIPTION
                      "When Lost Cells are greater than this threshold,
					   an active alarm is raised."
              ::= { atmNteAlarmIfEntry 8 }

          atmThresholdMisinsertedCells OBJECT-TYPE
              SYNTAX  Integer32
              MAX-ACCESS  read-write
              STATUS  current
              DESCRIPTION
                      "When Misinserted Cells are greater than this threshold,
					   an active alarm is raised."
              ::= { atmNteAlarmIfEntry 9 }



          atmInterfaceAlarmStatus OBJECT-TYPE
              SYNTAX  INTEGER { off(2),
			                    on(3) }
              MAX-ACCESS  read-only
              STATUS  current
              DESCRIPTION
                      "The variable is on(3) when there is any active alarm
                       on this interface."
              ::= { atmNteAlarmIfEntry 10 }

          atmInterfaceMaskAlarms OBJECT-TYPE
              SYNTAX  Integer32
              MAX-ACCESS  read-write
              STATUS  current
              DESCRIPTION
                      "A Bit String of alarms mask on this interface.
					   An up bit (1) means that the respective alarm is masked.
					   A down bit (0) means no mask.
                       The mask is supported for the following alarms:
                       1 - LOS
                       "
              ::= { atmNteAlarmIfEntry 11 }


          atmNteConfVpTable OBJECT-TYPE
              SYNTAX  SEQUENCE OF AtmNteConfVpEntry
              MAX-ACCESS  not-accessible
              STATUS  current
              DESCRIPTION
                      "The ATM VP configuration table.
                       The table is an extension to the atmVplTable of
                       RFC-1695."
              ::= { atmNtePrtConfig 3 }

          atmNteConfVpEntry OBJECT-TYPE
              SYNTAX  AtmNteConfVpEntry
              MAX-ACCESS  not-accessible
              STATUS  current
              DESCRIPTION
                      "An entry in the ATM VP configuration table.
                       ifIndex of the ATM layer."
              INDEX   { ifIndex, atmVplVpi }
              ::= { atmNteConfVpTable 1 }

          AtmNteConfVpEntry ::=
              SEQUENCE {
			atmConfVpPolicing            		INTEGER,
			atmConfVpCCAdminStatus       		INTEGER,
			atmConfVpLoopbackAdminStatus 		INTEGER,
			atmConfVpLoopbackSinkAddress 		OCTET STRING,
			atmConfVpCongestionControl   		OCTET STRING,
			atmConfVpCCDirection         		INTEGER,
            atmConfVpCreationTime        		DateAndTime,
            atmConfVpOamSupport          		INTEGER,
            atmConfVpCCOperStatus        		INTEGER,
			atmConfVpLoopbackTraffic     		INTEGER,
            atmConfVpLoopbackFailureInd	 		INTEGER,
            atmConfVpLoopbackFailureThreshold	Integer32,
			atmConfVpOamDirection        		INTEGER,
			atmConfVpOamDescrIndex	 	 		Integer32,
			atmConfVpConnected			 		INTEGER
           }

 atmConfVpPolicing OBJECT-TYPE
              SYNTAX  INTEGER {
                 none(1),
                 police(2),
                 monitor(3),
                 shaping(4),
                 policingAndShaping(5)
              }
              MAX-ACCESS  read-write
              STATUS  current
              DESCRIPTION
                      "Policing method desired for this VPL."
              ::= { atmNteConfVpEntry 1 }

        atmConfVpCCAdminStatus OBJECT-TYPE
             SYNTAX INTEGER {
		            up    (2),
            		down  (3),
		            source(4),      -- agent send Oam CC cells
		            sink  (5),      -- agent check received Oam CC cells
                    listenToActivationCells (6),
                    originateActivationCells(7)
                            }
             MAX-ACCESS read-write
             STATUS current
             DESCRIPTION
                     	"up(2) - Activate Continuity Check (CC).
                      	down(3) - Deactivate CC.
		                source(4)      - Activate OAM CC(Continuity Check) of local agent
                        			( start sending Oam cells to the remote side ).
      		            sink(5)          - Activate CC of remote agent ( start receiving Oam cells from
      		             				remote 	side ).
                     listenToActivationCells (6) - Passive listener till gets an activation request
                     originateActivationCells(7) - Sands Activation cell according to atmConfVcCCDirection."
             ::= {atmNteConfVpEntry 2}

	atmConfVpLoopbackAdminStatus OBJECT-TYPE
                    SYNTAX INTEGER {
		            up(2),
		            down(3),
		            llid(4),
		            segment(5),
		            endToEnd(6),
		            segmentLlid(7),
		            endToEndLlid(8)
	                }
             		MAX-ACCESS read-write
             		STATUS current
             		DESCRIPTION
                        "up(2) - Start loopback OAM cells.
                         down(3) - Stop sending loopback OAM cells.

                         For ace2002:
                         up(2)   - Transmitting LB cells with llid all ones
                                   (i.e. FFFF..FF)
                         down(3) - Not transmitting LB cells.
                         llid(4) - Transmitting LB cells with llid indicated
                                    in the address field.
                         segment(5) - Transmitting Segment LB cells with llid
                                       all ones.
                         endToEnd(6) - Transmitting End to End LB cells with llid
                                        all ones.
                         segmentLlid(7) - Transmitting Segment LB cells with
                                           llid indicated in the address field.
                         endToEndLlid(8) - Transmitting LB cells with llid
                                            indicated in the address field.

                         This parameter value might be in conflict with
                         atmConfVpOamSupport value, since this parameter is for LB,
                         while atmConfVpOamSupport is for any other OAM cells."
             ::= {atmNteConfVpEntry 3}

	atmConfVpLoopbackSinkAddress OBJECT-TYPE
             		SYNTAX OCTET STRING  (SIZE(0..20))
             		MAX-ACCESS read-write
             		STATUS current
             		DESCRIPTION
                    	 "Destination address.
                    	 For ace101: 2 bytes are used.
                    	 For ace2002: 16 bytes are used."
             ::= {atmNteConfVpEntry 4}

	atmConfVpCongestionControl OBJECT-TYPE
             		SYNTAX OCTET STRING
             		MAX-ACCESS read-write
             		STATUS current
             		DESCRIPTION
                    	 "Each bit indicates a selection of one option
                               as the following description.  All combinations
                               are possible and legal.
                               The codes are:
                               1 - EPD
                               2 - CLP
                               4 - EFCI"
             ::= {atmNteConfVpEntry 5}

     atmConfVpCCDirection OBJECT-TYPE
             SYNTAX  INTEGER {
		            both  (2),
		            source(4),
		            sink  (5)
                            }
             MAX-ACCESS read-write
             STATUS current
             DESCRIPTION
                     	"both(2) - Agent send OAM CC cells and check received OAM CC cells
                        source(4)- Agent send OAM CC cells.
      		            sink(5)  - Agent checks received OAM CC cells."
             ::= {atmNteConfVpEntry 6}

     atmConfVpCreationTime OBJECT-TYPE
         SYNTAX   DateAndTime
         MAX-ACCESS   read-only
         STATUS   current
         DESCRIPTION
            "A date-time in which the VP was created."
         ::= { atmNteConfVpEntry 7 }

     atmConfVpOamSupport OBJECT-TYPE
               SYNTAX  INTEGER {
                          intermediate(1),
                          segmentTermination(2),
                          endToEndTermination(3)
                      }
               MAX-ACCESS  read-write
               STATUS  current
               DESCRIPTION
               "OAM support  mode, which determines the device location
                in a segment wise."
               ::= { atmNteConfVpEntry 8 }


	atmConfVpCCOperStatus OBJECT-TYPE
             SYNTAX INTEGER {
		             initial (1),
		             source(4),
		             sink  (5),
					 both  (8),
		 			 timeout (9),
				     denied (10),
					 conflict (11),
					 manual (12)
                            }
             MAX-ACCESS read-only
             STATUS current
             DESCRIPTION
                     	"
		                initial(1) - The CC activation process is not started.
		                source(4) - Agent sends OAM CC cells.
      		            sink(5)   - Agent checks received OAM CC cells.
						both (8) - OAM CC of local and remote agents activation.
		                timeout (9) - Timeout occured on receiving answer from
                                      the remote agent.
		                denied  (10) - CC activation process rejected by remote agent.
		                conflict (11) - local and remote sides requested activation
                                      simultaneously.
				        manual (12) - OAM CC of local agent activated manually.
                        "
             ::= {atmNteConfVpEntry 9}

	atmConfVpLoopbackTraffic OBJECT-TYPE
             		SYNTAX INTEGER { off(2), on(3) }
             		MAX-ACCESS read-write
             		STATUS current
             		DESCRIPTION
                    	 "This parameter has both command and status meanings:
                    	 off(2) - Set to 'Off' will Stop traffic loop. Getting this
                    	          value means that the loop is not running.
                      	 on (3) - Set to 'On' will start traffic loop. Getting
                      	          this value means that the loop is currently running."
             ::= {atmNteConfVpEntry 10}

	atmConfVpLoopbackFailureInd OBJECT-TYPE
             		SYNTAX INTEGER {
             		disabled(2),
             		segmentAis(3),
             		segmentRdi(4),
             		segmentAisAndRdi(5),
             		endToEndAis(6),
             		endToEndRdi(7),
             		endToEndAisAndRdi(8)
             		}
             		MAX-ACCESS read-write
             		STATUS current
             		DESCRIPTION
    "This object allows user to define the Indication that will be created upon
     a LB cell failure.
     disabled(2) - no indication will be created.
     segmentAis(3) - will cause Tx of a segment AIS.
     segmentRdi(4) - will cause Tx of a segment RDI.
     segmentAisAndRdi(5) - will cause Tx of a segment AIS & RDI.
     endToEndAis(6) - will cause Tx of an End to End AIS.
     endToEndRdi(7)	- will cause Tx of an End to End RDI.
     endToEndAisAndRdi(8) - will cause Tx of an End to End AIS & RDI.
     Default: disabled(2)."
             ::= {atmNteConfVpEntry 11}

	atmConfVpLoopbackFailureThreshold OBJECT-TYPE
             		SYNTAX Integer32
             		MAX-ACCESS read-write
             		STATUS current
             		DESCRIPTION
    "The number of the LB failures before starting transmission of the
    Indication defined by atmConfVcLoopbackFailureInd.
    Range: 1..16. Default: 1."
             ::= {atmNteConfVpEntry 12}

     atmConfVpOamDirection OBJECT-TYPE
             SYNTAX  INTEGER {
		            notApplicable  (1),
		            downStream     (2),
		            upStream       (3)
                            }
             MAX-ACCESS read-write
             STATUS current
             DESCRIPTION
     "The direction of OAM cell insertion.
	 downStream(2) - The OAM cell will be inserted in downStream.
	 upStream(3)   - The OAM cell will be inserted in upStream."
             ::= {atmNteConfVpEntry 13}

atmConfVpOamDescrIndex OBJECT-TYPE
	SYNTAX  Integer32
	MAX-ACCESS read-write
	STATUS current
	DESCRIPTION
	"This parameter indicates the VPL's OAM Descriptor index,
	 according to the OAM Descriptor Configuration Table."
			::= {atmNteConfVpEntry 14}

atmConfVpConnected OBJECT-TYPE
	SYNTAX  INTEGER {
		notConnected	(1),
		mng				(2),
		bridgePort		(3),
		ds0Bundle		(4),
		atm				(5),
		pw				(6)
        }
	MAX-ACCESS read-write
	STATUS current
	DESCRIPTION
	"This object indicates whether this VP is connected
	and if connected, what is it connected to."
			::= {atmNteConfVpEntry 15}


--Alarm Table
          atmNteAlarmVpTable OBJECT-TYPE
              SYNTAX  SEQUENCE OF AtmNteAlarmVpEntry
              MAX-ACCESS  not-accessible
              STATUS  current
              DESCRIPTION
                      "The ATM VP Alarm table."
              ::= { atmNtePrtConfig 5 }

          atmNteAlarmVpEntry OBJECT-TYPE
              SYNTAX  AtmNteAlarmVpEntry
              MAX-ACCESS  not-accessible
              STATUS  current
              DESCRIPTION
                      "An entry in the ATM VP Alarm table.
                       ifIndex of the ATM layer."
              INDEX   { ifIndex, atmNteVpAlarmVpi}
              ::= { atmNteAlarmVpTable 1 }

          AtmNteAlarmVpEntry ::=
              SEQUENCE {
			    atmNteVpAlarmVpi
				      Integer32,
			    atmNteVpActiveAlarms
				      Integer32
              }

          atmNteVpAlarmVpi OBJECT-TYPE
              SYNTAX  Integer32
              MAX-ACCESS  read-only
              STATUS  current
              DESCRIPTION
                      "The VPI on which there is an active alarm."
              ::= { atmNteAlarmVpEntry 1 }

          atmNteVpActiveAlarms OBJECT-TYPE
              SYNTAX  Integer32
              MAX-ACCESS  read-only
              STATUS  current
              DESCRIPTION
                      "A Bit String of the active alarms on this VP.
					   An up bit (1) means there is an active alarm of this
					   type. A down bit (0) means there is no such alarm.
                       The meaning of the bits is as follows:
                       1 -	VP AIS
                       2 -	VP Loss Of Continuity
					   3 -  VP RDI Reception
					   4 -	VP Errored Cells > Threshold
					   5 -	VP Lost Cells > Threshold
					   6 -	VP Misinserted Cells > Threshold
					   9 -  VP Loopback Failure
                       "
              ::= { atmNteAlarmVpEntry 2 }

          atmNteAlarmVcTable OBJECT-TYPE
              SYNTAX  SEQUENCE OF AtmNteAlarmVcEntry
              MAX-ACCESS  not-accessible
              STATUS  current
              DESCRIPTION
                      "The ATM VC Alarm table."
              ::= { atmNtePrtConfig 6 }

          atmNteAlarmVcEntry OBJECT-TYPE
              SYNTAX  AtmNteAlarmVcEntry
              MAX-ACCESS  not-accessible
              STATUS  current
              DESCRIPTION
                      "An entry in the ATM VC Alarm table.
                       ifIndex of the ATM layer."
              INDEX   { ifIndex, atmNteVcAlarmVpi, atmNteVcAlarmVci}
              ::= { atmNteAlarmVcTable 1 }

          AtmNteAlarmVcEntry ::=
              SEQUENCE {
			    atmNteVcAlarmVpi
				      Integer32,
			    atmNteVcAlarmVci
				      Integer32,
			    atmNteVcActiveAlarms
				      Integer32
              }

          atmNteVcAlarmVpi OBJECT-TYPE
              SYNTAX  Integer32
              MAX-ACCESS  read-only
              STATUS  current
              DESCRIPTION
                      "The VPI of the VC on which there is an active alarm."
              ::= { atmNteAlarmVcEntry 1 }

          atmNteVcAlarmVci OBJECT-TYPE
              SYNTAX  Integer32
              MAX-ACCESS  read-only
              STATUS  current
              DESCRIPTION
                      "The VCI of the VC on which there is an active alarm."
              ::= { atmNteAlarmVcEntry 2 }

atmNteVcActiveAlarms OBJECT-TYPE
              SYNTAX  Integer32
              MAX-ACCESS  read-only
              STATUS  current
              DESCRIPTION
                      "A Bit String of the active alarms on this VC.
					   An up bit (1) means there is an active alarm of this
					   type. A down bit (0) means there is no such alarm.
                       The meaning of the bits is as follows:
                       1 -	VC AIS
                       2 -	VC Loss Of Continuity
					   3 -  VC RDI
					   4 -	VC Errored Cells > Threshold
					   5 -	VC Lost Cells > Threshold
					   6 -	VC Misinserted Cells > Threshold
					   7 - 	Tx VC AIS
					   8 - 	Tx VC RDI
					   9 -  VC Loopback Failure
                       "
              ::= { atmNteAlarmVcEntry 3 }


-- file  : ConfVcTable.txt

-- *******************************************************
--          Configuration Vc Table
-- *******************************************************

atmNteConfVcTable OBJECT-TYPE
              SYNTAX  SEQUENCE OF AtmNteConfVcEntry
              MAX-ACCESS  not-accessible
              STATUS  current
              DESCRIPTION
                      "The ATM VC configuration table.
                       The table is an extension to the atmVclTable of
                       RFC-2515."
              ::= { atmNtePrtConfig 4 }

          atmNteConfVcEntry OBJECT-TYPE
              SYNTAX  AtmNteConfVcEntry
              MAX-ACCESS  not-accessible
              STATUS  current
              DESCRIPTION
                      "An entry in the ATM VC configuration table.
                       ifIndex of the ATM layer."
              INDEX   { ifIndex , atmVclVpi, atmVclVci}
              ::= { atmNteConfVcTable 1 }

          AtmNteConfVcEntry ::=
              SEQUENCE {
				atmConfVcPolicing            		INTEGER,
				atmConfVcCCAdminStatus       		INTEGER,
				atmConfVcLoopbackAdminStatus 		INTEGER,
			    atmConfVcLoopbackSinkAddress 		OCTET STRING,
			    atmConfVcCongestionControl   		OCTET STRING,
                atmConfVcCCDirection		 		INTEGER,
                atmConfVcCreationTime        		DateAndTime,
                atmConfVcOamSupport          		INTEGER,
				atmConfVcCCActivationCtrl    		INTEGER,
				atmConfVcCCOperStatus        		INTEGER,
				atmConfVcLoopbackTraffic     		INTEGER,
				atmConfVcLoopbackFailureInd	 		INTEGER,
				atmConfVcLoopbackFailureThreshold	Integer32,
			    atmConfVcOamDirection        		INTEGER,
				atmConfVcName				 		DisplayString,
				atmConfVcConnected           		INTEGER,
				atmConfVcOamDescrIndex	 	 		Integer32,
				atmConfVcNoOfUsages					Unsigned32
              }

          atmConfVcPolicing OBJECT-TYPE
              SYNTAX  INTEGER {
		         none(1),
		         police(2),
		         monitor(3),
		         shaping(4),
                 policingAndShaping(5),
		         notApplicable(255)
	          }
              MAX-ACCESS  read-write
              STATUS  current
              DESCRIPTION
              "Policing method desired for this VCL."
              ::= { atmNteConfVcEntry 1 }

          atmConfVcCCAdminStatus OBJECT-TYPE
             SYNTAX  INTEGER {
		        up(2),
             	down(3),
		        source(4),       -- agent send Oam CC cells
		        sink(5),         -- agent check received Oam CC cells
                listenToActivationCells (6),
                originateActivationCells(7)
                            }
             MAX-ACCESS read-write
             STATUS current
             DESCRIPTION
             "up(2) - Activate Continuity Check (CC).
              down(3) - Deactivate CC.
		      source(4)      - Activate OAM CC(Continuity Check) of local agent
             			( start sending Oam cells to the remote side ).
      		  sink(5)  - Activate CC of remote agent ( start receiving Oam cells from
      		 	         remote side).
      		  listenToActivationCells (6) - Passive listener till gets an activation request
              originateActivationCells(7) - Sands Activation cell according to atmConfVcCCDirection."
             ::= {atmNteConfVcEntry 2}

          atmConfVcLoopbackAdminStatus OBJECT-TYPE
             SYNTAX INTEGER {
		      up(2),
		      down(3),
		      llid(4),
		      segment(5),
		      endToEnd(6),
		      segmentLlid(7),
		      endToEndLlid(8)
	         }
             MAX-ACCESS read-write
             STATUS current
             DESCRIPTION
             "up(2) - Start loopback OAM cells.
             down(3) - Stop sending loopback OAM cells.

             For ace2002:
             up(2)   - Transmitting LB cells with llid all ones
                       (i.e. FFFF..FF)
             down(3) - Not transmitting LB cells.
             llid(4) - Transmitting LB cells with llid indicated
                       in the address field.
             segment(5) - Transmitting Segment LB cells with llid
                       all ones.
             endToEnd(6) - Transmitting End to End LB cells with llid
                       all ones.
             segmentLlid(7) - Transmitting Segment LB cells with
                       llid indicated in the address field.
             endToEndLlid(8) - Transmitting LB cells with llid
                       indicated in the address field.

             This parameter value might be in conflict with
             atmConfVcOamSupport value, since this parameter is for LB,
             while atmConfVcOamSupport is for any other OAM cells."
             ::= {atmNteConfVcEntry 3}

	     atmConfVcLoopbackSinkAddress OBJECT-TYPE
             SYNTAX OCTET STRING  (SIZE(2..20))
             MAX-ACCESS read-write
             STATUS current
             DESCRIPTION
             "Destination address.
              For ace101: 2 bytes are used.
              For ace2002: 16 bytes are used."
             ::= {atmNteConfVcEntry 4}

	     atmConfVcCongestionControl OBJECT-TYPE
             SYNTAX OCTET STRING
             MAX-ACCESS read-write
             STATUS current
             DESCRIPTION
             "Each bit indicates a selection of one option
                    as the following description.  All combinations
                    are possible and legal.
                    The codes are:
                    1 - EPD
                    2 - CLP
                    4 - EFCI.
                    For ace2002:
                    1 - Packet Discard."
             ::= {atmNteConfVcEntry 5}

         atmConfVcCCDirection OBJECT-TYPE
             SYNTAX  INTEGER {
		    	both  (2),
		    	none  (3),
                source(4),
                sink  (5)
                       }
             MAX-ACCESS read-write
             STATUS current
             DESCRIPTION
             "both(2)  - Agent sends OAM CC cells and checks received OAM CC cells.
			  none(3) - Agent does not send and does not check received OAM CC cells.
              source(4)- Agent sends OAM CC cells.
 		      sink(5)  - Agent checks received OAM CC cells."
             ::= {atmNteConfVcEntry 6}

         atmConfVcCreationTime OBJECT-TYPE
         SYNTAX   DateAndTime
         MAX-ACCESS   read-only
         STATUS   current
         DESCRIPTION
         "A date-time in which the VC was created."
         ::= { atmNteConfVcEntry 7 }

         atmConfVcOamSupport OBJECT-TYPE
             SYNTAX  INTEGER {
                  intermediate(1),
                  segmentTermination(2),
                  endToEndTermination(3),
                  endToEndAndSegment(4)
              }
             MAX-ACCESS  read-write
             STATUS  current
             DESCRIPTION
             "OAM support mode, which determines the device location
              in a segment wise.

              endToEndAndSegment -  In this mode the OAM cells are generated
                                 before the ABM (ATM Buffer Manager), so
                                 that the PCR and CDVT will not be affected."
             ::= { atmNteConfVcEntry 8 }

         atmConfVcCCActivationCtrl OBJECT-TYPE
             SYNTAX  INTEGER {
		             manual(1),
                     activator(2),
		             listener(3)
                            }
             MAX-ACCESS read-write
             STATUS current
             DESCRIPTION
             "manual(1) - CC Activation process is disable
              activator(2) - ACE-101 initiate  CC Activation process
              listener(3) - ACE-101 wait to CC Activation request from remote side."
             ::= { atmNteConfVcEntry 9 }

          atmConfVcCCOperStatus OBJECT-TYPE
             SYNTAX  INTEGER {
					 initial(1),
		             up(2),
            	     down(3),
		             source(4),    -- agent send Oam CC cells
		             sink(5),       -- agent check received Oam CC cells
					 both (8),
		 			 timeout (9),
				     denied (10),
					 conflict (11),
					 manual (12)
                            }
             MAX-ACCESS read-only
             STATUS current
             DESCRIPTION
             "initial (1) - The CC activation process is not started.
              up (2) -  Continuity Check (CC) activated.
              down (3) - CC deactivated.
              source (4)  -  OAM CC(Continuity Check) of local agent activated.
              sink (5)  -  OAM CC of remote agent activated.
			  both (8) - OAM CC of local and remote agents activation.
		      timeout (9) - Timeout occured on receiving answer from
                           the remote agent.
		      denied  (10) - CC activation process rejected by remote agent.
		      conflict (11) - local and remote sides requested activation
                              simultaneously.
			  manual (12) - OAM CC of local agent activated manually.
			 	"
             ::= { atmNteConfVcEntry 10 }

	      atmConfVcLoopbackTraffic OBJECT-TYPE
               SYNTAX INTEGER { off(2), on(3) }
               MAX-ACCESS read-write
               STATUS current
               DESCRIPTION
               "This parameter has both command and status meanings:
                off(2) - Set to 'Off' will Stop traffic loop. Getting this
                        value means that the loop is not running.
                on (3) - Set to 'On' will start traffic loop. Getting
              	          this value means that the loop is currently running."
             ::= {atmNteConfVcEntry 11}

	      atmConfVcLoopbackFailureInd OBJECT-TYPE
             		SYNTAX INTEGER {
             		disabled(2),
             		segmentAis(3),
             		segmentRdi(4),
             		segmentAisAndRdi(5),
             		endToEndAis(6),
             		endToEndRdi(7),
             		endToEndAisAndRdi(8)
             		}
             		MAX-ACCESS read-write
             		STATUS current
             		DESCRIPTION
    "This object allows user to define the Indication that will be created upon
     a LB cell failure.
     disabled(2) - no indication will be created.
     segmentAis(3) - will cause Tx of a segment AIS.
     segmentRdi(4) - will cause Tx of a segment RDI.
     segmentAisAndRdi(5) - will cause Tx of a segment AIS & RDI.
     endToEndAis(6) - will cause Tx of an End to End AIS.
     endToEndRdi(7)	- will cause Tx of an End to End RDI.
     endToEndAisAndRdi(8) - will cause Tx of an End to End AIS & RDI.
     Default: disabled(2)."
             ::= {atmNteConfVcEntry 12}

	atmConfVcLoopbackFailureThreshold OBJECT-TYPE
             		SYNTAX Integer32
             		MAX-ACCESS read-write
             		STATUS current
             		DESCRIPTION
    "The number of the LB failures before starting transmission of the
    Indication defined by atmConfVcLoopbackFailureInd.
    Range: 1..16. Default: 1."
             ::= {atmNteConfVcEntry 13}

atmConfVcOamDirection OBJECT-TYPE
	SYNTAX  INTEGER {
		notApplicable  (1),
		downStream     (2),
		upStream       (3)
        }
	MAX-ACCESS read-write
	STATUS current
	DESCRIPTION
	"The direction of OAM cell insertion.
	 downStream(2) - The OAM cell will be inserted in downStream.
	 upStream(3)   - The OAM cell will be inserted in upStream."
	::= {atmNteConfVcEntry 14}

atmConfVcName OBJECT-TYPE
	SYNTAX  DisplayString
    MAX-ACCESS read-write
	STATUS current
	DESCRIPTION
	"VC Name."
    ::= {atmNteConfVcEntry 15}

atmConfVcConnected OBJECT-TYPE
	SYNTAX  INTEGER {
		notConnected	(1),
		mng				(2),
		bridgePort		(3),
		ds0Bundle		(4),
		atm				(5),
		pw				(6),
		routerInterface	(7),
		qos             (8),
		other           (9),
		logicalMac		(10),
        atmAal2         (11)
		        }
	MAX-ACCESS read-write		-- Originally read-only
	STATUS current
	DESCRIPTION
	"This object indicates whether this VC is connected
	 and if connected, what is it connected to.
	 Originally, it was read-only."
	::= {atmNteConfVcEntry 16}

atmConfVcOamDescrIndex OBJECT-TYPE
	SYNTAX  Integer32
	MAX-ACCESS read-write
	STATUS current
	DESCRIPTION
	"This parameter indicates the VCL's OAM Descriptor index,
	 according to the OAM Descriptor Configuration Table."
	::= {atmNteConfVcEntry 17}

atmConfVcNoOfUsages OBJECT-TYPE
	SYNTAX		Unsigned32
	MAX-ACCESS	read-only
	STATUS		current
	DESCRIPTION
		"This object indicates the number of times this VCL is used."
	::= { atmNteConfVcEntry 18 }



END

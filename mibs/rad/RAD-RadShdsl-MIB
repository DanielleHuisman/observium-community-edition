RAD-RadShdsl-MIB DEFINITIONS ::= BEGIN


-- It is RAD's intent to encourage the widespread use of
-- this Specification in connection with the management of
-- RAD products. RAD grants vendors, end-users,
-- and other interested parties a non-exclusive license to
-- use this Specification in connection with the management
-- of RAD products.

-- This Specification is supplied "as is," and RAD makes
-- no warranty, either express or implied, as to the use,
-- operation, condition, or performance of the Specification.


IMPORTS

       hdsl2ShdslEndpointCurrEntry, hdsl2ShdslInvIndex, hdsl2ShdslEndpointSide, 
       hdsl2ShdslSpanConfProfileEntry, hdsl2ShdslEndpointCurrAtn, hdsl2ShdslEndpointCurrSnrMgn, 
       hdsl2ShdslEndpointCurr15MinLOSWS, hdsl2ShdslEndpointCurr15MinCRCanomalies, hdsl2ShdslEndpointThreshLoopAttenuation, 
       hdsl2ShdslEndpointThreshSNRMargin, hdsl2ShdslEndpointThreshLOSWS, hdsl2ShdslEndpointThreshCRCanomalies     FROM  HDSL2-SHDSL-LINE-MIB
       ifAlias, ifIndex     FROM  IF-MIB
       Integer32, TimeTicks, Unsigned32, 
       OBJECT-TYPE, MODULE-IDENTITY, NOTIFICATION-TYPE     FROM  SNMPv2-SMI
       diverseIfWanGen     FROM  RAD-SMI-MIB
       alarmEventLogSourceName, alarmEventLogAlarmOrEventId, alarmEventLogDescription, 
       alarmEventLogSeverity, alarmEventLogDateAndTime, alarmEventReason     FROM  RAD-GEN-MIB; 


	shdslIf MODULE-IDENTITY
		LAST-UPDATED "201502191808Z"  -- February 19, 2015
        ORGANIZATION "RAD Data Communications Ltd."
        CONTACT-INFO
        "System Department

         Email:  mibs@rad.com
         Postal: RAD Data Communications Ltd.
                 24 Raoul Wallenberg St.
                 Tel-Aviv 6971920
                 Israel

         Phone:  +972-3-645-5421
         Fax:    +972-3-760-7844"
         DESCRIPTION
            "SHDSL MIB."
	::= { diverseIfWanGen 12 }



radHdsl2ShdslEvents  OBJECT IDENTIFIER ::= {shdslIf 0}

-- Segment Endpoint Current Status/Performance Group


shdslEndpointCurrTable OBJECT-TYPE
      SYNTAX      SEQUENCE OF ShdslEndpointCurrEntry
      MAX-ACCESS  not-accessible
      STATUS      current
      DESCRIPTION
        "This table is an extension of hdsl2ShdslEndpointCurrTable of rfc4319
         It contains current status and performance information
         for segment endpoints in HDSL2/SHDSL Lines.  As with other
         tables in this MIB indexed by ifIndex, entries in this table
         MUST be maintained in a persistent manner."
      ::= { shdslIf 1 }

shdslEndpointCurrEntry OBJECT-TYPE
      SYNTAX      ShdslEndpointCurrEntry
      MAX-ACCESS  not-accessible
      STATUS      current
      DESCRIPTION
        "An entry in the shdslEndpointCurrTable.  Each entry
        contains status and performance information relating to a
        single segment endpoint.  It is indexed by the ifIndex of the
        HDSL2/SHDSL line, the UnitId of the associated unit, the side
        of the unit, and the wire-pair of the associated modem."
      AUGMENTS {hdsl2ShdslEndpointCurrEntry}
      ::= { shdslEndpointCurrTable 1 }

ShdslEndpointCurrEntry ::= SEQUENCE {
	   hdsl2ShdslEndpointCurrRcvGain			  Integer32, 
    hdsl2ShdslEndpointCurrTransPower     Integer32,
    hdsl2ShdslEndpointCurrPowerBO     Integer32,
    hdsl2ShdslEndpointCurrLineStatus     INTEGER,
    hdsl2ShdslEndpointCurrOpState        BITS,
    hdsl2ShdslEndpointAccumulatedTimeElapsed   TimeTicks,
    hdsl2ShdslEndpointCurrPsd        INTEGER,
    hdsl2ShdslEndpointValidIntervals     Unsigned32,
    hdsl2ShdslEndpointValidDaysIntervals    Unsigned32 
 }
	                                

 hdsl2ShdslEndpointCurrRcvGain OBJECT-TYPE
    SYNTAX      Integer32
    UNITS       "dB"
    MAX-ACCESS  read-only
    STATUS      current
    DESCRIPTION
        "The current receive gain in hundredth of dB."
     ::= { shdslEndpointCurrEntry 1 }


hdsl2ShdslEndpointCurrTransPower  OBJECT-TYPE
    SYNTAX      Integer32
    MAX-ACCESS  read-only
    STATUS      current
    DESCRIPTION
        "The current transmit power in tenth of dBm."
    ::= { shdslEndpointCurrEntry 2 }

hdsl2ShdslEndpointCurrPowerBO   OBJECT-TYPE	-- added by RAD
    SYNTAX      Integer32
    UNITS       "dB"
    MAX-ACCESS  read-only
    STATUS      current
    DESCRIPTION
        "The current transceiver actual power backoff from 0dB to 31dB."
     ::= { shdslEndpointCurrEntry 3 }


hdsl2ShdslEndpointCurrLineStatus OBJECT-TYPE	-- added by RAD
    SYNTAX      INTEGER
	           {
	            noSync (2),
                sync  (3)
				}
    MAX-ACCESS  read-only
    STATUS      current
    DESCRIPTION
        "The current line synchronization status."
     ::= { shdslEndpointCurrEntry 4 }


hdsl2ShdslEndpointCurrOpState OBJECT-TYPE	-- added by RAD
    SYNTAX      BITS
	            {
                 idleMode(0),
                 dataMode(1),
                 bootUpload(2),
                 bootUploadDone(3),
                 startupHandshakeInProgress(4),
                 startupTrainingInProgress(5),
                 framerSyncInProgress(6),
                 localAnalogLoopbackInProgress(7),
                 remoteCoreLoopbackInProgress(8),
                 localDigitalLoopbackInProgress(9),
                 spectrumTestInProgress(10)
				 }
    MAX-ACCESS  read-only
    STATUS      current
    DESCRIPTION
        "The current operational state."
    ::= { shdslEndpointCurrEntry 5 }


hdsl2ShdslEndpointAccumulatedTimeElapsed   OBJECT-TYPE -- added by RAD
    SYNTAX       TimeTicks
    MAX-ACCESS   read-only
    STATUS       current
    DESCRIPTION
        "The time (in hundredths of a second) since the
         accumulated counters were last re-initialized:
         Accumulated counters are hdsl2ShdslEndpointES,
         hdsl2ShdslEndpointSES, hdsl2ShdslEndpointCRCanomalies
		 hdsl2ShdslEndpointLOSWS, and hdsl2ShdslEndpointUAS."
    ::= { shdslEndpointCurrEntry 6 }

hdsl2ShdslEndpointCurrPsd OBJECT-TYPE
   SYNTAX      INTEGER
               {
               asymmetric(2),
			   symmetric(3)
               }
   MAX-ACCESS  read-only
   STATUS      current
   DESCRIPTION
     "This object indicates use of symmetric/asymmetric PSD (Power
      Spectral Density) Mask for the associated SHDSL Line."
      ::= { shdslEndpointCurrEntry 7 }

hdsl2ShdslEndpointValidIntervals   OBJECT-TYPE
    SYNTAX       Unsigned32
    MAX-ACCESS   read-only
    STATUS       current
    DESCRIPTION
        "The number of previous 15 minutes intervals
         for which valid data was collected."
	::= { shdslEndpointCurrEntry 8 }

hdsl2ShdslEndpointValidDaysIntervals   OBJECT-TYPE
    SYNTAX       Unsigned32
    MAX-ACCESS   read-only
    STATUS       current
    DESCRIPTION
        "The number of previous Days intervals
         for which valid data was collected."
	::= { shdslEndpointCurrEntry 9 }



shdslEndpointMaintTable OBJECT-TYPE
      SYNTAX      SEQUENCE OF ShdslEndpointMaintEntry
      MAX-ACCESS  not-accessible
      STATUS      current
      DESCRIPTION
        "This table supports maintenance operations (eg. loopbacks)
         to be performed on HDSL2/SHDSL segment endpoints.  This table
         contains live data from equipment.  As such, it is NOT
         persistent."
      ::= { shdslIf 2 }

shdslEndpointMaintEntry OBJECT-TYPE
      SYNTAX      ShdslEndpointMaintEntry
      MAX-ACCESS  not-accessible
      STATUS      current
      DESCRIPTION
        "An entry in the hdsl2ShdslEndpointMaintTable.  Each entry
         corresponds to a single segment endpoint, and is indexed by the
         ifIndex of the HDSL2/SHDSL line, the UnitId of the associated
         unit and the side of the unit."
      INDEX { ifIndex, hdsl2ShdslInvIndex, hdsl2ShdslEndpointSide }
      ::= { shdslEndpointMaintTable 1 }

ShdslEndpointMaintEntry ::= SEQUENCE {
    shdslMaintPowerBackOff        INTEGER 
 }

shdslMaintPowerBackOff OBJECT-TYPE
      SYNTAX      INTEGER
                  {
                  default(1),
                  enhanced(2),
			      disabled (3)
                  }
      MAX-ACCESS  read-write
      STATUS      current
      DESCRIPTION
        "This object configures the receiver at the associated
         segment endpoint to operate in default or enhanced power
         backoff mode.
         powerbackoff may also be disabled"

      ::= { shdslEndpointMaintEntry 1 }


  -- Span Configuration Profile Group


shdslSpanConfProfileTable OBJECT-TYPE
      SYNTAX      SEQUENCE OF ShdslSpanConfProfileEntry
      MAX-ACCESS  not-accessible
      STATUS      current
      DESCRIPTION
        "This table supports definitions of span configuration
         profiles for SHDSL lines.  HDSL2 does not support these 
         configuration options.  This table MUST be maintained
         in a persistent manner."
      ::= { shdslIf 3 }

shdslSpanConfProfileEntry OBJECT-TYPE
      SYNTAX      ShdslSpanConfProfileEntry
      MAX-ACCESS  not-accessible
      STATUS      current
      DESCRIPTION
        "Each entry corresponds to a single span configuration
         profile.  Each profile contains a set of span configuration
         parameters.  The configuration parameters in a profile are
         applied to those lines referencing that profile (see the 
         hdsl2ShdslSpanConfProfile object).  Profiles may be 
         created/deleted using the row creation/deletion mechanism 
         via hdsl2ShdslSpanConfProfileRowStatus.  If an active
         entry is referenced in hdsl2ShdslSpanConfProfile, the 
         entry MUST remain active until all references are removed."
      AUGMENTS {hdsl2ShdslSpanConfProfileEntry}
      ::= { shdslSpanConfProfileTable 1 }

ShdslSpanConfProfileEntry ::=
      SEQUENCE
      {
	  hdsl2ShdslSpanConfEocCompatible			INTEGER, 
	  hdsl2ShdslSpanConfAsymmetricPSDRate		INTEGER,
	  hdsl2ShdslSpanConfWireInterfaceUsed		INTEGER,
	  hdsl2ShdslSpanConfHandshake				INTEGER
      }


hdsl2ShdslSpanConfEocCompatible	OBJECT-TYPE  -- Added by RAD
    SYNTAX      INTEGER
                {
                proprietary (2),
                standard    (3)
                }
    MAX-ACCESS  read-only
    STATUS      current
    DESCRIPTION
        "This object indicate if device  supports only 
          standard EOC messages or also proprietary messages."
    ::= { shdslSpanConfProfileEntry 1 }


hdsl2ShdslSpanConfAsymmetricPSDRate  OBJECT-TYPE
    SYNTAX      INTEGER
                {
                notApplicable   (1),
                asymmetricR1    (2),
				asymmetricR2    (3)    
                }
    MAX-ACCESS  read-write
    STATUS      current
    DESCRIPTION
        "This object indicates line rate when 
         rfc3276.hdsl2ShdslSpanConfPSD value is asymmetric(2).
		 Seleceted rate depends on transmission mode - 
		 specified in Annex A or B of G.991.2.
         For Annex A; 
           R1 selects the 776 or 784 kbit/s 
 		   R2 selects the 1544 or 1552 kbit/s  
		 For Annex B ;
           R1 selects the 2312 kbit/s 
           R2 selects the 2056 kbit/s "
    ::= { shdslSpanConfProfileEntry 2 }


hdsl2ShdslSpanConfWireInterfaceUsed	OBJECT-TYPE
    SYNTAX      INTEGER
                {
                notApplicable (1),
                twoWires      (2),
				fourWires     (3),
				autoDetection (4)    
                }
    MAX-ACCESS  read-write
    STATUS      current
    DESCRIPTION
	"This object enable user to configure SHDSL port with 4 wires
     to use 2 or  4 wires, or to auto detect far end number of wires"
    ::= { shdslSpanConfProfileEntry 3 }

hdsl2ShdslSpanConfHandshake	OBJECT-TYPE
    SYNTAX      INTEGER
                {
				automatic		(1),
				g994dot1rev2001	(2)		-- G994.1 02/2001
                }
    MAX-ACCESS  read-write
    STATUS      current
    DESCRIPTION
	"This object indicates the Handshake Procedure."
    ::= { shdslSpanConfProfileEntry 4 }


hdsl2ShdslIfConf OBJECT IDENTIFIER ::= { shdslIf 4 }

--Interface configuration with Configuration index

hdsl2ShdslIfConfTable OBJECT-TYPE
    SYNTAX      SEQUENCE OF Hdsl2ShdslIfConfEntry
    MAX-ACCESS  not-accessible
    STATUS      current
    DESCRIPTION
    "This table enables configuration of HDSL2/SHDSL interfaces
     per configuration index.
     Write operation for products supporting Active+Temp configurations,
     is possible only on the Temp configuration(255)."
    ::= { hdsl2ShdslIfConf 1 }

hdsl2ShdslIfConfEntry OBJECT-TYPE
    SYNTAX      Hdsl2ShdslIfConfEntry
    MAX-ACCESS  not-accessible
    STATUS      current
    DESCRIPTION
        "An entry in the hdsl2ShdslIfConfTable. "
    INDEX { hdsl2ShdslIfConfIdx, ifIndex, hdsl2ShdslSideIdx}
    ::= { hdsl2ShdslIfConfTable 1 }

Hdsl2ShdslIfConfEntry ::= SEQUENCE {
    hdsl2ShdslIfConfIdx             Integer32,
    hdsl2ShdslSideIdx               INTEGER,
    hdsl2ShdslMaxBw                 INTEGER,
    hdsl2ShdslPwrBackoff            INTEGER,
	hdsl2ShdslTxMode                INTEGER,
    hdsl2ShdslAttenuationThreshold  Integer32,
    hdsl2ShdslSnrMarginThreshold    Integer32,
	hdsl2ShdslTs0OverDsl            INTEGER,
    hdsl2ShdslMode                  INTEGER,
	hdsl2ShdslTsCompactionMode      INTEGER,
	hdsl2ShdslEocEnable             INTEGER,
	hdsl2ShdslFar1stIfNumOfTSs      Unsigned32,
	hdsl2ShdslFarEndDevice          INTEGER,
    hdsl2ShdslPwrBackoffDb          Integer32,
    hdsl2ShdslFarEndMuxTsa          OCTET STRING,
    hdsl2ShdslLineProbeEnable  INTEGER,
    hdsl2ShdslClockMode    INTEGER,
    hdsl2ShdslIfConfLinkDownReason  BITS 
 }

hdsl2ShdslIfConfIdx OBJECT-TYPE
    SYNTAX  Integer32 (1..255)
    MAX-ACCESS  read-only
    STATUS  current
    DESCRIPTION
    "This object indicates the Idx of the Config being accessed.
     Idx of 255 relates to the Temporary (Scratch) Config.
     Write operation for products supporting Active+Temp configurations,
     is allowed to Temporary configuration only. "
    ::= {hdsl2ShdslIfConfEntry 1}

hdsl2ShdslSideIdx OBJECT-TYPE
      SYNTAX  INTEGER {
	    nearEnd(2),
        farEnd (3),
		rptr1  (4),
		rptr2  (5),
		rptr3  (6),
		rptr4  (7),
		rptr5  (8),
		rptr6  (9),
		rptr7  (10),
		rptr8  (11)
        }
      MAX-ACCESS  read-only
      STATUS      current
      DESCRIPTION
      "This object indicates the Side of the managed object: Near-End
       or Far-End."
      ::= {hdsl2ShdslIfConfEntry 2}

hdsl2ShdslMaxBw     OBJECT-TYPE
      SYNTAX  INTEGER {
      notApplicable (1),
      r192          (2), 
      r256          (3), 
      r320          (4),
	  r384          (5),
	  r448          (6),
      r512          (7), 
      r576          (8),
	  r640          (9),
	  r704          (10),
      r768          (11), 
      r832          (12),
	  r896          (13),
	  r960          (14),
      r1024         (15), 
      r1088         (16),
	  r1152         (17),
	  r1216         (18),
	  r1280         (19),
	  r1344         (20),
	  r1408         (21),
	  r1472         (22),
	  r1536         (23),
	  r1600         (24),
	  r1664         (25),
	  r1728         (26),
	  r1792         (27),
	  r1856         (28),
	  r1920         (29),
	  r1984         (30),
	  r2048         (31)
        }
      MAX-ACCESS  read-write
      STATUS  current
      DESCRIPTION
      "Maximum BW (Bandwidth) of the Shdsl Line, in Kbps units.
       Respective Max No. of TSs =  Max. Rate/64
       This object can be Set only for a Central (xtuC) unit."
      ::= {hdsl2ShdslIfConfEntry 3}

hdsl2ShdslPwrBackoff OBJECT-TYPE
      SYNTAX  INTEGER {
	    notApplicable(1),
        enhanced(2),  -- enabled
 		disabled (3)  -- added by RAD
        }
      MAX-ACCESS  read-write
      STATUS      current
      DESCRIPTION
      "This object configures the receiver at the associated
       segment endpoint to enable/disable power	backoff mode.
       This object is similar to hdsl2ShdslMaintPowerBackOff, but per
       configuration. Therefore, the order of the enum values is the same. "
      ::= {hdsl2ShdslIfConfEntry 4}

hdsl2ShdslTxMode OBJECT-TYPE
    SYNTAX  INTEGER
      {
      notApplicable(1),
      annexA       (2),
      annexB       (3),
	  annexG       (4),
	  annexF       (5)
      }
    MAX-ACCESS  read-write
    STATUS      current
    DESCRIPTION
    "This object configures the Transmission Mode for the SHDSL Line.
     Normally, This object can be Set only for a Central (xtuC) unit."
    ::= { hdsl2ShdslIfConfEntry 5}

hdsl2ShdslAttenuationThreshold OBJECT-TYPE
    SYNTAX      Integer32
    UNITS       "dB"
    MAX-ACCESS  read-write
    STATUS      current
    DESCRIPTION
    "This object configures the Attentuation alarm threshold.
     0=Off
     Valid values: 0..127 ."
    ::= { hdsl2ShdslIfConfEntry 6}

hdsl2ShdslSnrMarginThreshold OBJECT-TYPE
    SYNTAX      Integer32
    UNITS       "dB"
    MAX-ACCESS  read-write
    STATUS      current
    DESCRIPTION
    "This object configures the SNR margin alarm threshold.
     0=Off
     Valid values: 0..15 ."
    ::= { hdsl2ShdslIfConfEntry 7}

hdsl2ShdslTs0OverDsl OBJECT-TYPE
    SYNTAX  INTEGER
      {
      notApplicable(1),
      looped       (2),
      transparent  (3)
      }
    MAX-ACCESS  read-write
    STATUS      current
    DESCRIPTION
    "This object configures the way TS0 will be treated over the SHDSL Line.
	 looped - looped inside
	 transparent - sent transparently over the DSL Line.
     This object can be Set only for a Central (xtuC) unit."
    ::= { hdsl2ShdslIfConfEntry 8}

hdsl2ShdslMode OBJECT-TYPE
    SYNTAX  INTEGER
      {
      notApplicable(1),
      stuC         (2),
      stuR         (3)
      }
    MAX-ACCESS  read-write
    STATUS      current
    DESCRIPTION
    "This object is relevant only for the Near-End device.
     stuC - Central
     stuR - Remote ."
    ::= { hdsl2ShdslIfConfEntry 9}

hdsl2ShdslTsCompactionMode OBJECT-TYPE
    SYNTAX  INTEGER
      {
      noCompaction (1),
      noMapping    (2),
      withMapping  (3),
	  lowTsMapping (4),
	  spareMapping (5)
      }
    MAX-ACCESS  read-write
    STATUS      current
    DESCRIPTION
    "This object configures how TSs will be compacted over the SHDSL Line.
	 In both mapping cases (2),(3), only the TSs connected on the E1 line will be 
	 transferred over the SHDSL Line
	 noCompaction - the whole E1 BW is reserved on the SHDSL Line, 
	             even if only part  of the TSs are actually connected.
	 noMapping - there is no mapping between the E1 TSs and the SHDSL frame TSs.
	             Therefore, E1 connected TSs are ordered in ascending order (e.g
				 E1 TSs 2, 16, 20 will occupy places 1, 2, 3 in SHDSL Line).
				 In this case, if user wants to add connection for 
				 a TS that is lower	than the existing ones on SHDSL, 
				 the TSs that are higher will have to  move. 
				 That causes breaks in service for the moved TSs. 
				 (e.g if E1 TS8 is added in the above case, 
				 TSs 16 and 20 will move, so that by the
				 end of this process, the E1 TSs 2, 8, 16, 20 will
				  be ordered in  SHDSL frame as 1, 2, 3, 4).
	 withMapping - there is a mapping between the E1 TSs and the SHDSL frame TSs.
	             Therefore, if some TSs were connected and then user wants to add
	             additional E1 TSs, there is no need to move the existing TSs of the 
	             SHDSL frame. The additional TSs will be added AFTER the existing ones, 
	             or in gaps created by E1 TSs removed by user. The main thing is that
				 the existing TSs will NOT be moved and so, their service will not be 
				 damaged by the addition or removal of E1 TS connections.
	 lowTsMapping - the first 2 TSs are used for Signaling (TS16) and Dedicated TS
	             if relevant. The payload starts afterwards, unmapped (according to 
	             E1 connected TSs order). This will ensure that Signaling and 
	             Dedicated TS will continue to function also when new TSs are 
	             connected.	User will still get service breaks when TSs are moved.
	 spareMapping - applicable only for MP-2100/2104 cards. It should be selected only 
	             when working vs. a MP-2100.2104. It resembles the noMapping option,
	             but it contains Spare TSs for unconnected TSs. These Spare TSs 
	             will prevent service breaks upon added connections, because these
	             will be selected from the Spare existing TSs."
    ::= { hdsl2ShdslIfConfEntry 10}

hdsl2ShdslEocEnable OBJECT-TYPE
    SYNTAX  INTEGER
      {
      notApplicable(1),
      no           (2),
      yes          (3)
      }
    MAX-ACCESS  read-write
    STATUS      current
    DESCRIPTION
    "This object configures whether EOC protocol is supported by the Far-End
     device working with this port."
    ::= { hdsl2ShdslIfConfEntry 11}

hdsl2ShdslFar1stIfNumOfTSs OBJECT-TYPE
    SYNTAX      Unsigned32
    MAX-ACCESS  read-write
    STATUS      current
    DESCRIPTION
    "This object configures the number of TSs of the SHDSL line
     that belong to the 1st Interface of the Far-End device, where
     1st means that these TSs are first on the SHDSL line.

	 It is applicable only for Near-End instance and only when Far-End
	 is an ASMi-52 SA unit having Agent and Mux configuration.
	 SHDSL TSs are arranged so that all TSs of a Far interface are together
	 at the beginning and afterwards all TSs of the other Far interface.
	 The assumption is that only 2 user interfaces exist in the Far End unit.  
	 Examples:
	 - When ASMi-52 has E1+ETH or E1+V.35 user interfaces, this object
	   represents the number of TSs assigned to the E1 interface.
	   They will be first on the SHDSL TSs.
	   Rest of the SHDSL TSs are for the other interface.
	 - When ASMi-52 has ETH+V.35 user interfaces, this object
	   represents the number of TSs assigned to the ETH interface.
	   They will be first on the SHDSL TSs.
	   Rest of the SHDSL TSs are for the V.35 interface.
	 Valid values: 0..32, 255.     
     255=NA "
    ::= { hdsl2ShdslIfConfEntry 12}

hdsl2ShdslFarEndDevice OBJECT-TYPE
    SYNTAX  INTEGER
      {
      other            (2),
	  mpComponent      (3),
	  asmi52SingleIf   (4),   
      asmi52E1AndData  (5),
	  asmi52E1AndEth   (6),
	  asmi52EthAndData (7),
	  fcdip            (8),
	  dxc              (9) 
      }
    MAX-ACCESS  read-write
    STATUS      current
    DESCRIPTION
    "This object indicates the Far-End device.
     It is used for 2 purposes:
    - in order to know if EOC is used (EOC is used only when the device
       is any of the ASMi52 options: (4)..(7))
     - in order to know how to work vs Far-End device, because Megaplex
       uses different SHDSL component than other devices. mpComponent(3)
	   means that Far-End device uses same component as Megaplex. All the
	   rest use a different component.
     other(2) - none of the other options.
     mpComponent(3) - for Megaplex or other future device having the same 
                   component as MP.
     asmi52SingleIf (4) - ASMi-52 with a Single user interface.                   
     asmi52E1AndData(5), asmi52E1AndEth(6), asmi52EthAndData (7),are 
     when Far-End unit is ASMi-52 V>=2.5 and the device has more than one 
     user interface. User should select the combination known to exist in 
     the Far-End unit.
	 Data - indicates an interface of V.35, X.21, RS-530, etc...
	 fcdip - includes both FCD-IP and FCD-IP/M
	 dxc   - includes DXC-30, DXC-30E, DXC-10A, DXC-8R and New. "
    ::= { hdsl2ShdslIfConfEntry 13}

hdsl2ShdslPwrBackoffDb OBJECT-TYPE
    SYNTAX      Integer32
    UNITS       "dB"
    MAX-ACCESS  read-write
    STATUS      current
    DESCRIPTION
    "This object configures the Power Backoff (in dB) of the
     receiver, at the associated segment endpoint.
     0=Off
     Valid values: 0..31 ."
    ::= { hdsl2ShdslIfConfEntry 14}

hdsl2ShdslFarEndMuxTsa OBJECT-TYPE
    SYNTAX  OCTET STRING
    MAX-ACCESS  read-write
    STATUS  current
    DESCRIPTION
    "This object represents Assignment of E1 TSs to Far-End MUX Interfaces.
	 It is relevant only when hdsl2ShdslSideIdx=nearEnd(2), when for the 
	 Near-End device, hdsl2ShdslMode=stuC(2)AND hdsl2ShdslFarEndDevice=(5),(6)or(7).
     Each Octet is divided in 2 nibbles. Each nibble represents a Near-End E1 TS 
     and indicates to which interface of the Far-End device this TS will be 
     assigned.
     The nibble values are as follows:
     0000  - no interface
     0001  - E1 interface
     0010  - ETH interface
     0011  - Data interface (V.35, X.21, RS-530, etc..)
     Rest  - not used
     Octet 1: TS1, TS2  (TS1 = Most nibble)
     Octet 2: TS3, TS4  (TS3 = Most nibble)
     Octet 3: TS5, TS6  (TS5 = Most nibble)
     ...
     Octet 12: TS23, TS24  (TS23 = Most nibble)
     ...
     Octet 16: TS31, TS32  (TS31 = Most nibble ; TS32 will be always empty )	 
     Only TSs that are connected for E1 port of Near-End can be assigned to
     a Far-End Interface."
    ::= { hdsl2ShdslIfConfEntry 15}    

hdsl2ShdslLineProbeEnable  OBJECT-TYPE
      SYNTAX      INTEGER
       {
       disable (1),
       enable  (2)
       }
      MAX-ACCESS  read-write
      STATUS      current
      DESCRIPTION
        "This object enables/disables support for Line Probe of
         the units in an SHDSL line.  When Line Probe is enabled, the
         system performs Line Probing to find the best possible
         rate.  If Line Probe is disabled, the rate adaptation phase
         is skipped to shorten set up time."
   ::= { hdsl2ShdslIfConfEntry 16 }

hdsl2ShdslClockMode  OBJECT-TYPE
      SYNTAX      INTEGER
       {
       plesiochronous1  (1),
       plesiochronousWithTimeReference2 (2),
	   synchronous3a    (3),
	   hybrid           (4)

       }
      MAX-ACCESS  read-write
      STATUS      current
      DESCRIPTION
        "This object enables configuration of the clock mode.
          (1) - 1 Plesiochronous (e.g. ASMi-52 / ASMi-54L)
          (2) - 2 Plesiochronous with timing reference (e.g. ASMi-54 / ASMi-54L)
          (3) - 3a - Synchronous
          (4) - 3b - Hybrid: downstream: synchronous; upstream: plesiochronous"
   ::= { hdsl2ShdslIfConfEntry 17 }

hdsl2ShdslIfConfLinkDownReason          OBJECT-TYPE
      SYNTAX       BITS
		{
		unknown         (0),
		es 	        	(1), -- Errored Seconds
		ses         	(2), -- Severely Errored Seconds
		crcAnomaly  	(3), -- Cyclic Redundancy Check anomaly
		losw            (4), -- Loss of Sync Word
		uas             (5), -- Unavailable Seconds
		snrMarginAlarm  (6)  -- Signal to Noise Ratio Margin Alarm
		}
MAX-ACCESS  read-only
      STATUS      current
      DESCRIPTION
       "
       "
   ::= { hdsl2ShdslIfConfEntry 19 }

-- SHSDL Notifications

--SHDSL EOC LOOPBACK TOWARDS NETWORK
radHdsl2ShdslLoopBackTrap NOTIFICATION-TYPE
   OBJECTS   { alarmSeverity,alarmState,ifAlias  }
   STATUS    current
   DESCRIPTION
   "This notification indicates that a remote loopback 
    has been activated on the Embedded Operations Channel (EOC) of the SHDSL
    link."
   ::= { radHdsl2ShdslEvents 1 }

-- RESERVED
--      ::= { radHdsl2ShdslEvents  6 }
--      ::= { radHdsl2ShdslEvents  7 }
--      ::= { radHdsl2ShdslEvents  8 }
--      ::= { radHdsl2ShdslEvents  9 }
--      ::= { radHdsl2ShdslEvents  10 }
--      ::= { radHdsl2ShdslEvents  11 }
--      ::= { radHdsl2ShdslEvents  12 }


--SHDSL LOSW

shdslLosw		NOTIFICATION-TYPE
	OBJECTS { alarmEventLogSourceName, alarmEventLogAlarmOrEventId, alarmEventLogDescription, 
     alarmEventLogSeverity, alarmEventLogDateAndTime, alarmEventReason, 
     ifAlias, hdsl2ShdslEndpointCurr15MinLOSWS, hdsl2ShdslEndpointThreshLOSWS } 
      STATUS  current
      DESCRIPTION
	  "This trap indicates Loss of sync word (LOSW)	 .
	  "
      ::= { radHdsl2ShdslEvents  13 }

-- RESERVED
--      ::= { radHdsl2ShdslEvents  14 }

-- 	 SHDSL EXCESSIVE CRC ERROR

shdslExcessiveCrcError		NOTIFICATION-TYPE
	OBJECTS { alarmEventLogSourceName, alarmEventLogAlarmOrEventId, alarmEventLogDescription, 
     alarmEventLogSeverity, alarmEventLogDateAndTime, alarmEventReason, 
     ifAlias, hdsl2ShdslEndpointCurr15MinCRCanomalies, hdsl2ShdslEndpointThreshCRCanomalies } 
      STATUS  current
      DESCRIPTION
	  "This trap indicates Excessive Crc Error.
	  "
      ::= { radHdsl2ShdslEvents  15 }


shdslLoopAttenuationOra     NOTIFICATION-TYPE
	OBJECTS { alarmEventLogSourceName, alarmEventLogAlarmOrEventId, alarmEventLogDescription, 
     alarmEventLogSeverity, alarmEventLogDateAndTime, alarmEventReason, 
     ifAlias, hdsl2ShdslEndpointCurrAtn, hdsl2ShdslEndpointThreshLoopAttenuation } 
      STATUS  current
      DESCRIPTION
      "This trap indicates that Loop attenuation has exceeded the threshold.
      "
      ::= { radHdsl2ShdslEvents 19 }

shdslSnrMarginOra        NOTIFICATION-TYPE
	OBJECTS { alarmEventLogSourceName, alarmEventLogAlarmOrEventId, alarmEventLogDescription, 
     alarmEventLogSeverity, alarmEventLogDateAndTime, alarmEventReason, 
     ifAlias, hdsl2ShdslEndpointCurrSnrMgn, hdsl2ShdslEndpointThreshSNRMargin } 
      STATUS  current
      DESCRIPTION
      "This trap indicates Signal-to-noise ratio (SNR) margin is below the threshold.
      "
      ::= { radHdsl2ShdslEvents 20 }

-- RESERVED
--      ::= { radHdsl2ShdslEvents  21 }






shdslLinkDown 	NOTIFICATION-TYPE
	OBJECTS { alarmEventLogSourceName, alarmEventLogAlarmOrEventId, alarmEventLogDescription, 
     alarmEventLogSeverity, alarmEventLogDateAndTime, alarmEventReason, 
     ifAlias, hdsl2ShdslIfConfLinkDownReason } 
      STATUS  current
      DESCRIPTION
      "This trap indicates that the Link is down.
      "
      ::= { radHdsl2ShdslEvents 23 }


END

RAD-SMI-MIB DEFINITIONS ::= BEGIN

IMPORTS
    MODULE-IDENTITY,
    OBJECT-IDENTITY,
    enterprises
        FROM SNMPv2-SMI;

rad MODULE-IDENTITY
        LAST-UPDATED "201502191808Z"  -- February 19, 2015
        ORGANIZATION "RAD Data Communications Ltd."
        CONTACT-INFO
        "System Department

         Email:  mibs@rad.com
         Postal: RAD Data Communications Ltd.
                 24 Raoul Wallenberg St.
                 Tel-Aviv 6971920
                 Israel

         Phone:  +972-3-645-5421
         Fax:    +972-3-760-7844"
         DESCRIPTION
            "SMI MIB."
    ::= { enterprises 164 }


radTokenRing OBJECT-IDENTITY
    STATUS          current
    DESCRIPTION
    "Token Ring tree."
    ::= { rad 1 }

radFddi      OBJECT-IDENTITY
    STATUS          current
    DESCRIPTION
    "FDDI Tree."
    ::= { rad 2 }

radWan       OBJECT-IDENTITY
    STATUS          current
    DESCRIPTION
    "RAD WAN."
    ::= { rad 3 }

wanGen          OBJECT IDENTIFIER ::= {radWan 1}
diverseIfWanGen OBJECT IDENTIFIER ::= {wanGen 6}

radBridges   OBJECT-IDENTITY
    STATUS          current
    DESCRIPTION
    "Bridges."
    ::= {rad 4 }

radConverters OBJECT-IDENTITY
    STATUS          current
    DESCRIPTION
    "Converters products' tree."
    ::= { rad 5 }

radGen       OBJECT-IDENTITY
    STATUS          current
    DESCRIPTION
    "General information."
    ::= { rad 6}


systems             OBJECT IDENTIFIER ::= { radGen 1}  --  list of RAD products
    radSysWan       OBJECT IDENTIFIER ::= { systems 3 }
    radSysPS        OBJECT IDENTIFIER ::=  { systems 8 }   -- RAD Packet Switch  (PS) products
    radSecurity     OBJECT IDENTIFIER ::= { systems 14 }  --RAD  AAA Security
agnt                OBJECT IDENTIFIER ::= { radGen 2}  -- agent general tree
    fileTransfer    OBJECT IDENTIFIER ::= { agnt 12 }
services            OBJECT IDENTIFIER ::= { radGen 3}  -- See services.txt
radTransport        OBJECT IDENTIFIER ::= { radGen 4} -- RAD transport tree
fmObjects           OBJECT IDENTIFIER ::= { radGen 5 }


radSysWanEvents OBJECT-IDENTITY
    STATUS  current
    DESCRIPTION
    "The events for RAD Wan products."
     ::= { radSysWan 0 }

radStkHub    OBJECT-IDENTITY
    STATUS          current
    DESCRIPTION
    "Stackable products."
    ::=  { rad 7 }

radPS        OBJECT-IDENTITY
    STATUS          current
    DESCRIPTION
    "Packet Switch."
    ::= { rad 8 }       -- Packet Switch

radEthRptr  OBJECT-IDENTITY
    STATUS          current
    DESCRIPTION
    "Ethernet Repeaters products."
    ::= { rad 9 }

radMpls      OBJECT-IDENTITY
    STATUS          current
    DESCRIPTION
    "MPLS."
    ::= { rad 10 }

radRouter    OBJECT-IDENTITY
    STATUS          current
    DESCRIPTION
    "Routers."
    ::= { rad 11 }

rtrBridge    OBJECT-IDENTITY
    STATUS          current
    DESCRIPTION
    "Bridges under routers."
    ::= { radRouter 7 }

radAtm       OBJECT-IDENTITY
    STATUS          current
    DESCRIPTION
    "ATM Products."
    ::= { rad 12 }

radSysAtm  OBJECT IDENTIFIER ::= { systems 12 } -- RAD ATM products

radSysAtmEvents OBJECT-IDENTITY
    STATUS  current
    DESCRIPTION
    "The events for RAD ATM products."
    ::= { radSysAtm 0 }

radPw        OBJECT-IDENTITY
    STATUS          current
    DESCRIPTION
    "Pseudo Wire."
    ::= { rad 14 }

radEMS   OBJECT-IDENTITY
    STATUS          current
    DESCRIPTION
    "RAD EMS."
    ::= { rad 15 }

radAaw   OBJECT-IDENTITY
    STATUS          current
    DESCRIPTION
    "Application Awareness."
    ::= { rad 16 }

radExperimental OBJECT-IDENTITY
    STATUS          current
    DESCRIPTION
    "Drafts that have no MIB tree yet."
    ::= { rad 20 }

radSpecificDevices OBJECT-IDENTITY
    STATUS          current
    DESCRIPTION
    "Specific Device families of RAD MIB."
    ::= { rad 40 }

radTextualConventions   OBJECT-IDENTITY
    STATUS          current
    DESCRIPTION
    "RAD Textual Conventions."
    ::= { rad 100 }




END

RAD-Webranger-MIB DEFINITIONS ::= BEGIN

-- It is RAD's intent to encourage the widespread use of
-- this Specification in connection with the management of
-- RAD products. RAD grants vendors, end-users,
-- and other interested parties a non-exclusive license to
-- use this Specification in connection with the management
-- of RAD products.

-- This Specification is supplied "as is," and RAD makes
-- no warranty, either express or implied, as to the use,
-- operation, condition, or performance of the Specification.


IMPORTS

       ifAlias, ifIndex     FROM  IF-MIB
       InetAddressType, InetAddress, InetAddressPrefixLength     FROM  INET-ADDRESS-MIB
       SnmpAdminString     FROM  SNMP-FRAMEWORK-MIB
       Integer32, IpAddress, Unsigned32, 
       OBJECT-TYPE, MODULE-IDENTITY, NOTIFICATION-TYPE     FROM  SNMPv2-SMI
       DisplayString, RowStatus, DateAndTime, 
       MacAddress     FROM  SNMPv2-TC
       rtrBridge     FROM  RAD-SMI-MIB
       alarmEventLogSourceName, alarmEventLogAlarmOrEventId, alarmEventLogDescription, 
       alarmEventLogSeverity, alarmEventLogDateAndTime, alarmEventReason     FROM  RAD-GEN-MIB
       serviceIdName     FROM  MEF-R-MIB
       rtrIfCfgName     FROM  RAD-SubRtr-MIB; 


    webranger MODULE-IDENTITY
        LAST-UPDATED "201608231437Z"  -- August 23, 2016
        ORGANIZATION "RAD Data Communications Ltd."
        CONTACT-INFO
        "System Department

         Email:  mibs@rad.com
         Postal: RAD Data Communications Ltd.
                 24 Raoul Wallenberg St.
                 Tel-Aviv 6971920
                 Israel

         Phone:  +972-3-645-5421
         Fax:    +972-3-760-7844"
         DESCRIPTION
            "RAD MIB."
    ::= { rtrBridge 2 }

wrSysConfig OBJECT IDENTIFIER ::= { webranger 1 }

wrBraodcastCtrlCmd OBJECT-TYPE
       SYNTAX INTEGER {
	   block    (1),
	   forward  (2),
       blockLinkPropagation (3)
	   }
       MAX-ACCESS read-write
       STATUS current
       DESCRIPTION
       "This parameter is a command to the webranger CPU. It
        enables blocking or forwarding broadcast frames, which
        may cause a trigger to a connection.
	  	block (1)   - blocks the broadcast frames.
	  	forward (2) - forwards the broadcast frames.
        blockLinkPropagation (3) - blocks the broadcast frames to the links, tx
        to the LAN. "
       ::= { wrSysConfig 1 }

wrFrSelfLearningMode OBJECT-TYPE
       SYNTAX INTEGER {
	   off (1),
	   on  (2)
	   }
       MAX-ACCESS read-write
       STATUS current
       DESCRIPTION
       "This parameter enables the webranger to learn the DLCi's
        configuration and maintanance protocol. 
        off - will get the configuration by setting it.
        on - disables configuration and start self learning."
       ::= { wrSysConfig 2 }

wrGratuitousArp OBJECT-TYPE
       SYNTAX INTEGER {
	   disable (2),
	   enable  (3)
	   }
       MAX-ACCESS read-write
       STATUS current
       DESCRIPTION
       "This parameter enables/disables the Gratuitous ARP feature.
        When enabled, the feature means: when receiving ARP with sender's 
        Source IP Address that already exists in the ARP table - replace 
        MAC Address with sender's Source MAC Address."
       ::= { wrSysConfig 3 }


wrIpRouterInfo OBJECT IDENTIFIER ::= { webranger 2 }

wrConfigIpDhcp OBJECT IDENTIFIER ::= { wrIpRouterInfo 1 }

wrConfigIpDNS OBJECT IDENTIFIER ::= { wrIpRouterInfo 2 }


wrDhcpAction OBJECT-TYPE
       SYNTAX INTEGER { 
       disable (2),
       enable (3)	   
       }
       MAX-ACCESS read-write
       STATUS current
       DESCRIPTION
       "Activating (disable/enable) DHCP server operation.
        Since DHCP Server and DHCP Relay cannot reside in same device,
        DHCP Relay may be enabled (per interface), only if server action is disabled.

        For some devices, this object is used in order to enable/disable 
        the DHCP Client. See device SDS."
       ::= { wrConfigIpDhcp 1 }

wrDhcpTable OBJECT-TYPE
       SYNTAX SEQUENCE OF WrDhcpEntry
       MAX-ACCESS not-accessible
       STATUS current
       DESCRIPTION
          "A list of DHCP entries. The number of entries is up to
           DHCP current entries, according to the WEBRANger model."
       ::= { wrConfigIpDhcp 2 }

    wrDhcpEntry OBJECT-TYPE
       SYNTAX  WrDhcpEntry
       MAX-ACCESS  not-accessible
       STATUS  current
       DESCRIPTION
           "DHCP parameters per entry of the DHCP table."
       INDEX   { wrDhcpLowIpAddress }
       ::= { wrDhcpTable 1 }

    WrDhcpEntry ::=
       SEQUENCE {
              wrDhcpLowIpAddress
                 IpAddress,
              wrDhcpHighIpAddress
                 IpAddress,
			  wrDhcpIpMaskAddress
                 IpAddress,
			  wrDhcpDefaultGateway
                 IpAddress,
			  wrDhcpPrimaryDNS
                 IpAddress,
			  wrDhcpSecondaryDNS
                 IpAddress,
			  wrDhcpInterface
                 INTEGER,
			  wrDhcpRowStatus
                 RowStatus,
			  wrDhcpIpAddressLeaseTime 
			     Integer32,
			  wrDhcpPoolName 
				  SnmpAdminString,
			  wrDhcpTftpServerIp
                 IpAddress,
			  wrDhcpConfigFileName  
    		     SnmpAdminString
				   }
   
wrDhcpLowIpAddress OBJECT-TYPE
       SYNTAX IpAddress
       MAX-ACCESS read-only
       STATUS current
       DESCRIPTION
           "DHCP Low Ip Address."
       ::= { wrDhcpEntry 1 }


wrDhcpHighIpAddress OBJECT-TYPE
       SYNTAX IpAddress
       MAX-ACCESS read-create
       STATUS current
       DESCRIPTION
           "DHCP High Ip Address."
       ::= { wrDhcpEntry 2 }

wrDhcpIpMaskAddress OBJECT-TYPE
       SYNTAX IpAddress
       MAX-ACCESS read-create
       STATUS current
       DESCRIPTION
           "IP mask Address."
       ::= { wrDhcpEntry 3 }

wrDhcpDefaultGateway OBJECT-TYPE
       SYNTAX IpAddress
       MAX-ACCESS read-create
       STATUS current
       DESCRIPTION
           "Default Gateway's IP Address."
       ::= { wrDhcpEntry 4 }

wrDhcpPrimaryDNS OBJECT-TYPE
       SYNTAX IpAddress
       MAX-ACCESS read-create
       STATUS current
       DESCRIPTION
           "Primary DNS."
       ::= { wrDhcpEntry 5 }

wrDhcpSecondaryDNS OBJECT-TYPE
	   SYNTAX IpAddress  
	   MAX-ACCESS read-create
       STATUS current
       DESCRIPTION
           "Secondary DNS."
       ::= { wrDhcpEntry 6 }

wrDhcpInterface OBJECT-TYPE
       SYNTAX INTEGER { 
       all (1),
       lan1 (2),
       lan2(3),
       anyLan(4),
       wan (5)
       }
       MAX-ACCESS read-create
       STATUS current
       DESCRIPTION
           "The IP addresse allocation is done according to the 
           interface type from which the DHCP request arrives."
       ::= { wrDhcpEntry 7 }


wrDhcpRowStatus OBJECT-TYPE
      SYNTAX  RowStatus
      MAX-ACCESS  read-create
      STATUS  current
      DESCRIPTION
          "This attribute allows to create/delete a row in this table.
          For creating a row, the NMS should set 
          wrDhcpRowStatus.id = active(1).
          For destroying a row, the NMS should set:
          wrDhcpStatus.id = destroy(6).
          Only rows with status active(1) are relevant.
		  The only possible supported RowStatus vaules are
		  active  (1) and destroy (6)."
      ::= { wrDhcpEntry 8 }

wrDhcpIpAddressLeaseTime OBJECT-TYPE 
       SYNTAX   Integer32
       MAX-ACCESS  read-create
       STATUS  current
       DESCRIPTION
          "Allocated IP Address lease time in seconds. 
           A zero  value specifies no time limitation."
     ::= { wrDhcpEntry 9 }
       
wrDhcpPoolName OBJECT-TYPE 
       SYNTAX SnmpAdminString (SIZE (1..10)) 
       MAX-ACCESS  read-create
       STATUS  current
       DESCRIPTION
          "DHCP pool name  - string with max length of 10  characters"
        ::= { wrDhcpEntry 10 }

wrDhcpTftpServerIp OBJECT-TYPE 
       SYNTAX IpAddress  
       MAX-ACCESS  read-create
       STATUS  current
       DESCRIPTION
          "DHCP pool -  TFTP-server IP Address."
        ::= { wrDhcpEntry 11 }

wrDhcpConfigFileName OBJECT-TYPE 
       SYNTAX SnmpAdminString (SIZE (1..50)) 
       MAX-ACCESS  read-create
       STATUS  current
       DESCRIPTION
          "TFTP-name of the configuration File Name for DHCP pool."
        ::= { wrDhcpEntry 12 }


 
-- DHCP (Dynamic Host Configuration Protocol) Pool Allocation Table

dhcpPoolAllocTable OBJECT-TYPE
    SYNTAX SEQUENCE OF DhcpPoolAllocEntry
    MAX-ACCESS not-accessible
    STATUS current
    DESCRIPTION
       "A list of  DHCP  Pool Allocation entries.
       	Each entry (row) consist of a single IP Address belonging to DHCP pool 
       	whose lowest IP address is dhcpPoolAllocLowIpAddress. 
       	This IP address may be offered for leasing, or may already be 
       	leased (in use) by Host it's MacAddress is dhcpPoolAllocMacAddress.
       	Time left for leasing period is indicated by dhcpPoolAllocTimeLeft.
        All posible statuses of IP address are indicated and controlled
        by dhcpPoolAllocFlags"
    ::= { wrConfigIpDhcp 3 }

dhcpPoolAllocEntry OBJECT-TYPE
    SYNTAX  DhcpPoolAllocEntry
    MAX-ACCESS  not-accessible
    STATUS  current
    DESCRIPTION
        "DHCP Pool Allocation parameters per entry of the DHCP Pool Allocation table."
    INDEX   {dhcpPoolAllocLowIpAddress, dhcpPoolAllocLeasingIpAddress}
    ::= { dhcpPoolAllocTable 1 }

DhcpPoolAllocEntry ::=
     SEQUENCE {
            dhcpPoolAllocLowIpAddress
               IpAddress,
            dhcpPoolAllocLeasingIpAddress
               IpAddress,
            dhcpPoolAllocMacAddress
               MacAddress,
            dhcpPoolAllocTimeLeft
              Integer32, 
            dhcpPoolAllocFlags
               INTEGER,
            dhcpPoolAllocFreeCmd
               INTEGER
               }
 

dhcpPoolAllocLowIpAddress  OBJECT-TYPE
     SYNTAX IpAddress
     MAX-ACCESS read-only
     STATUS current
     DESCRIPTION
         "Lowest IP address of this pool, value eqaul to wrDhcpLowIpAddress for 
          the pool."
     ::= { dhcpPoolAllocEntry 1 }

dhcpPoolAllocLeasingIpAddress OBJECT-TYPE
     SYNTAX IpAddress
     MAX-ACCESS read-only
     STATUS current
     DESCRIPTION
         "Single IP Address belonging to dhcp pool whose Lowest Ip Address is 
         dhcpPoolAllocLowIpAddress. This IP address may be offered for leasing
         or may be leased by Host its MacAddress is dhcpPoolAllocMacAddress.
         All posible statuses of IP address are indicated by dhcpPoolAllocFlags     "
     ::= { dhcpPoolAllocEntry 2 }

dhcpPoolAllocMacAddress OBJECT-TYPE
     SYNTAX  MacAddress
     MAX-ACCESS read-only
     STATUS current
	 DESCRIPTION
     "MAC Address to which the IP address has been leased "
     ::= { dhcpPoolAllocEntry 3 }
 
dhcpPoolAllocTimeLeft OBJECT-TYPE
     SYNTAX Integer32 
     MAX-ACCESS read-only
     STATUS current
	 DESCRIPTION
         "IP address leasing time left in seconds "
     ::= { dhcpPoolAllocEntry 4 }



dhcpPoolAllocFlags OBJECT-TYPE
     SYNTAX INTEGER
            {
             notApplicable (1),
			 free (2),
			 inUse (3),
			 offered (4),
			 forbidden (5)         
             } 
     MAX-ACCESS read-only
     STATUS current
     DESCRIPTION
     "These flags indicates status of each IP address. 
     User may change value to free, via dhcpPoolAllocFreeCmd "
     ::= { dhcpPoolAllocEntry 5 }


dhcpPoolAllocFreeCmd OBJECT-TYPE
     SYNTAX INTEGER
            {
             off (2),
			 on (3)
             } 
     MAX-ACCESS read-write
     STATUS current
     DESCRIPTION
	"Setting this attribute to On (3), will enforce the agent to 
	 Free this entry.
	 The Agent will change the value of this MIB object to off(2) 
	 automatically, after performing the command.
	 Setting this object to off(2), will do nothing"
     ::= { dhcpPoolAllocEntry 6 }



--DHCP Relay Table

dhcpRelayTable OBJECT-TYPE
    SYNTAX SEQUENCE OF DhcpRelayEntry
    MAX-ACCESS not-accessible
    STATUS current
    DESCRIPTION
       "A list of DHCP relay entries."
    ::= { wrConfigIpDhcp 4 }

dhcpRelayEntry OBJECT-TYPE
    SYNTAX  DhcpRelayEntry
    MAX-ACCESS  not-accessible
    STATUS  current
    DESCRIPTION
        "DHCP Relay parameters per entry of the DHCP relay table."
    INDEX   { ifIndex }
    ::= { dhcpRelayTable 1 }

DhcpRelayEntry ::=
     SEQUENCE {
			dhcpRelayAction
			   INTEGER, 
            dhcpRelayServerIpAddress
               IpAddress,
            dhcpRelayMaxHop
               Integer32
               }
   
dhcpRelayAction OBJECT-TYPE
     SYNTAX INTEGER
            {
			disable (2),
            enable (3) 
			 } 
     MAX-ACCESS read-write
     STATUS current
     DESCRIPTION
	"Setting this attribute to enable (3), will  
	 enable DHCP Relay action for this interface 
	 (Only if DHCP Server is disabled for device - wrDhcpAction=disable).
	 dhcpRelayServerIpAddressaddress should not be 0.0.0.0 when enable is set"
     ::= { dhcpRelayEntry 1 }


dhcpRelayServerIpAddress OBJECT-TYPE
     SYNTAX IpAddress
     MAX-ACCESS read-write
     STATUS current
     DESCRIPTION
         "DHCP Server IP Address."
     ::= { dhcpRelayEntry 2 }


dhcpRelayMaxHop OBJECT-TYPE
     SYNTAX Integer32 
     MAX-ACCESS read-write
     STATUS current
          DESCRIPTION
         "Maximum number of hops till DHCP Server.
          upper limit is 16 hops"
     DEFVAL {16}
     ::= { dhcpRelayEntry 3 }


wrDhcpPort OBJECT-TYPE
	  SYNTAX  INTEGER
	  { 
       notApplicable	(1),
       all          	(2),
       outOfBand 		(3),
       lan1 			(4),
	   lan2				(5)
       }

      MAX-ACCESS  read-write
      STATUS  current
      DESCRIPTION
          "This parameter defines the port that DHCP flow will be actiavted."
      ::= { wrConfigIpDhcp 5}


--DHCP Client Table

dhcpClientTable OBJECT-TYPE
    SYNTAX SEQUENCE OF DhcpClientEntry
    MAX-ACCESS not-accessible
    STATUS current
    DESCRIPTION
    "A list of DHCP client entries."
    ::= { wrConfigIpDhcp 6 }

dhcpClientEntry OBJECT-TYPE
    SYNTAX  DhcpClientEntry
    MAX-ACCESS  not-accessible
    STATUS  current
    DESCRIPTION
    "DHCP Client parameters per entry of the DHCP Client table."
    INDEX   { ifIndex }
    ::= { dhcpClientTable 1 }

DhcpClientEntry ::=
     SEQUENCE {
	 dhcpClientAction
	 INTEGER, 
     dhcpClientServerIpAddress
     IpAddress,
     dhcpClientLeaseExpirationTime
     Integer32,
	 dhcpClientStatus
	 DisplayString
     }

dhcpClientAction OBJECT-TYPE
     SYNTAX INTEGER
      {
	 	disable (2),
        enable (3) 
	  } 
     MAX-ACCESS read-write
     STATUS current
     DESCRIPTION
	"This parameter default value is enable(3).
	 Setting this attribute to disable (2), will  
	 disable DHCP Client action for this interface.
	 This parameter can be changed to disable (2) only 
	 (it cannot be changed from disable to enable)."
     ::= { dhcpClientEntry 1 }

dhcpClientServerIpAddress OBJECT-TYPE
     SYNTAX IpAddress
     MAX-ACCESS read-write
     STATUS current
     DESCRIPTION
     "DHCP Server IP Address."
     ::= { dhcpClientEntry 2 }

dhcpClientLeaseExpirationTime OBJECT-TYPE
     SYNTAX Integer32 
     MAX-ACCESS read-only
     STATUS current
     DESCRIPTION
     "This parameter holds the time (in minutes) left until lease expiration."
     ::= { dhcpClientEntry 3 }

dhcpClientStatus OBJECT-TYPE
     SYNTAX DisplayString
     MAX-ACCESS read-only
     STATUS current
     DESCRIPTION
     "This parametr displays the DHCP status."
     ::= { dhcpClientEntry 4 }


--DHCP Interface Client Table

dhcpIfClientTable OBJECT-TYPE
    SYNTAX SEQUENCE OF DhcpIfClientEntry
    MAX-ACCESS not-accessible
    STATUS current
    DESCRIPTION
    "DHCP client entries for each Interface."
    ::= { wrConfigIpDhcp 7 }

dhcpIfClientEntry OBJECT-TYPE
    SYNTAX  DhcpIfClientEntry
    MAX-ACCESS  not-accessible
    STATUS  current
    DESCRIPTION
    "DHCP Clients per entry of the DHCP Interface Client table."
    INDEX   { ifIndex, dhcpIfClientIpAddress }
    ::= { dhcpIfClientTable 1 }

DhcpIfClientEntry ::=
     SEQUENCE {
	 dhcpIfClientIpAddress
     IpAddress,
     dhcpIfClientRowStatus
	 RowStatus
     }

dhcpIfClientIpAddress OBJECT-TYPE
     SYNTAX IpAddress
     MAX-ACCESS read-only
     STATUS current
     DESCRIPTION
     "DHCP Client IP Address."
     ::= { dhcpIfClientEntry 2 }

dhcpIfClientRowStatus OBJECT-TYPE
     SYNTAX      RowStatus
     MAX-ACCESS  read-create
     STATUS      current
     DESCRIPTION
     "The row status used for creating, modifying, and deleting instances 
     of the columnar objects in the dhcpIfClientTable.
     
     For Vmux Devices, it will be possible only to Delete instances.
     The addition of Clients will be done automatically by the Server according
     to Network messages that are sent by the Clients; not via SNMP.

     In order to Delete a Client, this MIB object should be set to: destroy (6)."
     ::= { dhcpIfClientEntry 3 }

dhcpServerAction OBJECT-TYPE
    SYNTAX  INTEGER {
       noOp(2),       
       deleteAllClients(3)
     }
    MAX-ACCESS  read-write
    STATUS  current
    DESCRIPTION
	"This variable enables the operator to perform one of the
	specified actions on the Server.
      deleteAllClients (3) is an option that is used for a device functioning as a server.
      It will remove all the clients from all the interfaces of the device.
      When the operation is complete, the agent will return a noOp (2) value."
   ::= { wrConfigIpDhcp 8 }

-- *****************************************************************************
-- DHCP Client Table (New)
-- *****************************************************************************

dhcpClientNTable OBJECT-TYPE
    SYNTAX      SEQUENCE OF DhcpClientNEntry
    MAX-ACCESS  not-accessible
    STATUS      current
    DESCRIPTION
        "The DHCP Client table (New).
        The number of entries is determined by the number of
        router interface in the system."
    ::= { wrConfigIpDhcp 9 }

dhcpClientNEntry OBJECT-TYPE
    SYNTAX      DhcpClientNEntry
    MAX-ACCESS  not-accessible
    STATUS      current
    DESCRIPTION
        "An entry of this table."
    INDEX       { dhcpClientIndex }
    ::= { dhcpClientNTable 1 }

DhcpClientNEntry ::= SEQUENCE {
    dhcpClientIndex                     Unsigned32,
    dhcpClientAdminStatus               INTEGER,
    dhcpClientOperStatus                INTEGER,
    dhcpClientAddressType               InetAddressType,
    dhcpClientAddress                   InetAddress,
    dhcpClientAddressMask               InetAddress,
		dhcpClientNextHop					InetAddress,
    dhcpClientServerAddress             InetAddress,
		dhcpClientActualLeaseTime	  		Unsigned32,
		dhcpClientRemainLeaseTime			Unsigned32,
		dhcpClientCommand					INTEGER,
    dhcpClientOpAdminStatus             BITS,
		dhcpClientOpVendorClassId			SnmpAdminString,  -- option 60
    dhcpClientOpIpAddrLeaseTime         Unsigned32,
    dhcpClientOpServerId                IpAddress,
    dhcpClientOpClientIdType            INTEGER,
    dhcpClientOpClientId                SnmpAdminString,
    		dhcpClientOpHostName				SnmpAdminString,  -- option 12
		dhcpClientOpDns						OCTET STRING,     -- option 6
		dhcpClientOpTftpServerName			SnmpAdminString,  -- option 66
		dhcpClientOpBootFileName			SnmpAdminString   -- option 67
    dhcpClientLeaseObtainTime           DateAndTime,
    dhcpClientLeaseExpireTime           DateAndTime 
 }

dhcpClientIndex OBJECT-TYPE
    SYNTAX      Unsigned32
    MAX-ACCESS  not-accessible
    STATUS      current
    DESCRIPTION
        "The DHCP Client index.
         Index can be ifIndex and/or index of a router interface or host."
    ::= { dhcpClientNEntry 1 }

dhcpClientAdminStatus OBJECT-TYPE
    SYNTAX      INTEGER
    {
        down        (2),
        up          (3)
    }
    MAX-ACCESS  read-write
    STATUS      current
    DESCRIPTION
        "The Administrative Status of DHCP client."
    ::= { dhcpClientNEntry 2 }

dhcpClientOperStatus OBJECT-TYPE
    SYNTAX      INTEGER
    {
        notHoldingLease         (2),
        holdingLease            (3),
        waitingForLease         (4),
        failedToObtainLease     (5),
        initializing            (6),
        noLeaseAddressInUse     (7)
    }
    MAX-ACCESS  read-only
    STATUS      current
    DESCRIPTION
        "The Operational Status of DHCP client.
        notHoldingLease:        No IP address is allocated in the router interface
        holdingLease:           The router interface has a valid lease
        waitingForLease:        Acquiring a lease
        failedToObtainLease:    Failed to obtain lease
        initializing:           Initialization of DHCP client
        noLeaseAddressInUse:    Cannot use the lease because the received address
                                is used by another device
        "
    ::= { dhcpClientNEntry 3 }

dhcpClientAddressType OBJECT-TYPE
    SYNTAX      InetAddressType
    MAX-ACCESS  read-write
    STATUS      current
    DESCRIPTION
        "The Address Type of all InetAddress objects."
    ::= { dhcpClientNEntry 4 }

dhcpClientAddress OBJECT-TYPE
    SYNTAX      InetAddress
    MAX-ACCESS  read-only
    STATUS      current
    DESCRIPTION
        "The DHCP Client Address, which is assigned by the DHCP server."
    ::= { dhcpClientNEntry 5 }

dhcpClientAddressMask OBJECT-TYPE
    SYNTAX      InetAddress
    MAX-ACCESS  read-only
    STATUS      current
    DESCRIPTION
        "The DHCP Client Address Mask, which is assigned by the DHCP server."
    ::= { dhcpClientNEntry 6 }

dhcpClientNextHop OBJECT-TYPE
	SYNTAX		InetAddress
	MAX-ACCESS	read-only
	STATUS		current
	DESCRIPTION
		"The Next Hop (Default Gateway) of the DHCP client."
	::= { dhcpClientNEntry 7 }

dhcpClientServerAddress OBJECT-TYPE
    SYNTAX      InetAddress
    MAX-ACCESS  read-write
    STATUS      current
    DESCRIPTION
        "The DHCP Server Address.
         Although object is defined as read-write, current support is read-only."
    ::= { dhcpClientNEntry 8 }

dhcpClientActualLeaseTime OBJECT-TYPE
	SYNTAX		Unsigned32
	MAX-ACCESS	read-only
	STATUS		current
	DESCRIPTION
		"The Actual Lease Time (for Address received from the server),
		 measured in seconds.
		 Value=FFFFFFFF represents an infinite actual lease time."
	::= { dhcpClientNEntry 9 }

dhcpClientRemainLeaseTime OBJECT-TYPE
	SYNTAX		Unsigned32
	MAX-ACCESS	read-only
	STATUS		current
	DESCRIPTION
		"The Remaining Lease Time (for Address received from the server),
		 measured in seconds.
		 Value=FFFFFFFF represents an infinite remaining lease time."
	::= { dhcpClientNEntry 10 }

dhcpClientCommand OBJECT-TYPE
	SYNTAX		INTEGER
	{
		off			(2),
		renew		(3),	-- renew current lease
		release		(4)		-- release current lease
	} 
	MAX-ACCESS	read-write
	STATUS		current
	DESCRIPTION
		"The possible commands of DHCP client to DHCP server.
		 Upon performing a command, value should be automatically returned to off(2)."
	::= { dhcpClientNEntry 11 }

dhcpClientOpAdminStatus OBJECT-TYPE
    SYNTAX      BITS
    {
        vendorClassId       (0),  -- Vendor Class Identifier    (option 60)
        ipAddrLeaseTime     (1),  -- IP Address Lease Time      (option 51)
        serverId            (2),  -- Server Identifier          (option 54)
        clientId            (3),  -- Client Identifier          (option 61)
        hostName            (4),  -- Host Name                  (option 12)
		dns					(5),  -- Domain Name Server (DNS) 	(option 6)  
		tftpServerName		(6),  -- TFTP Server Name		 	(option 66) 
		bootFileName		(7)   -- Boot File Name			 	(option 67) 
    }
    MAX-ACCESS  read-write
    STATUS      current
    DESCRIPTION
        "The Administrative Status of the different options.
         Bit=1 means that respective option is enabled/activated."
    REFERENCE
        "RFC-2132."
    ::= { dhcpClientNEntry 12 }

dhcpClientOpVendorClassId OBJECT-TYPE
	SYNTAX		SnmpAdminString
	MAX-ACCESS	read-write
	STATUS		current
	DESCRIPTION
		"The Vendor Class Identifier.
		 Identifier should include at least 1 character."
	REFERENCE
		"RFC-2132, Option 60, Identifier."
	::= { dhcpClientNEntry 13 }

dhcpClientOpIpAddrLeaseTime OBJECT-TYPE
    SYNTAX      Unsigned32
    MAX-ACCESS  read-write
    STATUS      current
    DESCRIPTION
        "The IP Address Lease Time, measured in seconds."
    REFERENCE
        "RFC-2132, Option 51, Time."
    ::= { dhcpClientNEntry 14 }

dhcpClientOpServerId OBJECT-TYPE
    SYNTAX      IpAddress
    MAX-ACCESS  read-write
    STATUS      current
    DESCRIPTION
        "The Server Identifier (reported IP Address)."
    REFERENCE
        "RFC-2132, Option 54, IPv4 Address."
    ::= { dhcpClientNEntry 15 }

dhcpClientOpClientIdType OBJECT-TYPE
    SYNTAX      INTEGER {
        userId (0),
        ethernet (1)
        }
    MAX-ACCESS  read-write
    STATUS      current
    DESCRIPTION
         "Client Identifier type (the ID itself is set in dhcpClientOpClientId).
          0 - user-configured identifier.
          1 - Device MAC.
          255 - RAD ID default identifier"
    REFERENCE
        "RFC-2132, Option 61, Type."
    ::= { dhcpClientNEntry 16 }

dhcpClientOpClientId OBJECT-TYPE
    SYNTAX      SnmpAdminString
    MAX-ACCESS  read-write
    STATUS      current
    DESCRIPTION
        "The Client Identifier.
         Identifier should include at least 1 character.
         When dhcpClientOpClientIdType=1 it means that current object
         is irrelevant and shall be equal to null."
    REFERENCE
        "RFC-2132, Option 61, Identifier."
    ::= { dhcpClientNEntry 17 }

dhcpClientOpHostName OBJECT-TYPE
	SYNTAX		SnmpAdminString
	MAX-ACCESS	read-write
	STATUS		current
	DESCRIPTION
		"The Host Name.
		 Name should include at least 1 character."
	REFERENCE
		"RFC-2132, Option 12, Host."
	::= { dhcpClientNEntry 18 }

dhcpClientOpDns OBJECT-TYPE
	SYNTAX		OCTET STRING
	MAX-ACCESS	read-only
	STATUS		current
	DESCRIPTION
		"The Domain Name Server (DNS),
		 which is a list of servers available to the client.
		 This object should include at least 4 octets
		 and must always be a multiple of 4 octets."
	REFERENCE
		"RFC-2132, Option 6, List of Addresses."
	::= { dhcpClientNEntry 19 }

dhcpClientOpTftpServerName OBJECT-TYPE
	SYNTAX		SnmpAdminString
	MAX-ACCESS	read-only
	STATUS		current
	DESCRIPTION
		"The TFTP Server Name.
		 Name should include at least 1 character."
	REFERENCE
		"RFC-2132, Option 66, Server."
	::= { dhcpClientNEntry 20 }

dhcpClientOpBootFileName OBJECT-TYPE
	SYNTAX		SnmpAdminString
	MAX-ACCESS	read-only
	STATUS		current
	DESCRIPTION
		"The Boot File Name.
		 Name should include at least 1 character."
	REFERENCE
		"RFC-2132, Option 67, Name."
	::= { dhcpClientNEntry 21 }

dhcpClientLeaseObtainTime OBJECT-TYPE
    SYNTAX      DateAndTime
    MAX-ACCESS  read-only
    STATUS      current
    DESCRIPTION
        "The Lease Obtainment Time (composed of date and time). "
    ::= { dhcpClientNEntry 22 }

dhcpClientLeaseExpireTime OBJECT-TYPE
    SYNTAX      DateAndTime
    MAX-ACCESS  read-only
    STATUS      current
    DESCRIPTION
        "The Lease Expiration Time (composed of date and time)."
    ::= { dhcpClientNEntry 23 }


-- *****************************************************************************
-- DHCP Option List Table
-- *****************************************************************************

dhcpReceivedOptionTable      OBJECT-TYPE
    SYNTAX      SEQUENCE OF DhcpReceivedOptionEntry
    MAX-ACCESS  not-accessible
    STATUS      current
    DESCRIPTION
        "The table holds an DHCP option data that arrived from an DHCP
         server.The DHCP request is defined in dhcpClientNTable."
    ::= { wrConfigIpDhcp 10 }

dhcpReceivedOptionEntry OBJECT-TYPE
    SYNTAX      DhcpReceivedOptionEntry
    MAX-ACCESS  not-accessible
    STATUS      current
    DESCRIPTION
        "An entry of this table represents the DHCP options received from
        the DHCP server."
    INDEX       { dhcpReceivedOptionClientIndex ,dhcpReceivedOptionNumber  }
    ::= { dhcpReceivedOptionTable 1 }

DhcpReceivedOptionEntry ::= SEQUENCE {
    dhcpReceivedOptionClientIndex      Unsigned32,
    dhcpReceivedOptionNumber           Unsigned32,
    dhcpReceivedOptionInput           OCTET STRING 
 }

dhcpReceivedOptionClientIndex     OBJECT-TYPE
    SYNTAX      Unsigned32 (1..65535)
    MAX-ACCESS  not-accessible
    STATUS      current
    DESCRIPTION
        "This object represents the unique identifier of the router interface.
         The value shall be equal to dhcpClientIndex and rtrIfCfgIndex."
    ::= { dhcpReceivedOptionEntry 1 }

dhcpReceivedOptionNumber    OBJECT-TYPE
    SYNTAX      Unsigned32 (1..255)
    MAX-ACCESS  not-accessible
    STATUS      current
    DESCRIPTION
        "An index value that uniquely identifies the received DHCP option number."
    ::= { dhcpReceivedOptionEntry 2 }

dhcpReceivedOptionInput OBJECT-TYPE
    SYNTAX      OCTET STRING (SIZE(1..255))
    MAX-ACCESS  read-only
    STATUS      current
    DESCRIPTION
        "The DHCP information that was received from the DHCP server."
    ::= { dhcpReceivedOptionEntry 3 }

-- *****************************************************************************
-- DHCPv6 Client Table
-- *****************************************************************************

dhcpv6ClientTable OBJECT-TYPE
    SYNTAX      SEQUENCE OF Dhcpv6ClientEntry
    MAX-ACCESS  not-accessible
    STATUS      current
    DESCRIPTION
        "The DHCPv6 Client table.
        The number of entries is determined by the number of
        router interface in the system."
    ::= { wrConfigIpDhcp 12 }

dhcpv6ClientEntry OBJECT-TYPE
    SYNTAX      Dhcpv6ClientEntry
    MAX-ACCESS  not-accessible
    STATUS      current
    DESCRIPTION
        "DHCPv6 client entry."
    INDEX { dhcpv6ClientIndex,
            dhcpv6ClientIndex2 }
    ::= { dhcpv6ClientTable 1 }

Dhcpv6ClientEntry ::= SEQUENCE {
    dhcpv6ClientIndex               Unsigned32,
    dhcpv6ClientIndex2              Unsigned32,
    dhcpv6ClientAddressType         InetAddressType,
    dhcpv6ClientAddress             InetAddress,
    dhcpv6ClientPrefixLength        InetAddressPrefixLength,
    dhcpv6ClientServerDuid          OCTET STRING 
 }

dhcpv6ClientIndex OBJECT-TYPE
    SYNTAX      Unsigned32
    MAX-ACCESS  not-accessible
    STATUS      current
    DESCRIPTION
        "The DHCPv6 Client index.
         Index can be ifIndex and/or index of a router interface or host."
    ::= { dhcpv6ClientEntry 1 }

dhcpv6ClientIndex2 OBJECT-TYPE
    SYNTAX      Unsigned32
    MAX-ACCESS  not-accessible
    STATUS      current
    DESCRIPTION
        "DHCPv6 Client second index for case where getting multiple
         parameters of the same type."
    ::= { dhcpv6ClientEntry 2 }

dhcpv6ClientAddressType OBJECT-TYPE
    SYNTAX      InetAddressType
    MAX-ACCESS  read-only
    STATUS      current
    DESCRIPTION
        "The Address Type of all InetAddress objects."
    ::= { dhcpv6ClientEntry 3 }

dhcpv6ClientAddress OBJECT-TYPE
    SYNTAX      InetAddress
    MAX-ACCESS  read-only
    STATUS      current
    DESCRIPTION
        "The DHCPv6 Client Address, which is assigned by the DHCPv6 server."
    ::= { dhcpv6ClientEntry 4 }

dhcpv6ClientPrefixLength OBJECT-TYPE
    SYNTAX      InetAddressPrefixLength
    MAX-ACCESS  read-only
    STATUS      current
    DESCRIPTION
        "The DHCPv6 Client Address prefix length, which is assigned by the
         DHCPv6 server."
    ::= { dhcpv6ClientEntry 5 }

dhcpv6ClientServerDuid OBJECT-TYPE
    SYNTAX      OCTET STRING (SIZE(1..128))
    MAX-ACCESS  read-only
    STATUS      current
    DESCRIPTION
        "The DHCPv6 Server DUID."
    ::= { dhcpv6ClientEntry 6 }

-- *****************************************************************************
-- DHCPv6 Option List Table
-- *****************************************************************************

dhcpv6ReceivedOptionTable      OBJECT-TYPE
    SYNTAX      SEQUENCE OF Dhcpv6ReceivedOptionEntry
    MAX-ACCESS  not-accessible
    STATUS      current
    DESCRIPTION
        "The table holds DHCPv6 option data that arrived from a DHCPv6
         server.The DHCPv6 request is defined in dhcpv6ClientTable."
    ::= { wrConfigIpDhcp 13 }

dhcpv6ReceivedOptionEntry OBJECT-TYPE
    SYNTAX      Dhcpv6ReceivedOptionEntry
    MAX-ACCESS  not-accessible
    STATUS      current
    DESCRIPTION
        "An entry of this table represents the DHCPv6 options received from
        the DHCPv6 server."
    INDEX { dhcpv6ClientIndex,
            dhcpv6ClientIndex2,
            dhcpv6ClientOptionIndex,
            dhcpv6ReceivedOptionNumber,
            dhcpv6ReceivedSubOptionNumber }
    ::= { dhcpv6ReceivedOptionTable 1 }

Dhcpv6ReceivedOptionEntry ::= SEQUENCE {
    dhcpv6ClientOptionIndex         Unsigned32,
    dhcpv6ReceivedOptionNumber      Unsigned32,
    dhcpv6ReceivedSubOptionNumber   Unsigned32,
    dhcpv6ReceivedOptionInput       OCTET STRING 
 }

dhcpv6ClientOptionIndex OBJECT-TYPE
    SYNTAX      Unsigned32
    MAX-ACCESS  not-accessible
    STATUS      current
    DESCRIPTION
        "DHCPv6 Client option index for case where getting multiple
         options or sub-options of the same type."
    ::= { dhcpv6ReceivedOptionEntry 1 }

dhcpv6ReceivedOptionNumber    OBJECT-TYPE
    SYNTAX      Unsigned32
    MAX-ACCESS  not-accessible
    STATUS      current
    DESCRIPTION
        "An index value that uniquely identifies the received DHCPv6 option number."
    ::= { dhcpv6ReceivedOptionEntry 2 }

dhcpv6ReceivedSubOptionNumber    OBJECT-TYPE
    SYNTAX      Unsigned32
    MAX-ACCESS  not-accessible
    STATUS      current
    DESCRIPTION
        "An index value that uniquely identifies the received DHCPv6 sub-option number."
    ::= { dhcpv6ReceivedOptionEntry 3 }

dhcpv6ReceivedOptionInput OBJECT-TYPE
    SYNTAX      OCTET STRING (SIZE(1..255))
    MAX-ACCESS  read-only
    STATUS      current
    DESCRIPTION
        "The DHCPv6 information that was received from the DHCPv6 server."
    ::= { dhcpv6ReceivedOptionEntry 4 }
    
wrDNSRelayAction OBJECT-TYPE
       SYNTAX INTEGER { 
       notApplicable (1),
       disable       (2),
       enable        (3) 
       }
       MAX-ACCESS read-write
       STATUS current
       DESCRIPTION
       "When Enabled, device will act as a DNS Relay:
        whenever the device receives a DNS request from its host,
        it will forward it to the DNS server 
        as if the request was initiated by the  device itself.
        The reply from the DNS server is forwarded by the
        device to the host as if the device 
        was	answering the request."
       ::= { wrConfigIpDNS  1 }

wrConfigIpxRouterInfo OBJECT IDENTIFIER ::= { webranger 3 }

wrAutoLearnLanIpxNets OBJECT-TYPE
       SYNTAX INTEGER { 
       disable (2),
       enable (3)
       }
       MAX-ACCESS read-write
       STATUS current
       DESCRIPTION
           "Activating (disable/enable) the auto-learn operation."
       ::= { wrConfigIpxRouterInfo 1 }

wrLanIpxNetTable OBJECT-TYPE
       SYNTAX SEQUENCE OF WrLanIpxNetEntry
       MAX-ACCESS not-accessible
       STATUS current
       DESCRIPTION
           "Lan IPX nets Table."
       ::= { wrConfigIpxRouterInfo 2 }

wrLanIpxNetEntry OBJECT-TYPE
SYNTAX WrLanIpxNetEntry
MAX-ACCESS not-accessible
       STATUS current
       DESCRIPTION
          "IPX Nets per frame type & LAN port. The table entries 
           will be created by the agent"
INDEX   { wrLanifIndex, wrLanIpxFrameType }
       ::= { wrLanIpxNetTable 1 }

WrLanIpxNetEntry ::=
       SEQUENCE {
         wrLanifIndex
               Integer32,
         wrLanIpxFrameType
               INTEGER,
         wrIpxNetAddress
	           IpAddress
          }

wrLanifIndex OBJECT-TYPE 
          SYNTAX Integer32
          MAX-ACCESS  read-only
          STATUS  current
          DESCRIPTION
             "LAN port ifIndex."
          ::= { wrLanIpxNetEntry 1 }

wrLanIpxFrameType OBJECT-TYPE 
          SYNTAX  INTEGER{ 
          t8023 (1),
          ethernet (2),
          t8022(3),
          snap (4)
          }
          MAX-ACCESS  read-only
          STATUS  current
          DESCRIPTION
             "Frame Type"
          ::= { wrLanIpxNetEntry 2 }

wrIpxNetAddress OBJECT-TYPE 
          SYNTAX IpAddress
          MAX-ACCESS  read-write
          STATUS  current
          DESCRIPTION
             "Net address per Frame Type & LAN port."
          ::= { wrLanIpxNetEntry 3 }

wrDialInIpxNet OBJECT-TYPE
       SYNTAX IpAddress
       MAX-ACCESS read-write
       STATUS current
       DESCRIPTION
           "Net address through a link."
       ::= { wrConfigIpxRouterInfo 3 }

-- The RIP/SAP Interface Configuration Table.

    ripSapIfConfTable OBJECT-TYPE
        SYNTAX   SEQUENCE OF RipSapIfConfEntry
        MAX-ACCESS   not-accessible
        STATUS   current
        DESCRIPTION
           "A list of Interfaces which require separate
           configuration in RIP/SAP."
       ::= { wrConfigIpxRouterInfo 4 }

   ripSapIfConfEntry OBJECT-TYPE
       SYNTAX   RipSapIfConfEntry
       MAX-ACCESS   not-accessible
       STATUS   current
       DESCRIPTION
          "A Single Routing Domain in a single Subnet."
      INDEX { ripSapIfConfIfIndex }
      ::= { ripSapIfConfTable 1 }

    RipSapIfConfEntry ::=
        SEQUENCE {
            ripSapIfConfIfIndex
                Integer32,
            ripSapIfConfMode
                INTEGER,
            ripSapIfConfStatus
                RowStatus
    }

    ripSapIfConfIfIndex OBJECT-TYPE
        SYNTAX   Integer32
        MAX-ACCESS   read-only
        STATUS   current
        DESCRIPTION
           "The interface ifIndex."
       ::= { ripSapIfConfEntry 1 }

    ripSapIfConfMode OBJECT-TYPE
        SYNTAX   INTEGER {
		off(1),
		on (2)
		}
        MAX-ACCESS   read-create
        STATUS   current
        DESCRIPTION
           "The ifIndex RIP/SAP mode."
       ::= { ripSapIfConfEntry 2 }

    ripSapIfConfStatus OBJECT-TYPE
       SYNTAX RowStatus
       MAX-ACCESS read-create
       STATUS current
       DESCRIPTION
           "This attribute allows to create/delete a row in this table.
            For creating a row, the NMS should set 
            ripSapIfConfStatus.id1 = active(1).
            For destroying a row, the NMS should set:
            ripSapIfConfStatus.id1 = destroy(6).
            Only rows with status active(1) are relevant.
		    The only possible supported RowStatus vaules are
		    active  (1) and destroy (6)."
       ::= { ripSapIfConfEntry 3 }

wrInterface OBJECT IDENTIFIER ::= { webranger 4 }

wrIpAddressTable OBJECT-TYPE
       SYNTAX SEQUENCE OF WrIpAddressEntry
       MAX-ACCESS not-accessible
       STATUS current
       DESCRIPTION
           "Link IP addresses Table."
       ::= { wrInterface 1 }

wrIpAddressEntry OBJECT-TYPE
       SYNTAX WrIpAddressEntry
       MAX-ACCESS not-accessible
       STATUS current
       DESCRIPTION
          "Ip Address per Link"
       INDEX   { wrIpIfIndex }
       ::= { wrIpAddressTable 1 }

WrIpAddressEntry ::=
       SEQUENCE {
           wrIpIfIndex
		      Integer32,
           wrIpAddress
              IpAddress,
           wrIpMask
              IpAddress,
		   wrIpRowStatus
		      RowStatus
}

wrIpIfIndex OBJECT-TYPE
       SYNTAX Integer32
       MAX-ACCESS read-only
       STATUS current
       DESCRIPTION
           "Port interface index."
       ::= { wrIpAddressEntry 1 }

wrIpAddress OBJECT-TYPE
       SYNTAX IpAddress
       MAX-ACCESS read-create
       STATUS current
       DESCRIPTION
           "Link IP Address."
       ::= { wrIpAddressEntry 2 }

wrIpMask OBJECT-TYPE
       SYNTAX IpAddress
       MAX-ACCESS read-create
       STATUS current
       DESCRIPTION
           "Link IP mask Address."
       ::= { wrIpAddressEntry 3 }

wrIpRowStatus OBJECT-TYPE
       SYNTAX RowStatus
       MAX-ACCESS read-create
       STATUS current
       DESCRIPTION
           "This attribute allows to create/delete a row in this table.
            For creating a row, the NMS should set 
            wrIpRowStatus.id1 = active(1).
            For destroying a row, the NMS should set:
            wrIpRowStatus.id1 = destroy(6).
            Only rows with status active(1) are relevant.
		    The only possible supported RowStatus vaules are
		    active  (1) and destroy (6)." 
       ::= { wrIpAddressEntry 4 }

wrSpoofingTable OBJECT-TYPE
       SYNTAX SEQUENCE OF WrSpoofingEntry
       MAX-ACCESS not-accessible
       STATUS current
       DESCRIPTION
           "Spoofing Table."
       ::= { wrInterface 2 }

wrSpoofingEntry OBJECT-TYPE
       SYNTAX WrSpoofingEntry
       MAX-ACCESS not-accessible
       STATUS current
       DESCRIPTION
          "Spoofing per Link"
       INDEX   { wrSpoofingIfIndex }
       ::= { wrSpoofingTable 1 }

WrSpoofingEntry ::=
       SEQUENCE {
           wrSpoofingIfIndex
		      Integer32,
           wrSpoofingAction
		      Integer32,
           wrSpoofingAgingStation
              Integer32,
		   wrSpoofingRowStatus
		      RowStatus
}

wrSpoofingIfIndex OBJECT-TYPE
       SYNTAX Integer32
       MAX-ACCESS read-only
       STATUS current
       DESCRIPTION
           "Port interface index."
       ::= { wrSpoofingEntry 1 }


wrSpoofingAction  OBJECT-TYPE
       SYNTAX Integer32 
       MAX-ACCESS read-create
       STATUS current
       DESCRIPTION
	       "Spoofing action is applied by bit code:
            enable        :  bit 0 set (disable: bit 0 is 0)
            keepAlive     :  bit 1
               ...        :  bit 2
            and so on.
            For the above example, to set spoofing to keepAlive action,
            the object's value will be 3 = [ 2**0 + 2**1 ] 
            Only the Remote WEBRANger will accept this object !
                  -------                                  "
       ::= { wrSpoofingEntry 2 }

wrSpoofingAgingStation  OBJECT-TYPE
       SYNTAX Integer32 
       MAX-ACCESS read-create
       STATUS current
       DESCRIPTION
         " Aging time of stations list, in min. The agent 'translates'
           the time entered in minutes, to 10 min. resolution, as
		   follows: 
		   1..10  min - 10 min
		   11..20 min - 20 min
		   and so on...
		   0 is not a valid value.
           Only the Remote WEBRANger will accept this object !
                    ----------------                          "
       ::= { wrSpoofingEntry 3 }

wrSpoofingRowStatus OBJECT-TYPE
       SYNTAX RowStatus
       MAX-ACCESS read-create
       STATUS current
       DESCRIPTION
           "This attribute allows to create/delete a row in this table.
            For creating a row, the NMS should set 
            wrSpoofingRowStatus.id1 = active(1).
            For destroying a row, the NMS should set:
            wrSpoofingRowStatus.id1 = destroy(6).
            Only rows with status active(1) are relevant.
		    The only possible supported RowStatus vaules are
		    active  (1) and destroy (6)."
       ::= { wrSpoofingEntry 4 }


wrLanIfTable OBJECT-TYPE
       SYNTAX SEQUENCE OF WrLanIfEntry
       MAX-ACCESS not-accessible
       STATUS current
       DESCRIPTION
           "Link IP addresses Table."
       ::= { wrInterface 3 }

wrLanIfEntry OBJECT-TYPE
       SYNTAX WrLanIfEntry
       MAX-ACCESS not-accessible
       STATUS current
       DESCRIPTION
          "Ip Address per Link"
       INDEX   { wrLanIfIndex }
       ::= { wrLanIfTable 1 }

WrLanIfEntry ::=
       SEQUENCE {
           wrLanIfIndex
		      Integer32,
           wrLanBridgeRouterMode
              INTEGER,
		   wrLanIfState
		      INTEGER,
		   wrLanIfRdnTimeout
		      Integer32
       }

wrLanIfIndex OBJECT-TYPE
       SYNTAX Integer32
       MAX-ACCESS read-only
       STATUS current
       DESCRIPTION
           "Port interface index."
       ::= { wrLanIfEntry 1 }

wrLanBridgeRouterMode OBJECT-TYPE
     SYNTAX INTEGER {
              unknown         (1),
              bridge          (2),
              ipRouter        (3),
              ipxRouter       (4),
              ipAndIpxRouter  (5),
              bRouter         (6),
			  ipBrouter       (7),
			  ipxBrouter      (8),
			  ipAndIpxBrouter (9),
			  bridgeAndStp    (10)
              }
     MAX-ACCESS read-write
     STATUS current
     DESCRIPTION
         "This parameter indicates whether the link is Bridge 
          or Router	and specifies the Router's type."
     ::= { wrLanIfEntry 2 }

wrLanIfState OBJECT-TYPE
       SYNTAX INTEGER {      
              disable(2),
              enable (3),
			  redundancy(4)
	      }
       MAX-ACCESS read-write
       STATUS current
       DESCRIPTION
	   "The LAN is  disabled or enabled.
	    For LAN 2 it can be also 'redundancy'."
       ::= { wrLanIfEntry 3 }

wrLanIfRdnTimeout OBJECT-TYPE
       SYNTAX Integer32       
       MAX-ACCESS read-write
       STATUS current
       DESCRIPTION
	   "LAN Redundancy Timeout in seconds.
	    Applicable when wrLanIfState=redundancy."
       ::= { wrLanIfEntry 4 }

wrSyncCnfgTable OBJECT-TYPE
       SYNTAX SEQUENCE OF WrSyncCnfgEntry
       MAX-ACCESS not-accessible
       STATUS current
       DESCRIPTION
           "Configuration table for Async interface."
       ::= { wrInterface 4 }

wrSyncCnfgEntry OBJECT-TYPE
       SYNTAX WrSyncCnfgEntry
       MAX-ACCESS not-accessible
       STATUS current
       DESCRIPTION
          "Configuration table"
       INDEX   { wrSyncIfIndex }
       ::= { wrSyncCnfgTable 1 }

WrSyncCnfgEntry ::=
       SEQUENCE {
           wrSyncIfIndex
		      Integer32,
           wrSyncClkMode
              INTEGER,
           wrSyncClkRate
              INTEGER
       }

wrSyncIfIndex OBJECT-TYPE
       SYNTAX Integer32
       MAX-ACCESS read-only
       STATUS current
       DESCRIPTION
           "Sync interface index."
       ::= { wrSyncCnfgEntry 1 }

wrSyncClkMode OBJECT-TYPE
     SYNTAX INTEGER {
              notApplicable   (1),
              manual          (2),
              program         (3)
              }
     MAX-ACCESS read-write
     STATUS current
     DESCRIPTION
         "Clock Mode."
     ::= { wrSyncCnfgEntry 2 }

wrSyncClkRate OBJECT-TYPE
     SYNTAX INTEGER {

              notApplicable   (1),
              r16             (2),
              r32             (3),
              r48             (4),
              r64             (5),
              r96             (6),
              r128            (7),
			  r256            (8),
			  r768            (9)
              }
     MAX-ACCESS read-write
     STATUS current
     DESCRIPTION
         "Clock Rate in. Rate can be changed if Clock Mode is Program only."
     ::= { wrSyncCnfgEntry 3 }



wrFrCnfgTable OBJECT-TYPE
       SYNTAX SEQUENCE OF WrFrCnfgEntry
       MAX-ACCESS not-accessible
       STATUS current
       DESCRIPTION
           "Configuration table for Fr parameters that do not exist in RFC2115."
       ::= { wrInterface 5 }

wrFrCnfgEntry OBJECT-TYPE
       SYNTAX WrFrCnfgEntry
       MAX-ACCESS not-accessible
       STATUS current
       DESCRIPTION
           "Configuration entry for Fr parameters that do not exist in RFC2115."
       INDEX   { ifIndex }
       ::= { wrFrCnfgTable 1 }

WrFrCnfgEntry ::=
       SEQUENCE {
           wrFrDlciLearningMode
		      INTEGER,
		   wrFrCllmMessages
              INTEGER
       }

wrFrDlciLearningMode OBJECT-TYPE
       SYNTAX INTEGER {
	   off (2),
	   on  (3)
	   }
       MAX-ACCESS read-write
       STATUS current
       DESCRIPTION
           "This parameter enables the webranger to learn the DLCi's
            configuration and maintanance protocol for the current interface. 
            off - the WR will read the user's configuration for this interface.
            on -  the WR will begin self learning of the current interface's maintanance
                  protocol and DLCIs."
       ::= { wrFrCnfgEntry 1 }

wrFrCllmMessages OBJECT-TYPE
       SYNTAX INTEGER {
	   disable (2),
	   enable  (3)
	   }
       MAX-ACCESS read-write
       STATUS current
       DESCRIPTION
           "This parameter enables/disables the Webranger to Tx/Rx CLLM
            (Consolidated Link Layer Management) messages via DLCI 1023.
            The CLLM messages are link layer control messages. They can be used for example
		    in cases of congestion. The CLLM message contains a code for cause of congestion
		    and list of all DLCIs that should act to reduce data transmission."
       ::= { wrFrCnfgEntry 2 }
    
END

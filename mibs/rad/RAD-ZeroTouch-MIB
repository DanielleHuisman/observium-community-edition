RAD-ZeroTouch-MIB DEFINITIONS ::= BEGIN


-- It is RAD's intent to encourage the widespread use of
-- this Specification in connection with the management of
-- RAD products. RAD grants vendors, end-users,
-- and other interested parties a non-exclusive license to
-- use this Specification in connection with the management
-- of RAD products.

-- This Specification is supplied "as is," and RAD makes
-- no warranty, either express or implied, as to the use,
-- operation, condition, or performance of the Specification.


IMPORTS

       OBJECT-TYPE, MODULE-IDENTITY, NOTIFICATION-TYPE, 
       Integer32     FROM  SNMPv2-SMI
       systems     FROM  RAD-SMI-MIB
       systemsEvents     FROM  RAD-GEN-MIB
       MacAddress, DateAndTime     FROM  SNMPv2-TC
       SnmpAdminString     FROM  SNMP-FRAMEWORK-MIB; 

	radZeroTouch MODULE-IDENTITY
		LAST-UPDATED "201502191811Z"  -- February 19, 2015
        ORGANIZATION "RAD Data Communications Ltd."
        CONTACT-INFO
        "System Department

         Email:  mibs@rad.com
         Postal: RAD Data Communications Ltd.
                 24 Raoul Wallenberg St.
                 Tel-Aviv 6971920
                 Israel

         Phone:  +972-3-645-5421
         Fax:    +972-3-760-7844"
         DESCRIPTION
            "Zero Touch MIB."
	::= { systems 17 }


--  NE First Time Installation and usage of the Bootstrap trap notification
--
--  In RadGen.mib: radZeroTouch                        OBJECT IDENTIFIER ::= {systems 17}

bootstrapTable  OBJECT-TYPE
    SYNTAX      SEQUENCE OF BootstrapEntry
    MAX-ACCESS  not-accessible
    STATUS      current
    DESCRIPTION
        "This table contains bootstrap parameters.
         These will be attached to the bootstrap trap. "
    ::= { radZeroTouch 1 }

bootstrapEntry  OBJECT-TYPE
    SYNTAX      BootstrapEntry
    MAX-ACCESS  not-accessible
    STATUS      current
    DESCRIPTION
        "Entries for bootstrapTable.
        "
    INDEX   { bootstrapIfIndex }
    ::= { bootstrapTable 1 }

BootstrapEntry ::= SEQUENCE {
    bootstrapIfIndex   Integer32,
    bootstrapDeviceType   OBJECT IDENTIFIER,
    bootstrapDeviceMac   MacAddress,
    bootstrapDeviceSwVer  SnmpAdminString,
    bootstrapDeviceHwVer  SnmpAdminString,
    bootstrapState    INTEGER 
 }

bootstrapIfIndex		OBJECT-TYPE
    SYNTAX     	Integer32
    MAX-ACCESS  not-accessible
    STATUS      current
    DESCRIPTION
		"Index containing the Type, Slot and Port segment bits according to
		 RAD indexing convention. The agent will create a row in this table
		 for the local device. The value of the index will be:
		 Type segment = 1
		 Slot segment = 0
		 Port segment = 0

		 The agent will create a row in this table for each connected remote
		 device.
		 Type segment = 1
		 Slot segment = Local slot number to which the remote device is connected.
		 Port segment = Local port number to which the remote device is connected.
        "
    ::= { bootstrapEntry 1 }

bootstrapDeviceType	  OBJECT-TYPE
    SYNTAX     	OBJECT IDENTIFIER
    MAX-ACCESS  read-only
    STATUS      current
    DESCRIPTION
        "System Device Object ID.
	     See also RFC 3418 sysObjectID.
		 "
    ::= { bootstrapEntry 2 }

bootstrapDeviceMac OBJECT-TYPE
    SYNTAX   	MacAddress
    MAX-ACCESS  read-only
    STATUS      current
    DESCRIPTION
        "MAC Address of the management interface.
	    "
    ::= { bootstrapEntry 3 }

bootstrapDeviceSwVer OBJECT-TYPE
    SYNTAX   	SnmpAdminString
    MAX-ACCESS  read-only
    STATUS      current
    DESCRIPTION
        "Sofware version of the device.
         Same value as entPhysicalSoftwareRev when entPhysicalClass = chassis(3)
         (see RFC 4133).
	    "
    ::= { bootstrapEntry 4 }

bootstrapDeviceHwVer OBJECT-TYPE
    SYNTAX   	SnmpAdminString
    MAX-ACCESS  read-only
    STATUS      current
    DESCRIPTION
        "Hardware version of the device.
         Same value as entPhysicalHardwareRev when entPhysicalClass = chassis(3)
         (see RFC 4133).
	    "
    ::= { bootstrapEntry 5 }

bootstrapState OBJECT-TYPE
    SYNTAX      INTEGER	{
        on          (2),
        acknowledge (3)
        }
    MAX-ACCESS  read-write
    STATUS      current
    DESCRIPTION
       "State of bootstrap notification:
        (2) - device is waiting for acknowledge from the NMS/EMS.
        (3) - notification was acknowledged.
	   "
    ::= { bootstrapEntry 6 }

bootstrapActivationCmd OBJECT-TYPE
    SYNTAX      INTEGER	{
        off (2),
        on  (3)
        }
    MAX-ACCESS  read-write
    STATUS      current
    DESCRIPTION
       "Activation Command for enabling the bootstrap trap.
	    Default value is 'off (2)'.
       "
    ::= { radZeroTouch 2 }

--------------------------------------------
-- Trap Definitions
--------------------------------------------

systemBootstrap           NOTIFICATION-TYPE
	OBJECTS { bootstrapDeviceType, bootstrapDeviceMac, bootstrapDeviceSwVer, 
     bootstrapDeviceHwVer } 
    STATUS  current
    DESCRIPTION
        "This Notification will be sent by a device establishing first communication
         with the management system upon initial installation.
        "
    ::= { systemsEvents 85}

END

-- draft-ietf-syslog-device-mib-14-R.mib

SYSLOG-R-MIB DEFINITIONS ::= BEGIN

IMPORTS
    MODULE-IDENTITY, OBJECT-TYPE,
              Unsigned32, Counter32, Integer32,
              NOTIFICATION-TYPE
              FROM SNMPv2-SMI
    RowStatus, StorageType,
    TEXTUAL-CONVENTION, TimeStamp
              FROM SNMPv2-TC
    InetAddressType, InetAddress
              FROM INET-ADDRESS-MIB
    MODULE-COMPLIANCE, OBJECT-GROUP, NOTIFICATION-GROUP
              FROM SNMPv2-CONF
    radExperimental	   FROM RAD-SMI-MIB
    SnmpAdminString
              FROM SNMP-FRAMEWORK-MIB;

syslogMIBR  MODULE-IDENTITY
    LAST-UPDATED "201403051512Z"  -- March 05, 2014
        ORGANIZATION "RAD Data Communications Ltd."
        CONTACT-INFO
        "System Department
     
         Email:  mibs@rad.com    
         Postal: RAD Data Communications Ltd.
                 24 Raoul Wallenberg St.
                 Tel-Aviv 6971920
                 Israel

         Phone:  +972-3-645-5421
         Fax:    +972-3-760-7844"
         DESCRIPTION
            "Syslog MIB." 
	::= { radExperimental 14 }
   
--	radExperimental	OBJECT IDENTIFIER ::= { iso (1) org (3) dod (6) internet (1) private (4) enterprises (1) rad (164) 20 }

   -- ::= { mib-2 YYYY }     Will be assigned by IANA

   -- IANA Reg.: Please assign a value for "YYYY" under the
   -- 'mib-2' subtree and record the assignment in the SMI
   -- Numbers registry.

   -- RFC Ed.: When the above assignment has been made, please
   --     remove the above note
   --     replace "YYYY" here with the assigned value and
   --     remove this note.



-- -------------------------------------------------------------
-- Textual Conventions
-- -------------------------------------------------------------

SyslogRoles ::=  TEXTUAL-CONVENTION
    STATUS  current
    DESCRIPTION
        "This textual convention enumerates the roles of a
         syslog entity. Note that a syslog entity can have
         multiple roles.
        "
    REFERENCE
        "The Syslog Protocol [RFCPROT] sec. 3.
        "
    SYNTAX      BITS
          {
            sender    (0),
            receiver  (1),
            relay     (2)
          }

SyslogService  ::=  TEXTUAL-CONVENTION
    STATUS  current
    DESCRIPTION
        "The service name or port number that this syslog
         receiver will bind to.
         The service name must resolve to a port number on
         the local host.
        "
    SYNTAX OCTET STRING (SIZE (0..255))

SyslogEncapsulation  ::=  TEXTUAL-CONVENTION
    STATUS  current
    DESCRIPTION
        "This textual convention enumerates the encapsulations
         of the syslog message that is used between syslog
         application endpoints.
        "
    REFERENCE
        "Transmission of syslog messages over UDP [RFCUDPX],
         TLS Transport Mapping for Syslog [RFCTLSX],
         Reliable Delivery for syslog [RFCBEEP].
        "
    SYNTAX  INTEGER
         {
           other           (1),
           none            (2),  -- [RFCUDPX ] (no encapsulation)
           tls             (3),  -- [RFCTLSX]
           beep            (4)   -- [RFCBEEP]
         }

-- -------------------------------------------------------------
-- syslogMIB - the main groups
-- -------------------------------------------------------------

syslogNotifications       OBJECT IDENTIFIER
                      ::= { syslogMIBR 0 }

syslogObjects             OBJECT IDENTIFIER
                      ::= { syslogMIBR 1 }

syslogConformance         OBJECT IDENTIFIER
                      ::= { syslogMIBR 3 }

syslogSystem              OBJECT IDENTIFIER
                      ::= { syslogObjects 1 }

--syslogControlTable        OBJECT IDENTIFIER
--                    ::= { syslogObjects 2 }
--
--syslogOperationsTable     OBJECT IDENTIFIER
--                    ::= { syslogObjects 3 }



-- -------------------------------------------------------------
-- syslogSystem
-- -------------------------------------------------------------

-- The default parameters

syslogDefaultService OBJECT-TYPE
    SYNTAX      SyslogService
    MAX-ACCESS  read-only
    STATUS      current
    DESCRIPTION
        "The default service name or port number that a syslog
         receiver will bind to.
        "
    REFERENCE
        "Transmission of syslog messages over UDP
         [RFCUDPX] Sec. 3.3.
        "
    DEFVAL  { "514" }
    ::= { syslogSystem 1 }

syslogDefaultEncapsulation OBJECT-TYPE
    SYNTAX      SyslogEncapsulation
    MAX-ACCESS  read-only
    STATUS      current
    DESCRIPTION
        "The default encapsulation used by a syslog
         receiver to receive syslog messages.
        "
    DEFVAL  { none }
    ::= { syslogSystem 2 }



-- -------------------------------------------------------------
-- syslog entity configuration info table
-- -------------------------------------------------------------
syslogControlTable OBJECT-TYPE
    SYNTAX      SEQUENCE OF SyslogControlEntry
    MAX-ACCESS  not-accessible
    STATUS      current
    DESCRIPTION
        "A table containing the configuration parameters
         pertaining to the syslog entities serviced by an
         SNMP agent.
        "
    ::= { syslogObjects 2 }

syslogControlEntry OBJECT-TYPE
    SYNTAX      SyslogControlEntry
    MAX-ACCESS  not-accessible
    STATUS      current
    DESCRIPTION
        "The configuration parameters pertaining to a syslog
         entity.
        "
    INDEX  { syslogControlIndex }
    ::= { syslogControlTable 1 }

SyslogControlEntry ::=
    SEQUENCE {
        syslogControlIndex
             Unsigned32,
        syslogControlDescr
             SnmpAdminString,
        syslogControlRoles
             SyslogRoles,
        syslogControlBindAddrType
             InetAddressType,
        syslogControlBindAddr
             InetAddress,
        syslogControlService
             SyslogService,
        syslogControlEncapsulation
             SyslogEncapsulation,
        syslogControlMaxMessageSize
             Unsigned32,
        syslogControlConfFileName
             SnmpAdminString,
        syslogControlStorageType
             StorageType,
        syslogControlRowStatus
             RowStatus,
        syslogControlAccountingType
                BITS
     }

syslogControlIndex OBJECT-TYPE
    SYNTAX      Unsigned32 (1..2147483647)
    MAX-ACCESS  not-accessible
    STATUS      current
    DESCRIPTION
        "The Index that uniquely identifies the syslog entity in
         the syslogControlTable.
         The value of the index for a syslog entity may not be
         the same across system reboots. Users and Applications
         will need to determine the index of a syslog entity after
         system reboots.
        "
    ::= { syslogControlEntry 1 }

syslogControlDescr OBJECT-TYPE
    SYNTAX      SnmpAdminString
    MAX-ACCESS  read-create
    STATUS      current
    DESCRIPTION
        "A user definable description of the syslog entity.
         This description could be used by syslog management
         applications e.g. in reports or in user interfaces.
        "
    ::= { syslogControlEntry 2 }

syslogControlRoles OBJECT-TYPE
    SYNTAX      SyslogRoles
    MAX-ACCESS  read-create
    STATUS      current
    DESCRIPTION
        "The roles of the syslog entity.
        "
    ::= { syslogControlEntry 3 }


syslogControlBindAddrType OBJECT-TYPE
    SYNTAX      InetAddressType
    MAX-ACCESS  read-create
    STATUS      current
    DESCRIPTION
        "The type of Internet address which follows
         in syslogControlBindAddr.
         If this syslog entity is not a syslog receiver,
         the value of this object will be 'unknown' (0).
        "
    ::= { syslogControlEntry 4 }

syslogControlBindAddr OBJECT-TYPE
    SYNTAX      InetAddress
    MAX-ACCESS  read-create
    STATUS      current
    DESCRIPTION
        "The specific address the syslog receiver will bind to.
         The format of the address is specified by the
         corresponding syslogControlBindAddrType object.
         If the address is specified in the DNS domain name format
         [syslogControlBindAddrType = 'dns'], the
         corresponding IPv4 or IPv6 address obtained at the time
         of the binding operation by the syslog entity, will be
         used.
         If this syslog entity is not a syslog receiver, the value
         of this object will be a zero-length string.
        "
    ::= { syslogControlEntry 5 }

syslogControlService OBJECT-TYPE
    SYNTAX      SyslogService
    MAX-ACCESS  read-create
    STATUS      current
    DESCRIPTION
        "The service name or port number that this syslog
         receiver will bind to.

         If this syslog entity is not a syslog receiver the value
         of this object will be zero.

         If no value is specified, the syslog entity will use the
         service name or port number specified in
         syslogDefaultService.
        "
    ::= { syslogControlEntry 6 }

syslogControlEncapsulation OBJECT-TYPE
    SYNTAX      SyslogEncapsulation
    MAX-ACCESS  read-create
    STATUS      current
    DESCRIPTION
        "The encapsulation that will be used for syslog messages
         by the syslog receiver.

         If this syslog entity is not a syslog receiver the value
         of this object will be ''other''.

         If no value is specified, the syslog receiver will use the
         encapsulation specified in syslogDefaultEncapsulation.
        "
    ::= { syslogControlEntry 7 }

syslogControlMaxMessageSize OBJECT-TYPE
    SYNTAX      Unsigned32
    MAX-ACCESS  read-create
    STATUS      current
    DESCRIPTION
        "The maximum size of the syslog messages in bytes
         for this syslog entity.

         A syslog receiver may reject or truncate messages larger
         than the specified maximum syslog message size.
        "
    REFERENCE
        "The Syslog Protocol [RFCPROT] sec. 6.1.
        "
    ::= { syslogControlEntry 8 }

syslogControlConfFileName OBJECT-TYPE
    SYNTAX       SnmpAdminString
    MAX-ACCESS   read-create
    STATUS       current
    DESCRIPTION
      "The fullpath name of the configuration file where the
       syslog entity's message selection and corresponding
       action rules will be read from.
       If the syslog entity does not support the specification
       of a configuration file, the value of this object will
       be a zero-length string.
      "
    DEFVAL { "/etc/syslog.conf" }
    ::= { syslogControlEntry 9 }

syslogControlStorageType OBJECT-TYPE
    SYNTAX       StorageType
    MAX-ACCESS   read-create
    STATUS       current
    DESCRIPTION
        "This object defines whether the parameters defined in
         this row are kept in volatile storage and lost upon
         reboot or are backed up by non-volatile or permanent
         storage.
         Conceptual rows having the value 'permanent' need not
         allow write-access to any columnar objects in the row.
        "
    DEFVAL      { nonVolatile }
    ::= { syslogControlEntry 11 }

syslogControlRowStatus OBJECT-TYPE
    SYNTAX      RowStatus
    MAX-ACCESS  read-create
    STATUS      current
    DESCRIPTION
        "This object is used to create, modify and delete rows in
         the syslogControlTable.
         The value of syslogControlDescr can be changed
         when this object is in state ''active'' or in
         ''notInService''.
         The other objects in a row can be modified only when the
         value of this object in the corresponding conceptual row
         is not ''active''. Thus to modify one or more of the
         objects in this conceptual row,
           a. change the row status to ''notInService'',
           b. change the values of the row
           c. change the row status to ''active''
         The syslogControlRowStatus may be changed to
         ''active'' if all the managed objects in the conceptual
         row with MAX-ACCESS read-create except
         syslogControlService and
         syslogControlEncapsulation have been assigned valid
         values.
        "
    ::= { syslogControlEntry 12 }
    
    
syslogControlAccountingType OBJECT-TYPE
      SYNTAX      BITS
      {
      shell     (0),
      system    (1),
      commands  (2)
       }
      MAX-ACCESS  read-create
      STATUS      current
      DESCRIPTION
      "The accounting type can be configured as:  
      Bit 0 = shell (login and logout events)
      Bit 1 = system (system events and alarms)
      Bit 2 = commands (CLI commands)
      By default all bits are active (bit # = 0)."
      ::= { syslogControlEntry 13 }  
    


-- -------------------------------------------------------------
-- syslogOperations
-- -------------------------------------------------------------
syslogOperationsTable OBJECT-TYPE
    SYNTAX      SEQUENCE OF SyslogOperationsEntry
    MAX-ACCESS  not-accessible
    STATUS      current
    DESCRIPTION
        "A table containing operations information about
         the syslog entities serviced by an SNMP agent.
         This table complements the (configuration) information
         in syslogControlTable .
        "
    ::= { syslogObjects 3 }

syslogOperationsEntry OBJECT-TYPE
    SYNTAX      SyslogOperationsEntry
    MAX-ACCESS  not-accessible
    STATUS      current
    DESCRIPTION
        "The operations information pertaining to a syslog
         entity.
        "
    AUGMENTS  { syslogControlEntry }
    ::= { syslogOperationsTable 1 }

SyslogOperationsEntry ::=
    SEQUENCE {
        syslogOperationsMsgsReceived
             Counter32,
        syslogOperationsMsgsTransmitted
             Counter32,
        syslogOperationsMsgsRelayed
             Counter32,
        syslogOperationsMsgsDropped
             Counter32,
        syslogOperationsMsgsMalFormed
             Counter32,
        syslogOperationsMsgsDiscarded
             Counter32,
        syslogOperationsLastMsgRecdTime
             TimeStamp,
        syslogOperationsLastMsgTransmittedTime
             TimeStamp,
        syslogOperationsStartTime
             TimeStamp,
        syslogOperationsLastError
             SnmpAdminString,
        syslogOperationsLastErrorTime
             TimeStamp,
        syslogOperationsRunIndex
             Integer32,
        syslogOperationsCounterDiscontinuityTime
             TimeStamp,
        syslogOperationsStatus
             INTEGER
    }

syslogOperationsMsgsReceived OBJECT-TYPE
    SYNTAX      Counter32
    MAX-ACCESS  read-only
    STATUS      current
    DESCRIPTION
        "The number of messages received by the syslog
         receiver. This includes messages that were discarded.
         If this syslog entity is not a syslog receiver the
         value of this object will be zero.
         Discontinuities in the value of this counter can
         occur at re-initialization of the management system,




         and at other times as indicated by the value of
         syslogOperationsCounterDiscontinuityTime.
        "
    ::= { syslogOperationsEntry 1 }

syslogOperationsMsgsTransmitted OBJECT-TYPE
    SYNTAX      Counter32
    MAX-ACCESS  read-only
    STATUS      current
    DESCRIPTION
        "The number of messages transmitted by the syslog
         sender. This does not include the messages that could
         not be queued for transmission by the syslog sender.
         If this syslog entity is not a syslog sender the
         value of this object will be zero.
         Discontinuities in the value of this counter can
         occur at re-initialization of the management system,
         and at other times as indicated by the value of
         syslogOperationsCounterDiscontinuityTime.
        "
    ::= { syslogOperationsEntry 2 }

syslogOperationsMsgsRelayed OBJECT-TYPE
    SYNTAX      Counter32
    MAX-ACCESS  read-only
    STATUS      current
    DESCRIPTION
        "The number of messages relayed by the syslog
         relay to other syslog entities.
         If this syslog entity is not a syslog relay the value
         of this object will be zero.
         Discontinuities in the value of this counter can
         occur at re-initialization of the management system,
         and at other times as indicated by the value of
         syslogOperationsCounterDiscontinuityTime.
        "
    REFERENCE
        "The Syslog Protocol [RFCPROT] sec. 3.
        "
    ::= { syslogOperationsEntry 3 }

syslogOperationsMsgsDropped OBJECT-TYPE
    SYNTAX      Counter32
    MAX-ACCESS  read-only
    STATUS      current
    DESCRIPTION
        "The number of messages that could not be queued
         for transmission by the syslog sender.
         If this syslog entity is not a syslog sender the
         value of this object will be zero.
         Discontinuities in the value of this counter can
         occur at re-initialization of the management system,
         and at other times as indicated by the value of
         syslogOperationsCounterDiscontinuityTime.
        "
    ::= { syslogOperationsEntry 4 }

syslogOperationsMsgsMalFormed OBJECT-TYPE
    SYNTAX      Counter32
    MAX-ACCESS  read-only
    STATUS      current
    DESCRIPTION
        "The number of messages received by the syslog
         receiver which had malformed header.
         If this syslog entity is not a syslog receiver,
         then this object will have a zero value.
         Discontinuities in the value of this counter can
         occur at re-initialization of the management system,
         and at other times as indicated by the value of
         syslogOperationsCounterDiscontinuityTime.
        "
    REFERENCE
        "The Syslog Protocol [RFCPROT] sec. 6.3.
        "
    ::= { syslogOperationsEntry 5 }

syslogOperationsMsgsDiscarded OBJECT-TYPE
    SYNTAX      Counter32
    MAX-ACCESS  read-only
    STATUS      current
    DESCRIPTION
        "The number of messages that were discarded by the
         syslog receiver. This will include messages that
         were discarded because the message size was greater
         than the system's maximum message size.
         If this syslog entity is not a syslog receiver this
         object will have a zero value.
         Discontinuities in the value of this counter can
         occur at re-initialization of the management system,
         and at other times as indicated by the value of
         syslogOperationsCounterDiscontinuityTime.
        "
    REFERENCE
        "The Syslog Protocol [RFCPROT] sec. 6.1.
        "
    ::= { syslogOperationsEntry 6 }

syslogOperationsLastMsgRecdTime OBJECT-TYPE
    SYNTAX      TimeStamp
    MAX-ACCESS  read-only
    STATUS      current
    DESCRIPTION
        "The value of sysUpTime when the last message was
         received by the syslog receiver.
         If this syslog entity is not a syslog receiver or,
         if no messages have been received by this syslog
         entity, since the last re-initialization of the
         local SNMP management subsystem, then this object
         will have a zero value.
        "
    ::= { syslogOperationsEntry 7 }

syslogOperationsLastMsgTransmittedTime OBJECT-TYPE
    SYNTAX      TimeStamp
    MAX-ACCESS  read-only
    STATUS      current
    DESCRIPTION
        "The value of sysUpTime when the last message
         was transmitted by the syslog sender.
         If this syslog entity is not a syslog sender or,
         if no messages have been transmitted by this syslog
         entity, since the last re-initialization of the local
         management subsystem, then this object will have a
         zero value.
        "
    ::= { syslogOperationsEntry 8 }

syslogOperationsStartTime OBJECT-TYPE
    SYNTAX      TimeStamp
    MAX-ACCESS  read-only
    STATUS      current
    DESCRIPTION
        "The value of sysUpTime when this syslog entity was
         started.
        "
    ::= { syslogOperationsEntry 9 }

syslogOperationsLastError OBJECT-TYPE
    SYNTAX      SnmpAdminString
    MAX-ACCESS  read-only
    STATUS      current
    DESCRIPTION
        "A description of the last error related to sending,
         receiving or processing a syslog message that was
         encountered by this syslog entity.
         If no error has been encountered by this syslog
         entity then the value of this object will be a
         zero-length string.
         If no error has been encountered by this syslog
         entity since the last re-initialization of the
         local management subsystem then the value of this
         object will be a zero-length string.
        "
    ::= { syslogOperationsEntry 10 }

syslogOperationsLastErrorTime OBJECT-TYPE
    SYNTAX      TimeStamp
    MAX-ACCESS  read-only
    STATUS      current
    DESCRIPTION
        "The value of sysUpTime when the last error was
         encountered.
         If no error has been encountered by this syslog
         entity since the last re-initialization of the
         local management subsystem, then this object will
         have a zero value.
        "
    ::= { syslogOperationsEntry 11 }

syslogOperationsRunIndex OBJECT-TYPE
    SYNTAX      Integer32 (0..2147483647)
    MAX-ACCESS  read-only
    STATUS      current
    DESCRIPTION
        "If the Host resource MIB is instantiated on the
         host then this entry will have the value of the
         hrSWRunIndex of the corresponding entry in the
         hrSWRunTable.
         Note that the hrSWRunIndex is not persistent
         across system reboots or software restarts. The
         value of syslogOperationsRunIndex SHOULD
         reference the latest value of the hrSWRunIndex
         of the corresponding entry in the hrSWRunTable.

         The special value of zero indicates that the Host
         resource MIB is not instantiated.
        "
    ::= { syslogOperationsEntry 12 }


syslogOperationsCounterDiscontinuityTime OBJECT-TYPE
    SYNTAX      TimeStamp
    MAX-ACCESS  read-only
    STATUS      current
    DESCRIPTION
         "The value of sysUpTime on the most recent occasion
          at which any one or more of this syslog entity's
          counters, viz., counters with OID prefix
          'syslogOperationsMsgsReceived' or
          'syslogOperationsMsgsTransmitted' or
          'syslogOperationsMsgsRelayed' or
          'syslogOperationsMsgsDropped' or
          'syslogOperationsMsgsMalFormed' or
          'syslogOperationsMsgsDiscarded' suffered a
          discontinuity.
          If no such discontinuities have occurred since the
          last re-initialization of the local management
          subsystem, then this object will have a zero value.
         "
    ::= { syslogOperationsEntry 13 }

syslogOperationsStatus OBJECT-TYPE
    SYNTAX       INTEGER  {
                      unknown  (1),
                      started  (2),
                      suspended(3),
                      stopped  (4)
                    }
    MAX-ACCESS   read-only
    STATUS       current
    DESCRIPTION
        "The status of the syslog entity.
        "
    DEFVAL      { unknown }
    ::= { syslogOperationsEntry 14 }

syslogStatusChanged NOTIFICATION-TYPE
    OBJECTS   {
                 syslogControlDescr,
                 syslogControlRoles,
                 syslogControlBindAddrType,
                 syslogControlBindAddr,
                 syslogControlService,
                 syslogControlEncapsulation,
                 syslogControlConfFileName,
                 syslogOperationsStatus
              }
    STATUS    current
    DESCRIPTION
            "This notification is sent when a syslog entity
             changes state. For example when the syslog entity
             starts [syslogOperationsStatus is ''started'' ]
             or the syslog entity stops [syslogOperationsStatus
             is ''suspended'' or ''stopped''].
             The value of syslogOperationsStatus will be the
             new status of the syslog entity after the change.
             The syslog entity corresponding to the notification
             will be identified by the syslogOperationsIndex
             instance identifier of the objects in the notification.
            "
    ::= { syslogNotifications 1 }


-- -------------------------------------------------------------
-- Conformance Information
-- -------------------------------------------------------------

syslogGroups OBJECT IDENTIFIER
                          ::= { syslogConformance 1 }

syslogCompliances OBJECT IDENTIFIER
                          ::= { syslogConformance 2 }

-- -------------------------------------------------------------
-- units of conformance
-- -------------------------------------------------------------

syslogDefaultGroup OBJECT-GROUP
    OBJECTS {
             syslogDefaultService,
             syslogDefaultEncapsulation
    }
    STATUS  current
    DESCRIPTION
        "A collection of objects providing default
         parameters for syslog entities
        "
    ::= { syslogGroups 1}

syslogOperationsGroup OBJECT-GROUP
    OBJECTS {
            --  syslogOperationsIndex,
                syslogOperationsMsgsReceived,
                syslogOperationsMsgsTransmitted,
                syslogOperationsMsgsRelayed,
                syslogOperationsMsgsDropped,
                syslogOperationsMsgsMalFormed,
                syslogOperationsMsgsDiscarded,
                syslogOperationsLastMsgRecdTime,
                syslogOperationsLastMsgTransmittedTime,
                syslogOperationsStartTime,
                syslogOperationsLastError,
                syslogOperationsLastErrorTime,
                syslogOperationsRunIndex,
                syslogOperationsCounterDiscontinuityTime,
                syslogOperationsStatus
            }
    STATUS  current




    DESCRIPTION
        "A collection of objects providing message related
         statistics."
    ::= { syslogGroups 2}

syslogControlGroup OBJECT-GROUP
    OBJECTS {
                syslogControlDescr,
                syslogControlRoles,
                syslogControlBindAddrType,
                syslogControlBindAddr,
                syslogControlEncapsulation,
                syslogControlService,
                syslogControlMaxMessageSize,
                syslogControlConfFileName,
                syslogControlStorageType,
                syslogControlRowStatus
            }
    STATUS  current
    DESCRIPTION
        "A collection of objects representing the run time parameters
         for the syslog entities.
        "
    ::= { syslogGroups 3}

syslogNotificationGroup NOTIFICATION-GROUP
    NOTIFICATIONS {
                syslogStatusChanged
            }
    STATUS  current
    DESCRIPTION
        "A collection of notifications about the operational
         state of a syslog entity.
        "
    ::= { syslogGroups 4}


-- -------------------------------------------------------------
-- compliance statements
-- -------------------------------------------------------------

syslogFullCompliance1 MODULE-COMPLIANCE
    STATUS  current
    DESCRIPTION
        "The compliance statement for SNMP entities which
         implement the SYSLOG-MIB with support for writable
         objects and notifications. Such an implementation can
         be both monitored and configured via SNMP. It can
         also send notifications about change in the
         operational status of the syslog entity.
        "
    MODULE -- this module
    MANDATORY-GROUPS {
        syslogNotificationGroup,
        syslogDefaultGroup,
        syslogOperationsGroup,
        syslogControlGroup
    }

    ::= { syslogCompliances 1 }

syslogFullCompliance2 MODULE-COMPLIANCE
    STATUS  current
    DESCRIPTION
        "The compliance statement for SNMP entities which
         implement the SYSLOG-MIB with support for writable
         objects. Such an implementation can
         be both monitored and configured via SNMP.
        "
    MODULE -- this module
    MANDATORY-GROUPS {
        syslogDefaultGroup,
        syslogOperationsGroup,
        syslogControlGroup
    }

    ::= { syslogCompliances 2 }

syslogReadOnlyCompliance1 MODULE-COMPLIANCE
    STATUS  current
    DESCRIPTION
        "The compliance statement for SNMP entities which
         implement the syslog MIB without support
         for read-write (i.e. in read-only mode). It can
         also send notifications about change in the
         operational status of the syslog entity.
        "
    MODULE -- this module
    MANDATORY-GROUPS {
        syslogNotificationGroup,
        syslogDefaultGroup,
        syslogOperationsGroup,
        syslogControlGroup
    }

    OBJECT  syslogControlDescr
    MIN-ACCESS  read-only
    DESCRIPTION
        "Write access is not required.
        "
    OBJECT  syslogControlRoles
    MIN-ACCESS  read-only
    DESCRIPTION
        "Write access is not required.
        "
    OBJECT  syslogControlBindAddrType
    MIN-ACCESS  read-only
    DESCRIPTION
        "Write access is not required.
        "
    OBJECT  syslogControlBindAddr
    MIN-ACCESS  read-only
    DESCRIPTION
        "Write access is not required.
        "
    OBJECT  syslogControlService
    MIN-ACCESS  read-only
    DESCRIPTION
        "Write access is not required.
        "
    OBJECT  syslogControlEncapsulation
    MIN-ACCESS  read-only
    DESCRIPTION
        "Write access is not required.
        "
    OBJECT  syslogControlMaxMessageSize
    MIN-ACCESS  read-only
    DESCRIPTION
        "Write access is not required.
        "
    OBJECT  syslogControlConfFileName
    MIN-ACCESS   read-only
    DESCRIPTION
      "Write access is not required.
      "
    OBJECT  syslogControlStorageType
    MIN-ACCESS   read-only
    DESCRIPTION
        "Write access is not required.
        "
    OBJECT  syslogControlRowStatus
    MIN-ACCESS  read-only
    DESCRIPTION
        "Write access is not required.
        "
    ::= { syslogCompliances 3 }


syslogReadOnlyCompliance2 MODULE-COMPLIANCE
    STATUS  current
    DESCRIPTION
        "The compliance statement for SNMP entities which
         implement the syslog MIB without support
         for read-write (i.e. in read-only mode).
        "
    MODULE -- this module
    MANDATORY-GROUPS {
        syslogDefaultGroup,
        syslogOperationsGroup,
        syslogControlGroup
    }

    OBJECT  syslogControlDescr
    MIN-ACCESS  read-only
    DESCRIPTION
        "Write access is not required.
        "
    OBJECT  syslogControlRoles
    MIN-ACCESS  read-only
    DESCRIPTION
        "Write access is not required.
        "
    OBJECT  syslogControlBindAddrType
    MIN-ACCESS  read-only
    DESCRIPTION
        "Write access is not required.
        "
    OBJECT  syslogControlBindAddr
    MIN-ACCESS  read-only
    DESCRIPTION
        "Write access is not required.
        "
    OBJECT  syslogControlService
    MIN-ACCESS  read-only
    DESCRIPTION
        "Write access is not required.
        "
    OBJECT  syslogControlEncapsulation
    MIN-ACCESS  read-only
    DESCRIPTION
        "Write access is not required.
        "
    OBJECT  syslogControlMaxMessageSize
    MIN-ACCESS  read-only
    DESCRIPTION
        "Write access is not required.
        "
    OBJECT  syslogControlConfFileName
    MIN-ACCESS   read-only
    DESCRIPTION
      "Write access is not required.
      "
    OBJECT  syslogControlStorageType
    MIN-ACCESS   read-only
    DESCRIPTION
        "Write access is not required.
        "
    OBJECT  syslogControlRowStatus
    MIN-ACCESS  read-only
    DESCRIPTION
        "Write access is not required.
        "
    ::= { syslogCompliances 4 }

syslogNotificationCompliance MODULE-COMPLIANCE
    STATUS  current
    DESCRIPTION
        "The compliance statement for SNMP entities
         which implement the SYSLOG-MIB and support
         only notifications about change in the
         operational status of a syslog entity.
        "
    MODULE -- this module
    MANDATORY-GROUPS {
        syslogNotificationGroup
    }

    ::= { syslogCompliances 5 }


END

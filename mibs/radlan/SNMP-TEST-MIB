SNMP-TEST-MIB DEFINITIONS ::= BEGIN

-- Title:      SNMP testing MIB
--             This Private MIB supports the Radlan SNMP testing
-- Version:    7.10
-- Date:       09 Mar 2001
-- By:         Michael Indenbaum
-- E-mail:     michael@radlan.com
--
IMPORTS
    TEXTUAL-CONVENTION            FROM SNMPv2-TC
    Counter64, OBJECT-TYPE        FROM SNMPv2-SMI
    PortList                      FROM Q-BRIDGE-MIB
    rlSnmpTestSimulatedVariables  FROM RADLAN-rndApplications;


KeyBits ::= TEXTUAL-CONVENTION
    STATUS          current
    DESCRIPTION
        "Defined for the sole purpose of allowing syntax refinement"
    SYNTAX  BITS {
                    firstKey(0),
                    secondKey(1),
                    thirdKey(2),
                    fourthKey(3),
                    fifthKey(4)
     }
FieldBits ::= TEXTUAL-CONVENTION
    STATUS          current
    DESCRIPTION
        "Defined for the sole purpose of allowing syntax refinement"
    SYNTAX  BITS {
                    firstField(0),
                    secondField(1),
                    thirdField(2),
                    fourthField(3),
                    fifthField(4)
     }

rlSnmpTestMibVersion OBJECT-TYPE
    SYNTAX  INTEGER
    MAX-ACCESS  read-only
    STATUS  current
    DESCRIPTION
        "MIB's version, the current version is 1."
    ::= { rlSnmpTestSimulatedVariables 1 }

rlSetsTestTable OBJECT-TYPE
    SYNTAX  SEQUENCE OF RlSetsTestEntry
    MAX-ACCESS  not-accessible
    STATUS  current
    DESCRIPTION
        "This table will allow us to test the PortList and BITS support, both as table keys and
         fields."
    ::= { rlSnmpTestSimulatedVariables 2 }

rlSetsTestEntry OBJECT-TYPE
    SYNTAX  RlSetsTestEntry
    MAX-ACCESS  not-accessible
    STATUS  current
    DESCRIPTION
        "One entry in the rlSetsTestTable."
    INDEX  {
              rlSetsEntryBitsKey,
              rlSetsEntryPortListKey
     }
  ::= { rlSetsTestTable 1 }

 RlSetsTestEntry ::= SEQUENCE  {
             rlSetsEntryBitsKey        KeyBits,
             rlSetsEntryPortListKey    PortList,
             rlSetsEntryBitsField      FieldBits,
             rlSetsEntryPortListField  PortList,
             rlSetsEntryCounter64Field Counter64
}

  rlSetsEntryBitsKey OBJECT-TYPE
    SYNTAX  KeyBits {
                    firstKey(0),
                    secondKey(1),
                    thirdKey(2),
                    fifthKey(4)

     }
    MAX-ACCESS  not-accessible
    STATUS  current
    DESCRIPTION
        "BITS key"
    ::= { rlSetsTestEntry 1 }

 rlSetsEntryPortListKey OBJECT-TYPE
    SYNTAX  PortList
    MAX-ACCESS  not-accessible
    STATUS  current
    DESCRIPTION
        "Port list key"
    ::= { rlSetsTestEntry 2 }

  rlSetsEntryBitsField OBJECT-TYPE
    SYNTAX  FieldBits {
                    firstField(0),
                    secondField(1),
                    thirdField(2),
                    fifthField(4)
     }
    MAX-ACCESS  read-create
    STATUS  current
    DESCRIPTION
        "Bits Field"
    ::= { rlSetsTestEntry 3 }

 rlSetsEntryPortListField OBJECT-TYPE
    SYNTAX PortList
    MAX-ACCESS read-create
    STATUS current
    DESCRIPTION
        "Port list field"
    ::= { rlSetsTestEntry 4 }

 rlSetsEntryCounter64Field OBJECT-TYPE
    SYNTAX Counter64
    MAX-ACCESS read-create
    STATUS current
    DESCRIPTION
        "Counter64 field"
    ::= { rlSetsTestEntry 5 }





END

-- COPYRIGHT NOTICE
-- Copyright (c) Radware Ltd. 2009
-- All rights reserved

ALTEON-CHEETAH-BWM-MIB DEFINITIONS ::= BEGIN

IMPORTS
    MODULE-IDENTITY, OBJECT-TYPE, Integer32, Counter32,
    IpAddress    FROM SNMPv2-SMI
    DisplayString
        FROM SNMPv2-TC
    aws-switch 
        FROM ALTEON-ROOT-MIB;

bwm MODULE-IDENTITY
    LAST-UPDATED "200908050000Z" --  5 August, 2009
    ORGANIZATION "Radware Ltd"
    CONTACT-INFO "Lobby 1 (Visitors) and Lobby 2 (Deliveries)
                  575 Corporate Drive
                  Mahwah, NJ 07430
                  support@radware.com"
    DESCRIPTION
        "The MIB module for the Alteon OS BWM configuration, statistics and
         information ."
    REVISION "200908050000Z" --  5 August, 2009 
    DESCRIPTION
        "Added revision clause for SMIv2 compliance."
    ::= { aws-switch 6 }

bwmConfigs	  OBJECT IDENTIFIER ::= { bwm 1 }
bwmStats	  OBJECT IDENTIFIER ::= { bwm 2 }
bwmOpers	  OBJECT IDENTIFIER ::= { bwm 3 }

bwmGeneralConfig        OBJECT IDENTIFIER ::= { bwmConfigs 1 }
bwmPolicyConfig         OBJECT IDENTIFIER ::= { bwmConfigs 2 }
bwmContractConfig       OBJECT IDENTIFIER ::= { bwmConfigs 3 }
bwmContTimePolicyConfig OBJECT IDENTIFIER ::= { bwmConfigs 4 }
bwmContractGroupConfig  OBJECT IDENTIFIER ::= { bwmConfigs 5 }

bwmCurCfgGenState OBJECT-TYPE
    SYNTAX INTEGER {
	on(2),
	off(3)
        }
    MAX-ACCESS read-only
    STATUS current
    DESCRIPTION
        "The state of BWM on the switch."
    ::= { bwmGeneralConfig 1 }

bwmNewCfgGenState OBJECT-TYPE
    SYNTAX INTEGER {
	on(2),
	off(3)
	}
    MAX-ACCESS read-write
    STATUS current
    DESCRIPTION
        "The state of BWM in the switch."
    ::= { bwmGeneralConfig 2 }

bwmCurCfgGenEnforcePolicy OBJECT-TYPE
    SYNTAX INTEGER {
	enabled(2),
	disabled(3)
	}
    MAX-ACCESS read-only
    STATUS current
    DESCRIPTION
        "The state of BWM enforce policies. When disabled, no bandwidth limits
         will be applied on the queues."
    ::= { bwmGeneralConfig 3 }

bwmNewCfgGenEnforcePolicy OBJECT-TYPE
    SYNTAX INTEGER {
	enabled(2),
	disabled(3)
	}
    MAX-ACCESS read-write
    STATUS current
    DESCRIPTION
        "The state of BWM enforce policies. When disabled, no bandwidth limits
         will be applied on the queues."
    ::= { bwmGeneralConfig 4 }

bwmCurCfgGenSmtpUser OBJECT-TYPE
    SYNTAX DisplayString (SIZE(0..127))
    MAX-ACCESS read-only
    STATUS obsolete
    DESCRIPTION
        "The SMTP user name tp whom the history statistics will be mailed."
    ::= { bwmGeneralConfig 5 }
 
bwmNewCfgGenSmtpUser OBJECT-TYPE
    SYNTAX DisplayString (SIZE(0..127))
    MAX-ACCESS read-write
    STATUS obsolete
    DESCRIPTION
        "The SMTP user name tp whom the history statistics will be mailed."
    ::= { bwmGeneralConfig 6 }

bwmCurCfgGenEmailFrequency OBJECT-TYPE
    SYNTAX INTEGER (0..1440) 
    MAX-ACCESS read-only
    STATUS obsolete
    DESCRIPTION
        "The frequency of BWM email in minutes." 
    ::= { bwmGeneralConfig 7 }

bwmNewCfgGenEmailFrequency OBJECT-TYPE
    SYNTAX INTEGER (0..1440) 
    MAX-ACCESS read-write
    STATUS obsolete
    DESCRIPTION
        "The frequency of BWM email in minutes." 
    ::= { bwmGeneralConfig 8 }

bwmCurCfgGenIPUserLimit OBJECT-TYPE
    SYNTAX DisplayString (SIZE(0..4))
    MAX-ACCESS read-only
    STATUS current
    DESCRIPTION
        "The number of entries in the BWM IP user table in 64k|128k|256k|512k format." 
    ::= { bwmGeneralConfig 9 }
 
bwmNewCfgGenIPUserLimit OBJECT-TYPE
    SYNTAX DisplayString (SIZE(0..4))
    MAX-ACCESS read-write
    STATUS current
    DESCRIPTION
        "The number of entries in the BWM IP user table in 64k|128k|256k|512k format." 
    ::= { bwmGeneralConfig 10 }
 
bwmCurCfgGenEmail OBJECT-TYPE
    SYNTAX INTEGER {
	enabled(2),
	disabled(3)
	}
    MAX-ACCESS read-only
    STATUS obsolete
    DESCRIPTION
        "Specifies whether BWM history statistics are sent using email. 
         When disabled, the history statistics are sent using socket based 
         mechanism."
    ::= { bwmGeneralConfig 11 }

bwmNewCfgGenEmail OBJECT-TYPE
    SYNTAX INTEGER {
	enabled(2),
	disabled(3)
	}
    MAX-ACCESS read-write
    STATUS obsolete
    DESCRIPTION
        "Specifies whether BWM history statistics are sent using email. 
         When disabled, the history statistics are sent using socket based 
         mechanism."
    ::= { bwmGeneralConfig 12 }

bwmCurCfgGenReport OBJECT-TYPE
    SYNTAX  IpAddress
    MAX-ACCESS  read-only
    STATUS  obsolete
    DESCRIPTION
        "IP address of the reporting server."
    ::= { bwmGeneralConfig 13 }

bwmNewCfgGenReport OBJECT-TYPE
    SYNTAX  IpAddress
    MAX-ACCESS  read-write
    STATUS  obsolete
    DESCRIPTION
        "IP address of the reporting server."
    ::= { bwmGeneralConfig 14 }

bwmCurCfgGenReportStr OBJECT-TYPE
    SYNTAX  DisplayString
    MAX-ACCESS  read-only
    STATUS  current
    DESCRIPTION
        "IP address or Hostname of the reporting server."
    ::= { bwmGeneralConfig 15 }

bwmNewCfgGenReportStr OBJECT-TYPE
    SYNTAX  DisplayString
    MAX-ACCESS  read-write
    STATUS  current
    DESCRIPTION
        "IP address or Hostname of the reporting server."
    ::= { bwmGeneralConfig 16 }

bwmCurCfgGenAlarmsPerSec OBJECT-TYPE
    SYNTAX INTEGER (0..1000) 
    MAX-ACCESS read-only
    STATUS current
    DESCRIPTION
        "The amount of BWM alarms can be send per second." 
    ::= { bwmGeneralConfig 17 }

bwmNewCfgGenAlarmsPerSec OBJECT-TYPE
    SYNTAX INTEGER (0..1000) 
    MAX-ACCESS read-write
    STATUS current
    DESCRIPTION
        "The amount of BWM alarms can be send per second." 
    ::= { bwmGeneralConfig 18 }

bwmCurCfgGenAlarmsUpdateRate OBJECT-TYPE
    SYNTAX INTEGER (5..100) 
    MAX-ACCESS read-only
    STATUS current
    DESCRIPTION
        "The BWM alarms update rate in seconds." 
    ::= { bwmGeneralConfig 19 }

bwmNewCfgGenAlarmsUpdateRate OBJECT-TYPE
    SYNTAX INTEGER (5..100) 
    MAX-ACCESS read-write
    STATUS current
    DESCRIPTION
        "The BWM alarms update rate in seconds." 
    ::= { bwmGeneralConfig 20 }

bwmCurCfgGenIPPrefixLimit OBJECT-TYPE
    SYNTAX DisplayString (SIZE(0..4))
    MAX-ACCESS read-only
    STATUS current
    DESCRIPTION
        "The number of entries in the BWM IP Prefix table in 1k|16k|64k|128k|256k format." 
    ::= { bwmGeneralConfig 21 }
 
bwmNewCfgGenIPPrefixLimit OBJECT-TYPE
    SYNTAX DisplayString (SIZE(0..4))
    MAX-ACCESS read-write
    STATUS current
    DESCRIPTION
        "The number of entries in the BWM IP Prefix table in 1k|16k|64k|128k|256k format." 
    ::= { bwmGeneralConfig 22 }
 

bwmPolicyTableMaxEnt OBJECT-TYPE
    SYNTAX Integer32
    MAX-ACCESS read-only
    STATUS current
    DESCRIPTION
        "The maximum number of rows in the BWM policy configuration table."
    ::= { bwmPolicyConfig 1 }

bwmCurCfgPolicyTable OBJECT-TYPE
    SYNTAX SEQUENCE OF BwmCurCfgPolicyTableEntry
    MAX-ACCESS not-accessible
    STATUS current
    DESCRIPTION
        "The table of BWM traffic policy configuration."
    ::= { bwmPolicyConfig 2 }
 
bwmCurCfgPolicyTableEntry OBJECT-TYPE
    SYNTAX BwmCurCfgPolicyTableEntry
    MAX-ACCESS not-accessible
    STATUS current
    DESCRIPTION
        "A row in the BWM traffic policy configuration table."
    INDEX { bwmCurCfgPolicyIndx }
    ::= { bwmCurCfgPolicyTable 1 }
 
BwmCurCfgPolicyTableEntry ::= SEQUENCE {
    bwmCurCfgPolicyIndx       Integer32,
    bwmCurCfgPolicyTosIn      INTEGER,
    bwmCurCfgPolicyTosOut     INTEGER,
    bwmCurCfgPolicyHard       DisplayString,
    bwmCurCfgPolicySoft       DisplayString,
    bwmCurCfgPolicyResv       DisplayString,
    bwmCurCfgPolicyUserLimit  DisplayString,
    bwmCurCfgPolicyBuffer     INTEGER,
    bwmCurCfgPolicyType	      INTEGER,
    bwmCurCfgPolicyHardPPS    INTEGER,
    bwmCurCfgPolicyUserPPS    INTEGER
    }
 
bwmCurCfgPolicyIndx OBJECT-TYPE
    SYNTAX Integer32
    MAX-ACCESS read-only
    STATUS current
    DESCRIPTION
        "The index of the row in BWM traffic policy configurations table."
    ::= { bwmCurCfgPolicyTableEntry 1 }
 
bwmCurCfgPolicyTosIn OBJECT-TYPE
    SYNTAX INTEGER (0..255)
    MAX-ACCESS read-only
    STATUS current
    DESCRIPTION
        "The 'utos' value which overwrites the original TOS value if the 
         traffic for this contract is under the soft limit. With this option
         set to the default value of '0' the switch will not overwrite the
         TOS value."
    ::= { bwmCurCfgPolicyTableEntry 2 }

bwmCurCfgPolicyTosOut OBJECT-TYPE
    SYNTAX INTEGER (0..255)
    MAX-ACCESS read-only
    STATUS current
    DESCRIPTION
        "The 'otos' value which overwrites the original TOS value if the 
         traffic is over the soft limit. With this option set to the default 
         value of '0' the switch will not overwrite the TOS value."
    ::= { bwmCurCfgPolicyTableEntry 3 }

bwmCurCfgPolicyHard OBJECT-TYPE
    SYNTAX DisplayString (SIZE(0..5))
    MAX-ACCESS read-only
    STATUS current
    DESCRIPTION
        "The hard bandwidth limit for this traffic policy. This is the highest
         amount of bandwidth available to the policy."
    ::= { bwmCurCfgPolicyTableEntry 4 }
 
bwmCurCfgPolicySoft OBJECT-TYPE
    SYNTAX DisplayString (SIZE(0..5))
    MAX-ACCESS read-only
    STATUS current
    DESCRIPTION
        "The soft bandwidth limit for this traffic policy."
    ::= { bwmCurCfgPolicyTableEntry 5 }
 
bwmCurCfgPolicyResv OBJECT-TYPE
    SYNTAX DisplayString (SIZE(0..5))
    MAX-ACCESS read-only
    STATUS current
    DESCRIPTION
        "The reserve bandwidth limit for this traffic policy. This is the 
         amount of bandwidth always available to this policy."
    ::= { bwmCurCfgPolicyTableEntry 6 }
 
bwmCurCfgPolicyBuffer OBJECT-TYPE
    SYNTAX INTEGER (8192..128000)
    MAX-ACCESS read-only
    STATUS current
    DESCRIPTION
        "The buffer limit for the traffic policy."
    ::= { bwmCurCfgPolicyTableEntry 7 }

bwmCurCfgPolicyUserLimit OBJECT-TYPE
    SYNTAX DisplayString (SIZE(0..5))
    MAX-ACCESS read-only
    STATUS current
    DESCRIPTION
        "The per user (IP address) bandwidth limit for this traffic policy.
         This is the maximum amount of bandwidth available for each distinct
	 user (IP address) if the contract performs per user rate limiting."
    ::= { bwmCurCfgPolicyTableEntry 8 }

bwmCurCfgPolicyType OBJECT-TYPE
    SYNTAX INTEGER {
        throughput(1),
        pps(2)
	}
    MAX-ACCESS read-only
    STATUS current
    DESCRIPTION
        "policy type pps or throughput."
    ::= { bwmCurCfgPolicyTableEntry 9 }

bwmCurCfgPolicyHardPPS OBJECT-TYPE
    SYNTAX INTEGER (10..1000000)
    MAX-ACCESS read-only
    STATUS current
    DESCRIPTION
        "pps hard limit."
    ::= { bwmCurCfgPolicyTableEntry 10 }

bwmCurCfgPolicyUserPPS OBJECT-TYPE
    SYNTAX INTEGER (10..1000000)
    MAX-ACCESS read-only
    STATUS current
    DESCRIPTION
        "pps user limit."
    ::= { bwmCurCfgPolicyTableEntry 11 }

bwmNewCfgPolicyTable OBJECT-TYPE
    SYNTAX SEQUENCE OF BwmNewCfgPolicyTableEntry
    MAX-ACCESS not-accessible
    STATUS current
    DESCRIPTION
        "The table of BWM traffic policy configuration."
    ::= { bwmPolicyConfig 3 }
 
bwmNewCfgPolicyTableEntry OBJECT-TYPE
    SYNTAX BwmNewCfgPolicyTableEntry
    MAX-ACCESS not-accessible
    STATUS current
    DESCRIPTION
        "A row in the BWM traffic policy configuration table."
    INDEX   { bwmNewCfgPolicyIndx }
    ::= { bwmNewCfgPolicyTable 1 }
 
BwmNewCfgPolicyTableEntry ::= SEQUENCE {
    bwmNewCfgPolicyIndx       Integer32,
    bwmNewCfgPolicyTosIn      INTEGER,
    bwmNewCfgPolicyTosOut     INTEGER,
    bwmNewCfgPolicyHard       DisplayString,
    bwmNewCfgPolicySoft       DisplayString,
    bwmNewCfgPolicyResv       DisplayString,
    bwmNewCfgPolicyBuffer     INTEGER,
 
    bwmNewCfgPolicyUserLimit  DisplayString,
    bwmNewCfgPolicyDelete     INTEGER,
    bwmNewCfgPolicyType	      INTEGER, 		
    bwmNewCfgPolicyHardPPS    INTEGER, 		
    bwmNewCfgPolicyUserPPS    INTEGER
    }

bwmNewCfgPolicyIndx OBJECT-TYPE
    SYNTAX Integer32
    MAX-ACCESS read-only
    STATUS current
    DESCRIPTION
        "The index of the row in BWM traffic policy configurations table."
    ::= { bwmNewCfgPolicyTableEntry 1 }
 
bwmNewCfgPolicyTosIn OBJECT-TYPE
    SYNTAX INTEGER (0..255)
    MAX-ACCESS read-create
    STATUS current
    DESCRIPTION
        "The 'utos' value which overwrites the original TOS value if the 
         traffic for this contract is under the soft limit. With this option
         set to the default value of '0' the switch will not overwrite the
         TOS value."
    ::= { bwmNewCfgPolicyTableEntry 2 }

bwmNewCfgPolicyTosOut OBJECT-TYPE
    SYNTAX INTEGER (0..255)
    MAX-ACCESS read-create
    STATUS current
    DESCRIPTION
        "The 'otos' value which overwrites the original TOS value if the 
         traffic is over the soft limit. With this option set to the default 
         value of '0' the switch will not overwrite the TOS value."
    ::= { bwmNewCfgPolicyTableEntry 3 }

bwmNewCfgPolicyHard OBJECT-TYPE
    SYNTAX DisplayString (SIZE(0..6)) 
    MAX-ACCESS read-create
    STATUS current
    DESCRIPTION
        "The hard bandwidth limit for this traffic policy. This is the highest
         amount of bandwidth available to the policy."
::= { bwmNewCfgPolicyTableEntry 4 }
 
bwmNewCfgPolicySoft OBJECT-TYPE
    SYNTAX DisplayString (SIZE(0..6))
    MAX-ACCESS read-create
    STATUS current
    DESCRIPTION
        "The soft bandwidth limit for this traffic policy."
    ::= { bwmNewCfgPolicyTableEntry 5 }
 
bwmNewCfgPolicyResv OBJECT-TYPE
    SYNTAX DisplayString (SIZE(0..6))
    MAX-ACCESS read-create
    STATUS current
    DESCRIPTION
        "The reserve bandwidth limit for this traffic policy. This is the 
         amount of bandwidth always available to this policy."
    ::= { bwmNewCfgPolicyTableEntry 6 }
 
bwmNewCfgPolicyBuffer OBJECT-TYPE
    SYNTAX INTEGER (8192..128000)
    MAX-ACCESS read-create
    STATUS current
    DESCRIPTION
        "The buffer limit for the traffic policy."
    ::= { bwmNewCfgPolicyTableEntry 7 }
 
bwmNewCfgPolicyDelete OBJECT-TYPE
    SYNTAX INTEGER { 
        other(1),
        delete(2)
        }
    MAX-ACCESS read-create
    STATUS current
    DESCRIPTION
        "When set to the value of 2 (delete), the entire row
	 is deleted. When read, other(1) is returned. Setting the value
	 to anything other than 2(delete) has no effect on the state
	 of the row."
    ::= { bwmNewCfgPolicyTableEntry 8 }

bwmNewCfgPolicyUserLimit OBJECT-TYPE
    SYNTAX DisplayString (SIZE(0..6))
    MAX-ACCESS read-create
    STATUS current
    DESCRIPTION
        "The per user (IP address) bandwidth limit for this traffic policy.
         This is the maximum amount of bandwidth available for each distinct
	 user (IP address) if the contract performs per user rate limiting."
    ::= { bwmNewCfgPolicyTableEntry 9 }


bwmNewCfgPolicyType OBJECT-TYPE
    SYNTAX INTEGER {
        throughput(1),
        pps(2)
	}
    MAX-ACCESS read-create
    STATUS current
    DESCRIPTION
        "policy type pps or throughput."
    ::= { bwmNewCfgPolicyTableEntry 10 }

bwmNewCfgPolicyHardPPS OBJECT-TYPE
    SYNTAX INTEGER (10..1000000)
    MAX-ACCESS read-create
    STATUS current
    DESCRIPTION
        "pps hard limit."
    ::= { bwmNewCfgPolicyTableEntry 11 }

bwmNewCfgPolicyUserPPS OBJECT-TYPE
    SYNTAX INTEGER (10..1000000)
    MAX-ACCESS read-create
    STATUS current
    DESCRIPTION
        "pps user limit."
    ::= { bwmNewCfgPolicyTableEntry 12 }

-- BWM Contract Config Table
 
bwmContractTableMaxEnt OBJECT-TYPE
    SYNTAX Integer32
    MAX-ACCESS read-only
    STATUS current
    DESCRIPTION
        "The maximum number of rows in the BWM contract configuration table."
    ::= { bwmContractConfig 1 }
 
bwmCurCfgContractTable OBJECT-TYPE
    SYNTAX SEQUENCE OF BwmContractCurCfgTableEntry
    MAX-ACCESS not-accessible
    STATUS current
    DESCRIPTION
        "The table of BWM traffic contract configuration."
    ::= { bwmContractConfig 2 }
 
bwmCurCfgContractTableEntry OBJECT-TYPE
    SYNTAX BwmContractCurCfgTableEntry
    MAX-ACCESS not-accessible
    STATUS current
    DESCRIPTION
        "A row in the BWM traffic contract configuration table."
    INDEX   { bwmCurCfgContractIndx }
    ::= { bwmCurCfgContractTable 1 }
 
BwmContractCurCfgTableEntry ::= SEQUENCE {
    bwmCurCfgContractIndx        Integer32,
    bwmCurCfgContractName        DisplayString,
    bwmCurCfgContractState       INTEGER,
    bwmCurCfgContractPolicy      Integer32,
    bwmCurCfgContractPrec	 INTEGER,
    bwmCurCfgContractUseTos      INTEGER,
    bwmCurCfgContractHistory     INTEGER,
    bwmCurCfgContractShaping     INTEGER,
    bwmCurCfgContractResizeTcp   INTEGER,
    bwmCurCfgContractIpLimit     INTEGER,
    bwmCurCfgContractIpType      INTEGER,
    bwmCurCfgContractMonitorMode INTEGER,
    bwmCurCfgContractMaxSess     INTEGER,
    bwmCurCfgContractGroup       Integer32,
    bwmCurCfgContractRowType     INTEGER,
    bwmCurCfgContractOperMode    INTEGER,
    bwmCurCfgContractAlarmsPerSec INTEGER,
    bwmCurCfgContractPrefixLength  INTEGER
    }
 
bwmCurCfgContractIndx OBJECT-TYPE
    SYNTAX Integer32
    MAX-ACCESS read-only
    STATUS current
    DESCRIPTION
        "The index of the row in BWM traffic contract configurations table."
    ::= { bwmCurCfgContractTableEntry 1 }
 
bwmCurCfgContractName   OBJECT-TYPE
    SYNTAX DisplayString (SIZE(0..31))
    MAX-ACCESS read-only
    STATUS current
    DESCRIPTION
        "The traffic contract name."
    ::= { bwmCurCfgContractTableEntry 2 }
 
bwmCurCfgContractState OBJECT-TYPE
    SYNTAX INTEGER {
        enabled(2),
        disabled(3)
        }
    MAX-ACCESS read-only
    STATUS current
    DESCRIPTION
        "This is the state of the traffic contract."
    ::= { bwmCurCfgContractTableEntry 3 }
 
bwmCurCfgContractPolicy OBJECT-TYPE
    SYNTAX Integer32
    MAX-ACCESS read-only
    STATUS current
    DESCRIPTION
        "The policy number of the traffic contract"
    ::= { bwmCurCfgContractTableEntry 4 }
 
bwmCurCfgContractPrec OBJECT-TYPE
    SYNTAX INTEGER (1..255)
    MAX-ACCESS read-only
    STATUS current
    DESCRIPTION
        "The precedence value of the traffic contract"
    ::= { bwmCurCfgContractTableEntry 5 }
 
bwmCurCfgContractUseTos OBJECT-TYPE
    SYNTAX INTEGER {
        enabled(2),
        disabled(3)
        }
    MAX-ACCESS read-only
    STATUS current
    DESCRIPTION
        "Enable/disable overwriting the IP Type Of Service (TOS) for this 
         traffic contract."
    ::= { bwmCurCfgContractTableEntry 6 }
 
bwmCurCfgContractHistory OBJECT-TYPE
    SYNTAX INTEGER {
        enabled(2),
        disabled(3)
        }
    MAX-ACCESS read-only
    STATUS current
    DESCRIPTION
        "Enable/disable saving statistics for this contract on the TFTP 
         server."
    ::= { bwmCurCfgContractTableEntry 7 }
 
bwmCurCfgContractShaping OBJECT-TYPE
    SYNTAX INTEGER {
        enabled(1),
        disabled(2)
        }
    MAX-ACCESS read-only
    STATUS current
    DESCRIPTION
        "Enable/disable traffic shaping for this contract."
    ::= { bwmCurCfgContractTableEntry 8 }

bwmCurCfgContractResizeTcp OBJECT-TYPE
    SYNTAX INTEGER {
        enabled(2),
        disabled(3)
        }
    MAX-ACCESS read-only
    STATUS current
    DESCRIPTION
        "Enable/disable overwriting the TCP window size for this 
         traffic contract."
    ::= { bwmCurCfgContractTableEntry 9 }
 
bwmCurCfgContractIpLimit OBJECT-TYPE
    SYNTAX INTEGER {
        enabled(2),
        disabled(3)
        }
    MAX-ACCESS read-only
    STATUS current
    DESCRIPTION
        "Enable/disable per user rate limiting based on IP address
         for this traffic contract."
    ::= { bwmCurCfgContractTableEntry 10 }
 
bwmCurCfgContractIpType OBJECT-TYPE
    SYNTAX INTEGER {
	sip(1),
	dip(2)
	}
    MAX-ACCESS read-only
    STATUS current
    DESCRIPTION
        "Per user rate limiting done based on source/destination
	 IP address."
    ::= { bwmCurCfgContractTableEntry 11 }
 
bwmCurCfgContractMonitorMode OBJECT-TYPE
    SYNTAX INTEGER {
        enabled(1),
        disabled(2)
        }
    MAX-ACCESS read-only
    STATUS current
    DESCRIPTION
        "Enable/disable monitor-only mode for this contract."
    ::= { bwmCurCfgContractTableEntry 12 }

bwmCurCfgContractGroup OBJECT-TYPE
    SYNTAX Integer32
    MAX-ACCESS read-only
    STATUS current
    DESCRIPTION
        "The group number of the contract (zero if not part of a group)"
    ::= { bwmCurCfgContractTableEntry 13 }

bwmCurCfgContractMaxSess OBJECT-TYPE
    SYNTAX INTEGER(0..65534) 
    MAX-ACCESS read-only 
    STATUS current
    DESCRIPTION
        "Maximum number of sessions per user or contract."
    ::= { bwmCurCfgContractTableEntry 15 }

bwmCurCfgContractRowType OBJECT-TYPE
    SYNTAX INTEGER {
        regular(1),
        reserved(2)
        }
    MAX-ACCESS read-only
    STATUS current
    DESCRIPTION
        "The Row Type: Regular or Reserved"
    ::= { bwmCurCfgContractTableEntry 16 }

bwmCurCfgContractOperMode OBJECT-TYPE
    SYNTAX INTEGER {
        ratelimiting(1),
        shaping(2),
        monitor(3)
        }
    MAX-ACCESS read-only
    STATUS current
    DESCRIPTION
        "Operation mode of a contract."
    ::= { bwmCurCfgContractTableEntry 17 }
 

bwmCurCfgContractAlarmsPerSec OBJECT-TYPE
    SYNTAX INTEGER (0..1000) 
    MAX-ACCESS read-only
    STATUS current
    DESCRIPTION
        "The amount of Contract alarms can be send per second." 
    ::= { bwmCurCfgContractTableEntry 18 }

bwmCurCfgContractPrefixLength OBJECT-TYPE
    SYNTAX INTEGER (0..127) 
    MAX-ACCESS read-only
    STATUS current
    DESCRIPTION
        "Prefix len to use 0 - use user limit !=0 use prefix." 
    ::= { bwmCurCfgContractTableEntry 19 }



bwmNewCfgContractTable OBJECT-TYPE
    SYNTAX SEQUENCE OF BwmContractNewCfgTableEntry
    MAX-ACCESS not-accessible
    STATUS current
    DESCRIPTION
        "The table of BWM traffic contract configuration."
    ::= { bwmContractConfig 3 }
 
bwmNewCfgContractTableEntry OBJECT-TYPE
    SYNTAX BwmContractNewCfgTableEntry
    MAX-ACCESS not-accessible
    STATUS current
    DESCRIPTION
        "A row in the BWM traffic contract configuration table."
    INDEX { bwmNewCfgContractIndx }
    ::= { bwmNewCfgContractTable 1 }
 
BwmContractNewCfgTableEntry ::= SEQUENCE {
    bwmNewCfgContractIndx        Integer32,
    bwmNewCfgContractName        DisplayString,
    bwmNewCfgContractState       INTEGER,
    bwmNewCfgContractPolicy      Integer32,
    bwmNewCfgContractDelete      INTEGER,
    bwmNewCfgContractPrec	 INTEGER,
    bwmNewCfgContractUseTos      INTEGER,
    bwmNewCfgContractHistory     INTEGER,
    bwmNewCfgContractShaping     INTEGER,
    bwmNewCfgContractResizeTcp   INTEGER,
    bwmNewCfgContractIpLimit     INTEGER,
    bwmNewCfgContractIpType      INTEGER,
    bwmNewCfgContractMonitorMode INTEGER,
    bwmNewCfgContractMaxSess     INTEGER,
    bwmNewCfgContractGroup       Integer32,
    bwmNewCfgContractRowType     INTEGER,
    bwmNewCfgContractOperMode    INTEGER,
    bwmNewCfgContractAlarmsPerSec INTEGER,
    bwmNewCfgContractPrefixLength INTEGER
    }
 
bwmNewCfgContractIndx OBJECT-TYPE
    SYNTAX Integer32
    MAX-ACCESS read-only
    STATUS current
    DESCRIPTION
        "The index of the row in BWM traffic contract configuration table."
    ::= { bwmNewCfgContractTableEntry 1 }

bwmNewCfgContractName   OBJECT-TYPE
    SYNTAX DisplayString (SIZE(0..31))
    MAX-ACCESS read-create
    STATUS current
    DESCRIPTION
        "The traffic contract name."
    ::= { bwmNewCfgContractTableEntry 2 }
 
bwmNewCfgContractState OBJECT-TYPE
    SYNTAX INTEGER {
        enabled(2),
        disabled(3)
        }
    MAX-ACCESS read-create
    STATUS current
    DESCRIPTION
        "This is the state of the traffic contract."
    ::= { bwmNewCfgContractTableEntry 3 }
 
bwmNewCfgContractPolicy OBJECT-TYPE
    SYNTAX Integer32
    MAX-ACCESS read-create
    STATUS current
    DESCRIPTION
        "This is policy number of the traffic contract"
    ::= { bwmNewCfgContractTableEntry 4 }
 
bwmNewCfgContractDelete OBJECT-TYPE
    SYNTAX INTEGER  {
        other(1),
        delete(2)
        }
    MAX-ACCESS read-create
    STATUS current
    DESCRIPTION
        "When set to the value of 2 (delete), the entire row
         is deleted. When read, other(1) is returned. Setting the value
         to anything other than 2(delete) has no effect on the state
         of the row."
    ::= { bwmNewCfgContractTableEntry 5 }
 
bwmNewCfgContractPrec OBJECT-TYPE
    SYNTAX INTEGER (1..255)
    MAX-ACCESS read-create
    STATUS current
    DESCRIPTION
        "The precedence value of the traffic contract"
    ::= { bwmNewCfgContractTableEntry 6 }
 
bwmNewCfgContractUseTos OBJECT-TYPE
    SYNTAX INTEGER {
        enabled(2),
        disabled(3)
        }
    MAX-ACCESS read-create
    STATUS current
    DESCRIPTION
        "Enable/disable overwriting the IP Type Of Service (TOS) for this 
         traffic contract."
    ::= { bwmNewCfgContractTableEntry 7 }
 
bwmNewCfgContractHistory OBJECT-TYPE
    SYNTAX INTEGER {
        enabled(2),
        disabled(3)
    }
    MAX-ACCESS read-create
    STATUS current
    DESCRIPTION
        "Enable/disable saving statistics for this contract on the TFTP 
         server."
    ::= { bwmNewCfgContractTableEntry 8 }
 
bwmNewCfgContractShaping OBJECT-TYPE
    SYNTAX INTEGER {
        enabled(1),
        disabled(2)
        }
    MAX-ACCESS read-create
    STATUS current
    DESCRIPTION
        "Enable/disable traffic shaping for this contract."
    ::= { bwmNewCfgContractTableEntry 9 }

bwmNewCfgContractResizeTcp OBJECT-TYPE
    SYNTAX INTEGER {
        enabled(2),
        disabled(3)
        }
    MAX-ACCESS read-create
    STATUS current
    DESCRIPTION
        "Enable/disable overwriting the TCP window size for this 
         traffic contract."
    ::= { bwmNewCfgContractTableEntry 10 }
 
bwmNewCfgContractIpLimit OBJECT-TYPE
    SYNTAX INTEGER {
        enabled(2),
        disabled(3)
        }
    MAX-ACCESS read-create
    STATUS current
    DESCRIPTION
        "Enable/disable per user rate limiting based on IP address
         for this traffic contract."
    ::= { bwmNewCfgContractTableEntry 11 }
 
bwmNewCfgContractIpType OBJECT-TYPE
    SYNTAX INTEGER {
	sip(1),
	dip(2)
	}
    MAX-ACCESS read-create
    STATUS current
    DESCRIPTION
        "Per user rate limiting done based on source/destination
	 IP address."
    ::= { bwmNewCfgContractTableEntry 12 }
 
bwmNewCfgContractMonitorMode OBJECT-TYPE
    SYNTAX INTEGER {
        enabled(1),
        disabled(2)
        }
    MAX-ACCESS read-create
    STATUS current
    DESCRIPTION
        "Enable/disable monitor-only mode for this contract."
    ::= { bwmNewCfgContractTableEntry 13 }

bwmNewCfgContractGroup OBJECT-TYPE
    SYNTAX Integer32
    MAX-ACCESS read-only
    STATUS current
    DESCRIPTION
        "The group number of the contract (zero if not part of a group)"
    ::= { bwmNewCfgContractTableEntry 14 }

bwmNewCfgContractMaxSess OBJECT-TYPE
    SYNTAX INTEGER(0..65534)
    MAX-ACCESS read-create
    STATUS current
    DESCRIPTION
        "Maximum number of sessions per user or contract."
    ::= { bwmNewCfgContractTableEntry 16 }

bwmNewCfgContractRowType OBJECT-TYPE
    SYNTAX INTEGER {
        regular(1),
        reserved(2)
        }
    MAX-ACCESS read-only
    STATUS current
    DESCRIPTION
        "The Row Type: Regular or Reserved"
    ::= { bwmNewCfgContractTableEntry 17 }

bwmNewCfgContractOperMode OBJECT-TYPE
    SYNTAX INTEGER {
        ratelimiting(1),
        shaping(2),
        monitor(3)
        }
    MAX-ACCESS read-create
    STATUS current
    DESCRIPTION
        "Operation mode of a contract."
    ::= { bwmNewCfgContractTableEntry 18 }
 

bwmNewCfgContractAlarmsPerSec OBJECT-TYPE
    SYNTAX INTEGER (0..1000) 
    MAX-ACCESS read-create
    STATUS current
    DESCRIPTION
        "The amount of Contract alarms can be send per second." 
    ::= { bwmNewCfgContractTableEntry 19 }

bwmNewCfgContractPrefixLength OBJECT-TYPE
    SYNTAX INTEGER (0..127) 
    MAX-ACCESS read-create
    STATUS current
    DESCRIPTION
        "Prefix len to use 0 - use user limit !=0 use prefix." 
    ::= { bwmNewCfgContractTableEntry 20 }



bwmAvailableContractsTable OBJECT-TYPE
    SYNTAX SEQUENCE OF BwmAvailableContractsTableEntry
    MAX-ACCESS not-accessible
    STATUS current
    DESCRIPTION
        "The table of BWM traffic contracts that are available and 
         can be added to BWM contract Group."
    ::= { bwmContractConfig 4 }

bwmAvailableContractsTableEntry OBJECT-TYPE
    SYNTAX BwmAvailableContractsTableEntry
    MAX-ACCESS not-accessible
    STATUS current
    DESCRIPTION
        "A row in the BWM traffic contract configuration table."
    INDEX { bwmContractIndx }
    ::= { bwmAvailableContractsTable 1 }

BwmAvailableContractsTableEntry ::= SEQUENCE {
    bwmContractIndx        Integer32,
    bwmContractName        DisplayString
}

bwmContractIndx OBJECT-TYPE
    SYNTAX Integer32
    MAX-ACCESS read-only
    STATUS current
    DESCRIPTION
        "The index of the row in the available BWM traffic contract table."
    ::= { bwmAvailableContractsTableEntry 1 }

bwmContractName   OBJECT-TYPE
    SYNTAX DisplayString (SIZE(0..31))
    MAX-ACCESS read-only
    STATUS current
    DESCRIPTION
        "The traffic contract name."
    ::= { bwmAvailableContractsTableEntry 2 }

-- BWM Contract Time Policy Config Table
 
bwmContTimePolicyTableMaxEnt OBJECT-TYPE
    SYNTAX Integer32
    MAX-ACCESS read-only
    STATUS current
    DESCRIPTION
        "The maximum number of rows in the BWM contract configuration table."
    ::= { bwmContTimePolicyConfig 1 }
 
bwmCurCfgContTimePolicyTable OBJECT-TYPE
    SYNTAX SEQUENCE OF BwmCurCfgContTimePolicyTableEntry
    MAX-ACCESS not-accessible
    STATUS current
    DESCRIPTION
        "The table of BWM traffic contract time policy configuration."
    ::= { bwmContTimePolicyConfig 2 }
 
bwmCurCfgContTimePolicyTableEntry OBJECT-TYPE
    SYNTAX BwmCurCfgContTimePolicyTableEntry
    MAX-ACCESS not-accessible
    STATUS current
    DESCRIPTION
        "A row in the BWM contract time policy configuration table."
    INDEX   { bwmCurCfgContTimePolicyContIndx, bwmCurCfgContTimePolicyIndx }
    ::= { bwmCurCfgContTimePolicyTable 1 }
 
BwmCurCfgContTimePolicyTableEntry ::= SEQUENCE {
    bwmCurCfgContTimePolicyContIndx   Integer32,
    bwmCurCfgContTimePolicyIndx       Integer32,
    bwmCurCfgContTimePolicyDay        INTEGER,
    bwmCurCfgContTimePolicyFrom       INTEGER,
    bwmCurCfgContTimePolicyTo         INTEGER,
    bwmCurCfgContTimePolicyPol        Integer32,
    bwmCurCfgContTimePolicyState      INTEGER
    }
 
bwmCurCfgContTimePolicyContIndx OBJECT-TYPE
    SYNTAX Integer32
    MAX-ACCESS read-only
    STATUS current
    DESCRIPTION
        "The BWM contract number of the contract time policy."
    ::= { bwmCurCfgContTimePolicyTableEntry 1 }
 
bwmCurCfgContTimePolicyIndx OBJECT-TYPE
    SYNTAX Integer32
    MAX-ACCESS read-only
    STATUS current
    DESCRIPTION
        "The BWM time policy number of the contract time policy."
    ::= { bwmCurCfgContTimePolicyTableEntry 2 }
 
bwmCurCfgContTimePolicyDay OBJECT-TYPE
    SYNTAX INTEGER {
        sunday(1),
        monday(2),
        tuesday(3),
        wednesday(4),
        thursday(5),
        friday(6),
        saturday(7),
        weekday(8),
        weekend(9),
        everyday(10)
        }
    MAX-ACCESS read-only
    STATUS current
    DESCRIPTION
        "The BWM time policy day."
    ::= { bwmCurCfgContTimePolicyTableEntry 3 }
 
bwmCurCfgContTimePolicyFrom OBJECT-TYPE
    SYNTAX INTEGER (0..24)
    MAX-ACCESS read-only
    STATUS current
    DESCRIPTION
        "The BWM time policy starting time in hours"
    ::= { bwmCurCfgContTimePolicyTableEntry 4 }
 
bwmCurCfgContTimePolicyTo OBJECT-TYPE
    SYNTAX INTEGER (0..24)
    MAX-ACCESS read-only
    STATUS current
    DESCRIPTION
        "The BWM time policy ending time in hours"
    ::= { bwmCurCfgContTimePolicyTableEntry 5 }
 
bwmCurCfgContTimePolicyPol OBJECT-TYPE
    SYNTAX Integer32
    MAX-ACCESS read-only
    STATUS current
    DESCRIPTION
        "The policy number of the traffic contract time policy"
    ::= { bwmCurCfgContTimePolicyTableEntry 6 }
 
bwmCurCfgContTimePolicyState OBJECT-TYPE
    SYNTAX INTEGER {
        enabled(1),
        disabled(2)
        }
    MAX-ACCESS read-only
    STATUS current
    DESCRIPTION
        "The state of the contract time policy."
    ::= { bwmCurCfgContTimePolicyTableEntry 7 }
 
bwmNewCfgContTimePolicyTable OBJECT-TYPE
    SYNTAX SEQUENCE OF BwmNewCfgContTimePolicyTableEntry
    MAX-ACCESS not-accessible
    STATUS current
    DESCRIPTION
        "The table of BWM traffic contract time policy configuration."
    ::= { bwmContTimePolicyConfig 3 }
 
bwmNewCfgContTimePolicyTableEntry OBJECT-TYPE
    SYNTAX BwmNewCfgContTimePolicyTableEntry
    MAX-ACCESS not-accessible
    STATUS current
    DESCRIPTION
        "A row in the BWM contract time policy configuration table."
    INDEX   { bwmNewCfgContTimePolicyContIndx, bwmNewCfgContTimePolicyIndx }
    ::= { bwmNewCfgContTimePolicyTable 1 }
 
BwmNewCfgContTimePolicyTableEntry ::= SEQUENCE {
    bwmNewCfgContTimePolicyContIndx   Integer32,
    bwmNewCfgContTimePolicyIndx       Integer32,
    bwmNewCfgContTimePolicyDay        INTEGER,
    bwmNewCfgContTimePolicyFrom       INTEGER,
    bwmNewCfgContTimePolicyTo         INTEGER,
    bwmNewCfgContTimePolicyPol        Integer32,
    bwmNewCfgContTimePolicyState      INTEGER,
    bwmNewCfgContTimePolicyDelete     INTEGER
    }
 
bwmNewCfgContTimePolicyContIndx OBJECT-TYPE
    SYNTAX Integer32
    MAX-ACCESS read-only
    STATUS current
    DESCRIPTION
        "The BWM contract number of the contract time policy."
    ::= { bwmNewCfgContTimePolicyTableEntry 1 }
 
bwmNewCfgContTimePolicyIndx OBJECT-TYPE
    SYNTAX Integer32
    MAX-ACCESS read-only
    STATUS current
    DESCRIPTION
        "The BWM time policy number of the contract time policy."
    ::= { bwmNewCfgContTimePolicyTableEntry 2 }
 
bwmNewCfgContTimePolicyDay OBJECT-TYPE
    SYNTAX INTEGER {
        sunday(1),
        monday(2),
        tuesday(3),
        wednesday(4),
        thursday(5),
        friday(6),
        saturday(7),
        weekday(8),
        weekend(9),
        everyday(10)
        }
    MAX-ACCESS read-create
    STATUS current
    DESCRIPTION
        "The BWM time policy day."
    ::= { bwmNewCfgContTimePolicyTableEntry 3 }
 
bwmNewCfgContTimePolicyFrom OBJECT-TYPE
    SYNTAX INTEGER (0..24)
    MAX-ACCESS read-create
    STATUS current
    DESCRIPTION
        "The BWM time policy starting time in hours"
    ::= { bwmNewCfgContTimePolicyTableEntry 4 }
 
bwmNewCfgContTimePolicyTo OBJECT-TYPE
    SYNTAX INTEGER (0..24)
    MAX-ACCESS read-create
    STATUS current
    DESCRIPTION
        "The BWM time policy ending time in hours"
    ::= { bwmNewCfgContTimePolicyTableEntry 5 }
 
bwmNewCfgContTimePolicyPol OBJECT-TYPE
    SYNTAX Integer32
    MAX-ACCESS read-create
    STATUS current
    DESCRIPTION
        "The policy number of the traffic contract time policy"
    ::= { bwmNewCfgContTimePolicyTableEntry 6 }
 
bwmNewCfgContTimePolicyState OBJECT-TYPE
    SYNTAX INTEGER {
        enabled(1),
        disabled(2)
        }
    MAX-ACCESS read-create
    STATUS current
    DESCRIPTION
        "The state of the contract time policy."
    ::= { bwmNewCfgContTimePolicyTableEntry 7 }
 
bwmNewCfgContTimePolicyDelete OBJECT-TYPE
    SYNTAX INTEGER  {
        other(1),
        delete(2)
        }
    MAX-ACCESS read-create
    STATUS current
    DESCRIPTION
        "When set to the value of 2 (delete), the entire row
         is deleted. When read, other(1) is returned. Setting the value
         to anything other than 2(delete) has no effect on the state
         of the row."
    ::= { bwmNewCfgContTimePolicyTableEntry 8 }
 
-- BWM Contract Group Config Table

bwmContractGroupTableMaxEnt OBJECT-TYPE
    SYNTAX Integer32
    MAX-ACCESS read-only
    STATUS current
    DESCRIPTION
        "The maximum number of rows in BWM contract group configuration table."
    ::= { bwmContractGroupConfig 1 }
 
bwmCurCfgContractGroupTable OBJECT-TYPE
    SYNTAX SEQUENCE OF BwmCurCfgContractGroupTableEntry
    MAX-ACCESS not-accessible
    STATUS current
    DESCRIPTION
        "The table of BWM traffic contract group configuration."
    ::= { bwmContractGroupConfig 2 }
 
bwmCurCfgContractGroupTableEntry OBJECT-TYPE
    SYNTAX BwmCurCfgContractGroupTableEntry
    MAX-ACCESS not-accessible
    STATUS current
    DESCRIPTION
        "A row in the BWM contract group configuration table."
    INDEX   { bwmCurCfgContractGroupIndx }
    ::= { bwmCurCfgContractGroupTable 1 }
 
BwmCurCfgContractGroupTableEntry ::= SEQUENCE {
    bwmCurCfgContractGroupIndx       Integer32,
    bwmCurCfgContractGroupContracts  OCTET STRING,
    bwmCurCfgContractGroupName       DisplayString
    }
 
bwmCurCfgContractGroupIndx OBJECT-TYPE
    SYNTAX Integer32
    MAX-ACCESS read-only
    STATUS current
    DESCRIPTION
        "The BWM contract group number."
    ::= { bwmCurCfgContractGroupTableEntry 1 }
 
bwmCurCfgContractGroupContracts OBJECT-TYPE
    SYNTAX OCTET STRING
    MAX-ACCESS read-only
    STATUS current
    DESCRIPTION
        "The BWM contracts in the group.  The contracts are presented
         in bitmap format.

         in receiving order:

             OCTET 1  OCTET 2  .....
             xxxxxxxx xxxxxxxx ..... 
             |     || |_ contract 9
             |     ||  
             |     ||___ contract 8
             |     |____ contract 7
             |       .    .   .
             |__________ contract 1
 
         where x : 1 - The represented contract belongs to the group
                   0 - The represented contract does not belong to the group"
    ::= { bwmCurCfgContractGroupTableEntry 2 }
 
bwmCurCfgContractGroupName   OBJECT-TYPE
    SYNTAX DisplayString (SIZE(0..31))
    MAX-ACCESS read-only
    STATUS current
    DESCRIPTION
        "The traffic contract group name."
    ::= { bwmCurCfgContractGroupTableEntry 3 }
 
bwmNewCfgContractGroupTable OBJECT-TYPE
    SYNTAX SEQUENCE OF BwmNewCfgContractGroupTableEntry
    MAX-ACCESS not-accessible
    STATUS current
    DESCRIPTION
        "The table of BWM traffic contract group configuration."
    ::= { bwmContractGroupConfig 3 }
 
bwmNewCfgContractGroupTableEntry OBJECT-TYPE
    SYNTAX BwmNewCfgContractGroupTableEntry
    MAX-ACCESS not-accessible
    STATUS current
    DESCRIPTION
        "A row in the BWM contract group configuration table."
    INDEX   { bwmNewCfgContractGroupIndx }
    ::= { bwmNewCfgContractGroupTable 1 }
 
BwmNewCfgContractGroupTableEntry ::= SEQUENCE {
    bwmNewCfgContractGroupIndx       Integer32,
    bwmNewCfgContractGroupContracts  OCTET STRING,
    bwmNewCfgContractGroupAddCont    Integer32,
    bwmNewCfgContractGroupRemCont    Integer32,
    bwmNewCfgContractGroupDelete     INTEGER,
    bwmNewCfgContractGroupName       DisplayString
    }
 
bwmNewCfgContractGroupIndx OBJECT-TYPE
    SYNTAX Integer32
    MAX-ACCESS read-only
    STATUS current
    DESCRIPTION
        "The BWM contract group number."
    ::= { bwmNewCfgContractGroupTableEntry 1 }
 
bwmNewCfgContractGroupContracts OBJECT-TYPE
    SYNTAX OCTET STRING
    MAX-ACCESS read-only
    STATUS current
    DESCRIPTION
        "The BWM contracts in the group.  The contracts are presented
         in bitmap format.

         in receiving order:

             OCTET 1  OCTET 2  .....
             xxxxxxxx xxxxxxxx ..... 
             |     || |_ contract 9
             |     ||  
             |     ||___ contract 8
             |     |____ contract 7
             |       .    .   .
             |__________ contract 1
 
         where x : 1 - The represented contract belongs to the group
                   0 - The represented contract does not belong to the group"
    ::= { bwmNewCfgContractGroupTableEntry 2 }
 
bwmNewCfgContractGroupAddCont OBJECT-TYPE
    SYNTAX Integer32
    MAX-ACCESS read-create
    STATUS current
    DESCRIPTION
        "The BWM contract to be added to the group. A zero value
         is returned when read."
    ::= { bwmNewCfgContractGroupTableEntry 3 }
 
bwmNewCfgContractGroupRemCont OBJECT-TYPE
    SYNTAX Integer32
    MAX-ACCESS read-create
    STATUS current
    DESCRIPTION
        "The BWM contract to be removed from the group. A zero value
         is returned when read."
    ::= { bwmNewCfgContractGroupTableEntry 4 }
 

bwmNewCfgContractGroupDelete OBJECT-TYPE
    SYNTAX INTEGER  {
        other(1),
        delete(2)
        }
    MAX-ACCESS read-create
    STATUS current
    DESCRIPTION
        "When set to the value of 2 (delete), the entire row
         is deleted. When read, other(1) is returned. Setting the value
         to anything other than 2(delete) has no effect on the state
         of the row."
    ::= { bwmNewCfgContractGroupTableEntry 5 } 

bwmNewCfgContractGroupName   OBJECT-TYPE
    SYNTAX DisplayString (SIZE(0..31))
    MAX-ACCESS read-create
    STATUS current
    DESCRIPTION
        "The traffic contract group name."
    ::= { bwmNewCfgContractGroupTableEntry 6 }
 
bwmContractGroupTableMaxCont OBJECT-TYPE
    SYNTAX Integer32
    MAX-ACCESS read-only
    STATUS current
    DESCRIPTION
        "The maximum number of contracts in any BWM contract group."
    ::= { bwmContractGroupConfig 4 }

-- Statistics

-- BWM Traffic Contract Statistics Table
 
bwmStatTcTable  OBJECT-TYPE
    SYNTAX SEQUENCE OF BwmStatTcEntry
    MAX-ACCESS not-accessible
    STATUS current
    DESCRIPTION
        "The table of Bandwidth Management Traffic Contract statistics." 
    ::= { bwmStats 1 }
 
bwmStatTcEntry OBJECT-TYPE
    SYNTAX BwmStatTcEntry
    MAX-ACCESS not-accessible
    STATUS current
    DESCRIPTION
        "A row in the BWM traffic contract table."
    INDEX { bwmStatTcContractIndex }
    ::= { bwmStatTcTable 1 }

BwmStatTcEntry ::= SEQUENCE {
    bwmStatTcContractIndex     Integer32,
    bwmStatTcName              DisplayString,
    bwmStatTcOutoct            Counter32,
    bwmStatTcOutdisoct         Counter32,
    bwmStatTcBufferUsed        Integer32,
    bwmStatTcTotalPackets      Counter32,
    bwmStatTcSessRejected      Counter32,
    bwmStatTcBufferMax         Counter32 
    }
 
bwmStatTcContractIndex OBJECT-TYPE
    SYNTAX Integer32
    MAX-ACCESS read-only
    STATUS current
    DESCRIPTION
        "The contract queue number for which the statistics apply."
    ::= { bwmStatTcEntry 1 }
 
bwmStatTcName OBJECT-TYPE
    SYNTAX DisplayString (SIZE(0..32))
    MAX-ACCESS read-only
    STATUS current
    DESCRIPTION
        "The name of the traffic contract queue."
    ::= { bwmStatTcEntry 2 }
 
bwmStatTcOutoct OBJECT-TYPE
    SYNTAX Counter32
    MAX-ACCESS read-only
    STATUS current
    DESCRIPTION
        "The total number of octets sent out from the traffic contract queue."
    ::= { bwmStatTcEntry 3 }
 
bwmStatTcOutdisoct OBJECT-TYPE
    SYNTAX Counter32
    MAX-ACCESS read-only
    STATUS current
    DESCRIPTION
        "The total number of octets dropped from the traffic contract queue."
    ::= { bwmStatTcEntry 4 }
 
bwmStatTcBufferUsed OBJECT-TYPE
    SYNTAX Integer32
    MAX-ACCESS read-only
    STATUS current
    DESCRIPTION
        "The total number of buffers used by the traffic contract queue."
    ::= { bwmStatTcEntry 5 }
 
bwmStatTcBufferMax OBJECT-TYPE
    SYNTAX Counter32
    MAX-ACCESS read-only
    STATUS current
    DESCRIPTION
        "The total number of buffers assigned to the traffic contract queue."
    ::= { bwmStatTcEntry 6 }

bwmStatTcTotalPackets OBJECT-TYPE
    SYNTAX Counter32
    MAX-ACCESS read-only
    STATUS current
    DESCRIPTION
        "The total number of packets for a particular contract."
    ::= { bwmStatTcEntry 7 }
 
bwmStatTcSessRejected OBJECT-TYPE
    SYNTAX Counter32
    MAX-ACCESS read-only
    STATUS current
    DESCRIPTION
        "The total number of sessions rejected for a particular contract."
    ::= { bwmStatTcEntry 8 }


-- BWM Traffic Contract Rate Statistics Table
 
bwmStatTcrTable  OBJECT-TYPE
    SYNTAX SEQUENCE OF BwmStatTcrEntry
    MAX-ACCESS not-accessible
    STATUS current
    DESCRIPTION
        "The table of Bandwidth Management Traffic Contract Rate statistics."
    ::= { bwmStats 2 }
 
bwmStatTcrEntry OBJECT-TYPE
    SYNTAX BwmStatTcrEntry
    MAX-ACCESS not-accessible
    STATUS current
    DESCRIPTION
        "A row in the BWM traffic contract rate table."
    INDEX { bwmStatTcrContractIndex }
    ::= { bwmStatTcrTable 1 }
 
BwmStatTcrEntry ::= SEQUENCE {
    bwmStatTcrContractIndex     Integer32,
    bwmStatTcrName              DisplayString,
    bwmStatTcrRate              Integer32,
    bwmStatTcrOutoct            Counter32,
    bwmStatTcrOutdisoct         Counter32,
    bwmStatTcrBufferUsed        Integer32,
    bwmStatTcrTotalPackets      Counter32,
    bwmStatTcrBufferMax         Counter32
    }
 
bwmStatTcrContractIndex OBJECT-TYPE
    SYNTAX Integer32
    MAX-ACCESS read-only
    STATUS current
    DESCRIPTION
        "The contract queue number for which the statistics apply."
    ::= { bwmStatTcrEntry 1 }
 
bwmStatTcrName OBJECT-TYPE
    SYNTAX DisplayString (SIZE(0..32))
    MAX-ACCESS read-only
    STATUS current
    DESCRIPTION
        "The name of the traffic contract queue."
    ::= { bwmStatTcrEntry 2 }
 
bwmStatTcrRate OBJECT-TYPE
    SYNTAX Integer32
    MAX-ACCESS read-only
    STATUS current
    DESCRIPTION
        "The rate of octets sent out from the traffic contract queue."
    ::= { bwmStatTcrEntry 3 }
 
bwmStatTcrOutoct OBJECT-TYPE
    SYNTAX Counter32
    MAX-ACCESS read-only
    STATUS current
    DESCRIPTION
        "The of octets sent out from the traffic contract queue."
    ::= { bwmStatTcrEntry 4 }
 
bwmStatTcrOutdisoct OBJECT-TYPE
    SYNTAX Counter32
    MAX-ACCESS read-only
    STATUS current
    DESCRIPTION
        "The total number of octets dropped from the traffic contract queue."
    ::= { bwmStatTcrEntry 5 }

bwmStatTcrBufferUsed OBJECT-TYPE
    SYNTAX Integer32
    MAX-ACCESS read-only
    STATUS current
    DESCRIPTION
        "The total number of buffers used by the traffic contract queue."
    ::= { bwmStatTcrEntry 6 }
 
bwmStatTcrBufferMax OBJECT-TYPE
    SYNTAX Counter32
    MAX-ACCESS read-only
    STATUS current
    DESCRIPTION
        "The total number of buffers assigned to the traffic contract queue."
    ::= { bwmStatTcrEntry 7 }

bwmStatTcrTotalPackets OBJECT-TYPE
    SYNTAX Counter32
    MAX-ACCESS read-only
    STATUS current
    DESCRIPTION
        "The total number of packets for a particular contract."
    ::= { bwmStatTcrEntry 8 }

-- BWM Switch Port Traffic Contract Statistics Table
 
bwmStatPortTcTable  OBJECT-TYPE
    SYNTAX SEQUENCE OF BwmStatPortTcEntry
    MAX-ACCESS not-accessible
    STATUS current
    DESCRIPTION
        "The table of BWM Switch Port Traffic Contract statistics."
    ::= { bwmStats 3 }
 
bwmStatPortTcEntry OBJECT-TYPE
    SYNTAX BwmStatPortTcEntry
    MAX-ACCESS not-accessible
    STATUS current
    DESCRIPTION
         "A row in the BWM SP traffic contract table."
    INDEX   { bwmStatPortTcPortIndex, bwmStatPortTcContractIndex }
    ::= { bwmStatPortTcTable 1 }
 
BwmStatPortTcEntry ::= SEQUENCE {
    bwmStatPortTcPortIndex          Integer32,
    bwmStatPortTcContractIndex      Integer32,
    bwmStatPortTcName               DisplayString,
    bwmStatPortTcOutoct             Counter32,
    bwmStatPortTcOutdisoct          Counter32,
    bwmStatPortTcBufferUsed         Integer32,
    bwmStatPortTcTotalPackets       Counter32,
    bwmStatPortTcBufferMax          Counter32
    }
 
bwmStatPortTcPortIndex OBJECT-TYPE
    SYNTAX Integer32
    MAX-ACCESS read-only
    STATUS current
    DESCRIPTION
        "The Switch Port number for which the statistics apply."
    ::= { bwmStatPortTcEntry 1 }
 
bwmStatPortTcContractIndex OBJECT-TYPE
    SYNTAX Integer32
    MAX-ACCESS read-only
    STATUS current
    DESCRIPTION
        "The contract queue number for which the statistics apply."
    ::= { bwmStatPortTcEntry 2 }
 
bwmStatPortTcName OBJECT-TYPE
    SYNTAX DisplayString (SIZE(0..32))
    MAX-ACCESS read-only
    STATUS current
    DESCRIPTION
        "The name of the traffic contract queue."
    ::= { bwmStatPortTcEntry 3 }
 
bwmStatPortTcOutoct OBJECT-TYPE
    SYNTAX Counter32
    MAX-ACCESS read-only
    STATUS current
    DESCRIPTION
        "The total number of octets sent out from the traffic contract queue."
    ::= { bwmStatPortTcEntry 4 }
 
bwmStatPortTcOutdisoct OBJECT-TYPE
    SYNTAX Counter32
    MAX-ACCESS read-only
    STATUS current
    DESCRIPTION
        "The total number of octets dropped from the traffic contract queue."
    ::= { bwmStatPortTcEntry 5 }
 
bwmStatPortTcBufferUsed OBJECT-TYPE
    SYNTAX Integer32
    MAX-ACCESS read-only
    STATUS current
    DESCRIPTION
        "The total number of buffers used by the traffic contract queue."
    ::= { bwmStatPortTcEntry 6 }
 
bwmStatPortTcBufferMax OBJECT-TYPE
    SYNTAX Counter32
    MAX-ACCESS read-only
    STATUS current
    DESCRIPTION
        "The total number of buffers assigned to the traffic contract queue."
    ::= { bwmStatPortTcEntry 7 }

bwmStatPortTcTotalPackets OBJECT-TYPE
    SYNTAX Counter32
    MAX-ACCESS read-only
    STATUS current
    DESCRIPTION
        "The total number of packets for a particular contract."
    ::= { bwmStatPortTcEntry 8 }
 
-- BWM Switch Port Traffic Contract Rate Statistics Table
 
bwmStatPortTcrTable  OBJECT-TYPE
    SYNTAX SEQUENCE OF BwmStatPortTcrEntry
    MAX-ACCESS not-accessible
    STATUS current
    DESCRIPTION
        "The table of Bandwidth Management Switch Port Traffic Contract Rate 
         statistics."
    ::= { bwmStats 4 }
 
bwmStatPortTcrEntry OBJECT-TYPE
    SYNTAX BwmStatPortTcrEntry
    MAX-ACCESS not-accessible
    STATUS current
    DESCRIPTION
        "A row in the BWM traffic contract rate table."
    INDEX { bwmStatPortTcrPortIndex, bwmStatPortTcrContractIndex }
    ::= { bwmStatPortTcrTable 1 }
 
BwmStatPortTcrEntry ::= SEQUENCE {
    bwmStatPortTcrPortIndex          Integer32,
    bwmStatPortTcrContractIndex      Integer32,
    bwmStatPortTcrName               DisplayString,
    bwmStatPortTcrRate               Integer32,
    bwmStatPortTcrOutoct             Counter32,
    bwmStatPortTcrOutdisoct          Counter32,
    bwmStatPortTcrBufferUsed         Integer32,
    bwmStatPortTcrTotalPackets       Counter32,
    bwmStatPortTcrBufferMax          Counter32
    }
 
bwmStatPortTcrPortIndex OBJECT-TYPE
    SYNTAX Integer32
    MAX-ACCESS read-only
    STATUS current
    DESCRIPTION
        "The switch port number for which the statistics apply."
    ::= { bwmStatPortTcrEntry 1 }
 
bwmStatPortTcrContractIndex OBJECT-TYPE
    SYNTAX Integer32
    MAX-ACCESS read-only
    STATUS current
    DESCRIPTION
        "The contract queue number for which the statistics apply."
    ::= { bwmStatPortTcrEntry 2 }
 
bwmStatPortTcrName OBJECT-TYPE
    SYNTAX DisplayString (SIZE(0..32))
    MAX-ACCESS read-only
    STATUS current
    DESCRIPTION
        "The name of the traffic contract queue."
    ::= { bwmStatPortTcrEntry 3 }
 
bwmStatPortTcrRate OBJECT-TYPE
    SYNTAX Integer32
    MAX-ACCESS read-only
    STATUS current
    DESCRIPTION
        "The rate of octets sent out from the traffic contract queue."
    ::= { bwmStatPortTcrEntry 4 }
 
bwmStatPortTcrOutoct OBJECT-TYPE
    SYNTAX Counter32
    MAX-ACCESS read-only
    STATUS current
    DESCRIPTION
        "The of octets sent out from the traffic contract queue."
    ::= { bwmStatPortTcrEntry 5 }
 
bwmStatPortTcrOutdisoct OBJECT-TYPE
    SYNTAX Counter32
    MAX-ACCESS read-only
    STATUS current
    DESCRIPTION
        "The total number of octets dropped from the traffic contract queue."
    ::= { bwmStatPortTcrEntry 6 }
 
bwmStatPortTcrBufferUsed OBJECT-TYPE
    SYNTAX Integer32
    MAX-ACCESS read-only
    STATUS current
    DESCRIPTION
        "The total number of buffers used by the traffic contract queue."
    ::= { bwmStatPortTcrEntry 7 }
 
bwmStatPortTcrBufferMax OBJECT-TYPE
    SYNTAX Counter32
    MAX-ACCESS read-only
    STATUS current
    DESCRIPTION
        "The total number of buffers assigned to the traffic contract queue."
    ::= { bwmStatPortTcrEntry 8 }

bwmStatPortTcrTotalPackets OBJECT-TYPE
    SYNTAX Counter32
    MAX-ACCESS read-only
    STATUS current
    DESCRIPTION
        "The total number of packets for a particular contract."
    ::= { bwmStatPortTcrEntry 9 }

bwmStatsClear OBJECT-TYPE
    SYNTAX INTEGER {
	ok(1),
	clear(2)
	}
    MAX-ACCESS read-write
    STATUS current
    DESCRIPTION
        "This is an action object to clear the BWM statistics. 
         ok(1) is returned when read."
    ::= { bwmStats 5 }


-- Bandwidth Management - Operational Commands
  
bwmOperSendSMTP OBJECT-TYPE
    SYNTAX INTEGER {
	other(1),
	send(2)
	}
    MAX-ACCESS read-write
    STATUS current
    DESCRIPTION
        "This is an action object to send BWM history to SMTP server. 
         other(1) is returned when read."
    ::= { bwmOpers 1 }

bwmOperClearUsrEntry OBJECT-TYPE
    SYNTAX  INTEGER {
        ok(1),
        clear(2)
        }
    MAX-ACCESS  read-write
    STATUS  current
    DESCRIPTION
        "This is an action object to clear the BWM IP user entry table.
         When we set this to a value of clear(2) will clear the user entry table.
         ok(1) is returned when object is read."
    ::= { bwmOpers 2 }


END

-- COPYRIGHT NOTICE
-- Copyright (c) Radware Ltd. 2009
-- All rights reserved

ALTEON-CHEETAH-LAYER7-MIB DEFINITIONS ::= BEGIN

IMPORTS
    MODULE-IDENTITY, OBJECT-TYPE, Integer32, Counter32, Counter64, Gauge32, IpAddress 
        FROM SNMPv2-SMI
    DisplayString
        FROM SNMPv2-TC
    aws-switch 
        FROM ALTEON-ROOT-MIB;

layer7 MODULE-IDENTITY
    LAST-UPDATED "200908050000Z" --  05 August 2009
    ORGANIZATION "Radware Ltd."
    CONTACT-INFO "Lobby 1 (Visitors) and Lobby 2 (Deliveries)
                  575 Corporate Drive
                  Mahwah, NJ 07430
                  support@radware.com"
    DESCRIPTION
        "The MIB module for the Alteon OS layer 7 features."
    REVISION  "200908050000Z" --  05 August 2009
    DESCRIPTION
        "Added revision clause for SMIv2 compliance."
    ::= { aws-switch 5 }

layer7Configs     OBJECT IDENTIFIER ::= { layer7 1 }
layer7Stats       OBJECT IDENTIFIER ::= { layer7 2 }
layer7Info        OBJECT IDENTIFIER ::= { layer7 3 }
layer7Oper        OBJECT IDENTIFIER ::= { layer7 4 }

urlCfg	          OBJECT IDENTIFIER ::= { layer7Configs 1 }
layer7GeneralCfg  OBJECT IDENTIFIER ::= { layer7Configs 2 }
sdpCfg            OBJECT IDENTIFIER ::= { layer7Configs 3 }
httpModCfg        OBJECT IDENTIFIER ::= { layer7Configs 4 }
ruleCfg           OBJECT IDENTIFIER ::= { layer7Configs 5 }
contentClass      OBJECT IDENTIFIER ::= { layer7Configs 6 }
urlFiltering      OBJECT IDENTIFIER ::= { layer7Configs 7 }

slbUrlRedir       OBJECT IDENTIFIER ::= { urlCfg 1 }
slbUrlBalance     OBJECT IDENTIFIER ::= { urlCfg 2 }
slbUrlHttpMethods OBJECT IDENTIFIER ::= { urlCfg 3 }

urlStats          OBJECT IDENTIFIER ::= { layer7Stats  1 }
connPoolingStats  OBJECT IDENTIFIER ::= { layer7Stats 2 }

slbParsing        OBJECT IDENTIFIER ::= { layer7Info 1 }

-- Layer 7 Configuration 

-- SLB URL Redirection Group
slbCurCfgUrlRedirNonGetOrigSrv OBJECT-TYPE
    SYNTAX  INTEGER {
        enabled(1),
        disabled(2)
        }
    MAX-ACCESS  read-only
    STATUS  current
    DESCRIPTION
	"This is for controlling if the switch should redirect packet 
         to the origin server when HTTP non-GETs are detected.  

         enabled(1) - Allow redirect traffic to the origin server
         disabled(2)- redirect to a group of servers (cache server)"
    ::= { slbUrlRedir 3 }

slbNewCfgUrlRedirNonGetOrigSrv OBJECT-TYPE
    SYNTAX  INTEGER {
        enabled(1),
        disabled(2)
        }
    MAX-ACCESS  read-write
    STATUS  current
    DESCRIPTION
        "This is for controlling if the switch should redirect packet to 
         the origin server when HTTP non-GETs are detected.  

         enabled(1) - Allow redirect traffic to the origin server
         disabled(2)- redirect to a group of servers (cache server)"
    ::= { slbUrlRedir 4 }

slbCurCfgUrlRedirCookieOrigSrv OBJECT-TYPE
    SYNTAX  INTEGER {
        enabled(1),
        disabled(2)
        }
    MAX-ACCESS  read-only
    STATUS  current
    DESCRIPTION
        "This is for controlling if the switch should redirect packet to the 
         origin server when user cookies are detected.  

         enabled(1) - Allow redirect traffic to the origin server
         disabled(2)- redirect to a group of servers (cache server)"
    ::= { slbUrlRedir 5 }

slbNewCfgUrlRedirCookieOrigSrv OBJECT-TYPE
    SYNTAX  INTEGER {
        enabled(1),
        disabled(2)
        }
    MAX-ACCESS  read-write
    STATUS  current
    DESCRIPTION
        "This is for controlling if the switch should redirect packet to the 
         origin server when user cookies are detected.  

         enabled(1) - Allow redirect traffic to the origin server
         disabled(2)- redirect to a group of servers (cache server)"
    ::= { slbUrlRedir 6 }

slbCurCfgUrlRedirNoCacheOrigSrv OBJECT-TYPE
    SYNTAX  INTEGER {
        enabled(1),
        disabled(2)
        }
    MAX-ACCESS  read-only
    STATUS  current
    DESCRIPTION
        "This is for controlling if the switch should redirect packet to the 
         origin server when no-cache header are detected.  

         enabled(1) - Allow redirect traffic to the origin server
         disabled(2)- redirect to a group of servers (cache server)"
    ::= { slbUrlRedir 7 }

slbNewCfgUrlRedirNoCacheOrigSrv OBJECT-TYPE
    SYNTAX  INTEGER {
        enabled(1),
        disabled(2)
        }
    MAX-ACCESS  read-write
    STATUS  current
    DESCRIPTION
        "This is for controlling if the switch should redirect packet to the 
         origin server when no-cache header are detected.  

         enabled(1) - Allow redirect traffic to the origin server
         disabled(2)- redirect to a group of servers (cache server)"
    ::= { slbUrlRedir 8 }

slbCurCfgUrlRedirUriHashLength OBJECT-TYPE
    SYNTAX  INTEGER (0..255) 
    MAX-ACCESS  read-only
    STATUS  current
    DESCRIPTION
        "Specify the number of bytes in the URI will be used to hash 
         onto server"
    ::= { slbUrlRedir 9 }

slbNewCfgUrlRedirUriHashLength OBJECT-TYPE
    SYNTAX  INTEGER (1..255) 
    MAX-ACCESS  read-write
    STATUS  current
    DESCRIPTION
        "Specify the number of bytes in the URI will be used to hash 
         onto server"
    ::= { slbUrlRedir 10 }

slbCurCfgUrlRedirHeader OBJECT-TYPE
    SYNTAX  INTEGER {
        enabled(1),
        disabled(2)
        }
    MAX-ACCESS  read-only
    STATUS  current
    DESCRIPTION
	"This is for controlling if the switch should redirect packet to the 
         cache server based on HTTP header.

         enabled(1) - Redirect web traffic based on HTTP header
         disabled(2)- Redirect web traffic based on URI"
    ::= { slbUrlRedir 11 }

slbNewCfgUrlRedirHeader OBJECT-TYPE
    SYNTAX  INTEGER {
        enabled(1),
        disabled(2)
        }
    MAX-ACCESS  read-write
    STATUS  current
    DESCRIPTION
	"This is for controlling if the switch should redirect packet to the 
         cache server based on HTTP header.

         enabled(1) - Redirect web traffic based on HTTP header
         disabled(2)- Redirect web traffic based on URI"
    ::= { slbUrlRedir 12 }

slbCurCfgUrlRedirHeaderName OBJECT-TYPE
    SYNTAX DisplayString (SIZE(0..32))
    MAX-ACCESS read-only
    STATUS current
    DESCRIPTION
        "The HTTP header name"
    ::= { slbUrlRedir 13 }

slbNewCfgUrlRedirHeaderName OBJECT-TYPE
    SYNTAX DisplayString (SIZE(0..32))
    MAX-ACCESS read-write 
    STATUS current
    DESCRIPTION
        "The HTTP header name"
    ::= { slbUrlRedir 14 }

slbCurCfgUrlHashing OBJECT-TYPE
    SYNTAX  INTEGER {
        enabled(1),
        disabled(2)
    }
    MAX-ACCESS  read-only
    STATUS  current
    DESCRIPTION
         "This is to Enable/Disable URL hashing based on URI."
    ::= { slbUrlRedir 15 }

slbNewCfgUrlHashing OBJECT-TYPE
    SYNTAX  INTEGER {
        enabled(1),
        disabled(2)
    }
    MAX-ACCESS  read-write
    STATUS  current
    DESCRIPTION
         "This is to Enable/Disable URL hashing based on URI."
    ::= { slbUrlRedir 16 }

slbCurCfgUrlRedirHeaderNameType OBJECT-TYPE
    SYNTAX INTEGER {
        host(1),
        useragent(2),
        others(3)
    }
    MAX-ACCESS read-only
    STATUS current
    DESCRIPTION
        "HTTP header Application type."
    ::= { slbUrlRedir 17 }

slbNewCfgUrlRedirHeaderNameType OBJECT-TYPE
    SYNTAX INTEGER {
        host(1),
        useragent(2),
        others(3)
    }
    MAX-ACCESS read-write
    STATUS current
    DESCRIPTION
        "HTTP header Application type."
    ::= { slbUrlRedir 18 }

-- Operation Commands

sslInspectionCachePurge OBJECT IDENTIFIER ::= { layer7Oper 1 }

slbOperSslInspectionCachePurge OBJECT-TYPE
    SYNTAX INTEGER
    MAX-ACCESS  read-write
    STATUS  current
    DESCRIPTION
        "ssl Inspection Cache Purge."
    ::= {  sslInspectionCachePurge 1 }


urlfCachePurge OBJECT IDENTIFIER ::= { layer7Oper 2 }

slbOperUrlfCachePurge OBJECT-TYPE
    SYNTAX INTEGER
    MAX-ACCESS  read-write
    STATUS  current
    DESCRIPTION
        "URLF Cache Purge."
    ::= {  urlfCachePurge 1 }

tcktCachePurge OBJECT IDENTIFIER ::= { layer7Oper 3 }

slbOperTcktCachePurge OBJECT-TYPE
    SYNTAX INTEGER
    MAX-ACCESS  read-write
    STATUS  current
    DESCRIPTION
        "Session Ticket Table Purge."
    ::= {  tcktCachePurge 1 }

-- SLB URL Load Balancing

slbUrlLbPathTableMaxSize OBJECT-TYPE
    SYNTAX Integer32 
    MAX-ACCESS read-only 
    STATUS current 
    DESCRIPTION 
        "The maximum number of entries in SLB URL load balance table." 
    ::= { slbUrlBalance 1 }

slbCurCfgUrlLbPathTable OBJECT-TYPE
    SYNTAX  SEQUENCE OF SlbCurCfgUrlLbPathTableEntry
    MAX-ACCESS  not-accessible
    STATUS  current
    DESCRIPTION
        "The table of URL path for URL load balancing in the current_config."
    ::= { slbUrlBalance 2 }

slbCurCfgUrlLbPathTableEntry OBJECT-TYPE
    SYNTAX  SlbCurCfgUrlLbPathTableEntry
    MAX-ACCESS  not-accessible
    STATUS  current
    DESCRIPTION
        "Information about an URL path for URL load balancing."
    INDEX   { slbCurCfgUrlLbPathIndex }
    ::= { slbCurCfgUrlLbPathTable 1 }

SlbCurCfgUrlLbPathTableEntry ::= SEQUENCE {
    slbCurCfgUrlLbPathIndex             Integer32,
    slbCurCfgUrlLbBwmContract           Integer32,
    slbCurCfgUrlLbPathHTTPHeader        DisplayString,
    slbCurCfgUrlLbPathHTTPHeaderValue   DisplayString,
    slbCurCfgUrlLbPathPatternStringType INTEGER,
    slbCurCfgUrlLbPathOffset            INTEGER,
    slbCurCfgUrlLbPathDepth             INTEGER,
    slbCurCfgUrlLbPathOper              INTEGER,
    slbCurCfgUrlLbPathString            DisplayString,
    slbCurCfgUrlLbPathDnsQueryTypes     DisplayString,
    slbCurCfgUrlLbPathCompleteString    DisplayString,
    slbCurCfgUrlLbPathAllowRegExp       INTEGER,
    slbCurCfgUrlLbPathDnsType           INTEGER,
    slbCurCfgUrlLbPathApplication       INTEGER
   }

slbCurCfgUrlLbPathIndex OBJECT-TYPE
    SYNTAX  Integer32
    MAX-ACCESS  read-only
    STATUS  current
    DESCRIPTION
        "The URL path table index."
    ::= { slbCurCfgUrlLbPathTableEntry 1 }

slbCurCfgUrlLbPathString OBJECT-TYPE
    SYNTAX  DisplayString (SIZE(0..96))
    MAX-ACCESS  read-only
    STATUS  current
    DESCRIPTION
        "The SLB string or ASCII/BINARY string for pattern matching ."
    ::= { slbCurCfgUrlLbPathTableEntry 2 }

slbCurCfgUrlLbBwmContract OBJECT-TYPE
    SYNTAX  Integer32
    MAX-ACCESS  read-only
    STATUS  current
    DESCRIPTION
        "The BW contract for the path."
    ::= { slbCurCfgUrlLbPathTableEntry 3 }

slbCurCfgUrlLbPathHTTPHeader OBJECT-TYPE
    SYNTAX  DisplayString (SIZE(0..32))
    MAX-ACCESS  read-only
    STATUS  current
    DESCRIPTION
        "The HTTP header for URL load balancing."
    ::= { slbCurCfgUrlLbPathTableEntry 4 }

slbCurCfgUrlLbPathHTTPHeaderValue OBJECT-TYPE
    SYNTAX  DisplayString (SIZE(0..48))
    MAX-ACCESS  read-only
    STATUS  current
    DESCRIPTION
        "The HTTP header value for URL load balancing."
    ::= { slbCurCfgUrlLbPathTableEntry 5 }
 
slbCurCfgUrlLbPathDnsQueryTypes OBJECT-TYPE
    SYNTAX  DisplayString (SIZE(0..96))
    MAX-ACCESS  read-only
    STATUS  current
    DESCRIPTION
        "DNS Query type(s) (by number)."
    ::= { slbCurCfgUrlLbPathTableEntry 10 }

slbCurCfgUrlLbPathPatternStringType OBJECT-TYPE
    SYNTAX INTEGER {
        ascii(1),
        binary(2),
	none  (3)
        }
    MAX-ACCESS  read-only
    STATUS  current
    DESCRIPTION
        "Type of pattern string (ASCII or binary or none)."
    ::= { slbCurCfgUrlLbPathTableEntry 6 }

slbCurCfgUrlLbPathOffset OBJECT-TYPE
    SYNTAX  INTEGER (0..1500)
    MAX-ACCESS  read-only
    STATUS  current
    DESCRIPTION
        "Offset from beginning of IP packet to start matching the
	 pattern string."
    ::= { slbCurCfgUrlLbPathTableEntry 7 }

slbCurCfgUrlLbPathDepth OBJECT-TYPE
    SYNTAX  INTEGER (0..1500)
    MAX-ACCESS  read-only
    STATUS  current
    DESCRIPTION
        "Depth of IP packet to search and match the pattern string."
    ::= { slbCurCfgUrlLbPathTableEntry 8 }

slbCurCfgUrlLbPathOper OBJECT-TYPE
    SYNTAX  INTEGER {
	eq(1),
	gt(2),
	lt(3),
	none(4)
	} 
    MAX-ACCESS  read-only
    STATUS  current
    DESCRIPTION
	"Operation to be performed on the pattern match string.
	 For ASCII pattern strings, only the equal (eq) operation
	 is valid."
    ::= { slbCurCfgUrlLbPathTableEntry 9 }

slbCurCfgUrlLbPathCompleteString OBJECT-TYPE
    SYNTAX  DisplayString (SIZE(0..255))
    MAX-ACCESS  read-only
    STATUS  current
    DESCRIPTION
        "The complete SLB or ASCII/BINARY string for pattern matching ."
    ::= { slbCurCfgUrlLbPathTableEntry 11 }

slbCurCfgUrlLbPathAllowRegExp OBJECT-TYPE
    SYNTAX INTEGER {
        yes(1),
        no(2)
        }
    MAX-ACCESS  read-only
    STATUS  current
    DESCRIPTION
        "Allow regular expression for layer7 SLB path string."
    ::= { slbCurCfgUrlLbPathTableEntry 12 }	

slbCurCfgUrlLbPathDnsType OBJECT-TYPE
    SYNTAX INTEGER {
        dns(1),
        dnssec(2),
        any(3)
        }
    MAX-ACCESS  read-only
    STATUS  current
    DESCRIPTION
        "DNS type (dns, dnssec, any)."
    ::= { slbCurCfgUrlLbPathTableEntry 13 }

slbCurCfgUrlLbPathApplication OBJECT-TYPE
    SYNTAX INTEGER {
        http(1),
        dns(2),
        other(3)
        }
    MAX-ACCESS  read-only
    STATUS  current
    DESCRIPTION
        "Type of appliction (http, dns, other)."
    ::= { slbCurCfgUrlLbPathTableEntry 14 }

slbNewCfgUrlLbPathTable OBJECT-TYPE
    SYNTAX  SEQUENCE OF SlbNewCfgUrlLbPathTableEntry
    MAX-ACCESS  not-accessible
    STATUS  current
    DESCRIPTION
        "The table of URL path for URL load balancing in the new_config."
    ::= { slbUrlBalance 3 }

slbNewCfgUrlLbPathTableEntry OBJECT-TYPE
    SYNTAX  SlbNewCfgUrlLbPathTableEntry
    MAX-ACCESS  not-accessible
    STATUS  current
    DESCRIPTION
        "Information about an URL path for URL load balancing."
    INDEX   { slbNewCfgUrlLbPathIndex }
    ::= { slbNewCfgUrlLbPathTable 1 }

SlbNewCfgUrlLbPathTableEntry ::= SEQUENCE {
    slbNewCfgUrlLbPathIndex             Integer32,
    slbNewCfgUrlLbPathString            DisplayString,
    slbNewCfgUrlLbBwmContract           Integer32,
    slbNewCfgUrlLbPathHTTPHeader        DisplayString,
    slbNewCfgUrlLbPathHTTPHeaderValue   DisplayString,
    slbNewCfgUrlLbPathPatternStringType INTEGER,
    slbNewCfgUrlLbPathOffset            INTEGER,
    slbNewCfgUrlLbPathDepth             INTEGER,
    slbNewCfgUrlLbPathOper              INTEGER,
    slbNewCfgUrlLbPathDelete            INTEGER,
    slbNewCfgUrlLbPathDnsQueryTypes     DisplayString,
    slbNewCfgUrlLbPathCompleteString    DisplayString,
    slbNewCfgUrlLbPathAllowRegExp       INTEGER,
    slbNewCfgUrlLbPathDnsType           INTEGER,
    slbNewCfgUrlLbPathApplication       INTEGER 
    }

slbNewCfgUrlLbPathIndex OBJECT-TYPE
    SYNTAX  Integer32
    MAX-ACCESS  read-only
    STATUS  current
    DESCRIPTION
        "The URL path table index."
    ::= { slbNewCfgUrlLbPathTableEntry 1 }

slbNewCfgUrlLbPathString OBJECT-TYPE
    SYNTAX  DisplayString (SIZE(0..96))
    MAX-ACCESS  read-create
    STATUS  current
    DESCRIPTION
        "The SLB string or ASCII/BINARY string for pattern matching ."
    ::= { slbNewCfgUrlLbPathTableEntry 2 }

slbNewCfgUrlLbPathDnsQueryTypes OBJECT-TYPE
    SYNTAX  DisplayString (SIZE(0..96))
    MAX-ACCESS  read-create
    STATUS  current
    DESCRIPTION
        "DNS Query type(s) (by number)."
    ::= { slbNewCfgUrlLbPathTableEntry 11 }

slbNewCfgUrlLbBwmContract OBJECT-TYPE
    SYNTAX  Integer32
    MAX-ACCESS  read-create
    STATUS  current
    DESCRIPTION
        "The BW contract for the load path."
    ::= { slbNewCfgUrlLbPathTableEntry 4 }
    
slbNewCfgUrlLbPathHTTPHeader OBJECT-TYPE
    SYNTAX  DisplayString (SIZE(0..48))
    MAX-ACCESS  read-create
    STATUS  current
    DESCRIPTION
        "The HTTP header for URL load balancing."
    ::= { slbNewCfgUrlLbPathTableEntry 5 }

slbNewCfgUrlLbPathHTTPHeaderValue OBJECT-TYPE
    SYNTAX  DisplayString (SIZE(0..48))
    MAX-ACCESS  read-create
    STATUS  current
    DESCRIPTION
        "The HTTP header value for URL load balancing."
    ::= { slbNewCfgUrlLbPathTableEntry 6 }

slbNewCfgUrlLbPathPatternStringType OBJECT-TYPE
    SYNTAX INTEGER {
        ascii(1),
        binary(2),
	none  (3)
        }
    MAX-ACCESS  read-create
    STATUS  current
    DESCRIPTION
        "Type of pattern string (ASCII or binary)."
    ::= { slbNewCfgUrlLbPathTableEntry 7 }

slbNewCfgUrlLbPathOffset OBJECT-TYPE
    SYNTAX  INTEGER (0..1500)
    MAX-ACCESS  read-create
    STATUS  current
    DESCRIPTION
        "Offset from beginning of IP packet to start matching the
	 pattern string."
    ::= { slbNewCfgUrlLbPathTableEntry 8 }

slbNewCfgUrlLbPathDepth OBJECT-TYPE
    SYNTAX  INTEGER (0..1500)
    MAX-ACCESS  read-create
    STATUS  current
    DESCRIPTION
        "Depth of IP packet to search and match the pattern string."
    ::= { slbNewCfgUrlLbPathTableEntry 9 }

slbNewCfgUrlLbPathOper OBJECT-TYPE
    SYNTAX  INTEGER {
	eq(1),
	gt(2),
	lt(3),
	none(4)
	} 
    MAX-ACCESS  read-create
    STATUS  current
    DESCRIPTION
	"Operation to be performed on the pattern match string.
	 For ASCII pattern strings, only the equal (eq) operation
	 is valid."
    ::= { slbNewCfgUrlLbPathTableEntry 10 }

slbNewCfgUrlLbPathCompleteString OBJECT-TYPE
    SYNTAX  DisplayString (SIZE(0..255))
    MAX-ACCESS  read-only
    STATUS  current
    DESCRIPTION
        "The complete SLB or ASCII/BINARY string for pattern matching ."
    ::= { slbNewCfgUrlLbPathTableEntry 12 }

slbNewCfgUrlLbPathAllowRegExp OBJECT-TYPE
    SYNTAX INTEGER {
        yes(1),
        no(2)
        }
    MAX-ACCESS  read-create
    STATUS  current
    DESCRIPTION
        "Allow regular expression for layer7 SLB path string."
    ::= { slbNewCfgUrlLbPathTableEntry 13 }	

slbNewCfgUrlLbPathDnsType  OBJECT-TYPE
    SYNTAX INTEGER {
        dns(1),
        dnssec(2),
        any(3)
        }
    MAX-ACCESS  read-create
    STATUS  current
    DESCRIPTION
        "DNS type (dns, dnssec, any)."
    ::= { slbNewCfgUrlLbPathTableEntry 14 }

slbNewCfgUrlLbPathApplication  OBJECT-TYPE
    SYNTAX INTEGER {
        http(1),
        dns(2),
        other(3)
        }
    MAX-ACCESS  read-create
    STATUS  current
    DESCRIPTION
        "Type of application (http, dns, other)."
    ::= { slbNewCfgUrlLbPathTableEntry 15 }

slbNewCfgUrlLbPathDelete OBJECT-TYPE
    SYNTAX  INTEGER {
        other(1),
        delete(2)
        }
    MAX-ACCESS  read-create
    STATUS  current
    DESCRIPTION
        "Action object to delete an URL Path.  When set to the value 
         of 2 (delete), the entire row is deleted. When read, other(1) is 
         returned. Setting the value to anything other than delete(2) 
         has no effect on the state of the row."
    ::= { slbNewCfgUrlLbPathTableEntry 3 }

slbCurCfgUrlLbErrorMsg OBJECT-TYPE
    SYNTAX  DisplayString (SIZE(0..64))
    MAX-ACCESS  read-only
    STATUS  current
    DESCRIPTION
        "Customize error message to send back to client when switch cannot 
         bind client's request to servers."
    ::= { slbUrlBalance 4 }

slbNewCfgUrlLbErrorMsg OBJECT-TYPE
    SYNTAX  DisplayString (SIZE(0..64))
    MAX-ACCESS  read-write
    STATUS  current
    DESCRIPTION
        "Customize error message to send back to client when switch cannot 
         bind client's request to servers."
    ::= { slbUrlBalance 5 }

slbCurCfgUrlLbCaseSensitiveStrMatch OBJECT-TYPE
    SYNTAX  INTEGER {
        enabled(1),
        disabled(2)
        }
    MAX-ACCESS  read-only
    STATUS  current
    DESCRIPTION
	"This is for controlling if the URL String matching is case sensitive or not.  

         enabled(1) - URL String matching is case sensitive
         disabled(2)- URL String matching is not case sensitive"
    ::= { slbUrlBalance 6 }

slbNewCfgUrlLbCaseSensitiveStrMatch OBJECT-TYPE
    SYNTAX  INTEGER {
        enabled(1),
        disabled(2)
        }
    MAX-ACCESS  read-write
    STATUS  current
    DESCRIPTION
	"This is for controlling if the URL String matching is case sensitive or not.  

         enabled(1) - URL String matching is case sensitive
         disabled(2)- URL String matching is not case sensitive"
    ::= { slbUrlBalance 7 }

slbUrlHttpMethodsTableMaxSize OBJECT-TYPE
    SYNTAX  Integer32 
    MAX-ACCESS  read-only 
    STATUS  current 
    DESCRIPTION 
        "The maximum number of http method entries in layer7 processing engine." 
    ::= { slbUrlHttpMethods 1 }

slbCurCfgUrlHttpMethodsTable OBJECT-TYPE
    SYNTAX  SEQUENCE OF SlbCurCfgUrlHttpMethodsTableEntry 
    MAX-ACCESS  not-accessible
    STATUS  current
    DESCRIPTION
        "The http methods table in layer7 processing engine."
    ::= { slbUrlHttpMethods 2 }

slbCurCfgUrlHttpMethodsTableEntry OBJECT-TYPE
    SYNTAX  SlbCurCfgUrlHttpMethodsTableEntry
    MAX-ACCESS  not-accessible
    STATUS  current
    DESCRIPTION
        "A row in the http methods table."
    INDEX   { slbCurCfgUrlHttpMethodIndex }
    ::= { slbCurCfgUrlHttpMethodsTable 1 }

SlbCurCfgUrlHttpMethodsTableEntry ::= SEQUENCE {
    slbCurCfgUrlHttpMethodIndex          Integer32,
    slbCurCfgUrlHttpMethodString         DisplayString
    }

slbCurCfgUrlHttpMethodIndex OBJECT-TYPE 
    SYNTAX  Integer32 
    MAX-ACCESS  read-only 
    STATUS  current 
    DESCRIPTION 
        "The http method table index." 
    ::= { slbCurCfgUrlHttpMethodsTableEntry 1 }

slbCurCfgUrlHttpMethodString OBJECT-TYPE  
    SYNTAX  DisplayString (SIZE(0..32))
    MAX-ACCESS  read-only
    STATUS  current
    DESCRIPTION
        "The http method string to process in layer7 engine."
    ::= { slbCurCfgUrlHttpMethodsTableEntry 2 } 

slbNewCfgUrlHttpMethodsTable OBJECT-TYPE
    SYNTAX  SEQUENCE OF SlbNewCfgUrlHttpMethodsTableEntry 
    MAX-ACCESS  not-accessible
    STATUS  current
    DESCRIPTION
        "The http methods table in layer7 processing engine."
    ::= { slbUrlHttpMethods 3 }

slbNewCfgUrlHttpMethodsTableEntry OBJECT-TYPE
    SYNTAX  SlbNewCfgUrlHttpMethodsTableEntry
    MAX-ACCESS  not-accessible
    STATUS  current
    DESCRIPTION
        "A row in the http methods table."
    INDEX   { slbNewCfgUrlHttpMethodIndex }
    ::= { slbNewCfgUrlHttpMethodsTable 1 }

SlbNewCfgUrlHttpMethodsTableEntry ::= SEQUENCE {
    slbNewCfgUrlHttpMethodIndex    Integer32,
    slbNewCfgUrlHttpMethodString   DisplayString,
    slbNewCfgUrlHttpMethodDelete   INTEGER
    }

slbNewCfgUrlHttpMethodIndex OBJECT-TYPE 
    SYNTAX  Integer32 
    MAX-ACCESS  read-only 
    STATUS  current 
    DESCRIPTION 
        "The http method table index." 
    ::= { slbNewCfgUrlHttpMethodsTableEntry 1 }

slbNewCfgUrlHttpMethodString OBJECT-TYPE  
    SYNTAX  DisplayString (SIZE(0..32))
    MAX-ACCESS  read-create
    STATUS  current
    DESCRIPTION
        "The http method string to process in layer7 engine."
    ::= { slbNewCfgUrlHttpMethodsTableEntry 2 } 

slbNewCfgUrlHttpMethodDelete OBJECT-TYPE
    SYNTAX  INTEGER {
        other(1),
        delete(2)
        }
    MAX-ACCESS  read-create
    STATUS  current
    DESCRIPTION
        "When set to the value of 2 (delete), the entire row is deleted. 
         When read, other(1) is returned. Setting the value to anything 
         other than 2(delete) has no effect on the state of the row."
    ::= { slbNewCfgUrlHttpMethodsTableEntry 3 }

-- Layer7 General Configuration

layer7CurCfgDbindTimeout OBJECT-TYPE
    SYNTAX  INTEGER (10..60) 
    MAX-ACCESS  read-only
    STATUS  current 
    DESCRIPTION
        "The timeout for incomplete delayed binding connections."
    ::= { layer7GeneralCfg 1 }

layer7NewCfgDbindTimeout OBJECT-TYPE
    SYNTAX  INTEGER (10..60) 
    MAX-ACCESS  read-write
    STATUS  current 
    DESCRIPTION
        "The timeout for incomplete delayed binding connections."
    ::= { layer7GeneralCfg 2 }

layer7CurCfgURLFilteringEna OBJECT-TYPE
    SYNTAX  INTEGER (0..1) 
    MAX-ACCESS  read-only
    STATUS  current 
    DESCRIPTION
        "URL Filtering ena/dis feature."
    ::= { layer7GeneralCfg 3 }

layer7NewCfgURLFilteringEna OBJECT-TYPE
    SYNTAX  INTEGER (0..1) 
    MAX-ACCESS  read-write
    STATUS  current 
    DESCRIPTION
        "URL Filtering ena/dis feature."
    ::= { layer7GeneralCfg 4 }

layer7CurCfgURLFilteringCacheSize OBJECT-TYPE
    SYNTAX  INTEGER (1024..131072)
    MAX-ACCESS  read-only
    STATUS  current 
    DESCRIPTION
        "URL Filtering cache size."
    ::= { layer7GeneralCfg 5 }

layer7NewCfgURLFilteringCacheSize OBJECT-TYPE
    SYNTAX  INTEGER (1024..131072)
    MAX-ACCESS  read-write
    STATUS  current 
    DESCRIPTION
        "URL Filtering cache size."
    ::= { layer7GeneralCfg 6 }


layer7CurCfgHttpmodListTable OBJECT-TYPE
    SYNTAX  SEQUENCE OF Layer7CurCfgHttpmodListEntry
    MAX-ACCESS  not-accessible
    STATUS  current
    DESCRIPTION
        "The table for configuring HTTP content modification rule-lists."
    ::= { httpModCfg 1 }

layer7CurCfgHttpmodListEntry OBJECT-TYPE
    SYNTAX  Layer7CurCfgHttpmodListEntry
    MAX-ACCESS  not-accessible
    STATUS  current
    DESCRIPTION
        "A row in the HTTP content modification rule-lists table."
    INDEX   { layer7CurCfgHttpmodListNameIdIndex }
    ::= { layer7CurCfgHttpmodListTable 1 }

Layer7CurCfgHttpmodListEntry ::= SEQUENCE {
    layer7CurCfgHttpmodListNameIdIndex          DisplayString,
    layer7CurCfgHttpmodListName                 DisplayString,
    layer7CurCfgHttpmodListAdminStatus          INTEGER
    }

layer7CurCfgHttpmodListNameIdIndex OBJECT-TYPE
    SYNTAX   DisplayString (SIZE (0..32))
    MAX-ACCESS  read-only
    STATUS  current
    DESCRIPTION
        "HTTP content modification rule-lists name(key id) as an index."
    ::= { layer7CurCfgHttpmodListEntry 1 }

layer7CurCfgHttpmodListName OBJECT-TYPE
    SYNTAX   DisplayString (SIZE (0..32))
    MAX-ACCESS  read-only
    STATUS  current
    DESCRIPTION
        "HTTP content modification rule-lists name."
    ::= { layer7CurCfgHttpmodListEntry 2 }

layer7CurCfgHttpmodListAdminStatus OBJECT-TYPE
    SYNTAX  INTEGER {
        enabled(1),
        disabled(2)
    }
    MAX-ACCESS  read-only
    STATUS  current
    DESCRIPTION
        "Status (enable/disable) of rule_list."
    ::= { layer7CurCfgHttpmodListEntry 3 }

layer7NewCfgHttpmodListTable OBJECT-TYPE
    SYNTAX  SEQUENCE OF Layer7NewCfgHttpmodListEntry
    MAX-ACCESS  not-accessible
    STATUS  current
    DESCRIPTION
        "The table for configuring HTTP content modification rule-lists."
    ::= { httpModCfg 2 }

layer7NewCfgHttpmodListEntry OBJECT-TYPE
    SYNTAX  Layer7NewCfgHttpmodListEntry
    MAX-ACCESS  not-accessible
    STATUS  current
    DESCRIPTION
        "A row in the HTTP content modification rule-lists table."
    INDEX   { layer7NewCfgHttpmodListNameIdIndex }
    ::= { layer7NewCfgHttpmodListTable 1 }

Layer7NewCfgHttpmodListEntry ::= SEQUENCE {
    layer7NewCfgHttpmodListNameIdIndex          DisplayString,
    layer7NewCfgHttpmodListName                 DisplayString,
    layer7NewCfgHttpmodListAdminStatus          INTEGER,
    layer7NewCfgHttpmodListCopy                 DisplayString,
    layer7NewCfgHttpmodListDelete               INTEGER
    }

layer7NewCfgHttpmodListNameIdIndex OBJECT-TYPE
    SYNTAX   DisplayString (SIZE (0..32))
    MAX-ACCESS  read-only
    STATUS  current
    DESCRIPTION
        "HTTP content modification rule-lists name(key id) as an index, length of the string should be 32 characters."
    ::= { layer7NewCfgHttpmodListEntry 1 }

layer7NewCfgHttpmodListName OBJECT-TYPE
    SYNTAX   DisplayString (SIZE (0..32))
    MAX-ACCESS  read-create
    STATUS  current
    DESCRIPTION
        "HTTP content modification rule-list name, length of the string should be 32 characters."
    ::= { layer7NewCfgHttpmodListEntry 2 }

layer7NewCfgHttpmodListAdminStatus OBJECT-TYPE
    SYNTAX  INTEGER {
        enabled(1),
        disabled(2)
        }
    MAX-ACCESS  read-create
    STATUS  current
    DESCRIPTION
        "Status (enable/disable) of rule_list."
    ::= { layer7NewCfgHttpmodListEntry 3 }

layer7NewCfgHttpmodListCopy OBJECT-TYPE
    SYNTAX   DisplayString (SIZE (0..32))
    MAX-ACCESS  read-create
    STATUS  current
    DESCRIPTION
        "Copy rule-list."
    ::= { layer7NewCfgHttpmodListEntry 4 }

layer7NewCfgHttpmodListDelete OBJECT-TYPE
    SYNTAX  INTEGER {
        other(1),
        delete(2)
        }
    MAX-ACCESS  read-create
    STATUS  current
    DESCRIPTION
        "Delete HTTP modifications rule-list."
    ::= { layer7NewCfgHttpmodListEntry 5 }

layer7CurCfgHttpmodRuleTable OBJECT-TYPE
    SYNTAX  SEQUENCE OF Layer7CurCfgHttpmodRuleEntry
    MAX-ACCESS  not-accessible
    STATUS  current
    DESCRIPTION
        "The table for configuring HTTP content modification rules."
    ::= { httpModCfg 3 }

layer7CurCfgHttpmodRuleEntry OBJECT-TYPE
    SYNTAX  Layer7CurCfgHttpmodRuleEntry
    MAX-ACCESS  not-accessible
    STATUS  current
    DESCRIPTION
        "A row in the HTTP content modification rule table."
    INDEX   { layer7CurCfgHttpmodRuleListIdIndex, layer7CurCfgHttpmodRuleIndex }
    ::= { layer7CurCfgHttpmodRuleTable 1 }

Layer7CurCfgHttpmodRuleEntry ::= SEQUENCE {
    layer7CurCfgHttpmodRuleListIdIndex          DisplayString,
    layer7CurCfgHttpmodRuleIndex                INTEGER,
    layer7CurCfgHttpmodRuleName                 DisplayString,
    layer7CurCfgHttpmodRuleDirectn              INTEGER,
    layer7CurCfgHttpmodRuleAction               INTEGER,
    layer7CurCfgHttpmodRuleAdminStatus          INTEGER,

    layer7CurCfgHttpmodRuleElement              INTEGER,
    layer7CurCfgHttpmodRuleHttpBody             INTEGER
    }

layer7CurCfgHttpmodRuleListIdIndex OBJECT-TYPE
    SYNTAX   DisplayString (SIZE (0..32))
    MAX-ACCESS  read-only
    STATUS  current
    DESCRIPTION
        "The HTTP Modification Rule List (key id) as an index."
    ::= { layer7CurCfgHttpmodRuleEntry 1 }
    
layer7CurCfgHttpmodRuleIndex OBJECT-TYPE
    SYNTAX   INTEGER
    MAX-ACCESS  read-only
    STATUS  current
    DESCRIPTION
        "The HTTP Modification Rule number as an index."
    ::= { layer7CurCfgHttpmodRuleEntry 2 }

layer7CurCfgHttpmodRuleName OBJECT-TYPE
    SYNTAX   DisplayString (SIZE (0..32))
    MAX-ACCESS  read-only
    STATUS  current
    DESCRIPTION
        "The HTTP Modification Rule name."
    ::= { layer7CurCfgHttpmodRuleEntry 3 }

layer7CurCfgHttpmodRuleDirectn OBJECT-TYPE
    SYNTAX   INTEGER {
        request(1),
        response(2),
        bidirectional(3)
        }
    MAX-ACCESS  read-only
    STATUS  current
    DESCRIPTION
        "Defines whether rule modification direction should be evaluated as Request or Response (default Request)."
    ::= { layer7CurCfgHttpmodRuleEntry 4 }

layer7CurCfgHttpmodRuleAction OBJECT-TYPE
    SYNTAX   INTEGER {
        insert(1),
        replace(2),
        remove(3),
        none(4)
        }
    MAX-ACCESS  read-only
    STATUS  current
    DESCRIPTION
        "Defines rule action (default none)."
    ::= { layer7CurCfgHttpmodRuleEntry 5 }

layer7CurCfgHttpmodRuleAdminStatus OBJECT-TYPE
    SYNTAX   INTEGER {
        enable(1),
        disable(2)
        }
    MAX-ACCESS  read-only
    STATUS  current
    DESCRIPTION
        "Status (enable/disable) of rule."
    ::= { layer7CurCfgHttpmodRuleEntry 6 }

layer7CurCfgHttpmodRuleElement OBJECT-TYPE
    SYNTAX   INTEGER {
        url(1),
        header(2),
        cookie(3),
        filetype(4),
        statusline(5),
        text(6)
        }
    MAX-ACCESS  read-only
    STATUS  current
    DESCRIPTION
        "Element to be modified."
    ::= { layer7CurCfgHttpmodRuleEntry 7 }

layer7CurCfgHttpmodRuleHttpBody OBJECT-TYPE
    SYNTAX   INTEGER {
        include(1),
        exclude(2)
        }
    MAX-ACCESS  read-only
    STATUS  current
    DESCRIPTION
        "Modifications to also be done in the HTTP body."
    ::= { layer7CurCfgHttpmodRuleEntry 8 }

layer7NewCfgHttpmodRuleTable OBJECT-TYPE
    SYNTAX  SEQUENCE OF Layer7NewCfgHttpmodRuleEntry
    MAX-ACCESS  not-accessible
    STATUS  current
    DESCRIPTION
        "The table for configuring HTTP content modification rules."
    ::= { httpModCfg 4 }

layer7NewCfgHttpmodRuleEntry OBJECT-TYPE
    SYNTAX  Layer7NewCfgHttpmodRuleEntry
    MAX-ACCESS  not-accessible
    STATUS  current
    DESCRIPTION
        "A row in the HTTP content modification rule table."
    INDEX   { layer7NewCfgHttpmodRuleListIdIndex, layer7NewCfgHttpmodRuleIndex }
    ::= { layer7NewCfgHttpmodRuleTable 1 }

Layer7NewCfgHttpmodRuleEntry ::= SEQUENCE {
    layer7NewCfgHttpmodRuleListIdIndex          DisplayString,
    layer7NewCfgHttpmodRuleIndex                INTEGER,
    layer7NewCfgHttpmodRuleName                 DisplayString,
    layer7NewCfgHttpmodRuleDirectn              INTEGER,
    layer7NewCfgHttpmodRuleAction               INTEGER,
    layer7NewCfgHttpmodRuleAdminStatus          INTEGER,
    layer7NewCfgHttpmodRuleCopy                 DisplayString,
    layer7NewCfgHttpmodRuleDelete               INTEGER,

    layer7NewCfgHttpmodRuleElement              INTEGER,
    layer7NewCfgHttpmodRuleHttpBody             INTEGER
    }

layer7NewCfgHttpmodRuleListIdIndex OBJECT-TYPE
    SYNTAX   DisplayString (SIZE (0..32))
    MAX-ACCESS  read-only
    STATUS  current
    DESCRIPTION
        "The HTTP Modification Rule List (key id) as an index."
    ::= { layer7NewCfgHttpmodRuleEntry 1 }

layer7NewCfgHttpmodRuleIndex OBJECT-TYPE
    SYNTAX   INTEGER
    MAX-ACCESS  read-only
    STATUS  current
    DESCRIPTION
        "The HTTP Modification Rule number as an index."
    ::= { layer7NewCfgHttpmodRuleEntry 2 }

layer7NewCfgHttpmodRuleName OBJECT-TYPE
    SYNTAX   DisplayString (SIZE (0..32))
    MAX-ACCESS  read-create
    STATUS  current
    DESCRIPTION
        "The HTTP Modification Rule name."
    ::= { layer7NewCfgHttpmodRuleEntry 3 }

layer7NewCfgHttpmodRuleDirectn OBJECT-TYPE
    SYNTAX   INTEGER {
        request(1),
        response(2),
        bidirectional(3)
        }
    MAX-ACCESS  read-create
    STATUS  current
    DESCRIPTION
        "Defines whether rule modification direction should be evaluated as Request or Response (default Response). SET layer7NewCfgHttpmodRuleElementbefore SETTING the direction."
    ::= { layer7NewCfgHttpmodRuleEntry 4 }

layer7NewCfgHttpmodRuleAction OBJECT-TYPE
    SYNTAX   INTEGER {
        insert(1),
        replace(2),
        remove(3),
        none(4)
    }
    MAX-ACCESS  read-create
    STATUS  current
    DESCRIPTION
        "Defines rule action (default none)."
    ::= { layer7NewCfgHttpmodRuleEntry 5 }

layer7NewCfgHttpmodRuleAdminStatus OBJECT-TYPE
    SYNTAX   INTEGER {
        enable(1),
        disable(2)
        }
    MAX-ACCESS  read-create
    STATUS  current
    DESCRIPTION
        "Status (enable/disable) of rule."
    ::= { layer7NewCfgHttpmodRuleEntry 6 }

layer7NewCfgHttpmodRuleCopy OBJECT-TYPE
    SYNTAX   DisplayString 
    MAX-ACCESS  read-create
    STATUS  current
    DESCRIPTION
        "Copy rules."
    ::= { layer7NewCfgHttpmodRuleEntry 7 }

layer7NewCfgHttpmodRuleDelete OBJECT-TYPE
    SYNTAX  INTEGER {
        other(1),
        delete(2)
        }
    MAX-ACCESS  read-create
    STATUS  current
    DESCRIPTION
        "By setting the value to delete(2), the entire row is deleted."
    ::= { layer7NewCfgHttpmodRuleEntry 8 }

layer7NewCfgHttpmodRuleElement OBJECT-TYPE
    SYNTAX   INTEGER {
        url(1),
        header(2),
        cookie(3),
        filetype(4),
        statusline(5),
        text(6)
        }
    MAX-ACCESS  read-create
    STATUS  current
    DESCRIPTION
        "Element to be modified."
    ::= { layer7NewCfgHttpmodRuleEntry 9 }

layer7NewCfgHttpmodRuleHttpBody OBJECT-TYPE
    SYNTAX   INTEGER {
        include(1),
        exclude(2)
        }
    MAX-ACCESS  read-create
    STATUS  current
    DESCRIPTION
        "Modifications to also be done in the HTTP body."
    ::= { layer7NewCfgHttpmodRuleEntry 10 }


layer7CurCfgHttpmodRuleUrlTable OBJECT-TYPE
    SYNTAX  SEQUENCE OF Layer7CurCfgHttpmodRuleUrlEntry
    MAX-ACCESS  not-accessible
    STATUS  current
    DESCRIPTION
        "The table for configuring HTTP content modification rules."
    ::= { httpModCfg 5 }

layer7CurCfgHttpmodRuleUrlEntry OBJECT-TYPE
    SYNTAX  Layer7CurCfgHttpmodRuleUrlEntry
    MAX-ACCESS  not-accessible
    STATUS  current
    DESCRIPTION
        "A row in the HTTP content modification rule table."
    INDEX   { layer7CurCfgHttpmodRuleUrlListIdIndex, layer7CurCfgHttpmodRuleUrlIndex }
    ::= { layer7CurCfgHttpmodRuleUrlTable 1 }

Layer7CurCfgHttpmodRuleUrlEntry ::= SEQUENCE {
    layer7CurCfgHttpmodRuleUrlListIdIndex       DisplayString,
    layer7CurCfgHttpmodRuleUrlIndex             INTEGER,
    layer7CurCfgHttpmodRuleUrlMtchProtcol       INTEGER,
    layer7CurCfgHttpmodRuleUrlMtchPort          Integer32,
    layer7CurCfgHttpmodRuleUrlMtchHostTyp       INTEGER,
    layer7CurCfgHttpmodRuleUrlMtchHost          DisplayString,
    layer7CurCfgHttpmodRuleUrlMtchPathTyp       INTEGER,
    layer7CurCfgHttpmodRuleUrlMtchPath          DisplayString,

    layer7CurCfgHttpmodRuleUrlMtchPgName        DisplayString,
    layer7CurCfgHttpmodRuleUrlMtchPgTyp         DisplayString,

    layer7CurCfgHttpmodRuleUrlActnProtcl        INTEGER,
    layer7CurCfgHttpmodRuleUrlActnPort          Integer32,
    layer7CurCfgHttpmodRuleUrlActnHostTyp       INTEGER,
    layer7CurCfgHttpmodRuleUrlActnHost          DisplayString,
    layer7CurCfgHttpmodRuleUrlActnHstSec        INTEGER,
    layer7CurCfgHttpmodRuleUrlActnHstRplc       DisplayString,
    layer7CurCfgHttpmodRuleUrlActnPathTyp       INTEGER,
    layer7CurCfgHttpmodRuleUrlActnPath          DisplayString,
    layer7CurCfgHttpmodRuleUrlActnPthSctn       INTEGER,
    layer7CurCfgHttpmodRuleUrlActnPthRplc       DisplayString,

    layer7CurCfgHttpmodRuleUrlActnPgName        DisplayString,
    layer7CurCfgHttpmodRuleUrlActnPgTyp         DisplayString
    }

layer7CurCfgHttpmodRuleUrlListIdIndex OBJECT-TYPE
    SYNTAX   DisplayString (SIZE (0..32))
    MAX-ACCESS  read-only
    STATUS  current
    DESCRIPTION
        "The HTTP Modification Rule List (key id) as an index."
    ::= { layer7CurCfgHttpmodRuleUrlEntry 1 }
    
layer7CurCfgHttpmodRuleUrlIndex OBJECT-TYPE
    SYNTAX   INTEGER
    MAX-ACCESS  read-only
    STATUS  current
    DESCRIPTION
        "The HTTP Modification Rule number as an index."
    ::= { layer7CurCfgHttpmodRuleUrlEntry 2 }

layer7CurCfgHttpmodRuleUrlMtchProtcol OBJECT-TYPE
    SYNTAX   INTEGER {
        http(1),
        https(2)
        }
    MAX-ACCESS  read-only
    STATUS  current
    DESCRIPTION
        "Match protocol."
    ::= { layer7CurCfgHttpmodRuleUrlEntry 3 }

layer7CurCfgHttpmodRuleUrlMtchPort OBJECT-TYPE
    SYNTAX   Integer32
    MAX-ACCESS  read-only
    STATUS  current
    DESCRIPTION
        "Match port."
    ::= { layer7CurCfgHttpmodRuleUrlEntry 4 }

layer7CurCfgHttpmodRuleUrlMtchHostTyp OBJECT-TYPE
    SYNTAX   INTEGER {
        suffix(1),
        prefix(2),
        equal(3),
        include(4),
        any(5)
        }
    MAX-ACCESS  read-only
    STATUS  current
    DESCRIPTION
        "Host match parameters."
    ::= { layer7CurCfgHttpmodRuleUrlEntry 5 }

layer7CurCfgHttpmodRuleUrlMtchHost OBJECT-TYPE
    SYNTAX   DisplayString (SIZE (0..250))
    MAX-ACCESS  read-only
    STATUS  current
    DESCRIPTION
        "Host to Match."
    ::= { layer7CurCfgHttpmodRuleUrlEntry  6 }

layer7CurCfgHttpmodRuleUrlMtchPathTyp OBJECT-TYPE
    SYNTAX   INTEGER {
        suffix(1),
        prefix(2),
        equal(3),
        include(4),
        any(5)
        }
    MAX-ACCESS  read-only
    STATUS  current
    DESCRIPTION
        "Path match parameters."
    ::= { layer7CurCfgHttpmodRuleUrlEntry 7 }

layer7CurCfgHttpmodRuleUrlMtchPath OBJECT-TYPE
    SYNTAX   DisplayString (SIZE (0..250))
    MAX-ACCESS  read-only
    STATUS  current
    DESCRIPTION
        "Path to match."
    ::= { layer7CurCfgHttpmodRuleUrlEntry  8 }

layer7CurCfgHttpmodRuleUrlMtchPgName OBJECT-TYPE
    SYNTAX   DisplayString (SIZE (0..250))
    MAX-ACCESS  read-only
    STATUS  current
    DESCRIPTION
        "Match page."
    ::= { layer7CurCfgHttpmodRuleUrlEntry 9 }

layer7CurCfgHttpmodRuleUrlMtchPgTyp OBJECT-TYPE
    SYNTAX   DisplayString (SIZE (0..250))
    MAX-ACCESS  read-only
    STATUS  current
    DESCRIPTION
        "Match page type."
    ::= { layer7CurCfgHttpmodRuleUrlEntry 10 }

layer7CurCfgHttpmodRuleUrlActnProtcl OBJECT-TYPE
    SYNTAX   INTEGER {
        http(1),
        https(2)
        }
    MAX-ACCESS  read-only
    STATUS  current
    DESCRIPTION
        "Action protocol."
    ::= { layer7CurCfgHttpmodRuleUrlEntry 11 }

layer7CurCfgHttpmodRuleUrlActnPort OBJECT-TYPE
    SYNTAX   Integer32
    MAX-ACCESS  read-only
    STATUS  current
    DESCRIPTION
        "Action port."
    ::= { layer7CurCfgHttpmodRuleUrlEntry 12 }

layer7CurCfgHttpmodRuleUrlActnHostTyp OBJECT-TYPE
    SYNTAX   INTEGER {
        insert(1),
        replace(2),
        remove(3),
        none(4)
        }
    MAX-ACCESS  read-only
    STATUS  current
    DESCRIPTION
        "Host action parameters."
    ::= { layer7CurCfgHttpmodRuleUrlEntry 13 }

layer7CurCfgHttpmodRuleUrlActnHost OBJECT-TYPE
    SYNTAX   DisplayString (SIZE (0..250))
    MAX-ACCESS  read-only
    STATUS  current
    DESCRIPTION
        "Host to Insert."
    ::= { layer7CurCfgHttpmodRuleUrlEntry 14 }

layer7CurCfgHttpmodRuleUrlActnHstSec OBJECT-TYPE
    SYNTAX   INTEGER {
        before(1),
        after(2)
        }
    MAX-ACCESS  read-only
    STATUS  current
    DESCRIPTION
        "Insert Matched Section."
    ::= { layer7CurCfgHttpmodRuleUrlEntry  15 }

layer7CurCfgHttpmodRuleUrlActnHstRplc OBJECT-TYPE
    SYNTAX   DisplayString (SIZE (0..250))
    MAX-ACCESS  read-only
    STATUS  current
    DESCRIPTION
        "New Host to Replace."
    ::= { layer7CurCfgHttpmodRuleUrlEntry  16 }

layer7CurCfgHttpmodRuleUrlActnPathTyp OBJECT-TYPE
    SYNTAX   INTEGER {
        insert(1),
        replace(2),
        remove(3),
        none(4)
        }
    MAX-ACCESS  read-only
    STATUS  current
    DESCRIPTION
        "Path action parameters."
    ::= { layer7CurCfgHttpmodRuleUrlEntry 17 }

layer7CurCfgHttpmodRuleUrlActnPath OBJECT-TYPE
    SYNTAX   DisplayString (SIZE (0..250))
    MAX-ACCESS  read-only
    STATUS  current
    DESCRIPTION
        "Path to Insert."
    ::= { layer7CurCfgHttpmodRuleUrlEntry  18 }

layer7CurCfgHttpmodRuleUrlActnPthSctn OBJECT-TYPE
    SYNTAX   INTEGER {
        before(1),
        after(2)
        }
    MAX-ACCESS  read-only
    STATUS  current
    DESCRIPTION
        "Insert Matched Section."
    ::= { layer7CurCfgHttpmodRuleUrlEntry  19 }

layer7CurCfgHttpmodRuleUrlActnPthRplc OBJECT-TYPE
    SYNTAX   DisplayString (SIZE (0..250))
    MAX-ACCESS  read-only
    STATUS  current
    DESCRIPTION
        "New Path to Replace."
    ::= { layer7CurCfgHttpmodRuleUrlEntry  20 }

layer7CurCfgHttpmodRuleUrlActnPgName OBJECT-TYPE
    SYNTAX   DisplayString (SIZE (0..250))
    MAX-ACCESS  read-only
    STATUS  current
    DESCRIPTION
        "Action page."
    ::= { layer7CurCfgHttpmodRuleUrlEntry 21 }

layer7CurCfgHttpmodRuleUrlActnPgTyp OBJECT-TYPE
    SYNTAX   DisplayString (SIZE (0..250))
    MAX-ACCESS  read-only
    STATUS  current
    DESCRIPTION
        "Action page type."
    ::= { layer7CurCfgHttpmodRuleUrlEntry 22 }


layer7NewCfgHttpmodRuleUrlTable OBJECT-TYPE
    SYNTAX  SEQUENCE OF Layer7NewCfgHttpmodRuleUrlEntry
    MAX-ACCESS  not-accessible
    STATUS  current
    DESCRIPTION
        "The table for configuring HTTP content modification rules."
    ::= { httpModCfg 6 }

layer7NewCfgHttpmodRuleUrlEntry OBJECT-TYPE
    SYNTAX  Layer7NewCfgHttpmodRuleUrlEntry
    MAX-ACCESS  not-accessible
    STATUS  current
    DESCRIPTION
        "A row in the HTTP content modification rule table."
    INDEX   { layer7NewCfgHttpmodRuleUrlListIdIndex, layer7NewCfgHttpmodRuleUrlIndex }
    ::= { layer7NewCfgHttpmodRuleUrlTable 1 }

Layer7NewCfgHttpmodRuleUrlEntry ::= SEQUENCE {
    layer7NewCfgHttpmodRuleUrlListIdIndex       DisplayString,
    layer7NewCfgHttpmodRuleUrlIndex             INTEGER,
    layer7NewCfgHttpmodRuleUrlMtchProtcol       INTEGER,
    layer7NewCfgHttpmodRuleUrlMtchPort          Integer32,
    layer7NewCfgHttpmodRuleUrlMtchHostTyp       INTEGER,
    layer7NewCfgHttpmodRuleUrlMtchHost          DisplayString,
    layer7NewCfgHttpmodRuleUrlMtchPathTyp       INTEGER,
    layer7NewCfgHttpmodRuleUrlMtchPath          DisplayString,

    layer7NewCfgHttpmodRuleUrlMtchPgName        DisplayString,
    layer7NewCfgHttpmodRuleUrlMtchPgTyp         DisplayString,

    layer7NewCfgHttpmodRuleUrlActnProtcl        INTEGER,
    layer7NewCfgHttpmodRuleUrlActnPort          Integer32,
    layer7NewCfgHttpmodRuleUrlActnHostTyp       INTEGER,
    layer7NewCfgHttpmodRuleUrlActnHost          DisplayString,
    layer7NewCfgHttpmodRuleUrlActnHstSec        INTEGER,
    layer7NewCfgHttpmodRuleUrlActnHstRplc       DisplayString,
    layer7NewCfgHttpmodRuleUrlActnPathTyp       INTEGER,
    layer7NewCfgHttpmodRuleUrlActnPath          DisplayString,
    layer7NewCfgHttpmodRuleUrlActnPthSctn       INTEGER,
    layer7NewCfgHttpmodRuleUrlActnPthRplc       DisplayString,

    layer7NewCfgHttpmodRuleUrlActnPgName        DisplayString,
    layer7NewCfgHttpmodRuleUrlActnPgTyp         DisplayString
    }

layer7NewCfgHttpmodRuleUrlListIdIndex OBJECT-TYPE
    SYNTAX   DisplayString (SIZE (0..32))
    MAX-ACCESS  read-only
    STATUS  current
    DESCRIPTION
        "The HTTP Modification Rule List (key id) as an index."
    ::= { layer7NewCfgHttpmodRuleUrlEntry 1 }

layer7NewCfgHttpmodRuleUrlIndex OBJECT-TYPE
    SYNTAX   INTEGER
    MAX-ACCESS  read-only
    STATUS  current
    DESCRIPTION
        "The HTTP Modification Rule number as an index."
    ::= { layer7NewCfgHttpmodRuleUrlEntry 2 }

layer7NewCfgHttpmodRuleUrlMtchProtcol OBJECT-TYPE
    SYNTAX   INTEGER {
        http(1),
        https(2)
        }
    MAX-ACCESS  read-create
    STATUS  current
    DESCRIPTION
        "Match protocol."
    ::= { layer7NewCfgHttpmodRuleUrlEntry 3 }

layer7NewCfgHttpmodRuleUrlMtchPort OBJECT-TYPE
    SYNTAX   Integer32
    MAX-ACCESS  read-create
    STATUS  current
    DESCRIPTION
        "Match port."
    ::= { layer7NewCfgHttpmodRuleUrlEntry 4 }

layer7NewCfgHttpmodRuleUrlMtchHostTyp OBJECT-TYPE
    SYNTAX   INTEGER {
        suffix(1),
        prefix(2),
        equal(3),
        include(4),
        any(5)
        }
    MAX-ACCESS  read-create
    STATUS  current
    DESCRIPTION
        "Host match parameters."
    ::= { layer7NewCfgHttpmodRuleUrlEntry 5 }

layer7NewCfgHttpmodRuleUrlMtchHost OBJECT-TYPE
    SYNTAX   DisplayString (SIZE (0..250))
    MAX-ACCESS  read-create
    STATUS  current
    DESCRIPTION
        "Host to Match."
    ::= { layer7NewCfgHttpmodRuleUrlEntry  6 }

layer7NewCfgHttpmodRuleUrlMtchPathTyp OBJECT-TYPE
    SYNTAX   INTEGER {
        suffix(1),
        prefix(2),
        equal(3),
        include(4),
        any(5)
        }
    MAX-ACCESS  read-create
    STATUS  current
    DESCRIPTION
        "Path match parameters."
    ::= { layer7NewCfgHttpmodRuleUrlEntry 7 }

layer7NewCfgHttpmodRuleUrlMtchPath OBJECT-TYPE
    SYNTAX   DisplayString (SIZE (0..250))
    MAX-ACCESS  read-create
    STATUS  current
    DESCRIPTION
        "Path to match."
    ::= { layer7NewCfgHttpmodRuleUrlEntry  8 }

layer7NewCfgHttpmodRuleUrlMtchPgName OBJECT-TYPE
    SYNTAX   DisplayString (SIZE (0..250))
    MAX-ACCESS  read-create
    STATUS  current
    DESCRIPTION
        "Match page."
    ::= { layer7NewCfgHttpmodRuleUrlEntry 9 }

layer7NewCfgHttpmodRuleUrlMtchPgTyp OBJECT-TYPE
    SYNTAX   DisplayString (SIZE (0..250))
    MAX-ACCESS  read-create
    STATUS  current
    DESCRIPTION
        "Match page type."
    ::= { layer7NewCfgHttpmodRuleUrlEntry 10 }

layer7NewCfgHttpmodRuleUrlActnProtcl OBJECT-TYPE
    SYNTAX   INTEGER {
        http(1),
        https(2)
        }
    MAX-ACCESS  read-create
    STATUS  current
    DESCRIPTION
        "Action protocol."
    ::= { layer7NewCfgHttpmodRuleUrlEntry 11 }

layer7NewCfgHttpmodRuleUrlActnPort OBJECT-TYPE
    SYNTAX   Integer32
    MAX-ACCESS  read-create
    STATUS  current
    DESCRIPTION
        "Action port."
    ::= { layer7NewCfgHttpmodRuleUrlEntry 12 }

layer7NewCfgHttpmodRuleUrlActnHostTyp OBJECT-TYPE
    SYNTAX   INTEGER {
        insert(1),
        replace(2),
        remove(3),
        none(4)
        }
    MAX-ACCESS  read-create
    STATUS  current
    DESCRIPTION
        "Host action parameters."
    ::= { layer7NewCfgHttpmodRuleUrlEntry 13 }

layer7NewCfgHttpmodRuleUrlActnHost OBJECT-TYPE
    SYNTAX   DisplayString (SIZE (0..250))
    MAX-ACCESS  read-create
    STATUS  current
    DESCRIPTION
        "Host to Insert."
    ::= { layer7NewCfgHttpmodRuleUrlEntry 14 }

layer7NewCfgHttpmodRuleUrlActnHstSec OBJECT-TYPE
    SYNTAX   INTEGER {
        before(1),
        after(2)
        }
    MAX-ACCESS  read-create
    STATUS  current
    DESCRIPTION
        "Insert Matched Section."
    ::= { layer7NewCfgHttpmodRuleUrlEntry 15 }

layer7NewCfgHttpmodRuleUrlActnHstRplc OBJECT-TYPE
    SYNTAX   DisplayString (SIZE (0..250))
    MAX-ACCESS  read-create
    STATUS  current
    DESCRIPTION
        "New Host to Replace."
    ::= { layer7NewCfgHttpmodRuleUrlEntry 16 }

layer7NewCfgHttpmodRuleUrlActnPathTyp OBJECT-TYPE
    SYNTAX   INTEGER {
        insert(1),
        replace(2),
        remove(3),
        none(4)
        }
    MAX-ACCESS  read-create
    STATUS  current
    DESCRIPTION
        "Path action parameters."
    ::= { layer7NewCfgHttpmodRuleUrlEntry 17 }

layer7NewCfgHttpmodRuleUrlActnPath OBJECT-TYPE
    SYNTAX   DisplayString (SIZE (0..250))
    MAX-ACCESS  read-create
    STATUS  current
    DESCRIPTION
        "Path to Insert."
    ::= { layer7NewCfgHttpmodRuleUrlEntry 18 }

layer7NewCfgHttpmodRuleUrlActnPthSctn OBJECT-TYPE
    SYNTAX   INTEGER {
        before(1),
        after(2)
        }
    MAX-ACCESS  read-create
    STATUS  current
    DESCRIPTION
        "Insert Matched Section."
    ::= { layer7NewCfgHttpmodRuleUrlEntry 19 }

layer7NewCfgHttpmodRuleUrlActnPthRplc OBJECT-TYPE
    SYNTAX   DisplayString (SIZE (0..250))
    MAX-ACCESS  read-create
    STATUS  current
    DESCRIPTION
        "New Path to Replace."
    ::= { layer7NewCfgHttpmodRuleUrlEntry 20 }

layer7NewCfgHttpmodRuleUrlActnPgName OBJECT-TYPE
    SYNTAX   DisplayString (SIZE (0..250))
    MAX-ACCESS  read-create
    STATUS  current
    DESCRIPTION
        "Action page."
    ::= { layer7NewCfgHttpmodRuleUrlEntry 21 }

layer7NewCfgHttpmodRuleUrlActnPgTyp OBJECT-TYPE
    SYNTAX   DisplayString (SIZE (0..250))
    MAX-ACCESS  read-create
    STATUS  current
    DESCRIPTION
        "Action page type."
    ::= { layer7NewCfgHttpmodRuleUrlEntry 22 }


layer7CurCfgHttpmodRuleHdrTable OBJECT-TYPE
    SYNTAX  SEQUENCE OF Layer7CurCfgHttpmodRuleHdrEntry
    MAX-ACCESS  not-accessible
    STATUS  current
    DESCRIPTION
        "The table for configuring HTTP content modification rules."
    ::= { httpModCfg 7 }

layer7CurCfgHttpmodRuleHdrEntry OBJECT-TYPE
    SYNTAX  Layer7CurCfgHttpmodRuleHdrEntry
    MAX-ACCESS  not-accessible
    STATUS  current
    DESCRIPTION
        "A row in the HTTP content modification rule table."
    INDEX   { layer7CurCfgHttpmodRuleHdrListIdIndex, layer7CurCfgHttpmodRuleHdrIndex }
    ::= { layer7CurCfgHttpmodRuleHdrTable 1 }

Layer7CurCfgHttpmodRuleHdrEntry ::= SEQUENCE {
    layer7CurCfgHttpmodRuleHdrListIdIndex       DisplayString,
    layer7CurCfgHttpmodRuleHdrIndex             INTEGER,
    layer7CurCfgHttpmodRuleHdrInsert            DisplayString,
    layer7CurCfgHttpmodRuleHdrValue             DisplayString,
    layer7CurCfgHttpmodRuleHdrElmnt             INTEGER,
    layer7CurCfgHttpmodRuleHdrElmntUrlHost      DisplayString,
    layer7CurCfgHttpmodRuleHdrElmntUrlPath      DisplayString,
    layer7CurCfgHttpmodRuleHdrElmntHdrField     DisplayString,
    layer7CurCfgHttpmodRuleHdrElmntHdrVal       DisplayString,
    layer7CurCfgHttpmodRuleHdrElmntCookey       DisplayString,
    layer7CurCfgHttpmodRuleHdrElmntCkieVal      DisplayString,
    layer7CurCfgHttpmodRuleHdrElmntFileTyp      DisplayString,
    layer7CurCfgHttpmodRuleHdrElmntStatusCode   Integer32,
    layer7CurCfgHttpmodRuleHdrElmntStatusTxt    DisplayString,
    layer7CurCfgHttpmodRuleHdrElmntTxt          DisplayString,
    layer7CurCfgHttpmodRuleHdrElmntRegx         DisplayString,

    layer7CurCfgHttpmodRuleHdrReplacHdr         DisplayString,
    layer7CurCfgHttpmodRuleHdrReplacVal         DisplayString,
    layer7CurCfgHttpmodRuleHdrReplacNewHdr      DisplayString,
    layer7CurCfgHttpmodRuleHdrReplacNewVal      DisplayString,

    layer7CurCfgHttpmodRuleHdrRemvHdr           DisplayString,
    layer7CurCfgHttpmodRuleHdrRemvVal           DisplayString
    }

layer7CurCfgHttpmodRuleHdrListIdIndex OBJECT-TYPE
    SYNTAX   DisplayString (SIZE (0..32))
    MAX-ACCESS  read-only
    STATUS  current
    DESCRIPTION
        "The HTTP Modification Rule List (key id) as an index."
    ::= { layer7CurCfgHttpmodRuleHdrEntry 1 }
    
layer7CurCfgHttpmodRuleHdrIndex OBJECT-TYPE
    SYNTAX   INTEGER
    MAX-ACCESS  read-only
    STATUS  current
    DESCRIPTION
        "The HTTP Modification Rule number as an index."
    ::= { layer7CurCfgHttpmodRuleHdrEntry 2 }

layer7CurCfgHttpmodRuleHdrInsert OBJECT-TYPE
    SYNTAX   DisplayString (SIZE (0..250))
    MAX-ACCESS  read-only
    STATUS  current
    DESCRIPTION
        "Header Field to Insert."
    ::= { layer7CurCfgHttpmodRuleHdrEntry 3 }

layer7CurCfgHttpmodRuleHdrValue OBJECT-TYPE
    SYNTAX   DisplayString (SIZE (0..250))
    MAX-ACCESS  read-only
    STATUS  current
    DESCRIPTION
        "Value to Insert."
    ::= { layer7CurCfgHttpmodRuleHdrEntry 4 }

layer7CurCfgHttpmodRuleHdrElmnt OBJECT-TYPE
    SYNTAX   INTEGER {
        url(1),
        header(2),
        cookie(3),
        filetype(4),
        statusline(5),
        text(6),
        regex(7),
        none(8)
        }
    MAX-ACCESS  read-only
    STATUS  current
    DESCRIPTION
        "Element to match."
    ::= { layer7CurCfgHttpmodRuleHdrEntry 5 }

layer7CurCfgHttpmodRuleHdrElmntUrlHost OBJECT-TYPE
    SYNTAX   DisplayString (SIZE (0..250))
    MAX-ACCESS  read-only
    STATUS  current
    DESCRIPTION
        "Host to match."
    ::= { layer7CurCfgHttpmodRuleHdrEntry 6 }

layer7CurCfgHttpmodRuleHdrElmntUrlPath OBJECT-TYPE
    SYNTAX   DisplayString (SIZE (0..250))
    MAX-ACCESS  read-only
    STATUS  current
    DESCRIPTION
        "Path to match."
    ::= { layer7CurCfgHttpmodRuleHdrEntry 7 }

layer7CurCfgHttpmodRuleHdrElmntHdrField OBJECT-TYPE
    SYNTAX   DisplayString (SIZE (0..250))
    MAX-ACCESS  read-only
    STATUS  current
    DESCRIPTION
        "Header Field to Match."
    ::= { layer7CurCfgHttpmodRuleHdrEntry 8 }

layer7CurCfgHttpmodRuleHdrElmntHdrVal  OBJECT-TYPE
    SYNTAX   DisplayString (SIZE (0..250))
    MAX-ACCESS  read-only
    STATUS  current
    DESCRIPTION
        "Value to Match."
    ::= { layer7CurCfgHttpmodRuleHdrEntry 9 }

layer7CurCfgHttpmodRuleHdrElmntCookey  OBJECT-TYPE
    SYNTAX   DisplayString (SIZE (0..20))
    MAX-ACCESS  read-only
    STATUS  current
    DESCRIPTION
        "Cookie Key to Match."
    ::= { layer7CurCfgHttpmodRuleHdrEntry 10 }

layer7CurCfgHttpmodRuleHdrElmntCkieVal  OBJECT-TYPE
    SYNTAX   DisplayString (SIZE (0..20))
    MAX-ACCESS  read-only
    STATUS  current
    DESCRIPTION
        "Cookie Value to Match."
    ::= { layer7CurCfgHttpmodRuleHdrEntry 11 }

layer7CurCfgHttpmodRuleHdrElmntFileTyp  OBJECT-TYPE
    SYNTAX   DisplayString (SIZE (0..250))
    MAX-ACCESS  read-only
    STATUS  current
    DESCRIPTION
        "File Type To Match."
    ::= { layer7CurCfgHttpmodRuleHdrEntry 12 }

layer7CurCfgHttpmodRuleHdrElmntStatusCode OBJECT-TYPE
    SYNTAX   Integer32
    MAX-ACCESS  read-only
    STATUS  current
    DESCRIPTION
        "Status Code to Match."
    ::= { layer7CurCfgHttpmodRuleHdrEntry 13 }

layer7CurCfgHttpmodRuleHdrElmntStatusTxt  OBJECT-TYPE
    SYNTAX   DisplayString (SIZE (0..250))
    MAX-ACCESS  read-only
    STATUS  current
    DESCRIPTION
        "Status Text to Match."
    ::= { layer7CurCfgHttpmodRuleHdrEntry 14 }

layer7CurCfgHttpmodRuleHdrElmntTxt   OBJECT-TYPE
    SYNTAX   DisplayString (SIZE (0..250))
    MAX-ACCESS  read-only
    STATUS  current
    DESCRIPTION
        "Text to Match."
    ::= { layer7CurCfgHttpmodRuleHdrEntry 15 }

layer7CurCfgHttpmodRuleHdrElmntRegx  OBJECT-TYPE
    SYNTAX   DisplayString (SIZE (0..250))
    MAX-ACCESS  read-only
    STATUS  current
    DESCRIPTION
        "Regex to Match."
    ::= { layer7CurCfgHttpmodRuleHdrEntry 16 }

layer7CurCfgHttpmodRuleHdrReplacHdr  OBJECT-TYPE
    SYNTAX   DisplayString (SIZE (0..250))
    MAX-ACCESS  read-only
    STATUS  current
    DESCRIPTION
        "Header Field to Replace."
    ::= { layer7CurCfgHttpmodRuleHdrEntry 17 }

layer7CurCfgHttpmodRuleHdrReplacVal  OBJECT-TYPE
    SYNTAX   DisplayString (SIZE (0..250))
    MAX-ACCESS  read-only
    STATUS  current
    DESCRIPTION
        "Value to Replace."
    ::= { layer7CurCfgHttpmodRuleHdrEntry 18 }

layer7CurCfgHttpmodRuleHdrReplacNewHdr  OBJECT-TYPE
    SYNTAX   DisplayString (SIZE (0..250))
    MAX-ACCESS  read-only
    STATUS  current
    DESCRIPTION
        "New Header Field."
    ::= { layer7CurCfgHttpmodRuleHdrEntry 19 }

layer7CurCfgHttpmodRuleHdrReplacNewVal  OBJECT-TYPE
    SYNTAX   DisplayString (SIZE (0..250))
    MAX-ACCESS  read-only
    STATUS  current
    DESCRIPTION
        "New Value."
    ::= { layer7CurCfgHttpmodRuleHdrEntry 20 }

layer7CurCfgHttpmodRuleHdrRemvHdr  OBJECT-TYPE
    SYNTAX   DisplayString (SIZE (0..250))
    MAX-ACCESS  read-only
    STATUS  current
    DESCRIPTION
        "Header Field to Remove."
    ::= { layer7CurCfgHttpmodRuleHdrEntry 21 }

layer7CurCfgHttpmodRuleHdrRemvVal  OBJECT-TYPE
    SYNTAX   DisplayString (SIZE (0..250))
    MAX-ACCESS  read-only
    STATUS  current
    DESCRIPTION
        "Value to Remove."
    ::= { layer7CurCfgHttpmodRuleHdrEntry 22 }


layer7NewCfgHttpmodRuleHdrTable OBJECT-TYPE
    SYNTAX  SEQUENCE OF Layer7NewCfgHttpmodRuleHdrEntry
    MAX-ACCESS  not-accessible
    STATUS  current
    DESCRIPTION
        "The table for configuring HTTP content modification rules."
    ::= { httpModCfg 8 }

layer7NewCfgHttpmodRuleHdrEntry OBJECT-TYPE
    SYNTAX  Layer7NewCfgHttpmodRuleHdrEntry
    MAX-ACCESS  not-accessible
    STATUS  current
    DESCRIPTION
        "A row in the HTTP content modification rule table."
    INDEX   { layer7NewCfgHttpmodRuleHdrListIdIndex, layer7NewCfgHttpmodRuleHdrIndex }
    ::= { layer7NewCfgHttpmodRuleHdrTable 1 }

Layer7NewCfgHttpmodRuleHdrEntry ::= SEQUENCE {
    layer7NewCfgHttpmodRuleHdrListIdIndex          DisplayString,
    layer7NewCfgHttpmodRuleHdrIndex                INTEGER,
    layer7NewCfgHttpmodRuleHdrInsert            DisplayString,
    layer7NewCfgHttpmodRuleHdrValue             DisplayString,
    layer7NewCfgHttpmodRuleHdrElmnt             INTEGER,
    layer7NewCfgHttpmodRuleHdrElmntUrlHost      DisplayString,
    layer7NewCfgHttpmodRuleHdrElmntUrlPath      DisplayString,
    layer7NewCfgHttpmodRuleHdrElmntHdrField     DisplayString,
    layer7NewCfgHttpmodRuleHdrElmntHdrVal       DisplayString,
    layer7NewCfgHttpmodRuleHdrElmntCookey       DisplayString,
    layer7NewCfgHttpmodRuleHdrElmntCkieVal      DisplayString,
    layer7NewCfgHttpmodRuleHdrElmntFileTyp      DisplayString,
    layer7NewCfgHttpmodRuleHdrElmntStatusCode   Integer32,
    layer7NewCfgHttpmodRuleHdrElmntStatusTxt    DisplayString,
    layer7NewCfgHttpmodRuleHdrElmntTxt          DisplayString,
    layer7NewCfgHttpmodRuleHdrElmntRegx         DisplayString,

    layer7NewCfgHttpmodRuleHdrReplacHdr         DisplayString,
    layer7NewCfgHttpmodRuleHdrReplacVal         DisplayString,
    layer7NewCfgHttpmodRuleHdrReplacNewHdr      DisplayString,
    layer7NewCfgHttpmodRuleHdrReplacNewVal      DisplayString,

    layer7NewCfgHttpmodRuleHdrRemvHdr           DisplayString,
    layer7NewCfgHttpmodRuleHdrRemvVal           DisplayString
    }

layer7NewCfgHttpmodRuleHdrListIdIndex OBJECT-TYPE
    SYNTAX   DisplayString (SIZE (0..32))
    MAX-ACCESS  read-only
    STATUS  current
    DESCRIPTION
        "The HTTP Modification Rule List (key id) as an index."
    ::= { layer7NewCfgHttpmodRuleHdrEntry 1 }

layer7NewCfgHttpmodRuleHdrIndex OBJECT-TYPE
    SYNTAX   INTEGER
    MAX-ACCESS  read-only
    STATUS  current
    DESCRIPTION
        "The HTTP Modification Rule number as an index."
    ::= { layer7NewCfgHttpmodRuleHdrEntry 2 }

layer7NewCfgHttpmodRuleHdrInsert OBJECT-TYPE
    SYNTAX   DisplayString (SIZE (0..250))
    MAX-ACCESS  read-create
    STATUS  current
    DESCRIPTION
        "Header Field to Insert."
    ::= { layer7NewCfgHttpmodRuleHdrEntry 3 }

layer7NewCfgHttpmodRuleHdrValue OBJECT-TYPE
    SYNTAX   DisplayString (SIZE (0..250))
    MAX-ACCESS  read-create
    STATUS  current
    DESCRIPTION
        "Value to Insert."
    ::= { layer7NewCfgHttpmodRuleHdrEntry 4 }

layer7NewCfgHttpmodRuleHdrElmnt OBJECT-TYPE
    SYNTAX   INTEGER {
        url(1),
        header(2),
        cookie(3),
        filetype(4),
        statusline(5),
        text(6),
        regex(7),
        none(8)
        }
    MAX-ACCESS  read-create
    STATUS  current
    DESCRIPTION
        "Element to match."
    ::= { layer7NewCfgHttpmodRuleHdrEntry 5 }

layer7NewCfgHttpmodRuleHdrElmntUrlHost OBJECT-TYPE
    SYNTAX   DisplayString (SIZE (0..250))
    MAX-ACCESS  read-create
    STATUS  current
    DESCRIPTION
        "Host to match."
    ::= { layer7NewCfgHttpmodRuleHdrEntry 6 }

layer7NewCfgHttpmodRuleHdrElmntUrlPath OBJECT-TYPE
    SYNTAX   DisplayString (SIZE (0..250))
    MAX-ACCESS  read-create
    STATUS  current
    DESCRIPTION
        "Path to match."
    ::= { layer7NewCfgHttpmodRuleHdrEntry 7 }

layer7NewCfgHttpmodRuleHdrElmntHdrField OBJECT-TYPE
    SYNTAX   DisplayString (SIZE (0..250))
    MAX-ACCESS  read-create
    STATUS  current
    DESCRIPTION
        "Header Field to Match."
    ::= { layer7NewCfgHttpmodRuleHdrEntry 8 }

layer7NewCfgHttpmodRuleHdrElmntHdrVal  OBJECT-TYPE
    SYNTAX   DisplayString (SIZE (0..250))
    MAX-ACCESS  read-create
    STATUS  current
    DESCRIPTION
        "Value to Match."
    ::= { layer7NewCfgHttpmodRuleHdrEntry 9 }

layer7NewCfgHttpmodRuleHdrElmntCookey  OBJECT-TYPE
    SYNTAX   DisplayString (SIZE (0..20))
    MAX-ACCESS  read-create
    STATUS  current
    DESCRIPTION
        "Cookie Key to Match."
    ::= { layer7NewCfgHttpmodRuleHdrEntry 10 }

layer7NewCfgHttpmodRuleHdrElmntCkieVal  OBJECT-TYPE
    SYNTAX   DisplayString (SIZE (0..20))
    MAX-ACCESS  read-create
    STATUS  current
    DESCRIPTION
        "Cookie Value to Match."
    ::= { layer7NewCfgHttpmodRuleHdrEntry 11 }

layer7NewCfgHttpmodRuleHdrElmntFileTyp  OBJECT-TYPE
    SYNTAX   DisplayString (SIZE (0..250))
    MAX-ACCESS  read-create
    STATUS  current
    DESCRIPTION
        "File Type To Match."
    ::= { layer7NewCfgHttpmodRuleHdrEntry 12 }

layer7NewCfgHttpmodRuleHdrElmntStatusCode OBJECT-TYPE
    SYNTAX   Integer32
    MAX-ACCESS  read-create
    STATUS  current
    DESCRIPTION
        "Status Code to Match."
    ::= { layer7NewCfgHttpmodRuleHdrEntry 13 }

layer7NewCfgHttpmodRuleHdrElmntStatusTxt  OBJECT-TYPE
    SYNTAX   DisplayString (SIZE (0..250))
    MAX-ACCESS  read-create
    STATUS  current
    DESCRIPTION
        "Status Text to Match."
    ::= { layer7NewCfgHttpmodRuleHdrEntry 14 }

layer7NewCfgHttpmodRuleHdrElmntTxt   OBJECT-TYPE
    SYNTAX   DisplayString (SIZE (0..250))
    MAX-ACCESS  read-create
    STATUS  current
    DESCRIPTION
        "Text to Match."
    ::= { layer7NewCfgHttpmodRuleHdrEntry 15 }

layer7NewCfgHttpmodRuleHdrElmntRegx  OBJECT-TYPE
    SYNTAX   DisplayString (SIZE (0..250))
    MAX-ACCESS  read-create
    STATUS  current
    DESCRIPTION
        "Regex to Match."
    ::= { layer7NewCfgHttpmodRuleHdrEntry 16 }

layer7NewCfgHttpmodRuleHdrReplacHdr  OBJECT-TYPE
    SYNTAX   DisplayString (SIZE (0..249))
    MAX-ACCESS  read-create
    STATUS  current
    DESCRIPTION
        "Header Field to Replace."
    ::= { layer7NewCfgHttpmodRuleHdrEntry 17 }

layer7NewCfgHttpmodRuleHdrReplacVal  OBJECT-TYPE
    SYNTAX   DisplayString (SIZE (0..249))
    MAX-ACCESS  read-create
    STATUS  current
    DESCRIPTION
        "Value to Replace."
    ::= { layer7NewCfgHttpmodRuleHdrEntry 18 }

layer7NewCfgHttpmodRuleHdrReplacNewHdr  OBJECT-TYPE
    SYNTAX   DisplayString (SIZE (0..249))
    MAX-ACCESS  read-create
    STATUS  current
    DESCRIPTION
        "New Header Field."
    ::= { layer7NewCfgHttpmodRuleHdrEntry 19 }

layer7NewCfgHttpmodRuleHdrReplacNewVal  OBJECT-TYPE
    SYNTAX   DisplayString (SIZE (0..249))
    MAX-ACCESS  read-create
    STATUS  current
    DESCRIPTION
        "New Value."
    ::= { layer7NewCfgHttpmodRuleHdrEntry 20 }

layer7NewCfgHttpmodRuleHdrRemvHdr  OBJECT-TYPE
    SYNTAX   DisplayString (SIZE (0..250))
    MAX-ACCESS  read-create
    STATUS  current
    DESCRIPTION
        "Header Field to Remove."
    ::= { layer7NewCfgHttpmodRuleHdrEntry 21 }

layer7NewCfgHttpmodRuleHdrRemvVal  OBJECT-TYPE
    SYNTAX   DisplayString (SIZE (0..250))
    MAX-ACCESS  read-create
    STATUS  current
    DESCRIPTION
        "Value to Remove."
    ::= { layer7NewCfgHttpmodRuleHdrEntry 22 }


layer7CurCfgHttpmodRuleCookieTable OBJECT-TYPE
    SYNTAX  SEQUENCE OF Layer7CurCfgHttpmodRuleCookieEntry
    MAX-ACCESS  not-accessible
    STATUS  current
    DESCRIPTION
        "The table for configuring HTTP content modification rules."
    ::= { httpModCfg 9 }

layer7CurCfgHttpmodRuleCookieEntry OBJECT-TYPE
    SYNTAX  Layer7CurCfgHttpmodRuleCookieEntry
    MAX-ACCESS  not-accessible
    STATUS  current
    DESCRIPTION
        "A row in the HTTP content modification rule table."
    INDEX   { layer7CurCfgHttpmodRuleCookieListIdIndex, layer7CurCfgHttpmodRuleCookieIndex }
    ::= { layer7CurCfgHttpmodRuleCookieTable 1 }

Layer7CurCfgHttpmodRuleCookieEntry ::= SEQUENCE {
    layer7CurCfgHttpmodRuleCookieListIdIndex    DisplayString,
    layer7CurCfgHttpmodRuleCookieIndex          INTEGER,
    layer7CurCfgHttpmodRuleCookieInsrtKey       DisplayString,
    layer7CurCfgHttpmodRuleCookieInsrtVal       DisplayString,
    layer7CurCfgHttpmodRuleCookieInsrtPath      DisplayString,
    layer7CurCfgHttpmodRuleCookieInsrtDomn      DisplayString,
    layer7CurCfgHttpmodRuleCookieInsrtExp       DisplayString,
    layer7CurCfgHttpmodRuleCookieInsrtElem      INTEGER,
    layer7CurCfgHttpmodRuleCookieInsrtUrlHost   DisplayString,
    layer7CurCfgHttpmodRuleCookieInsrtUrlPath   DisplayString,
    layer7CurCfgHttpmodRuleCookieInsrtHdrFld    DisplayString,
    layer7CurCfgHttpmodRuleCookieInsrtHdrVal    DisplayString,
    layer7CurCfgHttpmodRuleCookieInsrtCookey    DisplayString,
    layer7CurCfgHttpmodRuleCookieInsrtCookieVal DisplayString,
    layer7CurCfgHttpmodRuleCookieInsrtFiletyp   DisplayString,
    layer7CurCfgHttpmodRuleCookieInsrtStatsCode Integer32,
    layer7CurCfgHttpmodRuleCookieInsrtStatsTxt  DisplayString,
    layer7CurCfgHttpmodRuleCookieInsrtTxt       DisplayString,
    layer7CurCfgHttpmodRuleCookieInsrtRegx      DisplayString,

    layer7CurCfgHttpmodRuleCookieReplcCookey    DisplayString,
    layer7CurCfgHttpmodRuleCookieReplcVal       DisplayString,
    layer7CurCfgHttpmodRuleCookieReplcNewKey    DisplayString,
    layer7CurCfgHttpmodRuleCookieReplcNewVal    DisplayString,

    layer7CurCfgHttpmodRuleCookieRemvCookey     DisplayString,
    layer7CurCfgHttpmodRuleCookieRemvCookieVal  DisplayString
    }

layer7CurCfgHttpmodRuleCookieListIdIndex OBJECT-TYPE
    SYNTAX   DisplayString (SIZE (0..32))
    MAX-ACCESS  read-only
    STATUS  current
    DESCRIPTION
        "The HTTP Modification Rule List (key id) as an index."
    ::= { layer7CurCfgHttpmodRuleCookieEntry 1 }
    
layer7CurCfgHttpmodRuleCookieIndex OBJECT-TYPE
    SYNTAX   INTEGER
    MAX-ACCESS  read-only
    STATUS  current
    DESCRIPTION
        "The HTTP Modification Rule number as an index."
    ::= { layer7CurCfgHttpmodRuleCookieEntry 2 }

layer7CurCfgHttpmodRuleCookieInsrtKey  OBJECT-TYPE
    SYNTAX   DisplayString (SIZE (0..20))
    MAX-ACCESS  read-only
    STATUS  current
    DESCRIPTION
        "Cookie Key to Insert."
    ::= { layer7CurCfgHttpmodRuleCookieEntry 3 }

layer7CurCfgHttpmodRuleCookieInsrtVal  OBJECT-TYPE
    SYNTAX   DisplayString (SIZE (0..20))
    MAX-ACCESS  read-only
    STATUS  current
    DESCRIPTION
        "Cookie Value to Insert."
    ::= { layer7CurCfgHttpmodRuleCookieEntry 4 }

layer7CurCfgHttpmodRuleCookieInsrtPath  OBJECT-TYPE
    SYNTAX   DisplayString (SIZE (0..32))
    MAX-ACCESS  read-only
    STATUS  current
    DESCRIPTION
        "Cookie Path to Insert."
    ::= { layer7CurCfgHttpmodRuleCookieEntry 5 }

layer7CurCfgHttpmodRuleCookieInsrtDomn  OBJECT-TYPE
    SYNTAX   DisplayString (SIZE (0..65))
    MAX-ACCESS  read-only
    STATUS  current
    DESCRIPTION
        "Cookie Domain Name to Insert."
    ::= { layer7CurCfgHttpmodRuleCookieEntry 6 }

layer7CurCfgHttpmodRuleCookieInsrtExp  OBJECT-TYPE
    SYNTAX   DisplayString (SIZE (0..64))
    MAX-ACCESS  read-only
    STATUS  current
    DESCRIPTION
        "Cookie Expiration Time to Insert."
    ::= { layer7CurCfgHttpmodRuleCookieEntry 7 }

layer7CurCfgHttpmodRuleCookieInsrtElem  OBJECT-TYPE
    SYNTAX   INTEGER {
        url(1),
        header(2),
        cookie(3),
        filetype(4),
        statusline(5),
        text(6),
        regex(7),
        none(8)
        }
    MAX-ACCESS  read-only
    STATUS  current
    DESCRIPTION
        "Element to match."
    ::= { layer7CurCfgHttpmodRuleCookieEntry 8 }

layer7CurCfgHttpmodRuleCookieInsrtUrlHost  OBJECT-TYPE
    SYNTAX   DisplayString (SIZE (0..250))
    MAX-ACCESS  read-only
    STATUS  current
    DESCRIPTION
        "Host to Match."
    ::= { layer7CurCfgHttpmodRuleCookieEntry 9 }

layer7CurCfgHttpmodRuleCookieInsrtUrlPath  OBJECT-TYPE
    SYNTAX   DisplayString (SIZE (0..250))
    MAX-ACCESS  read-only
    STATUS  current
    DESCRIPTION
        "Path to Match."
    ::= { layer7CurCfgHttpmodRuleCookieEntry 10 }

layer7CurCfgHttpmodRuleCookieInsrtHdrFld  OBJECT-TYPE
    SYNTAX   DisplayString (SIZE (0..250))
    MAX-ACCESS  read-only
    STATUS  current
    DESCRIPTION
        "Header Field to Match."
    ::= { layer7CurCfgHttpmodRuleCookieEntry 11 }

layer7CurCfgHttpmodRuleCookieInsrtHdrVal  OBJECT-TYPE
    SYNTAX   DisplayString (SIZE (0..250))
    MAX-ACCESS  read-only
    STATUS  current
    DESCRIPTION
        "Value to Match."
    ::= { layer7CurCfgHttpmodRuleCookieEntry 12 }

layer7CurCfgHttpmodRuleCookieInsrtCookey  OBJECT-TYPE
    SYNTAX   DisplayString (SIZE (0..20))
    MAX-ACCESS  read-only
    STATUS  current
    DESCRIPTION
        "Cookie Key to Match."
    ::= { layer7CurCfgHttpmodRuleCookieEntry 13 }

layer7CurCfgHttpmodRuleCookieInsrtCookieVal  OBJECT-TYPE
    SYNTAX   DisplayString (SIZE (0..20))
    MAX-ACCESS  read-only
    STATUS  current
    DESCRIPTION
        "Cookie Value to Match."
    ::= { layer7CurCfgHttpmodRuleCookieEntry 14 }

layer7CurCfgHttpmodRuleCookieInsrtFiletyp  OBJECT-TYPE
    SYNTAX   DisplayString (SIZE (0..250))
    MAX-ACCESS  read-only
    STATUS  current
    DESCRIPTION
        "File Type To Match."
    ::= { layer7CurCfgHttpmodRuleCookieEntry 15 }

layer7CurCfgHttpmodRuleCookieInsrtStatsCode  OBJECT-TYPE
    SYNTAX   Integer32
    MAX-ACCESS  read-only
    STATUS  current
    DESCRIPTION
        "Status Code to Match."
    ::= { layer7CurCfgHttpmodRuleCookieEntry 16 }

layer7CurCfgHttpmodRuleCookieInsrtStatsTxt  OBJECT-TYPE
    SYNTAX   DisplayString (SIZE (0..250))
    MAX-ACCESS  read-only
    STATUS  current
    DESCRIPTION
        "Status Text to Match."
    ::= { layer7CurCfgHttpmodRuleCookieEntry 17 }

layer7CurCfgHttpmodRuleCookieInsrtTxt   OBJECT-TYPE
    SYNTAX   DisplayString (SIZE (0..250))
    MAX-ACCESS  read-only
    STATUS  current
    DESCRIPTION
        "Text to Match."
    ::= { layer7CurCfgHttpmodRuleCookieEntry 18 }

layer7CurCfgHttpmodRuleCookieInsrtRegx  OBJECT-TYPE
    SYNTAX   DisplayString (SIZE (0..250))
    MAX-ACCESS  read-only
    STATUS  current
    DESCRIPTION
        "Regex to Match."
    ::= { layer7CurCfgHttpmodRuleCookieEntry 19 }

layer7CurCfgHttpmodRuleCookieReplcCookey  OBJECT-TYPE
    SYNTAX   DisplayString (SIZE (0..20))
    MAX-ACCESS  read-only
    STATUS  current
    DESCRIPTION
        "Cookie Key to Replace."
    ::= { layer7CurCfgHttpmodRuleCookieEntry 20 }

layer7CurCfgHttpmodRuleCookieReplcVal   OBJECT-TYPE
    SYNTAX   DisplayString (SIZE (0..20))
    MAX-ACCESS  read-only
    STATUS  current
    DESCRIPTION
        "Cookie Value to Replace."
    ::= { layer7CurCfgHttpmodRuleCookieEntry 21 }

layer7CurCfgHttpmodRuleCookieReplcNewKey  OBJECT-TYPE
    SYNTAX   DisplayString (SIZE (0..20))
    MAX-ACCESS  read-only
    STATUS  current
    DESCRIPTION
        "New Cookie Key."
    ::= { layer7CurCfgHttpmodRuleCookieEntry 22 }

layer7CurCfgHttpmodRuleCookieReplcNewVal OBJECT-TYPE
    SYNTAX   DisplayString (SIZE (0..20))
    MAX-ACCESS  read-only
    STATUS  current
    DESCRIPTION
        "New Cookie Value."
    ::= { layer7CurCfgHttpmodRuleCookieEntry 23 }

layer7CurCfgHttpmodRuleCookieRemvCookey  OBJECT-TYPE
    SYNTAX   DisplayString (SIZE (0..20))
    MAX-ACCESS  read-only
    STATUS  current
    DESCRIPTION
        "Cookie Key to Remove."
    ::= { layer7CurCfgHttpmodRuleCookieEntry 24 }

layer7CurCfgHttpmodRuleCookieRemvCookieVal OBJECT-TYPE
    SYNTAX   DisplayString (SIZE (0..20))
    MAX-ACCESS  read-only
    STATUS  current
    DESCRIPTION
        "Cookie Value to Remove."
    ::= { layer7CurCfgHttpmodRuleCookieEntry 25 }


layer7NewCfgHttpmodRuleCookieTable OBJECT-TYPE
    SYNTAX  SEQUENCE OF Layer7NewCfgHttpmodRuleCookieEntry
    MAX-ACCESS  not-accessible
    STATUS  current
    DESCRIPTION
        "The table for configuring HTTP content modification rules."
    ::= { httpModCfg 10 }

layer7NewCfgHttpmodRuleCookieEntry OBJECT-TYPE
    SYNTAX  Layer7NewCfgHttpmodRuleCookieEntry
    MAX-ACCESS  not-accessible
    STATUS  current
    DESCRIPTION
        "A row in the HTTP content modification rule table."
    INDEX   { layer7NewCfgHttpmodRuleCookieListIdIndex, layer7NewCfgHttpmodRuleCookieIndex }
    ::= { layer7NewCfgHttpmodRuleCookieTable 1 }

Layer7NewCfgHttpmodRuleCookieEntry ::= SEQUENCE {
    layer7NewCfgHttpmodRuleCookieListIdIndex    DisplayString,
    layer7NewCfgHttpmodRuleCookieIndex          INTEGER,
    layer7NewCfgHttpmodRuleCookieInsrtKey       DisplayString,
    layer7NewCfgHttpmodRuleCookieInsrtVal       DisplayString,
    layer7NewCfgHttpmodRuleCookieInsrtPath      DisplayString,
    layer7NewCfgHttpmodRuleCookieInsrtDomn      DisplayString,
    layer7NewCfgHttpmodRuleCookieInsrtExp       DisplayString,
    layer7NewCfgHttpmodRuleCookieInsrtElem      INTEGER,
    layer7NewCfgHttpmodRuleCookieInsrtUrlHost   DisplayString,
    layer7NewCfgHttpmodRuleCookieInsrtUrlPath   DisplayString,
    layer7NewCfgHttpmodRuleCookieInsrtHdrFld    DisplayString,
    layer7NewCfgHttpmodRuleCookieInsrtHdrVal    DisplayString,
    layer7NewCfgHttpmodRuleCookieInsrtCookey    DisplayString,
    layer7NewCfgHttpmodRuleCookieInsrtCookieVal DisplayString,
    layer7NewCfgHttpmodRuleCookieInsrtFiletyp   DisplayString,
    layer7NewCfgHttpmodRuleCookieInsrtStatsCode Integer32,
    layer7NewCfgHttpmodRuleCookieInsrtStatsTxt  DisplayString,
    layer7NewCfgHttpmodRuleCookieInsrtTxt       DisplayString,
    layer7NewCfgHttpmodRuleCookieInsrtRegx      DisplayString,

    layer7NewCfgHttpmodRuleCookieReplcCookey    DisplayString,
    layer7NewCfgHttpmodRuleCookieReplcVal       DisplayString,
    layer7NewCfgHttpmodRuleCookieReplcNewKey    DisplayString,
    layer7NewCfgHttpmodRuleCookieReplcNewVal    DisplayString,

    layer7NewCfgHttpmodRuleCookieRemvCookey     DisplayString,
    layer7NewCfgHttpmodRuleCookieRemvCookieVal  DisplayString
    }

layer7NewCfgHttpmodRuleCookieListIdIndex OBJECT-TYPE
    SYNTAX   DisplayString (SIZE (0..32))
    MAX-ACCESS  read-only
    STATUS  current
    DESCRIPTION
        "The HTTP Modification Rule List (key id) as an index."
    ::= { layer7NewCfgHttpmodRuleCookieEntry 1 }

layer7NewCfgHttpmodRuleCookieIndex OBJECT-TYPE
    SYNTAX   INTEGER
    MAX-ACCESS  read-only
    STATUS  current
    DESCRIPTION
        "The HTTP Modification Rule number as an index."
    ::= { layer7NewCfgHttpmodRuleCookieEntry 2 }

layer7NewCfgHttpmodRuleCookieInsrtKey  OBJECT-TYPE
    SYNTAX   DisplayString (SIZE (0..20))
    MAX-ACCESS  read-create
    STATUS  current
    DESCRIPTION
        "Cookie Key to Insert."
    ::= { layer7NewCfgHttpmodRuleCookieEntry 3 }

layer7NewCfgHttpmodRuleCookieInsrtVal  OBJECT-TYPE
    SYNTAX   DisplayString (SIZE (0..20))
    MAX-ACCESS  read-create
    STATUS  current
    DESCRIPTION
        "Cookie Value to Insert."
    ::= { layer7NewCfgHttpmodRuleCookieEntry 4 }

layer7NewCfgHttpmodRuleCookieInsrtPath  OBJECT-TYPE
    SYNTAX   DisplayString (SIZE (0..32))
    MAX-ACCESS  read-create
    STATUS  current
    DESCRIPTION
        "Cookie Path to Insert."
    ::= { layer7NewCfgHttpmodRuleCookieEntry 5 }

layer7NewCfgHttpmodRuleCookieInsrtDomn  OBJECT-TYPE
    SYNTAX   DisplayString (SIZE (0..65))
    MAX-ACCESS  read-create
    STATUS  current
    DESCRIPTION
        "Cookie Domain Name to Insert."
    ::= { layer7NewCfgHttpmodRuleCookieEntry 6 }

layer7NewCfgHttpmodRuleCookieInsrtExp  OBJECT-TYPE
    SYNTAX   DisplayString (SIZE (0..64))
    MAX-ACCESS  read-create
    STATUS  current
    DESCRIPTION
        "Cookie Expiration Time to Insert."
    ::= { layer7NewCfgHttpmodRuleCookieEntry 7 }

layer7NewCfgHttpmodRuleCookieInsrtElem  OBJECT-TYPE
    SYNTAX   INTEGER {
        url(1),
        header(2),
        cookie(3),
        filetype(4),
        statusline(5),
        text(6),
        regex(7),
        none(8)
        }
    MAX-ACCESS  read-create
    STATUS  current
    DESCRIPTION
        "Element to match."
    ::= { layer7NewCfgHttpmodRuleCookieEntry 8 }

layer7NewCfgHttpmodRuleCookieInsrtUrlHost  OBJECT-TYPE
    SYNTAX   DisplayString (SIZE (0..250))
    MAX-ACCESS  read-create
    STATUS  current
    DESCRIPTION
        "Host to Match."
    ::= { layer7NewCfgHttpmodRuleCookieEntry 9}

layer7NewCfgHttpmodRuleCookieInsrtUrlPath  OBJECT-TYPE
    SYNTAX   DisplayString (SIZE (0..250))
    MAX-ACCESS  read-create
    STATUS  current
    DESCRIPTION
        "Path to Match."
    ::= { layer7NewCfgHttpmodRuleCookieEntry 10 }

layer7NewCfgHttpmodRuleCookieInsrtHdrFld  OBJECT-TYPE
    SYNTAX   DisplayString (SIZE (0..250))
    MAX-ACCESS  read-create
    STATUS  current
    DESCRIPTION
        "Header Field to Match."
    ::= { layer7NewCfgHttpmodRuleCookieEntry 11 }

layer7NewCfgHttpmodRuleCookieInsrtHdrVal  OBJECT-TYPE
    SYNTAX   DisplayString (SIZE (0..250))
    MAX-ACCESS  read-create
    STATUS  current
    DESCRIPTION
        "Value to Match."
    ::= { layer7NewCfgHttpmodRuleCookieEntry 12 }

layer7NewCfgHttpmodRuleCookieInsrtCookey  OBJECT-TYPE
    SYNTAX   DisplayString (SIZE (0..20))
    MAX-ACCESS  read-create
    STATUS  current
    DESCRIPTION
        "Cookie Key to Match."
    ::= { layer7NewCfgHttpmodRuleCookieEntry 13 }

layer7NewCfgHttpmodRuleCookieInsrtCookieVal  OBJECT-TYPE
    SYNTAX   DisplayString (SIZE (0..20))
    MAX-ACCESS  read-create
    STATUS  current
    DESCRIPTION
        "Cookie Value to Match."
    ::= { layer7NewCfgHttpmodRuleCookieEntry 14 }

layer7NewCfgHttpmodRuleCookieInsrtFiletyp  OBJECT-TYPE
    SYNTAX   DisplayString (SIZE (0..250))
    MAX-ACCESS  read-create
    STATUS  current
    DESCRIPTION
        "File Type To Match."
    ::= { layer7NewCfgHttpmodRuleCookieEntry 15 }

layer7NewCfgHttpmodRuleCookieInsrtStatsCode  OBJECT-TYPE
    SYNTAX   Integer32
    MAX-ACCESS  read-create
    STATUS  current
    DESCRIPTION
        "Status Code to Match."
    ::= { layer7NewCfgHttpmodRuleCookieEntry 16}

layer7NewCfgHttpmodRuleCookieInsrtStatsTxt  OBJECT-TYPE
    SYNTAX   DisplayString (SIZE (0..250))
    MAX-ACCESS  read-create
    STATUS  current
    DESCRIPTION
        "Status Text to Match."
    ::= { layer7NewCfgHttpmodRuleCookieEntry 17 }

layer7NewCfgHttpmodRuleCookieInsrtTxt   OBJECT-TYPE
    SYNTAX   DisplayString (SIZE (0..250))
    MAX-ACCESS  read-create
    STATUS  current
    DESCRIPTION
        "Text to Match."
    ::= { layer7NewCfgHttpmodRuleCookieEntry 18 }

layer7NewCfgHttpmodRuleCookieInsrtRegx  OBJECT-TYPE
    SYNTAX   DisplayString (SIZE (0..250))
    MAX-ACCESS  read-create
    STATUS  current
    DESCRIPTION
        "Regex to Match."
    ::= { layer7NewCfgHttpmodRuleCookieEntry 19 }

layer7NewCfgHttpmodRuleCookieReplcCookey  OBJECT-TYPE
    SYNTAX   DisplayString (SIZE (0..20))
    MAX-ACCESS  read-create
    STATUS  current
    DESCRIPTION
        "Cookie Key to Replace."
    ::= { layer7NewCfgHttpmodRuleCookieEntry 20 }

layer7NewCfgHttpmodRuleCookieReplcVal   OBJECT-TYPE
    SYNTAX   DisplayString (SIZE (0..20))
    MAX-ACCESS  read-create
    STATUS  current
    DESCRIPTION
        "Cookie Value to Replace."
    ::= { layer7NewCfgHttpmodRuleCookieEntry 21 }

layer7NewCfgHttpmodRuleCookieReplcNewKey  OBJECT-TYPE
    SYNTAX   DisplayString (SIZE (0..20))
    MAX-ACCESS  read-create
    STATUS  current
    DESCRIPTION
        "New Cookie Key."
    ::= { layer7NewCfgHttpmodRuleCookieEntry 22 }

layer7NewCfgHttpmodRuleCookieReplcNewVal OBJECT-TYPE
    SYNTAX   DisplayString (SIZE (0..20))
    MAX-ACCESS  read-create
    STATUS  current
    DESCRIPTION
        "New Cookie Value."
    ::= { layer7NewCfgHttpmodRuleCookieEntry 23 }

layer7NewCfgHttpmodRuleCookieRemvCookey  OBJECT-TYPE
    SYNTAX   DisplayString (SIZE (0..20))
    MAX-ACCESS  read-create
    STATUS  current
    DESCRIPTION
        "Cookie Key to Remove."
    ::= { layer7NewCfgHttpmodRuleCookieEntry 24 }

layer7NewCfgHttpmodRuleCookieRemvCookieVal OBJECT-TYPE
    SYNTAX   DisplayString (SIZE (0..20))
    MAX-ACCESS  read-create
    STATUS  current
    DESCRIPTION
        "Cookie Value to Remove."
    ::= { layer7NewCfgHttpmodRuleCookieEntry 25 }


layer7CurCfgHttpmodRuleFileLineTextTable OBJECT-TYPE
    SYNTAX  SEQUENCE OF Layer7CurCfgHttpmodRuleFileLineTextEntry
    MAX-ACCESS  not-accessible
    STATUS  current
    DESCRIPTION
        "The table for configuring HTTP content modification rules."
    ::= { httpModCfg 11 }

layer7CurCfgHttpmodRuleFileLineTextEntry OBJECT-TYPE
    SYNTAX  Layer7CurCfgHttpmodRuleFileLineTextEntry
    MAX-ACCESS  not-accessible
    STATUS  current
    DESCRIPTION
        "A row in the HTTP content modification rule table."
    INDEX   { layer7CurCfgHttpmodRuleFileLineTextListIdIndex, layer7CurCfgHttpmodRuleFileLineTextIndex }
    ::= { layer7CurCfgHttpmodRuleFileLineTextTable 1 }

Layer7CurCfgHttpmodRuleFileLineTextEntry ::= SEQUENCE {
    layer7CurCfgHttpmodRuleFileLineTextListIdIndex  DisplayString,
    layer7CurCfgHttpmodRuleFileLineTextIndex        INTEGER,
    layer7CurCfgHttpmodRuleFileTypRep               DisplayString,
    layer7CurCfgHttpmodRuleFileTypNew               DisplayString,
    layer7CurCfgHttpmodRuleStatlineCode             Integer32,
    layer7CurCfgHttpmodRuleStatlineTxt              DisplayString,
    layer7CurCfgHttpmodRuleStatlineNewCode          Integer32,
    layer7CurCfgHttpmodRuleStatlineNewTxt           DisplayString,
    layer7CurCfgHttpmodRuleTextReplace              DisplayString,
    layer7CurCfgHttpmodRuleTextNewText              DisplayString,
    layer7CurCfgHttpmodRuleTextRemove               DisplayString
    }

layer7CurCfgHttpmodRuleFileLineTextListIdIndex OBJECT-TYPE
    SYNTAX   DisplayString (SIZE (0..32))
    MAX-ACCESS  read-only
    STATUS  current
    DESCRIPTION
        "The HTTP Modification Rule List (key id) as an index."
    ::= { layer7CurCfgHttpmodRuleFileLineTextEntry 1 }
    
layer7CurCfgHttpmodRuleFileLineTextIndex OBJECT-TYPE
    SYNTAX   INTEGER
    MAX-ACCESS  read-only
    STATUS  current
    DESCRIPTION
        "The HTTP Modification Rule number as an index."
    ::= { layer7CurCfgHttpmodRuleFileLineTextEntry 2 }

layer7CurCfgHttpmodRuleFileTypRep OBJECT-TYPE
    SYNTAX   DisplayString (SIZE (0..250))
    MAX-ACCESS  read-only
    STATUS  current
    DESCRIPTION
        "File Type to Replace."
    ::= { layer7CurCfgHttpmodRuleFileLineTextEntry  3 }

layer7CurCfgHttpmodRuleFileTypNew OBJECT-TYPE
    SYNTAX   DisplayString (SIZE (0..250))
    MAX-ACCESS  read-only
    STATUS  current
    DESCRIPTION
        "New File Type."
    ::= { layer7CurCfgHttpmodRuleFileLineTextEntry 4 }

layer7CurCfgHttpmodRuleStatlineCode  OBJECT-TYPE
    SYNTAX   Integer32
    MAX-ACCESS  read-only
    STATUS  current
    DESCRIPTION
        "Status Code to Replace."
    ::= { layer7CurCfgHttpmodRuleFileLineTextEntry 5 }

layer7CurCfgHttpmodRuleStatlineTxt OBJECT-TYPE
    SYNTAX   DisplayString (SIZE (0..250))
    MAX-ACCESS  read-only
    STATUS  current
    DESCRIPTION
        "Status Text to Replace."
    ::= { layer7CurCfgHttpmodRuleFileLineTextEntry 6 }

layer7CurCfgHttpmodRuleStatlineNewCode  OBJECT-TYPE
    SYNTAX   Integer32
    MAX-ACCESS  read-only
    STATUS  current
    DESCRIPTION
        "New Status Code."
    ::= { layer7CurCfgHttpmodRuleFileLineTextEntry 7 }

layer7CurCfgHttpmodRuleStatlineNewTxt OBJECT-TYPE
    SYNTAX   DisplayString (SIZE (0..250))
    MAX-ACCESS  read-only
    STATUS  current
    DESCRIPTION
        "New Status Text."
    ::= { layer7CurCfgHttpmodRuleFileLineTextEntry 8 }

layer7CurCfgHttpmodRuleTextReplace OBJECT-TYPE
    SYNTAX   DisplayString (SIZE (0..250))
    MAX-ACCESS  read-only
    STATUS  current
    DESCRIPTION
        "Text to Replace."
    ::= { layer7CurCfgHttpmodRuleFileLineTextEntry 9 }

layer7CurCfgHttpmodRuleTextNewText OBJECT-TYPE
    SYNTAX   DisplayString (SIZE (0..250))
    MAX-ACCESS  read-only
    STATUS  current
    DESCRIPTION
        "New Text."
    ::= { layer7CurCfgHttpmodRuleFileLineTextEntry 10 }

layer7CurCfgHttpmodRuleTextRemove OBJECT-TYPE
    SYNTAX   DisplayString (SIZE (0..250))
    MAX-ACCESS  read-only
    STATUS  current
    DESCRIPTION
    "Text to Remove."
    ::= { layer7CurCfgHttpmodRuleFileLineTextEntry 11 }


layer7NewCfgHttpmodRuleFileLineTextTable OBJECT-TYPE
    SYNTAX  SEQUENCE OF Layer7NewCfgHttpmodRuleFileLineTextEntry
    MAX-ACCESS  not-accessible
    STATUS  current
    DESCRIPTION
        "The table for configuring HTTP content modification rules."
    ::= { httpModCfg 12 }

layer7NewCfgHttpmodRuleFileLineTextEntry OBJECT-TYPE
    SYNTAX  Layer7NewCfgHttpmodRuleFileLineTextEntry
    MAX-ACCESS  not-accessible
    STATUS  current
    DESCRIPTION
        "A row in the HTTP content modification rule table."
    INDEX   { layer7NewCfgHttpmodRuleFileLineTextListIdIndex, layer7NewCfgHttpmodRuleFileLineTextIndex }
    ::= { layer7NewCfgHttpmodRuleFileLineTextTable 1 }

Layer7NewCfgHttpmodRuleFileLineTextEntry ::= SEQUENCE {
    layer7NewCfgHttpmodRuleFileLineTextListIdIndex  DisplayString,
    layer7NewCfgHttpmodRuleFileLineTextIndex        INTEGER,
    layer7NewCfgHttpmodRuleFileTypRep               DisplayString,
    layer7NewCfgHttpmodRuleFileTypNew               DisplayString,
    layer7NewCfgHttpmodRuleStatlineCode             Integer32,
    layer7NewCfgHttpmodRuleStatlineTxt              DisplayString,
    layer7NewCfgHttpmodRuleStatlineNewCode          Integer32,
    layer7NewCfgHttpmodRuleStatlineNewTxt           DisplayString,
    layer7NewCfgHttpmodRuleTextReplace              DisplayString,
    layer7NewCfgHttpmodRuleTextNewText              DisplayString,
    layer7NewCfgHttpmodRuleTextRemove               DisplayString
    }

layer7NewCfgHttpmodRuleFileLineTextListIdIndex OBJECT-TYPE
    SYNTAX   DisplayString (SIZE (0..32))
    MAX-ACCESS  read-only
    STATUS  current
    DESCRIPTION
        "The HTTP Modification Rule List (key id) as an index."
    ::= { layer7NewCfgHttpmodRuleFileLineTextEntry 1 }

layer7NewCfgHttpmodRuleFileLineTextIndex OBJECT-TYPE
    SYNTAX   INTEGER
    MAX-ACCESS  read-only
    STATUS  current
    DESCRIPTION
        "The HTTP Modification Rule number as an index."
    ::= { layer7NewCfgHttpmodRuleFileLineTextEntry 2 }

layer7NewCfgHttpmodRuleFileTypRep OBJECT-TYPE
    SYNTAX   DisplayString (SIZE (0..250))
    MAX-ACCESS  read-create
    STATUS  current
    DESCRIPTION
        "File Type to Replace."
    ::= { layer7NewCfgHttpmodRuleFileLineTextEntry  3 }

layer7NewCfgHttpmodRuleFileTypNew OBJECT-TYPE
    SYNTAX   DisplayString (SIZE (0..250))
    MAX-ACCESS  read-create
    STATUS  current
    DESCRIPTION
        "New File Type."
    ::= { layer7NewCfgHttpmodRuleFileLineTextEntry 4 }

layer7NewCfgHttpmodRuleStatlineCode  OBJECT-TYPE
    SYNTAX   Integer32
    MAX-ACCESS  read-create
    STATUS  current
    DESCRIPTION
        "Status Code to Replace."
    ::= { layer7NewCfgHttpmodRuleFileLineTextEntry 5 }

layer7NewCfgHttpmodRuleStatlineTxt OBJECT-TYPE
    SYNTAX   DisplayString (SIZE (0..250))
    MAX-ACCESS  read-create
    STATUS  current
    DESCRIPTION
        "Status Text to Replace."
    ::= { layer7NewCfgHttpmodRuleFileLineTextEntry 6 }

layer7NewCfgHttpmodRuleStatlineNewCode  OBJECT-TYPE
    SYNTAX   Integer32
    MAX-ACCESS  read-create
    STATUS  current
    DESCRIPTION
        "New Status Code."
    ::= { layer7NewCfgHttpmodRuleFileLineTextEntry 7 }

layer7NewCfgHttpmodRuleStatlineNewTxt OBJECT-TYPE
    SYNTAX   DisplayString (SIZE (0..250))
    MAX-ACCESS  read-create
    STATUS  current
    DESCRIPTION
        "New Status Text."
    ::= { layer7NewCfgHttpmodRuleFileLineTextEntry 8 }

layer7NewCfgHttpmodRuleTextReplace OBJECT-TYPE
    SYNTAX   DisplayString (SIZE (0..250))
    MAX-ACCESS  read-create
    STATUS  current
    DESCRIPTION
        "Text to Replace."
    ::= { layer7NewCfgHttpmodRuleFileLineTextEntry 9 }

layer7NewCfgHttpmodRuleTextNewText OBJECT-TYPE
    SYNTAX   DisplayString (SIZE (0..250))
    MAX-ACCESS  read-create
    STATUS  current
    DESCRIPTION
        "New Text."
    ::= { layer7NewCfgHttpmodRuleFileLineTextEntry 10 }

layer7NewCfgHttpmodRuleTextRemove OBJECT-TYPE
    SYNTAX   DisplayString (SIZE (0..250))
    MAX-ACCESS  read-create
    STATUS  current
    DESCRIPTION
        "Text to Remove."
    ::= { layer7NewCfgHttpmodRuleFileLineTextEntry 11 }


-- Layer7 Content Switching configuration

layer7CurCfgContentClassTable OBJECT-TYPE
    SYNTAX  SEQUENCE OF Layer7CurCfgContentClassEntry
    MAX-ACCESS  not-accessible
    STATUS  current
    DESCRIPTION
        "The table for configuring Content Class."
    ::= { contentClass 1 }

layer7CurCfgContentClassEntry OBJECT-TYPE
    SYNTAX  Layer7CurCfgContentClassEntry 
    MAX-ACCESS  not-accessible
    STATUS  current
    DESCRIPTION
        "A row in the Content Class table."
    INDEX   { layer7CurCfgContentClassID }
    ::= { layer7CurCfgContentClassTable 1 }

Layer7CurCfgContentClassEntry ::= SEQUENCE {
    layer7CurCfgContentClassID                DisplayString,
    layer7CurCfgContentClassName              DisplayString,
    layer7CurCfgContentClassLogicalExpression DisplayString,
    layer7CurCfgContentClassHostName          INTEGER,
    layer7CurCfgContentClassPath              INTEGER,
    layer7CurCfgContentClassFileName          INTEGER,
    layer7CurCfgContentClassFileType          INTEGER,
    layer7CurCfgContentClassHeader            INTEGER,
    layer7CurCfgContentClassCookie            INTEGER,
    layer7CurCfgContentClassText              INTEGER,
    layer7CurCfgContentClassXMLTag            INTEGER,
    layer7CurCfgContentClassType              INTEGER
    }

layer7CurCfgContentClassID OBJECT-TYPE
    SYNTAX   DisplayString (SIZE(0..32))
    MAX-ACCESS  read-only
    STATUS  current
    DESCRIPTION
        "The content Class ID(key id) as an index."
    ::= { layer7CurCfgContentClassEntry  1 }

layer7CurCfgContentClassName OBJECT-TYPE
    SYNTAX   DisplayString (SIZE(0..32))
    MAX-ACCESS  read-only
    STATUS  current
    DESCRIPTION
        "Content Class name."
    ::= { layer7CurCfgContentClassEntry  2 }

layer7CurCfgContentClassLogicalExpression OBJECT-TYPE
    SYNTAX   DisplayString (SIZE(0..255))
    MAX-ACCESS  read-only
    STATUS  current
    DESCRIPTION
        "Enter logical expression needs to be applied between classes."
    ::= { layer7CurCfgContentClassEntry  3 }

layer7CurCfgContentClassHostName OBJECT-TYPE
    SYNTAX      INTEGER { yes(1), no(2) }
    MAX-ACCESS  read-only
    STATUS  current
    DESCRIPTION
        "URL Hostname table is not empty for current content class."
    ::= { layer7CurCfgContentClassEntry  4 }

layer7CurCfgContentClassPath OBJECT-TYPE
    SYNTAX   INTEGER { yes(1), no(2) }
    MAX-ACCESS  read-only
    STATUS  current
    DESCRIPTION
        "URL path table is not empty for current content class."
    ::= { layer7CurCfgContentClassEntry  5 }

layer7CurCfgContentClassFileName OBJECT-TYPE
    SYNTAX   INTEGER { yes(1), no(2) }
    MAX-ACCESS  read-only
    STATUS  current
    DESCRIPTION
        "URL file name table is not empty for current content class."
    ::= { layer7CurCfgContentClassEntry  6 }

layer7CurCfgContentClassFileType OBJECT-TYPE
    SYNTAX   INTEGER { yes(1), no(2) }
    MAX-ACCESS  read-only
    STATUS  current
    DESCRIPTION
        "URL file type table is not empty for current content class."
    ::= { layer7CurCfgContentClassEntry  7 }

layer7CurCfgContentClassHeader OBJECT-TYPE
    SYNTAX   INTEGER { yes(1), no(2) }
    MAX-ACCESS  read-only
    STATUS  current
    DESCRIPTION
        "Header table is not empty for current content class."
    ::= { layer7CurCfgContentClassEntry  8 }

layer7CurCfgContentClassCookie OBJECT-TYPE
    SYNTAX   INTEGER { yes(1), no(2) }
    MAX-ACCESS  read-only
    STATUS  current
    DESCRIPTION
        "Cookie table is not empty for current content class."
    ::= { layer7CurCfgContentClassEntry  9 }

layer7CurCfgContentClassText OBJECT-TYPE
    SYNTAX   INTEGER { yes(1), no(2) }
    MAX-ACCESS  read-only
    STATUS  current
    DESCRIPTION
        "Text table is not empty for current content class."
    ::= { layer7CurCfgContentClassEntry  10 }

layer7CurCfgContentClassXMLTag OBJECT-TYPE
    SYNTAX   INTEGER { yes(1), no(2) }
    MAX-ACCESS  read-only
    STATUS  current
    DESCRIPTION
        "XML tag table is not empty for current content class."
    ::= { layer7CurCfgContentClassEntry  11 }

layer7CurCfgContentClassType OBJECT-TYPE
    SYNTAX   INTEGER { http(1), rtsp(3), ssl(6) }
    MAX-ACCESS  read-only
    STATUS  current
    DESCRIPTION
        "Content Class type."
    ::= { layer7CurCfgContentClassEntry  12 }

layer7NewCfgContentClassTable OBJECT-TYPE
    SYNTAX  SEQUENCE OF Layer7NewCfgContentClassEntry
    MAX-ACCESS  not-accessible
    STATUS  current
    DESCRIPTION
        "The table for configuring Content Class."
    ::= { contentClass 2 }

layer7NewCfgContentClassEntry OBJECT-TYPE
    SYNTAX  Layer7NewCfgContentClassEntry 
    MAX-ACCESS  not-accessible
    STATUS  current
    DESCRIPTION
        "Content Class name."
    INDEX   { layer7NewCfgContentClassID }
    ::= { layer7NewCfgContentClassTable 1 }

Layer7NewCfgContentClassEntry ::= SEQUENCE {
    layer7NewCfgContentClassID                DisplayString,
    layer7NewCfgContentClassName              DisplayString,
    layer7NewCfgContentClassLogicalExpression DisplayString,
    layer7NewCfgContentClassHostName          INTEGER,
    layer7NewCfgContentClassPath              INTEGER,
    layer7NewCfgContentClassFileName          INTEGER,
    layer7NewCfgContentClassFileType          INTEGER,
    layer7NewCfgContentClassHeader            INTEGER,
    layer7NewCfgContentClassCookie            INTEGER,
    layer7NewCfgContentClassText              INTEGER,
    layer7NewCfgContentClassXMLTag            INTEGER,
    layer7NewCfgContentClassDelete            INTEGER,
    layer7NewCfgContentClassCopy              DisplayString,
    layer7NewCfgContentClassType              INTEGER
    }

layer7NewCfgContentClassID OBJECT-TYPE
    SYNTAX   DisplayString (SIZE(0..32))
    MAX-ACCESS  read-create
    STATUS  current
    DESCRIPTION
        "The content Class ID(key id) as an index."
    ::= { layer7NewCfgContentClassEntry  1 }

layer7NewCfgContentClassName OBJECT-TYPE
    SYNTAX   DisplayString (SIZE(0..32))
    MAX-ACCESS  read-write
    STATUS  current
    DESCRIPTION
        "Content Class name."
    ::= { layer7NewCfgContentClassEntry  2 }

layer7NewCfgContentClassLogicalExpression OBJECT-TYPE
    SYNTAX   DisplayString (SIZE(0..255))
    MAX-ACCESS  read-write
    STATUS  current
    DESCRIPTION
        "Enter logical expression needs to be applied between classes.."
    ::= { layer7NewCfgContentClassEntry  3 }

layer7NewCfgContentClassHostName OBJECT-TYPE
    SYNTAX   INTEGER { yes(1), no(2) }
    MAX-ACCESS  read-only
    STATUS  current
    DESCRIPTION
        "URL host name table is not empty for current content class."
    ::= { layer7NewCfgContentClassEntry  4 }

layer7NewCfgContentClassPath OBJECT-TYPE
    SYNTAX   INTEGER { yes(1), no(2) }
    MAX-ACCESS  read-only
    STATUS  current
    DESCRIPTION
        "URL path table is not empty for current content class."
    ::= { layer7NewCfgContentClassEntry  5 }

layer7NewCfgContentClassFileName OBJECT-TYPE
    SYNTAX   INTEGER { yes(1), no(2) }
    MAX-ACCESS  read-only
    STATUS  current
    DESCRIPTION
        "URL file name table is not empty for current content class."
    ::= { layer7NewCfgContentClassEntry  6 }

layer7NewCfgContentClassFileType OBJECT-TYPE
    SYNTAX   INTEGER { yes(1), no(2) }
    MAX-ACCESS  read-only
    STATUS  current
    DESCRIPTION
        "URL file type table is not empty for current content class."
    ::= { layer7NewCfgContentClassEntry  7 }

layer7NewCfgContentClassHeader OBJECT-TYPE
    SYNTAX   INTEGER { yes(1), no(2) }
    MAX-ACCESS  read-only
    STATUS  current
    DESCRIPTION
        "Header table is not empty for current content class."
    ::= { layer7NewCfgContentClassEntry  8 }

layer7NewCfgContentClassCookie OBJECT-TYPE
    SYNTAX   INTEGER { yes(1), no(2) }
    MAX-ACCESS  read-only
    STATUS  current
    DESCRIPTION
        "Cookie table is not empty for current content class."
    ::= { layer7NewCfgContentClassEntry  9 }

layer7NewCfgContentClassText OBJECT-TYPE
    SYNTAX   INTEGER { yes(1), no(2) }
    MAX-ACCESS  read-only
    STATUS  current
    DESCRIPTION
        "Text table is not empty for current content class."
    ::= { layer7NewCfgContentClassEntry  10 }

layer7NewCfgContentClassXMLTag OBJECT-TYPE
    SYNTAX   INTEGER { yes(1), no(2) }
    MAX-ACCESS  read-only
    STATUS  current
    DESCRIPTION
        "XML tag table is not empty for current content class."
    ::= { layer7NewCfgContentClassEntry  11 }

layer7NewCfgContentClassDelete OBJECT-TYPE
    SYNTAX  INTEGER {
        other(1),
        delete(2)
        }
    MAX-ACCESS  read-write
    STATUS  current
    DESCRIPTION
        "By setting the value to delete(2), the entire row is deleted."
    ::= { layer7NewCfgContentClassEntry 12 }

layer7NewCfgContentClassCopy OBJECT-TYPE
    SYNTAX   DisplayString (SIZE(0..32))
    MAX-ACCESS  read-write
    STATUS  current
    DESCRIPTION
        "This is an action object.Enter the content Class ID(key id)
         to which the current content Class has to be copied.
         Value 1 is returned always when read this object."
    ::= { layer7NewCfgContentClassEntry 13 }

layer7NewCfgContentClassType OBJECT-TYPE
    SYNTAX INTEGER { http(1), rtsp(3), ssl(6) }
    MAX-ACCESS read-write
    STATUS  current
    DESCRIPTION
        "Content Class Type."
    ::= { layer7NewCfgContentClassEntry  14 }

-- URL Filtering configuration

layer7CurCfgURLFilteringTable OBJECT-TYPE
    SYNTAX  SEQUENCE OF Layer7CurCfgURLFilteringEntry
    MAX-ACCESS  not-accessible
    STATUS  current
    DESCRIPTION
        "The table for configuring URL Filtering."
    ::= { urlFiltering 1 }

layer7CurCfgURLFilteringEntry OBJECT-TYPE
    SYNTAX  Layer7CurCfgURLFilteringEntry 
    MAX-ACCESS  not-accessible
    STATUS  current
    DESCRIPTION
        "A row in the URL Filtering table."
    INDEX   { layer7CurCfgURLFilteringID }
    ::= { layer7CurCfgURLFilteringTable 1 }

Layer7CurCfgURLFilteringEntry ::= SEQUENCE {
    layer7CurCfgURLFilteringID                DisplayString,
    layer7CurCfgURLFilteringName              DisplayString,
    layer7CurCfgURLFilteringSecCatgs          DisplayString,
    layer7CurCfgURLFilteringCompCatgs         DisplayString,
    layer7CurCfgURLFilteringProdCatgs         DisplayString,
    layer7CurCfgURLFilteringFallbackCatgs     DisplayString
    }

layer7CurCfgURLFilteringID OBJECT-TYPE
    SYNTAX   DisplayString (SIZE(0..32))
    MAX-ACCESS  read-only
    STATUS  current
    DESCRIPTION
        "The URL Filtering policy ID(key id)."
    ::= { layer7CurCfgURLFilteringEntry  1 }

layer7CurCfgURLFilteringName OBJECT-TYPE
    SYNTAX   DisplayString (SIZE(0..32))
    MAX-ACCESS  read-only
    STATUS  current
    DESCRIPTION
        "The URL Filtering policy name."
    ::= { layer7CurCfgURLFilteringEntry  2 }

layer7CurCfgURLFilteringSecCatgs OBJECT-TYPE
    SYNTAX   DisplayString (SIZE(0..96))
    MAX-ACCESS  read-only
    STATUS  current
    DESCRIPTION
        "The URL Filtering policy security categories srting."
    ::= { layer7CurCfgURLFilteringEntry  3 }

layer7CurCfgURLFilteringCompCatgs OBJECT-TYPE
    SYNTAX   DisplayString (SIZE(0..96))
    MAX-ACCESS  read-only
    STATUS  current
    DESCRIPTION
        "The URL Filtering policy compliance categories srting."
    ::= { layer7CurCfgURLFilteringEntry  4 }

layer7CurCfgURLFilteringProdCatgs OBJECT-TYPE
    SYNTAX   DisplayString (SIZE(0..96))
    MAX-ACCESS  read-only
    STATUS  current
    DESCRIPTION
        "The URL Filtering policy productivity categories srting."
    ::= { layer7CurCfgURLFilteringEntry  5 }

layer7CurCfgURLFilteringFallbackCatgs OBJECT-TYPE
    SYNTAX   DisplayString (SIZE(0..96))
    MAX-ACCESS  read-only
    STATUS  current
    DESCRIPTION
        "The URL Filtering policy fallback categories srting."
    ::= { layer7CurCfgURLFilteringEntry  7 }

layer7NewCfgURLFilteringTable OBJECT-TYPE
    SYNTAX  SEQUENCE OF Layer7NewCfgURLFilteringEntry
    MAX-ACCESS  not-accessible
    STATUS  current
    DESCRIPTION
        "The table for configuring URL Filtering."
    ::= { urlFiltering 2 }

layer7NewCfgURLFilteringEntry OBJECT-TYPE
    SYNTAX  Layer7NewCfgURLFilteringEntry 
    MAX-ACCESS  not-accessible
    STATUS  current
    DESCRIPTION
        "A row in the URL Filtering table."
    INDEX   { layer7NewCfgURLFilteringID }
    ::= { layer7NewCfgURLFilteringTable 1 }

Layer7NewCfgURLFilteringEntry ::= SEQUENCE {
    layer7NewCfgURLFilteringID                DisplayString,
    layer7NewCfgURLFilteringName              DisplayString,
    layer7NewCfgURLFilteringSecCatgs          DisplayString,
    layer7NewCfgURLFilteringCompCatgs         DisplayString,
    layer7NewCfgURLFilteringProdCatgs         DisplayString,
    layer7NewCfgURLFilteringDelete            INTEGER,
    layer7NewCfgURLFilteringFallbackCatgs     DisplayString
    }

layer7NewCfgURLFilteringID OBJECT-TYPE
    SYNTAX   DisplayString (SIZE(0..32))
    MAX-ACCESS  read-create
    STATUS  current
    DESCRIPTION
        "The URL Filtering policy ID(key id)."
    ::= { layer7NewCfgURLFilteringEntry  1 }

layer7NewCfgURLFilteringName OBJECT-TYPE
    SYNTAX   DisplayString (SIZE(0..32))
    MAX-ACCESS  read-write
    STATUS  current
    DESCRIPTION
        "The URL Filtering policy name."
    ::= { layer7NewCfgURLFilteringEntry  2 }

layer7NewCfgURLFilteringSecCatgs OBJECT-TYPE
    SYNTAX   DisplayString (SIZE(0..32))
    MAX-ACCESS  read-write
    STATUS  current
    DESCRIPTION
        "The URL Filtering policy security categories srting."
    ::= { layer7NewCfgURLFilteringEntry  3 }

layer7NewCfgURLFilteringCompCatgs OBJECT-TYPE
    SYNTAX   DisplayString (SIZE(0..32))
    MAX-ACCESS  read-write
    STATUS  current
    DESCRIPTION
        "The URL Filtering policy compliance categories srting."
    ::= { layer7NewCfgURLFilteringEntry  4 }

layer7NewCfgURLFilteringProdCatgs OBJECT-TYPE
    SYNTAX   DisplayString (SIZE(0..32))
    MAX-ACCESS  read-write
    STATUS  current
    DESCRIPTION
        "The URL Filtering policy productivity categories srting."
    ::= { layer7NewCfgURLFilteringEntry  5 }

layer7NewCfgURLFilteringDelete OBJECT-TYPE
    SYNTAX  INTEGER {
        other(1),
        delete(2)
        }
    MAX-ACCESS  read-write
    STATUS  current
    DESCRIPTION
        "By setting the value to delete(2), the entire row is deleted."
    ::= { layer7NewCfgURLFilteringEntry 6 }

layer7NewCfgURLFilteringFallbackCatgs OBJECT-TYPE
    SYNTAX   DisplayString (SIZE(0..32))
    MAX-ACCESS  read-write
    STATUS  current
    DESCRIPTION
        "The URL Filtering policy fallback categories srting."
    ::= { layer7NewCfgURLFilteringEntry  7 }

layer7CurCfgContentClassHostNameTable OBJECT-TYPE
    SYNTAX  SEQUENCE OF Layer7CurCfgContentClassHostNameEntry
    MAX-ACCESS  not-accessible
    STATUS  current
    DESCRIPTION
        "The table for configuring Content Class Hostname."
    ::= { contentClass 3 }

layer7CurCfgContentClassHostNameEntry OBJECT-TYPE
    SYNTAX  Layer7CurCfgContentClassHostNameEntry
    MAX-ACCESS  not-accessible
    STATUS  current
    DESCRIPTION
        "A row in the Content Class table."
    INDEX   { layer7CurCfgContentClassHostNameContentClassID, layer7CurCfgContentClassHostNameID }
    ::= { layer7CurCfgContentClassHostNameTable 1 }

Layer7CurCfgContentClassHostNameEntry ::= SEQUENCE {
    layer7CurCfgContentClassHostNameContentClassID DisplayString,
    layer7CurCfgContentClassHostNameID             DisplayString,
    layer7CurCfgContentClassHostNameHostName       DisplayString,
    layer7CurCfgContentClassHostNameMatchType      INTEGER,
    layer7CurCfgContentClassHostNameDataclassID	   DisplayString
    }

layer7CurCfgContentClassHostNameContentClassID OBJECT-TYPE
    SYNTAX   DisplayString (SIZE (0..32))
    MAX-ACCESS  read-only
    STATUS  current
    DESCRIPTION
        "The content Class HostName ID(key id) as an index, length of the string should be 32 characters."
    ::= { layer7CurCfgContentClassHostNameEntry 1 }

layer7CurCfgContentClassHostNameID OBJECT-TYPE
    SYNTAX   DisplayString (SIZE (0..32))
    MAX-ACCESS  read-only
    STATUS  current
    DESCRIPTION
        "The content Class ID(key id) as an index, length of the string should be 32 characters."
    ::= { layer7CurCfgContentClassHostNameEntry 2 }

layer7CurCfgContentClassHostNameHostName OBJECT-TYPE
    SYNTAX   DisplayString (SIZE (0..128))
    MAX-ACCESS  read-only
    STATUS  current
    DESCRIPTION
        "Content Class Hostname to match, length of the string should be 32 characters."
    ::= { layer7CurCfgContentClassHostNameEntry 3 }

layer7CurCfgContentClassHostNameMatchType OBJECT-TYPE
    SYNTAX  INTEGER {
        sufx(1),
        prefx(2),
        equal(3),
        include(4),
        regex(5)
        }
    MAX-ACCESS  read-only
    STATUS  current
    DESCRIPTION
        "Host Name Match type."
    ::= { layer7CurCfgContentClassHostNameEntry 4 }

layer7CurCfgContentClassHostNameDataclassID OBJECT-TYPE
    SYNTAX   DisplayString (SIZE (0..32))
    MAX-ACCESS  read-only
    STATUS  current
    DESCRIPTION
        "Id of a data class to associate Hostname element with."
    ::= { layer7CurCfgContentClassHostNameEntry 5 }

layer7NewCfgContentClassHostNameTable OBJECT-TYPE
    SYNTAX  SEQUENCE OF Layer7NewCfgContentClassHostNameEntry
    MAX-ACCESS  not-accessible
    STATUS  current
    DESCRIPTION
        "The table for configuring Content Class Hostname."
    ::= { contentClass 4 }

layer7NewCfgContentClassHostNameEntry OBJECT-TYPE
    SYNTAX  Layer7NewCfgContentClassHostNameEntry
    MAX-ACCESS  not-accessible
    STATUS  current
    DESCRIPTION
        "A row in the Content Class table."
    INDEX   { layer7NewCfgContentClassHostNameContentClassID, layer7NewCfgContentClassHostNameID }
    ::= { layer7NewCfgContentClassHostNameTable 1 }

Layer7NewCfgContentClassHostNameEntry ::= SEQUENCE {
    layer7NewCfgContentClassHostNameContentClassID DisplayString,
    layer7NewCfgContentClassHostNameID             DisplayString,
    layer7NewCfgContentClassHostNameHostName       DisplayString,
    layer7NewCfgContentClassHostNameMatchType      INTEGER,
    layer7NewCfgContentClassHostNameDelete         INTEGER,
    layer7NewCfgContentClassHostNameDataclassID	   DisplayString,
    layer7NewCfgContentClassHostNameCopy           DisplayString
    }

layer7NewCfgContentClassHostNameContentClassID OBJECT-TYPE
    SYNTAX   DisplayString (SIZE (0..32))
    MAX-ACCESS  read-create
    STATUS  current
    DESCRIPTION
        "The content Class HostName ID(key id) as an index, length of the string should be 32 characters."
    ::= { layer7NewCfgContentClassHostNameEntry 1 }

layer7NewCfgContentClassHostNameID OBJECT-TYPE
    SYNTAX   DisplayString (SIZE (0..32))
    MAX-ACCESS  read-create
    STATUS  current
    DESCRIPTION
        "The content Class ID(key id) as an index, length of the string should be 32 characters."
    ::= { layer7NewCfgContentClassHostNameEntry 2 }

layer7NewCfgContentClassHostNameHostName OBJECT-TYPE
    SYNTAX   DisplayString (SIZE (0..128))
    MAX-ACCESS  read-write
    STATUS  current
    DESCRIPTION
        "Content Class Hostname to match, length of the string should be 32 characters."
    ::= { layer7NewCfgContentClassHostNameEntry 3 }

layer7NewCfgContentClassHostNameMatchType OBJECT-TYPE
    SYNTAX  INTEGER {
        sufx(1),
        prefx(2),
        equal(3),
        include(4),
        regex(5)
        }
    MAX-ACCESS  read-write
    STATUS  current
    DESCRIPTION
        "Host Name Match type."
    ::= { layer7NewCfgContentClassHostNameEntry 4 }

layer7NewCfgContentClassHostNameDelete OBJECT-TYPE
    SYNTAX  INTEGER {
        other(1),
        delete(2)
        }
    MAX-ACCESS  read-write
    STATUS  current
    DESCRIPTION
        "By setting the value to delete(2), the entire row is deleted."
    ::= { layer7NewCfgContentClassHostNameEntry 5 }

layer7NewCfgContentClassHostNameDataclassID OBJECT-TYPE
    SYNTAX   DisplayString (SIZE (0..32))
    MAX-ACCESS  read-write
    STATUS  current
    DESCRIPTION
        "Id of a data class to associate Hostname element with."
    ::= { layer7NewCfgContentClassHostNameEntry 6 }

layer7NewCfgContentClassHostNameCopy OBJECT-TYPE
    SYNTAX   DisplayString (SIZE (0..32))
    MAX-ACCESS  read-write
    STATUS  current
    DESCRIPTION
        "This is an action object.Enter the new HostName
         to which the curent HostName has to be copied."
    ::= { layer7NewCfgContentClassHostNameEntry 7 }

layer7CurCfgContentClassPathTable OBJECT-TYPE
    SYNTAX  SEQUENCE OF Layer7CurCfgContentClassPathEntry
    MAX-ACCESS  not-accessible
    STATUS  current
    DESCRIPTION
        "The table for configuring Content Class Path."
    ::= { contentClass 5 }

layer7CurCfgContentClassPathEntry OBJECT-TYPE
    SYNTAX  Layer7CurCfgContentClassPathEntry
    MAX-ACCESS  not-accessible
    STATUS  current
    DESCRIPTION
        "A row in the Content Class table."
    INDEX   { layer7CurCfgContentClassPathContentClassID, layer7CurCfgContentClassPathID }
    ::= { layer7CurCfgContentClassPathTable 1 }

Layer7CurCfgContentClassPathEntry ::= SEQUENCE {
    layer7CurCfgContentClassPathContentClassID  DisplayString,
    layer7CurCfgContentClassPathID              DisplayString,
    layer7CurCfgContentClassPathFilePath        DisplayString,
    layer7CurCfgContentClassPathMatchType       INTEGER,
    layer7CurCfgContentClassPathCase            INTEGER,
    layer7CurCfgContentClassPathDataclassID     DisplayString
    }

layer7CurCfgContentClassPathContentClassID OBJECT-TYPE
    SYNTAX   DisplayString (SIZE (0..32))
    MAX-ACCESS  read-only
    STATUS  current
    DESCRIPTION
        "The content Class Path ID(key id) as an index, length of the string should be 32 characters."
    ::= { layer7CurCfgContentClassPathEntry 1 }

layer7CurCfgContentClassPathID OBJECT-TYPE
    SYNTAX   DisplayString (SIZE (0..32))
    MAX-ACCESS  read-only
    STATUS  current
    DESCRIPTION
        "The content Class ID(key id) as an index, length of the string should be 32 characters."
    ::= { layer7CurCfgContentClassPathEntry 2 }

layer7CurCfgContentClassPathFilePath OBJECT-TYPE
    SYNTAX   DisplayString (SIZE (0..255))
    MAX-ACCESS  read-only
    STATUS  current
    DESCRIPTION
        "Content Class Path to match, length of the string should be 32 characters."
    ::= { layer7CurCfgContentClassPathEntry 3 }

layer7CurCfgContentClassPathMatchType OBJECT-TYPE
    SYNTAX  INTEGER {
        sufx(1),
        prefx(2),
        equal(3),
        include(4),
        regex(5)
        }
    MAX-ACCESS  read-only
    STATUS  current
    DESCRIPTION
        "Path Match type."
    ::= { layer7CurCfgContentClassPathEntry 4 }

layer7CurCfgContentClassPathCase OBJECT-TYPE
    SYNTAX  INTEGER {
        enabled(1),
        disabled(2)
        }
    MAX-ACCESS  read-only
    STATUS  current
    DESCRIPTION
        "Enable or Disable Case sensitive for String matching."
    ::= { layer7CurCfgContentClassPathEntry 5 }
    
layer7CurCfgContentClassPathDataclassID OBJECT-TYPE
    SYNTAX   DisplayString (SIZE (0..32))
    MAX-ACCESS  read-only
    STATUS  current
    DESCRIPTION
        "Id of a data class to associate Path element with."
    ::= { layer7CurCfgContentClassPathEntry 6 }


layer7NewCfgContentClassPathTable OBJECT-TYPE
    SYNTAX  SEQUENCE OF Layer7NewCfgContentClassPathEntry
    MAX-ACCESS  not-accessible
    STATUS  current
    DESCRIPTION
        "The table for configuring Content Class Path."
    ::= { contentClass 6 }

layer7NewCfgContentClassPathEntry OBJECT-TYPE
    SYNTAX  Layer7NewCfgContentClassPathEntry
    MAX-ACCESS  not-accessible
    STATUS  current
    DESCRIPTION
        "A row in the Content Class table."
    INDEX   { layer7NewCfgContentClassPathContentClassID, layer7NewCfgContentClassPathID }
    ::= { layer7NewCfgContentClassPathTable 1 }

Layer7NewCfgContentClassPathEntry ::= SEQUENCE {
    layer7NewCfgContentClassPathContentClassID  DisplayString,
    layer7NewCfgContentClassPathID              DisplayString,
    layer7NewCfgContentClassPathFilePath        DisplayString,
    layer7NewCfgContentClassPathMatchType       INTEGER,
    layer7NewCfgContentClassPathCase            INTEGER,
    layer7NewCfgContentClassPathDelete          INTEGER,
    layer7NewCfgContentClassPathDataclassID	DisplayString,
    layer7NewCfgContentClassPathCopy            DisplayString
    }

layer7NewCfgContentClassPathContentClassID OBJECT-TYPE
    SYNTAX   DisplayString (SIZE (0..32))
    MAX-ACCESS  read-create
    STATUS  current
    DESCRIPTION
        "The content Class Path ID(key id) as an index, length of the string should be 32 characters."
    ::= { layer7NewCfgContentClassPathEntry 1 }

layer7NewCfgContentClassPathID OBJECT-TYPE
    SYNTAX   DisplayString (SIZE (0..32))
    MAX-ACCESS  read-create
    STATUS  current
    DESCRIPTION
        "The content Class ID(key id) as an index, length of the string should be 32 characters."
    ::= { layer7NewCfgContentClassPathEntry 2 }

layer7NewCfgContentClassPathFilePath OBJECT-TYPE
    SYNTAX   DisplayString (SIZE (0..255))
    MAX-ACCESS  read-write
    STATUS  current
    DESCRIPTION
        "Content Class Path to match, length of the string should be 32 characters."
    ::= { layer7NewCfgContentClassPathEntry 3 }

layer7NewCfgContentClassPathMatchType OBJECT-TYPE
    SYNTAX  INTEGER {
        sufx(1),
        prefx(2),
        equal(3),
        include(4),
        regex(5)
        }
    MAX-ACCESS  read-write
    STATUS  current
    DESCRIPTION
        "Path Match type."
    ::= { layer7NewCfgContentClassPathEntry 4 }

layer7NewCfgContentClassPathCase OBJECT-TYPE
    SYNTAX  INTEGER {
        enabled(1),
        disabled(2)
        }
    MAX-ACCESS  read-write
    STATUS  current
    DESCRIPTION
        "Enable or Disable Case sensitive for String matching."
    ::= { layer7NewCfgContentClassPathEntry 5 }

layer7NewCfgContentClassPathDelete OBJECT-TYPE
    SYNTAX  INTEGER {
        other(1),
        delete(2)
        }
    MAX-ACCESS  read-write
    STATUS  current
    DESCRIPTION
        "By setting the value to delete(2), the entire row is deleted."
    ::= { layer7NewCfgContentClassPathEntry 7 }
    
layer7NewCfgContentClassPathDataclassID OBJECT-TYPE
    SYNTAX   DisplayString (SIZE (0..32))
    MAX-ACCESS  read-write
    STATUS  current
    DESCRIPTION
        "Id of a data class to associate Path element with."
    ::= { layer7NewCfgContentClassPathEntry 8 }

layer7NewCfgContentClassPathCopy OBJECT-TYPE
    SYNTAX   DisplayString (SIZE (0..32))
    MAX-ACCESS  read-write
    STATUS  current
    DESCRIPTION
        "This is an action object.Enter the new Classpath
         to which the curent Classpath has to be copied."
    ::= { layer7NewCfgContentClassPathEntry 9 }

layer7CurCfgContentClassFileNameTable OBJECT-TYPE
    SYNTAX  SEQUENCE OF Layer7CurCfgContentClassFileNameEntry
    MAX-ACCESS  not-accessible
    STATUS  current
    DESCRIPTION
        "The table for configuring Content Class File Name."
    ::= { contentClass 7 }

layer7CurCfgContentClassFileNameEntry OBJECT-TYPE
    SYNTAX  Layer7CurCfgContentClassFileNameEntry
    MAX-ACCESS  not-accessible
    STATUS  current
    DESCRIPTION
        "A row in the Content Class table."
    INDEX   { layer7CurCfgContentClassFileNameContentClassID, layer7CurCfgContentClassFileNameID }
    ::= { layer7CurCfgContentClassFileNameTable 1 }

Layer7CurCfgContentClassFileNameEntry ::= SEQUENCE {
    layer7CurCfgContentClassFileNameContentClassID  DisplayString,
    layer7CurCfgContentClassFileNameID              DisplayString,
    layer7CurCfgContentClassFileNameFileName        DisplayString,
    layer7CurCfgContentClassFileNameMatchType       INTEGER,
    layer7CurCfgContentClassFileNameCase            INTEGER
    }

layer7CurCfgContentClassFileNameContentClassID OBJECT-TYPE
    SYNTAX   DisplayString (SIZE (0..32))
    MAX-ACCESS  read-only
    STATUS  current
    DESCRIPTION
        "The content Class FileName ID(key id) as an index, length of the string should be 32 characters."
    ::= { layer7CurCfgContentClassFileNameEntry 1 }

layer7CurCfgContentClassFileNameID OBJECT-TYPE
    SYNTAX   DisplayString (SIZE (0..32))
    MAX-ACCESS  read-only
    STATUS  current
    DESCRIPTION
        "The content Class ID(key id) as an index, length of the string should be 32 characters."
    ::= { layer7CurCfgContentClassFileNameEntry 2 }

layer7CurCfgContentClassFileNameFileName OBJECT-TYPE
    SYNTAX   DisplayString (SIZE (0..128))
    MAX-ACCESS  read-only
    STATUS  current
    DESCRIPTION
        "Content Class Filename to match, length of the string should be 32 characters."
    ::= { layer7CurCfgContentClassFileNameEntry 3 }

layer7CurCfgContentClassFileNameMatchType OBJECT-TYPE
    SYNTAX  INTEGER {
        sufx(1),
        prefx(2),
        equal(3),
        include(4),
        regex(5)
        }
    MAX-ACCESS  read-only
    STATUS  current
    DESCRIPTION
        "File Name Match type."
    ::= { layer7CurCfgContentClassFileNameEntry 4 }

layer7CurCfgContentClassFileNameCase OBJECT-TYPE
    SYNTAX  INTEGER {
        enabled(1),
        disabled(2)
        }
    MAX-ACCESS  read-only
    STATUS  current
    DESCRIPTION
        "Enable or Disable Case sensitive for String matching."
    ::= { layer7CurCfgContentClassFileNameEntry 5 }


layer7NewCfgContentClassFileNameTable OBJECT-TYPE
    SYNTAX  SEQUENCE OF Layer7NewCfgContentClassFileNameEntry
    MAX-ACCESS  not-accessible
    STATUS  current
    DESCRIPTION
        "The table for configuring Content Class File Name."
    ::= { contentClass 8 }

layer7NewCfgContentClassFileNameEntry OBJECT-TYPE
    SYNTAX  Layer7NewCfgContentClassFileNameEntry
    MAX-ACCESS  not-accessible
    STATUS  current
    DESCRIPTION
        "A row in the Content Class table."
    INDEX   { layer7NewCfgContentClassFileNameContentClassID, layer7NewCfgContentClassFileNameID }
    ::= { layer7NewCfgContentClassFileNameTable 1 }

Layer7NewCfgContentClassFileNameEntry ::= SEQUENCE {
    layer7NewCfgContentClassFileNameContentClassID  DisplayString,
    layer7NewCfgContentClassFileNameID              DisplayString,
    layer7NewCfgContentClassFileNameFileName        DisplayString,
    layer7NewCfgContentClassFileNameMatchType       INTEGER,
    layer7NewCfgContentClassFileNameCase            INTEGER,
    layer7NewCfgContentClassFileNameDelete          INTEGER,
    layer7NewCfgContentClassFileNameCopy            DisplayString
    }

layer7NewCfgContentClassFileNameContentClassID OBJECT-TYPE
    SYNTAX   DisplayString (SIZE (0..32))
    MAX-ACCESS  read-create
    STATUS  current
    DESCRIPTION
        "The content Class FileName ID(key id) as an index, length of the string should be 32 characters."
    ::= { layer7NewCfgContentClassFileNameEntry 1 }

layer7NewCfgContentClassFileNameID OBJECT-TYPE
    SYNTAX   DisplayString (SIZE (0..32))
    MAX-ACCESS  read-create
    STATUS  current
    DESCRIPTION
        "The content Class ID(key id) as an index, length of the string should be 32 characters."
    ::= { layer7NewCfgContentClassFileNameEntry 2 }

layer7NewCfgContentClassFileNameFileName OBJECT-TYPE
    SYNTAX   DisplayString (SIZE (0..128))
    MAX-ACCESS  read-write
    STATUS  current
    DESCRIPTION
        "Content Class Filename to match, length of the string should be 32 characters."
    ::= { layer7NewCfgContentClassFileNameEntry 3 }

layer7NewCfgContentClassFileNameMatchType OBJECT-TYPE
    SYNTAX  INTEGER {
        sufx(1),
        prefx(2),
        equal(3),
        include(4),
        regex(5)
        }
    MAX-ACCESS  read-write
    STATUS  current
    DESCRIPTION
        "File Name Match type."
    ::= { layer7NewCfgContentClassFileNameEntry 4 }

layer7NewCfgContentClassFileNameCase OBJECT-TYPE
    SYNTAX  INTEGER {
        enabled(1),
        disabled(2)
        }
    MAX-ACCESS  read-write
    STATUS  current
    DESCRIPTION
        "Enable or Disable Case sensitive for String matching."
    ::= { layer7NewCfgContentClassFileNameEntry 5 }

layer7NewCfgContentClassFileNameDelete OBJECT-TYPE
    SYNTAX  INTEGER {
        other(1),
        delete(2)
        }
    MAX-ACCESS  read-write
    STATUS  current
    DESCRIPTION
        "By setting the value to delete(2), the entire row is deleted."
    ::= { layer7NewCfgContentClassFileNameEntry 6 }

layer7NewCfgContentClassFileNameCopy OBJECT-TYPE
    SYNTAX   DisplayString (SIZE (0..32))
    MAX-ACCESS  read-write
    STATUS  current
    DESCRIPTION
        "This is an action object.Enter the new Filename
         to which the curent Filename has to be copied."
    ::= { layer7NewCfgContentClassFileNameEntry 7 }


layer7CurCfgContentClassFileTypeTable OBJECT-TYPE
    SYNTAX  SEQUENCE OF Layer7CurCfgContentClassFileTypeEntry
    MAX-ACCESS  not-accessible
    STATUS  current
    DESCRIPTION
        "The table for configuring Content Class File Name."
    ::= { contentClass 9 }

layer7CurCfgContentClassFileTypeEntry OBJECT-TYPE
    SYNTAX  Layer7CurCfgContentClassFileTypeEntry
    MAX-ACCESS  not-accessible
    STATUS  current
    DESCRIPTION
        "A row in the Content Class table."
    INDEX   { layer7CurCfgContentClassFileTypeContentClassID, layer7CurCfgContentClassFileTypeID }
    ::= { layer7CurCfgContentClassFileTypeTable 1 }

Layer7CurCfgContentClassFileTypeEntry ::= SEQUENCE {
    layer7CurCfgContentClassFileTypeContentClassID  DisplayString,
    layer7CurCfgContentClassFileTypeID              DisplayString,
    layer7CurCfgContentClassFileTypeFileType        DisplayString,
    layer7CurCfgContentClassFileTypeMatchType       INTEGER,
    layer7CurCfgContentClassFileTypeCase            INTEGER
    }

layer7CurCfgContentClassFileTypeContentClassID OBJECT-TYPE
    SYNTAX   DisplayString (SIZE (0..32))
    MAX-ACCESS  read-only
    STATUS  current
    DESCRIPTION
        "The content Class Filetype ID(key id) as an index, length of the string should be 32 characters."
    ::= { layer7CurCfgContentClassFileTypeEntry 1 }

layer7CurCfgContentClassFileTypeID OBJECT-TYPE
    SYNTAX   DisplayString (SIZE (0..32))
    MAX-ACCESS  read-only
    STATUS  current
    DESCRIPTION
        "The content Class ID(key id) as an index, length of the string should be 32 characters."
    ::= { layer7CurCfgContentClassFileTypeEntry 2 }

layer7CurCfgContentClassFileTypeFileType OBJECT-TYPE
    SYNTAX   DisplayString (SIZE (0..128))
    MAX-ACCESS  read-only
    STATUS  current
    DESCRIPTION
        "Content Class Filetype to match, length of the string should be 32 characters."
    ::= { layer7CurCfgContentClassFileTypeEntry 3 }

layer7CurCfgContentClassFileTypeMatchType OBJECT-TYPE
    SYNTAX  INTEGER {
        sufx(1),
        prefx(2),
        equal(3),
        include(4),
        regex(5)
        }
    MAX-ACCESS  read-only
    STATUS  current
    DESCRIPTION
        "Filetype Match type."
    ::= { layer7CurCfgContentClassFileTypeEntry 4 }

layer7CurCfgContentClassFileTypeCase OBJECT-TYPE
    SYNTAX  INTEGER {
        enabled(1),
        disabled(2)
        }
    MAX-ACCESS  read-only
    STATUS  current
    DESCRIPTION
        "Enable or Disable Case sensitive for String matching."
    ::= { layer7CurCfgContentClassFileTypeEntry 5 }


layer7NewCfgContentClassFileTypeTable OBJECT-TYPE
    SYNTAX  SEQUENCE OF Layer7NewCfgContentClassFileTypeEntry
    MAX-ACCESS  not-accessible
    STATUS  current
    DESCRIPTION
        "The table for configuring Content Class File Name."
    ::= { contentClass 10 }

layer7NewCfgContentClassFileTypeEntry OBJECT-TYPE
    SYNTAX  Layer7NewCfgContentClassFileTypeEntry
    MAX-ACCESS  not-accessible
    STATUS  current
    DESCRIPTION
        "A row in the Content Class table."
    INDEX   { layer7NewCfgContentClassFileTypeContentClassID, layer7NewCfgContentClassFileTypeID }
    ::= { layer7NewCfgContentClassFileTypeTable 1 }

Layer7NewCfgContentClassFileTypeEntry ::= SEQUENCE {
    layer7NewCfgContentClassFileTypeContentClassID  DisplayString,
    layer7NewCfgContentClassFileTypeID              DisplayString,
    layer7NewCfgContentClassFileTypeFileType        DisplayString,
    layer7NewCfgContentClassFileTypeMatchType       INTEGER,
    layer7NewCfgContentClassFileTypeCase            INTEGER,
    layer7NewCfgContentClassFileTypeDelete          INTEGER,
    layer7NewCfgContentClassFileTypeCopy            DisplayString
    }

layer7NewCfgContentClassFileTypeContentClassID OBJECT-TYPE
    SYNTAX   DisplayString (SIZE (0..32))
    MAX-ACCESS  read-create
    STATUS  current
    DESCRIPTION
        "The content Class Filetype ID(key id) as an index, length of the string should be 32 characters."
    ::= { layer7NewCfgContentClassFileTypeEntry 1 }

layer7NewCfgContentClassFileTypeID OBJECT-TYPE
    SYNTAX   DisplayString (SIZE (0..32))
    MAX-ACCESS  read-create
    STATUS  current
    DESCRIPTION
        "The content Class ID(key id) as an index, length of the string should be 32 characters."
    ::= { layer7NewCfgContentClassFileTypeEntry 2 }

layer7NewCfgContentClassFileTypeFileType OBJECT-TYPE
    SYNTAX   DisplayString (SIZE (0..128))
    MAX-ACCESS  read-write
    STATUS  current
    DESCRIPTION
        "Content Class Filetype to match, length of the string should be 32 characters."
    ::= { layer7NewCfgContentClassFileTypeEntry 3 }

layer7NewCfgContentClassFileTypeMatchType OBJECT-TYPE
    SYNTAX  INTEGER {
        sufx(1),
        prefx(2),
        equal(3),
        include(4),
        regex(5)
        }
    MAX-ACCESS  read-write
    STATUS  current
    DESCRIPTION
        "Filetype Match type."
    ::= { layer7NewCfgContentClassFileTypeEntry 4 }

layer7NewCfgContentClassFileTypeCase OBJECT-TYPE
    SYNTAX  INTEGER {
        enabled(1),
        disabled(2)
        }
    MAX-ACCESS  read-write
    STATUS  current
    DESCRIPTION
        "Enable or Disable Case sensitive for String matching."
    ::= { layer7NewCfgContentClassFileTypeEntry 5 }

layer7NewCfgContentClassFileTypeDelete OBJECT-TYPE
    SYNTAX  INTEGER {
        other(1),
        delete(2)
        }
    MAX-ACCESS  read-write
    STATUS  current
    DESCRIPTION
        "By setting the value to delete(2), the entire row is deleted."
    ::= { layer7NewCfgContentClassFileTypeEntry 6 }

layer7NewCfgContentClassFileTypeCopy OBJECT-TYPE
    SYNTAX   DisplayString (SIZE (0..32))
    MAX-ACCESS  read-write
    STATUS  current
    DESCRIPTION
        "This is an action object.Enter the new Filetype
         to which the curent Filetype has to be copied."
    ::= { layer7NewCfgContentClassFileTypeEntry 7 }

layer7CurCfgContentClassHeaderTable OBJECT-TYPE
    SYNTAX  SEQUENCE OF Layer7CurCfgContentClassHeaderEntry
    MAX-ACCESS  not-accessible
    STATUS  current
    DESCRIPTION
        "The table for configuring Content Class Header."
    ::= { contentClass 11 }

layer7CurCfgContentClassHeaderEntry OBJECT-TYPE
    SYNTAX  Layer7CurCfgContentClassHeaderEntry
    MAX-ACCESS  not-accessible
    STATUS  current
    DESCRIPTION
        "A row in the Content Class table."
    INDEX   { layer7CurCfgContentClassHeaderContentClassID, layer7CurCfgContentClassHeaderID }
    ::= { layer7CurCfgContentClassHeaderTable 1 }

Layer7CurCfgContentClassHeaderEntry ::= SEQUENCE {
    layer7CurCfgContentClassHeaderContentClassID  DisplayString,
    layer7CurCfgContentClassHeaderID              DisplayString,
    layer7CurCfgContentClassHeaderName            DisplayString,
    layer7CurCfgContentClassHeaderVal             DisplayString,
    layer7CurCfgContentClassHeaderMatchTypeName   INTEGER,
    layer7CurCfgContentClassHeaderMatchTypeVal    INTEGER,
    layer7CurCfgContentClassHeaderCase            INTEGER
    }

layer7CurCfgContentClassHeaderContentClassID OBJECT-TYPE
    SYNTAX   DisplayString (SIZE (0..32))
    MAX-ACCESS  read-only
    STATUS  current
    DESCRIPTION
        "The content Class Header ID(key id) as an index, length of the string should be 32 characters."
    ::= { layer7CurCfgContentClassHeaderEntry 1 }

layer7CurCfgContentClassHeaderID OBJECT-TYPE
    SYNTAX   DisplayString (SIZE (0..32))
    MAX-ACCESS  read-only
    STATUS  current
    DESCRIPTION
        "The content Class ID(key id) as an index, length of the string should be 32 characters."
    ::= { layer7CurCfgContentClassHeaderEntry 2 }

layer7CurCfgContentClassHeaderName OBJECT-TYPE
    SYNTAX   DisplayString (SIZE (0..128))
    MAX-ACCESS  read-only
    STATUS  current
    DESCRIPTION
        "Content Class Header to match, length of the string should be 32 characters."
    ::= { layer7CurCfgContentClassHeaderEntry 3 }

layer7CurCfgContentClassHeaderVal OBJECT-TYPE
    SYNTAX   DisplayString (SIZE (0..128))
    MAX-ACCESS  read-only
    STATUS  current
    DESCRIPTION
        "Content Class Header to match, length of the string should be 32 characters."
    ::= { layer7CurCfgContentClassHeaderEntry 4 }

layer7CurCfgContentClassHeaderMatchTypeName OBJECT-TYPE
    SYNTAX  INTEGER {
        equal(3),
        include(4),
        regex(5)
        }
    MAX-ACCESS  read-only
    STATUS  current
    DESCRIPTION
        "Header Match type."
    ::= { layer7CurCfgContentClassHeaderEntry 5 }

layer7CurCfgContentClassHeaderMatchTypeVal OBJECT-TYPE
    SYNTAX  INTEGER {
        equal(3),
        include(4),
        regex(5)
        }
    MAX-ACCESS  read-only
    STATUS  current
    DESCRIPTION
        "Header Match type."
    ::= { layer7CurCfgContentClassHeaderEntry 6 }

layer7CurCfgContentClassHeaderCase OBJECT-TYPE
    SYNTAX  INTEGER {
        enabled(1),
        disabled(2)
        }
    MAX-ACCESS  read-only
    STATUS  current
    DESCRIPTION
        "Enable or Disable Case sensitive for String matching."
    ::= { layer7CurCfgContentClassHeaderEntry 7 }

layer7NewCfgContentClassHeaderTable OBJECT-TYPE
    SYNTAX  SEQUENCE OF Layer7NewCfgContentClassHeaderEntry
    MAX-ACCESS  not-accessible
    STATUS  current
    DESCRIPTION
        "The table for configuring Content Class Header."
    ::= { contentClass 12 }

layer7NewCfgContentClassHeaderEntry OBJECT-TYPE
    SYNTAX  Layer7NewCfgContentClassHeaderEntry
    MAX-ACCESS  not-accessible
    STATUS  current
    DESCRIPTION
        "A row in the Content Class table."
    INDEX   { layer7NewCfgContentClassHeaderContentClassID, layer7NewCfgContentClassHeaderID }
    ::= { layer7NewCfgContentClassHeaderTable 1 }

Layer7NewCfgContentClassHeaderEntry ::= SEQUENCE {
    layer7NewCfgContentClassHeaderContentClassID  DisplayString,
    layer7NewCfgContentClassHeaderID              DisplayString,
    layer7NewCfgContentClassHeaderName            DisplayString,
    layer7NewCfgContentClassHeaderVal             DisplayString,
    layer7NewCfgContentClassHeaderMatchTypeName   INTEGER,
    layer7NewCfgContentClassHeaderMatchTypeVal    INTEGER,
    layer7NewCfgContentClassHeaderCase            INTEGER,
    layer7NewCfgContentClassHeaderDelete          INTEGER,
    layer7NewCfgContentClassHeaderCopy            DisplayString
    }

layer7NewCfgContentClassHeaderContentClassID OBJECT-TYPE
    SYNTAX   DisplayString (SIZE (0..32))
    MAX-ACCESS  read-create
    STATUS  current
    DESCRIPTION
        "The content Class Header ID(key id) as an index, length of the string should be 32 characters."
    ::= { layer7NewCfgContentClassHeaderEntry 1 }

layer7NewCfgContentClassHeaderID OBJECT-TYPE
    SYNTAX   DisplayString (SIZE (0..32))
    MAX-ACCESS  read-create
    STATUS  current
    DESCRIPTION
        "The content Class ID(key id) as an index, length of the string should be 32 characters."
    ::= { layer7NewCfgContentClassHeaderEntry 2 }

layer7NewCfgContentClassHeaderName OBJECT-TYPE
    SYNTAX   DisplayString (SIZE (0..128))
    MAX-ACCESS  read-write
    STATUS  current
    DESCRIPTION
        "Content Class Header to match, length of the string should be 32 characters."
    ::= { layer7NewCfgContentClassHeaderEntry 3 }

layer7NewCfgContentClassHeaderVal OBJECT-TYPE
    SYNTAX   DisplayString (SIZE (0..128))
    MAX-ACCESS  read-write
    STATUS  current
    DESCRIPTION
        "Content Class Header to match, length of the string should be 32 characters."
    ::= { layer7NewCfgContentClassHeaderEntry 4 }

layer7NewCfgContentClassHeaderMatchTypeName OBJECT-TYPE
    SYNTAX  INTEGER {
        equal(3),
        include(4),
        regex(5)
        }
    MAX-ACCESS  read-write
    STATUS  current
    DESCRIPTION
        "Header Match type."
    ::= { layer7NewCfgContentClassHeaderEntry 5 }

layer7NewCfgContentClassHeaderMatchTypeVal OBJECT-TYPE
    SYNTAX  INTEGER {
        equal(3),
        include(4),
        regex(5)
        }
    MAX-ACCESS  read-write
    STATUS  current
    DESCRIPTION
        "Header Match type."
    ::= { layer7NewCfgContentClassHeaderEntry 6 }

layer7NewCfgContentClassHeaderCase OBJECT-TYPE
    SYNTAX  INTEGER {
        enabled(1),
        disabled(2)
        }
    MAX-ACCESS  read-write
    STATUS  current
    DESCRIPTION
        "Enable or Disable Case sensitive for String matching."
    ::= { layer7NewCfgContentClassHeaderEntry 7 }

layer7NewCfgContentClassHeaderDelete OBJECT-TYPE
    SYNTAX  INTEGER {
        other(1),
        delete(2)
        }
    MAX-ACCESS  read-write
    STATUS  current
    DESCRIPTION
        "By setting the value to delete(2), the entire row is deleted."
    ::= { layer7NewCfgContentClassHeaderEntry 8 }

layer7NewCfgContentClassHeaderCopy OBJECT-TYPE
    SYNTAX   DisplayString (SIZE (0..32))
    MAX-ACCESS  read-write
    STATUS  current
    DESCRIPTION
        "This is an action object.Enter the new Header
         to which the curent Header has to be copied."
    ::= { layer7NewCfgContentClassHeaderEntry 9 }

layer7CurCfgContentClassCookieTable OBJECT-TYPE
    SYNTAX  SEQUENCE OF Layer7CurCfgContentClassCookieEntry
    MAX-ACCESS  not-accessible
    STATUS  current
    DESCRIPTION
        "The table for configuring Content Class Cookie."
    ::= { contentClass 13 }

layer7CurCfgContentClassCookieEntry OBJECT-TYPE
    SYNTAX  Layer7CurCfgContentClassCookieEntry
    MAX-ACCESS  not-accessible
    STATUS  current
    DESCRIPTION
        "A row in the Content Class table."
    INDEX   { layer7CurCfgContentClassCookieContentClassID, layer7CurCfgContentClassCookieID }
    ::= { layer7CurCfgContentClassCookieTable 1 }

Layer7CurCfgContentClassCookieEntry ::= SEQUENCE {
    layer7CurCfgContentClassCookieContentClassID  DisplayString,
    layer7CurCfgContentClassCookieID              DisplayString,
    layer7CurCfgContentClassCookieKey             DisplayString,
	layer7CurCfgContentClassCookieVal             DisplayString,
    layer7CurCfgContentClassCookieMatchTypeKey    INTEGER,
	layer7CurCfgContentClassCookieMatchTypeVal    INTEGER,
    layer7CurCfgContentClassCookieCase            INTEGER
    }

layer7CurCfgContentClassCookieContentClassID OBJECT-TYPE
    SYNTAX   DisplayString (SIZE (0..32))
    MAX-ACCESS  read-only
    STATUS  current
    DESCRIPTION
        "The content Class Cookie ID(key id) as an index, length of the string should be 32 characters."
    ::= { layer7CurCfgContentClassCookieEntry 1 }

layer7CurCfgContentClassCookieID OBJECT-TYPE
    SYNTAX   DisplayString (SIZE (0..32))
    MAX-ACCESS  read-only
    STATUS  current
    DESCRIPTION
        "The content Class ID(key id) as an index, length of the string should be 32 characters."
    ::= { layer7CurCfgContentClassCookieEntry 2 }

layer7CurCfgContentClassCookieKey OBJECT-TYPE
    SYNTAX   DisplayString (SIZE (0..128))
    MAX-ACCESS  read-only
    STATUS  current
    DESCRIPTION
        "Content Class Cookie to match, length of the string should be 32 characters."
    ::= { layer7CurCfgContentClassCookieEntry 3 }

layer7CurCfgContentClassCookieVal OBJECT-TYPE
    SYNTAX   DisplayString (SIZE (0..128))
    MAX-ACCESS  read-only
    STATUS  current
    DESCRIPTION
        "Content Class Cookie to match, length of the string should be 32 characters."
    ::= { layer7CurCfgContentClassCookieEntry 4 }

layer7CurCfgContentClassCookieMatchTypeKey OBJECT-TYPE
    SYNTAX  INTEGER {
        equal(3),
        include(4),
        regex(5)
        }
    MAX-ACCESS  read-only
    STATUS  current
    DESCRIPTION
        "Header Match type."
    ::= { layer7CurCfgContentClassCookieEntry 5 }

layer7CurCfgContentClassCookieMatchTypeVal OBJECT-TYPE
    SYNTAX  INTEGER {
        equal(3),
        include(4),
        regex(5)
        }
    MAX-ACCESS  read-only
    STATUS  current
    DESCRIPTION
        "Header Match type."
    ::= { layer7CurCfgContentClassCookieEntry 6 }

layer7CurCfgContentClassCookieCase OBJECT-TYPE
    SYNTAX  INTEGER {
        enabled(1),
        disabled(2)
        }
    MAX-ACCESS  read-only
    STATUS  current
    DESCRIPTION
        "Enable or Disable Case sensitive for String matching."
    ::= { layer7CurCfgContentClassCookieEntry 7 }


layer7NewCfgContentClassCookieTable OBJECT-TYPE
    SYNTAX  SEQUENCE OF Layer7NewCfgContentClassCookieEntry
    MAX-ACCESS  not-accessible
    STATUS  current
    DESCRIPTION
        "The table for configuring Content Class Cookie."
    ::= { contentClass 14 }

layer7NewCfgContentClassCookieEntry OBJECT-TYPE
    SYNTAX  Layer7NewCfgContentClassCookieEntry
    MAX-ACCESS  not-accessible
    STATUS  current
    DESCRIPTION
        "A row in the Content Class table."
    INDEX   { layer7NewCfgContentClassCookieContentClassID, layer7NewCfgContentClassCookieID }
    ::= { layer7NewCfgContentClassCookieTable 1 }

Layer7NewCfgContentClassCookieEntry ::= SEQUENCE {
    layer7NewCfgContentClassCookieContentClassID  DisplayString,
    layer7NewCfgContentClassCookieID              DisplayString,
    layer7NewCfgContentClassCookieKey             DisplayString,
    layer7NewCfgContentClassCookieVal             DisplayString,
    layer7NewCfgContentClassCookieMatchTypeKey    INTEGER,
    layer7NewCfgContentClassCookieMatchTypeVal    INTEGER,
    layer7NewCfgContentClassCookieCase            INTEGER,
    layer7NewCfgContentClassCookieDelete          INTEGER,
    layer7NewCfgContentClassCookieCopy            DisplayString
    }

layer7NewCfgContentClassCookieContentClassID OBJECT-TYPE
    SYNTAX   DisplayString (SIZE (0..32))
    MAX-ACCESS  read-only
    STATUS  current
    DESCRIPTION
        "The content Class Cookie ID(key id) as an index, length of the string should be 32 characters."
    ::= { layer7NewCfgContentClassCookieEntry 1 }

layer7NewCfgContentClassCookieID OBJECT-TYPE
    SYNTAX   DisplayString (SIZE (0..32))
    MAX-ACCESS  read-only
    STATUS  current
    DESCRIPTION
        "The content Class ID(key id) as an index, length of the string should be 32 characters."
    ::= { layer7NewCfgContentClassCookieEntry 2 }

layer7NewCfgContentClassCookieKey OBJECT-TYPE
    SYNTAX   DisplayString (SIZE (0..128))
    MAX-ACCESS  read-create
    STATUS  current
    DESCRIPTION
        "Content Class Cookie to match, length of the string should be 32 characters."
    ::= { layer7NewCfgContentClassCookieEntry 3 }

layer7NewCfgContentClassCookieVal OBJECT-TYPE
    SYNTAX   DisplayString (SIZE (0..128))
    MAX-ACCESS  read-create
    STATUS  current
    DESCRIPTION
        "Content Class Cookie to match, length of the string should be 32 characters."
    ::= { layer7NewCfgContentClassCookieEntry 4 }

layer7NewCfgContentClassCookieMatchTypeKey OBJECT-TYPE
    SYNTAX  INTEGER {
        equal(3),
        include(4),
        regex(5)
        }
    MAX-ACCESS  read-create
    STATUS  current
    DESCRIPTION
        "Header Match type."
    ::= { layer7NewCfgContentClassCookieEntry 5 }

layer7NewCfgContentClassCookieMatchTypeVal OBJECT-TYPE
    SYNTAX  INTEGER {
        equal(3),
        include(4),
        regex(5)
        }
    MAX-ACCESS  read-create
    STATUS  current
    DESCRIPTION
        "Header Match type."
    ::= { layer7NewCfgContentClassCookieEntry 6 }

layer7NewCfgContentClassCookieCase OBJECT-TYPE
    SYNTAX  INTEGER {
        enabled(1),
        disabled(2)
        }
    MAX-ACCESS  read-create
    STATUS  current
    DESCRIPTION
        "Enable or Disable Case sensitive for String matching."
    ::= { layer7NewCfgContentClassCookieEntry 7 }

layer7NewCfgContentClassCookieDelete OBJECT-TYPE
    SYNTAX  INTEGER {
        other(1),
        delete(2)
        }
    MAX-ACCESS  read-create
    STATUS  current
    DESCRIPTION
        "By setting the value to delete(2), the entire row is deleted."
    ::= { layer7NewCfgContentClassCookieEntry 8 }

layer7NewCfgContentClassCookieCopy OBJECT-TYPE
    SYNTAX   DisplayString (SIZE (0..32))
    MAX-ACCESS  read-write
    STATUS  current
    DESCRIPTION
        "This is an action object.Enter the new Cookie
         to which the curent Cookie has to be copied."
    ::= { layer7NewCfgContentClassCookieEntry 9 }

layer7CurCfgContentClassTextTable OBJECT-TYPE
    SYNTAX  SEQUENCE OF Layer7CurCfgContentClassTextEntry
    MAX-ACCESS  not-accessible
    STATUS  current
    DESCRIPTION
        "The table for configuring Content Class Text."
    ::= { contentClass 15 }

layer7CurCfgContentClassTextEntry OBJECT-TYPE
    SYNTAX  Layer7CurCfgContentClassTextEntry
    MAX-ACCESS  not-accessible
    STATUS  current
    DESCRIPTION
        "A row in the Content Class table."
    INDEX   { layer7CurCfgContentClassTextContentClassID, layer7CurCfgContentClassTextID }
    ::= { layer7CurCfgContentClassTextTable 1 }

Layer7CurCfgContentClassTextEntry ::= SEQUENCE {
    layer7CurCfgContentClassTextContentClassID  DisplayString,
    layer7CurCfgContentClassTextID              DisplayString,
    layer7CurCfgContentClassTextText            DisplayString,
    layer7CurCfgContentClassTextMatchType       INTEGER,
    layer7CurCfgContentClassTextLookupArea      INTEGER,
	layer7CurCfgContentClassTextCase            INTEGER
    }

layer7CurCfgContentClassTextContentClassID OBJECT-TYPE
    SYNTAX   DisplayString (SIZE (0..32))
    MAX-ACCESS  read-only
    STATUS  current
    DESCRIPTION
        "The content Class Text ID(key id) as an index, length of the string should be 32 characters."
    ::= { layer7CurCfgContentClassTextEntry 1 }

layer7CurCfgContentClassTextID OBJECT-TYPE
    SYNTAX   DisplayString (SIZE (0..32))
    MAX-ACCESS  read-only
    STATUS  current
    DESCRIPTION
        "The content Class ID(key id) as an index, length of the string should be 32 characters."
    ::= { layer7CurCfgContentClassTextEntry 2 }

layer7CurCfgContentClassTextText OBJECT-TYPE
    SYNTAX   DisplayString (SIZE (0..128))
    MAX-ACCESS  read-only
    STATUS  current
    DESCRIPTION
        "Content Class Text to match, length of the string should be 32 characters."
    ::= { layer7CurCfgContentClassTextEntry 3 }

layer7CurCfgContentClassTextMatchType OBJECT-TYPE
    SYNTAX  INTEGER {
        include(4),
        regex(5)
        }
    MAX-ACCESS  read-only
    STATUS  current
    DESCRIPTION
        "Text Match type."
    ::= { layer7CurCfgContentClassTextEntry 4 }

layer7CurCfgContentClassTextLookupArea OBJECT-TYPE
    SYNTAX  INTEGER {
        header(1),
        body(2),
		both(3)
        }
    MAX-ACCESS  read-only
    STATUS  current
    DESCRIPTION
        "Text Match type."
    ::= { layer7CurCfgContentClassTextEntry 5 }

layer7CurCfgContentClassTextCase OBJECT-TYPE
    SYNTAX  INTEGER {
        enabled(1),
        disabled(2)
        }
    MAX-ACCESS  read-only
    STATUS  current
    DESCRIPTION
        "Enable or Disable Case sensitive for String matching."
    ::= { layer7CurCfgContentClassTextEntry 6 }


layer7NewCfgContentClassTextTable OBJECT-TYPE
    SYNTAX  SEQUENCE OF Layer7NewCfgContentClassTextEntry
    MAX-ACCESS  not-accessible
    STATUS  current
    DESCRIPTION
        "The table for configuring Content Class Text."
    ::= { contentClass 16 }

layer7NewCfgContentClassTextEntry OBJECT-TYPE
    SYNTAX  Layer7NewCfgContentClassTextEntry
    MAX-ACCESS  not-accessible
    STATUS  current
    DESCRIPTION
        "A row in the Content Class table."
    INDEX   { layer7NewCfgContentClassTextContentClassID, layer7NewCfgContentClassTextID }
    ::= { layer7NewCfgContentClassTextTable 1 }

Layer7NewCfgContentClassTextEntry ::= SEQUENCE {
    layer7NewCfgContentClassTextContentClassID  DisplayString,
    layer7NewCfgContentClassTextID              DisplayString,
    layer7NewCfgContentClassTextText            DisplayString,
    layer7NewCfgContentClassTextMatchType       INTEGER,
    layer7NewCfgContentClassTextLookupArea      INTEGER,
    layer7NewCfgContentClassTextCase            INTEGER,
    layer7NewCfgContentClassTextDelete          INTEGER,
    layer7NewCfgContentClassTextCopy            DisplayString
    }

layer7NewCfgContentClassTextContentClassID OBJECT-TYPE
    SYNTAX   DisplayString (SIZE (0..32))
    MAX-ACCESS  read-only
    STATUS  current
    DESCRIPTION
        "The content Class Text ID(key id) as an index, length of the string should be 32 characters."
    ::= { layer7NewCfgContentClassTextEntry 1 }

layer7NewCfgContentClassTextID OBJECT-TYPE
    SYNTAX   DisplayString (SIZE (0..32))
    MAX-ACCESS  read-only
    STATUS  current
    DESCRIPTION
        "The content Class ID(key id) as an index, length of the string should be 32 characters."
    ::= { layer7NewCfgContentClassTextEntry 2 }

layer7NewCfgContentClassTextText OBJECT-TYPE
    SYNTAX   DisplayString (SIZE (0..128))
    MAX-ACCESS  read-create
    STATUS  current
    DESCRIPTION
        "Content Class Text to match, length of the string should be 32 characters."
    ::= { layer7NewCfgContentClassTextEntry 3 }

layer7NewCfgContentClassTextMatchType OBJECT-TYPE
    SYNTAX  INTEGER {
        include(4),
        regex(5)
        }
    MAX-ACCESS  read-create
    STATUS  current
    DESCRIPTION
        "Text Match type."
    ::= { layer7NewCfgContentClassTextEntry 4 }

layer7NewCfgContentClassTextLookupArea OBJECT-TYPE
    SYNTAX  INTEGER {
        header(1),
        body(2),
		both(3)
        }
    MAX-ACCESS  read-create
    STATUS  current
    DESCRIPTION
        "Text Match type."
    ::= { layer7NewCfgContentClassTextEntry 5 }

layer7NewCfgContentClassTextCase OBJECT-TYPE
    SYNTAX  INTEGER {
        enabled(1),
        disabled(2)
        }
    MAX-ACCESS  read-create
    STATUS  current
    DESCRIPTION
        "Enable or Disable Case sensitive for String matching."
    ::= { layer7NewCfgContentClassTextEntry 6 }

layer7NewCfgContentClassTextDelete OBJECT-TYPE
    SYNTAX  INTEGER {
        other(1),
        delete(2)
        }
    MAX-ACCESS  read-create
    STATUS  current
    DESCRIPTION
        "By setting the value to delete(2), the entire row is deleted."
    ::= { layer7NewCfgContentClassTextEntry 7 }

layer7NewCfgContentClassTextCopy OBJECT-TYPE
    SYNTAX   DisplayString (SIZE (0..32))
    MAX-ACCESS  read-write
    STATUS  current
    DESCRIPTION
        "This is an action object.Enter the new Text
         to which the curent Text has to be copied."
    ::= { layer7NewCfgContentClassTextEntry 8 }

layer7CurCfgContentClassXmlTable OBJECT-TYPE
    SYNTAX  SEQUENCE OF Layer7CurCfgContentClassXmlEntry
    MAX-ACCESS  not-accessible
    STATUS  current
    DESCRIPTION
        "The table for configuring Content Class Xml Tag."
    ::= { contentClass 17 }

layer7CurCfgContentClassXmlEntry OBJECT-TYPE
    SYNTAX  Layer7CurCfgContentClassXmlEntry
    MAX-ACCESS  not-accessible
    STATUS  current
    DESCRIPTION
        "A row in the Content Class table."
    INDEX   { layer7CurCfgContentClassXmlTagContentClassID, layer7CurCfgContentClassXmlTagID }
    ::= { layer7CurCfgContentClassXmlTable 1 }

Layer7CurCfgContentClassXmlEntry ::= SEQUENCE {
    layer7CurCfgContentClassXmlTagContentClassID  DisplayString,
    layer7CurCfgContentClassXmlTagID              DisplayString,
    layer7CurCfgContentClassXmlTagName            DisplayString,
	layer7CurCfgContentClassXmlTagVal             DisplayString,
    layer7CurCfgContentClassXmlTagMatchTypeName   INTEGER,
	layer7CurCfgContentClassXmlTagMatchTypeVal    INTEGER,
    layer7CurCfgContentClassXmlTagCase            INTEGER
    }

layer7CurCfgContentClassXmlTagContentClassID OBJECT-TYPE
    SYNTAX   DisplayString (SIZE (0..32))
    MAX-ACCESS  read-only
    STATUS  current
    DESCRIPTION
        "content Class Text ID(key id) as an index, length of the string should be 32 characters."
    ::= { layer7CurCfgContentClassXmlEntry 1 }

layer7CurCfgContentClassXmlTagID OBJECT-TYPE
    SYNTAX   DisplayString (SIZE (0..32))
    MAX-ACCESS  read-only
    STATUS  current
    DESCRIPTION
        "Content Class ID(key id) as an index, length of the string should be 32 characters."
    ::= { layer7CurCfgContentClassXmlEntry 2 }

layer7CurCfgContentClassXmlTagName OBJECT-TYPE
    SYNTAX   DisplayString (SIZE (0..128))
    MAX-ACCESS  read-only
    STATUS  current
    DESCRIPTION
        "Content Class Xml to match, length of the string should be 32 characters."
    ::= { layer7CurCfgContentClassXmlEntry 3 }


layer7CurCfgContentClassXmlTagVal OBJECT-TYPE
    SYNTAX   DisplayString (SIZE (0..128))
    MAX-ACCESS  read-only
    STATUS  current
    DESCRIPTION
        "Content Class Xml to match, length of the string should be 32 characters."
    ::= { layer7CurCfgContentClassXmlEntry 4 }

layer7CurCfgContentClassXmlTagMatchTypeName OBJECT-TYPE
    SYNTAX  INTEGER {
        sufx(1),
        equal(3)
        }
    MAX-ACCESS  read-only
    STATUS  current
    DESCRIPTION
        "Xml Match type."
    ::= { layer7CurCfgContentClassXmlEntry 5 }

layer7CurCfgContentClassXmlTagMatchTypeVal OBJECT-TYPE
    SYNTAX  INTEGER {
        sufx(1),
        equal(3),
        include(4)
        }
    MAX-ACCESS  read-only
    STATUS  current
    DESCRIPTION
        "Xml Match type."
    ::= { layer7CurCfgContentClassXmlEntry 6 }

layer7CurCfgContentClassXmlTagCase OBJECT-TYPE
    SYNTAX  INTEGER {
        enabled(1),
        disabled(2)
        }
    MAX-ACCESS  read-only
    STATUS  current
    DESCRIPTION
        "Enable or Disable Case sensitive for String matching."
    ::= { layer7CurCfgContentClassXmlEntry 7 }


layer7NewCfgContentClassXmlTable OBJECT-TYPE
    SYNTAX  SEQUENCE OF Layer7NewCfgContentClassXmlEntry
    MAX-ACCESS  not-accessible
    STATUS  current
    DESCRIPTION
        "The table for configuring Content Class Xml Tag."
    ::= { contentClass 18 }

layer7NewCfgContentClassXmlEntry OBJECT-TYPE
    SYNTAX  Layer7NewCfgContentClassXmlEntry
    MAX-ACCESS  not-accessible
    STATUS  current
    DESCRIPTION
        "A row in the Content Class table."
    INDEX   { layer7NewCfgContentClassXmlTagContentClassID, layer7NewCfgContentClassXmlTagID }
    ::= { layer7NewCfgContentClassXmlTable 1 }

Layer7NewCfgContentClassXmlEntry ::= SEQUENCE {
    layer7NewCfgContentClassXmlTagContentClassID  DisplayString,
    layer7NewCfgContentClassXmlTagID              DisplayString,
    layer7NewCfgContentClassXmlTagName            DisplayString,
    layer7NewCfgContentClassXmlTagVal             DisplayString,
    layer7NewCfgContentClassXmlTagMatchTypeName   INTEGER,
    layer7NewCfgContentClassXmlTagMatchTypeVal    INTEGER,
    layer7NewCfgContentClassXmlTagCase            INTEGER,
    layer7NewCfgContentClassXmlTagDelete          INTEGER,
    layer7NewCfgContentClassXmlTagCopy            DisplayString
    }

layer7NewCfgContentClassXmlTagContentClassID OBJECT-TYPE
    SYNTAX   DisplayString (SIZE (0..32))
    MAX-ACCESS  read-only
    STATUS  current
    DESCRIPTION
        "content Class Text ID(key id) as an index, length of the string should be 32 characters."
    ::= { layer7NewCfgContentClassXmlEntry 1 }

layer7NewCfgContentClassXmlTagID OBJECT-TYPE
    SYNTAX   DisplayString (SIZE (0..32))
    MAX-ACCESS  read-only
    STATUS  current
    DESCRIPTION
        "Content Class ID(key id) as an index, length of the string should be 32 characters."
    ::= { layer7NewCfgContentClassXmlEntry 2 }

layer7NewCfgContentClassXmlTagName OBJECT-TYPE
    SYNTAX   DisplayString (SIZE (0..128))
    MAX-ACCESS  read-create
    STATUS  current
    DESCRIPTION
        "Content Class Xml to match, length of the string should be 32 characters."
    ::= { layer7NewCfgContentClassXmlEntry 3 }

layer7NewCfgContentClassXmlTagVal OBJECT-TYPE
    SYNTAX   DisplayString (SIZE (0..128))
    MAX-ACCESS  read-create
    STATUS  current
    DESCRIPTION
        "Content Class Xml to match, length of the string should be 32 characters."
    ::= { layer7NewCfgContentClassXmlEntry 4 }

layer7NewCfgContentClassXmlTagMatchTypeName OBJECT-TYPE
    SYNTAX  INTEGER {
        sufx(1),
        equal(3)
        }
    MAX-ACCESS  read-create
    STATUS  current
    DESCRIPTION
        "Xml Match type."
    ::= { layer7NewCfgContentClassXmlEntry 5 }

layer7NewCfgContentClassXmlTagMatchTypeVal OBJECT-TYPE
    SYNTAX  INTEGER {
        sufx(1),
        equal(3),
        include(4)
        }
    MAX-ACCESS  read-create
    STATUS  current
    DESCRIPTION
        "Xml Match type."
    ::= { layer7NewCfgContentClassXmlEntry 6 }

layer7NewCfgContentClassXmlTagCase OBJECT-TYPE
    SYNTAX  INTEGER {
        enabled(1),
        disabled(2)
        }
    MAX-ACCESS  read-create
    STATUS  current
    DESCRIPTION
        "Enable or Disable Case sensitive for String matching."
    ::= { layer7NewCfgContentClassXmlEntry 7 }

layer7NewCfgContentClassXmlTagDelete OBJECT-TYPE
    SYNTAX  INTEGER {
        other(1),
        delete(2)
        }
    MAX-ACCESS  read-create
    STATUS  current
    DESCRIPTION
        "By setting the value to delete(2), the entire row is deleted."
    ::= { layer7NewCfgContentClassXmlEntry 8 }

layer7NewCfgContentClassXmlTagCopy OBJECT-TYPE
    SYNTAX   DisplayString (SIZE (0..32))
    MAX-ACCESS  read-write
    STATUS  current
    DESCRIPTION
        "This is an action object.Enter the new Xmltag
         to which the curent Xmltag has to be copied."
    ::= { layer7NewCfgContentClassXmlEntry 9 }


slbSdpTableMaxSize OBJECT-TYPE
    SYNTAX  Integer32 
    MAX-ACCESS  read-only 
    STATUS  current 
    DESCRIPTION 
        "The maximum number of SDP entries in layer7 processing engine." 
    ::= { sdpCfg 1 }

slbCurCfgSdpTable OBJECT-TYPE
    SYNTAX  SEQUENCE OF SlbCurCfgSdpTableEntry 
    MAX-ACCESS  not-accessible
    STATUS  current
    DESCRIPTION
        "The SDP table in layer7 processing engine."
    ::= { sdpCfg 2 }

slbCurCfgSdpTableEntry OBJECT-TYPE
    SYNTAX  SlbCurCfgSdpTableEntry
    MAX-ACCESS  not-accessible
    STATUS  current
    DESCRIPTION
        "A row in the table."
    INDEX   { slbCurCfgSdpIndex }
    ::= { slbCurCfgSdpTable 1 }

SlbCurCfgSdpTableEntry ::= SEQUENCE {
    slbCurCfgSdpIndex                Integer32,
    slbCurCfgSdpPrivAddr             IpAddress,
    slbCurCfgSdpPublicAddr           IpAddress
    }   

slbCurCfgSdpIndex   OBJECT-TYPE 
    SYNTAX  Integer32 
    MAX-ACCESS  read-only 
    STATUS  current 
    DESCRIPTION 
        "The SDP table index." 
    ::= { slbCurCfgSdpTableEntry 1 }

slbCurCfgSdpPrivAddr OBJECT-TYPE
    SYNTAX  IpAddress
    MAX-ACCESS  read-only
    STATUS  current
    DESCRIPTION
        "The private IP address of SDP entry."
    ::= { slbCurCfgSdpTableEntry 2 }

slbCurCfgSdpPublicAddr OBJECT-TYPE
    SYNTAX  IpAddress
    MAX-ACCESS  read-only
    STATUS  current
    DESCRIPTION
        "The public IP address of SDP entry."
    ::= { slbCurCfgSdpTableEntry 3 }

slbNewCfgSdpTable OBJECT-TYPE
    SYNTAX  SEQUENCE OF SlbNewCfgSdpTableEntry
    MAX-ACCESS  not-accessible
    STATUS  current
    DESCRIPTION
        "The SDP table in layer7 processing engine."
    ::= { sdpCfg 3 }

slbNewCfgSdpTableEntry OBJECT-TYPE
    SYNTAX  SlbNewCfgSdpTableEntry
    MAX-ACCESS  not-accessible
    STATUS  current
    DESCRIPTION
        "A row in the SDP table."
    INDEX   { slbNewCfgSdpIndex }
    ::= { slbNewCfgSdpTable 1 }

SlbNewCfgSdpTableEntry ::= SEQUENCE {
    slbNewCfgSdpIndex                Integer32,
    slbNewCfgSdpPrivAddr             IpAddress,
    slbNewCfgSdpPublicAddr           IpAddress,
    slbNewCfgSdpDelete               INTEGER
    }

slbNewCfgSdpIndex   OBJECT-TYPE
    SYNTAX  Integer32
    MAX-ACCESS  read-only
    STATUS  current
    DESCRIPTION
        "The SDP table index.Maximum entries you can configure is 16"
    ::= { slbNewCfgSdpTableEntry 1 }

slbNewCfgSdpPrivAddr OBJECT-TYPE
    SYNTAX  IpAddress
    MAX-ACCESS  read-create
    STATUS  current
    DESCRIPTION
        "The private IP address of SDP entry."
    ::= { slbNewCfgSdpTableEntry 2 }

slbNewCfgSdpPublicAddr OBJECT-TYPE
    SYNTAX  IpAddress
    MAX-ACCESS  read-create
    STATUS  current
    DESCRIPTION
        "The public IP address of SDP entry."
    ::= { slbNewCfgSdpTableEntry 3 }

slbNewCfgSdpDelete  OBJECT-TYPE
    SYNTAX  INTEGER {
        other(1),
        delete(2)
        }
    MAX-ACCESS  read-create
    STATUS  current
    DESCRIPTION
        "When set to the value of 2 (delete), the entire row is
         deleted. When read, other(1) is returned. Setting the value
         to anything other than 2(delete) has no effect on the state of the row." 
    ::= { slbNewCfgSdpTableEntry 4 }

-- Layer7 SIP UDP Rules

slbCurCfgSipUdpRuleTable OBJECT-TYPE
    SYNTAX SEQUENCE OF SlbCurCfgSipUdpRuleTableEntry 
    MAX-ACCESS not-accessible
    STATUS current
    DESCRIPTION
      "The table of SIP Udp rule configuration in the current_config."
    ::= { ruleCfg 1 }

slbCurCfgSipUdpRuleTableEntry OBJECT-TYPE
    SYNTAX SlbCurCfgSipUdpRuleTableEntry 
    MAX-ACCESS not-accessible
    STATUS current
    DESCRIPTION
      "A row in the table."
    INDEX { slbCurCfgSipUdpRuleIndex }
    ::= { slbCurCfgSipUdpRuleTable 1 }

SlbCurCfgSipUdpRuleTableEntry ::= SEQUENCE {
    slbCurCfgSipUdpRuleIndex         Integer32,
    slbCurCfgSipUdpRuleHdrFld        INTEGER,
    slbCurCfgSipUdpRuleContent       DisplayString,
    slbCurCfgSipUdpRuleContract      Integer32,
    slbCurCfgSipUdpRuleMsg           DisplayString,
    slbCurCfgSipUdpRuleSeverity      Integer32,
    slbCurCfgSipUdpRuleAdd           DisplayString,
    slbCurCfgSipUdpRuleState         INTEGER,
    slbCurCfgSipUdpRuleBmap          OCTET STRING
    }
slbCurCfgSipUdpRuleIndex OBJECT-TYPE
    SYNTAX Integer32
    MAX-ACCESS read-only
    STATUS current
    DESCRIPTION
        "The UDP Rule number for which the SIP UDP rule table is related."
    ::= { slbCurCfgSipUdpRuleTableEntry 1}

slbCurCfgSipUdpRuleHdrFld OBJECT-TYPE
    SYNTAX INTEGER {
      	none(0),
	callid(1),
        contact(2),
        contentlen(3),
	cseq(4),
	expires(5),
	from(6),
	replyto(7),
	to(8),
	via(9),
	reqline(10),
	method(11),
	sdpcontent(12)
        }
    MAX-ACCESS read-only
    STATUS current
    DESCRIPTION
        "The name of the header field."
    ::= { slbCurCfgSipUdpRuleTableEntry 2 }

 slbCurCfgSipUdpRuleContent OBJECT-TYPE
    SYNTAX DisplayString (SIZE(0..50))
    MAX-ACCESS read-only
    STATUS current
    DESCRIPTION
        "The content length of the UDP header field."
    ::= { slbCurCfgSipUdpRuleTableEntry 3 }

slbCurCfgSipUdpRuleContract OBJECT-TYPE
    SYNTAX  Integer32 (1..1024)
    MAX-ACCESS  read-only
    STATUS  current
    DESCRIPTION
        "BWM contract for this rule."
    ::= { slbCurCfgSipUdpRuleTableEntry 4 }

slbCurCfgSipUdpRuleMsg OBJECT-TYPE
    SYNTAX DisplayString (SIZE(0..20))
    MAX-ACCESS read-only
    STATUS current
    DESCRIPTION
        "The Alert message for this rule."
    ::= { slbCurCfgSipUdpRuleTableEntry 5 }

slbCurCfgSipUdpRuleSeverity OBJECT-TYPE
    SYNTAX  Integer32 (1..5)
    MAX-ACCESS  read-only
    STATUS  current
    DESCRIPTION
        "The severity of this rule."
    ::= { slbCurCfgSipUdpRuleTableEntry 6 }

slbCurCfgSipUdpRuleAdd OBJECT-TYPE
    SYNTAX DisplayString (SIZE(0..255)) 
    MAX-ACCESS read-only
    STATUS current
    DESCRIPTION
        "The dependent rules of this rule."
    ::= { slbCurCfgSipUdpRuleTableEntry 7 }

slbCurCfgSipUdpRuleState OBJECT-TYPE
    SYNTAX INTEGER {
	enabled(1),
        disabled(2)
        }
    MAX-ACCESS read-only
    STATUS current
    DESCRIPTION
        "Enable or disable this rule."
    ::= { slbCurCfgSipUdpRuleTableEntry 8 }

slbCurCfgSipUdpRuleBmap OBJECT-TYPE
    SYNTAX  OCTET STRING
    MAX-ACCESS  read-only
    STATUS  current
    DESCRIPTION
        "The SIP UDP Dependent Rules.
         The SIP UDP Dependent Rules are presented in a bitmap format.

        in receiving order:

        OCTET 1  OCTET 2  .....
        xxxxxxxx xxxxxxxx .....
        ||    || |_ Dependent Rule
        ||    ||
        ||    ||___ Dependent Rule 4
        ||    |____ Dependent Rule 3
        ||      .    .   .
        ||_________ Dependent Rule 2
        |__________ Dependent Rule 1

        where x : 1 - The represented Dependent Rule is selected
                  0 - The represented Dependent Rule is not selected"
    ::= { slbCurCfgSipUdpRuleTableEntry 9 }


slbNewCfgSipUdpRuleTable OBJECT-TYPE
    SYNTAX SEQUENCE OF SlbNewCfgSipUdpRuleTableEntry
    MAX-ACCESS not-accessible
    STATUS current
    DESCRIPTION
      "The table of SIP Udp rule configuration in the current_config."
    ::= { ruleCfg 2 }

slbNewCfgSipUdpRuleTableEntry OBJECT-TYPE
    SYNTAX SlbNewCfgSipUdpRuleTableEntry 
    MAX-ACCESS not-accessible
    STATUS current
    DESCRIPTION
      "A row in the table."
    INDEX { slbNewCfgSipUdpRuleIndex }
    ::= { slbNewCfgSipUdpRuleTable 1 }

SlbNewCfgSipUdpRuleTableEntry ::= SEQUENCE {
    slbNewCfgSipUdpRuleIndex         Integer32,
    slbNewCfgSipUdpRuleHdrFld        INTEGER,
    slbNewCfgSipUdpRuleContent       DisplayString,
    slbNewCfgSipUdpRuleContract      Integer32,
    slbNewCfgSipUdpRuleMsg           DisplayString,
    slbNewCfgSipUdpRuleSeverity      Integer32,
    slbNewCfgSipUdpRuleAdd           Integer32,
    slbNewCfgSipUdpRuleRem           Integer32,
    slbNewCfgSipUdpRuleState         INTEGER,
    slbNewCfgSipUdpRuleDelete        INTEGER,
    slbNewCfgSipUdpRuleBmap          OCTET STRING
    }
slbNewCfgSipUdpRuleIndex OBJECT-TYPE
    SYNTAX Integer32
    MAX-ACCESS read-only
    STATUS current
    DESCRIPTION
        "The UDP Rule number for which the SIP UDP rule table is related."
    ::= { slbNewCfgSipUdpRuleTableEntry 1}

slbNewCfgSipUdpRuleHdrFld OBJECT-TYPE
    SYNTAX INTEGER {
      	none(0),
	callid(1),
        contact(2),
        contentlen(3),
	cseq(4),
	expires(5),
	from(6),
	replyto(7),
	to(8),
	via(9),
	reqline(10),
	method(11),
	sdpcontent(12)
        }
    MAX-ACCESS read-create
    STATUS current
    DESCRIPTION
        "The name of the header field."
    ::= { slbNewCfgSipUdpRuleTableEntry 2 }

 slbNewCfgSipUdpRuleContent OBJECT-TYPE
    SYNTAX DisplayString (SIZE(0..50))
    MAX-ACCESS read-create
    STATUS current
    DESCRIPTION
        "The content length of the UDP header field."
    ::= { slbNewCfgSipUdpRuleTableEntry 3 }

slbNewCfgSipUdpRuleContract OBJECT-TYPE
    SYNTAX  Integer32 (1..1024)
    MAX-ACCESS  read-create
    STATUS  current
    DESCRIPTION
        "BWM contract for this rule."
    ::= { slbNewCfgSipUdpRuleTableEntry 4 }

slbNewCfgSipUdpRuleMsg OBJECT-TYPE
    SYNTAX DisplayString (SIZE(0..20))
    MAX-ACCESS read-create
    STATUS current
    DESCRIPTION
        "The Alert message for this rule."
    ::= { slbNewCfgSipUdpRuleTableEntry 5 }

slbNewCfgSipUdpRuleSeverity OBJECT-TYPE
    SYNTAX  Integer32 (0..5)
    MAX-ACCESS  read-create
    STATUS  current
    DESCRIPTION
        "The severity of this rule."
    ::= { slbNewCfgSipUdpRuleTableEntry 6 }

slbNewCfgSipUdpRuleAdd OBJECT-TYPE
    SYNTAX Integer32 (1..100)
    MAX-ACCESS read-create
    STATUS current
    DESCRIPTION
        "Add dependent rules to this rule. A '0' value is returned when read." 
    ::= { slbNewCfgSipUdpRuleTableEntry 7 }

slbNewCfgSipUdpRuleRem OBJECT-TYPE
    SYNTAX Integer32 (1..100)
    MAX-ACCESS read-create
    STATUS current
    DESCRIPTION
        "Remove dependent rules from this rule."
    ::= { slbNewCfgSipUdpRuleTableEntry 8 }


slbNewCfgSipUdpRuleState OBJECT-TYPE
    SYNTAX INTEGER {
	enabled(1),
        disabled(2)
        }
    MAX-ACCESS read-create
    STATUS current
    DESCRIPTION
        "Enable or disable this rule."
    ::= { slbNewCfgSipUdpRuleTableEntry 9 }

slbNewCfgSipUdpRuleDelete  OBJECT-TYPE
    SYNTAX  INTEGER {
        other(1),
        delete(2)
        }
    MAX-ACCESS  read-create
    STATUS  current
    DESCRIPTION
        "When set to the value of 2 (delete), the entire row is
         deleted. When read, other(1) is returned. Setting the value
         to anything other than 2(delete) has no effect on the state of the row."
    ::= { slbNewCfgSipUdpRuleTableEntry 10 }

slbNewCfgSipUdpRuleBmap OBJECT-TYPE
    SYNTAX  OCTET STRING
    MAX-ACCESS  read-only
    STATUS  current
    DESCRIPTION
        "The SIP UDP Dependent Rules.
         The SIP UDP Dependent Rules are presented in a bitmap format.

         in receiving order:

         OCTET 1  OCTET 2  .....
         xxxxxxxx xxxxxxxx .....
         ||    || |_ Dependent Rule
         ||    ||
         ||    ||___ Dependent Rule 4
         ||    |____ Dependent Rule 3
         ||      .    .   .
         ||_________ Dependent Rule 2
         |__________ Dependent Rule 1

         where x : 1 - The represented Dependent Rule is selected
                   0 - The represented Dependent Rule is not selected"
    ::= { slbNewCfgSipUdpRuleTableEntry 11 }


-- The URL Redirection/Load Balancing Statistics

urlRedirStats    OBJECT IDENTIFIER ::= { urlStats  1 }

urlStatRedRedirs OBJECT-TYPE 
    SYNTAX  Counter32 
    MAX-ACCESS  read-only
    STATUS  current 
    DESCRIPTION 
        "The number of instances that the received packet matches the 
         specified URL expressions and redirected to specified group of 
         real servers."
    ::= { urlRedirStats 1 }

urlStatRedOrigSrvs OBJECT-TYPE 
    SYNTAX  Counter32 
    MAX-ACCESS  read-only
    STATUS  current 
    DESCRIPTION 
        "The number of instances that the received packet is sent to the 
         origin server due to mis-match with the specified URL expressions 
         or detecting of HTTP non-GETs,user cookies, and no-cache as users 
         configuration."
    ::= { urlRedirStats 2 }

urlStatRedNonGets OBJECT-TYPE 
    SYNTAX  Counter32 
    MAX-ACCESS  read-only
    STATUS  current 
    DESCRIPTION 
        "The number of instances that the received packet contains 
         none GETs(POST ,HEAD ,PUT..) methods."
    ::= { urlRedirStats 3 }

urlStatRedCookie OBJECT-TYPE 
    SYNTAX  Counter32 
    MAX-ACCESS  read-only
    STATUS  current 
    DESCRIPTION 
        "The number of instances that the received packet contains
         a 'Cookie: ' header."
    ::= { urlRedirStats 4 }

urlStatRedNoCache OBJECT-TYPE 
    SYNTAX  Counter32 
    MAX-ACCESS  read-only
    STATUS  current 
    DESCRIPTION 
        "The number of instances that the received packet contains
         a no-cache header value."
    ::= { urlRedirStats 5 }

urlStatRedStraightOrigSrvs OBJECT-TYPE 
    SYNTAX  Counter32 
    MAX-ACCESS  read-only
    STATUS  current 
    DESCRIPTION 
        "The number of HTTP requests forwarded straight to the origin server."
    ::= { urlRedirStats 6 }

urlStatRedRtspCacheSrvs OBJECT-TYPE 
    SYNTAX  Counter32 
    MAX-ACCESS  read-only
    STATUS  current 
    DESCRIPTION 
        "The number of RTSP requests redirected to the cache server."
    ::= { urlRedirStats 7 }

urlStatRedRtspOrigSrvs OBJECT-TYPE 
    SYNTAX  Counter32 
    MAX-ACCESS  read-only
    STATUS  current 
    DESCRIPTION 
        "The number of RTSP requests forwarded to the origin server."
    ::= { urlRedirStats 8 }

urlSlbStats    OBJECT IDENTIFIER ::= { urlStats  2 }

urlStatSlbPathTable OBJECT-TYPE
    SYNTAX  SEQUENCE OF UrlStatSlbPathTableEntry
    MAX-ACCESS  not-accessible
    STATUS  current
    DESCRIPTION
        "The statistics table of instances that the URL path matched."
    ::= { urlSlbStats 1 }

urlStatSlbPathTableEntry OBJECT-TYPE
    SYNTAX  UrlStatSlbPathTableEntry
    MAX-ACCESS  not-accessible
    STATUS  current
    DESCRIPTION
        "Information about the number of instances that are 
	 load-balanced due to match of a particular URL path."
    INDEX   { urlStatSlbPathIndex }
    ::= { urlStatSlbPathTable 1 }

UrlStatSlbPathTableEntry ::= SEQUENCE {
    urlStatSlbPathIndex       Integer32,
    urlStatSlbPathHits        Counter32
    }

urlStatSlbPathIndex OBJECT-TYPE
    SYNTAX  Integer32
    MAX-ACCESS  read-only
    STATUS  current
    DESCRIPTION
        "The URL path table index."
    ::= { urlStatSlbPathTableEntry 1 }

urlStatSlbPathHits OBJECT-TYPE
    SYNTAX  Counter32
    MAX-ACCESS  read-only
    STATUS  current
    DESCRIPTION
        "The number of instances that are load-balanced due to match of 
         the particular URL path."
    ::= { urlStatSlbPathTableEntry 2 }

-- Layer 7 Maintenance Statistics

urlMaintStats    OBJECT IDENTIFIER ::= { urlStats  3 }

urlMaintStatClientReset OBJECT-TYPE
    SYNTAX  Counter32
    MAX-ACCESS  read-only
    STATUS  current
    DESCRIPTION
	"The number of reset frames sent to the client by the switch during
         client connection termination."
    ::= { urlMaintStats 1 }

urlMaintStatServerReset OBJECT-TYPE
    SYNTAX  Counter32
    MAX-ACCESS  read-only
    STATUS  current
    DESCRIPTION
	"The number of reset frames sent to the server by the switch during
         server connection termination."
    ::= { urlMaintStats 2 }

urlMaintStatConnSplicing OBJECT-TYPE
    SYNTAX  Counter32
    MAX-ACCESS  read-only
    STATUS  current
    DESCRIPTION
	"The total number of connection swapping between different real
         servers in supporting multiple HTTP/1.1 client requests."
    ::= { urlMaintStats 3 }

urlMaintStatHalfOpens OBJECT-TYPE
    SYNTAX  Gauge32 
    MAX-ACCESS  read-only
    STATUS  current
    DESCRIPTION
	"The number of outstanding TCP connections have been half opened.
	 This statistics is valid only when URL parsing has been turned on.
	 It is incremented when the switch respond to TCP SYN packet and 
	 decremented upon receiving TCP SYN ACK packet from the requester."
    ::= { urlMaintStats 4 }

urlMaintStatSwitchRetries OBJECT-TYPE
    SYNTAX  Counter32
    MAX-ACCESS  read-only
    STATUS  current
    DESCRIPTION
	"The total number of switch retries to connect to the real server."
    ::= { urlMaintStats 5 }

urlMaintStatRandomEarlyDrops OBJECT-TYPE
    SYNTAX  Counter32
    MAX-ACCESS  read-only
    STATUS  current
    DESCRIPTION
	"The total number of SYN frames dropped when the buffer is low."
    ::= { urlMaintStats 6 }

urlMaintStatReqTooLong OBJECT-TYPE
    SYNTAX  Counter32
    MAX-ACCESS  read-only
    STATUS  current
    DESCRIPTION
	"The total number of GET requests that exceeded 4500 bytes."
    ::= { urlMaintStats 7 }

urlMaintStatInvalidHandshakes OBJECT-TYPE
    SYNTAX  Counter32
    MAX-ACCESS  read-only
    STATUS  current
    DESCRIPTION
	"The total number of dropped frames because of invalid 3-way 
         handshakes."
    ::= { urlMaintStats 8 }

urlMaintStatCurSPMemUnits OBJECT-TYPE
    SYNTAX  Gauge32
    MAX-ACCESS  read-only
    STATUS  current
    DESCRIPTION
	"The current available SP memory units."
    ::= { urlMaintStats 9 }

urlMaintStatCurSEQBufEntries OBJECT-TYPE
    SYNTAX  Gauge32
    MAX-ACCESS  read-only
    STATUS  current
    DESCRIPTION
	"The number of outstanding sequence buffers used."
    ::= { urlMaintStats 10 }

urlMaintStatHighestSEQBufEntries OBJECT-TYPE
    SYNTAX  Counter32
    MAX-ACCESS  read-only
    STATUS  current
    DESCRIPTION
	"The highest number of sequence buffers ever used."
    ::= { urlMaintStats 11 }

urlMaintStatCurDataBufUse OBJECT-TYPE
    SYNTAX  Gauge32
    MAX-ACCESS  read-only
    STATUS  current
    DESCRIPTION
	"The number of outstanding data buffers used."
    ::= { urlMaintStats 12 }

urlMaintStatHighestDataBufUse OBJECT-TYPE
    SYNTAX  Counter32
    MAX-ACCESS  read-only
    STATUS  current
    DESCRIPTION
	"The highest number of data buffers ever used."
    ::= { urlMaintStats 13 }

urlMaintStatCurSPBufEntries OBJECT-TYPE
    SYNTAX  Gauge32
    MAX-ACCESS  read-only
    STATUS  current
    DESCRIPTION
	"The number of outstanding SP buffers used."
    ::= { urlMaintStats 14 }

urlMaintStatHighestSPBufEntries OBJECT-TYPE
    SYNTAX  Counter32
    MAX-ACCESS  read-only
    STATUS  current
    DESCRIPTION
	"The number of SP buffers ever used."
    ::= { urlMaintStats 15 }

urlMaintStatTotalNonZeroSEQAlloc OBJECT-TYPE
    SYNTAX  Counter32
    MAX-ACCESS  read-only
    STATUS  current
    DESCRIPTION
	"The total number of sequence buffer allocations with non zero length."
    ::= { urlMaintStats 16 }

urlMaintStatTotalSEQBufAllocs OBJECT-TYPE
    SYNTAX  Counter32
    MAX-ACCESS  read-only
    STATUS  current
    DESCRIPTION
	"The total number of sequence buffer allocations."
    ::= { urlMaintStats 17 }

urlMaintStatTotalSEQBufFrees OBJECT-TYPE
    SYNTAX  Counter32
    MAX-ACCESS  read-only
    STATUS  current
    DESCRIPTION
	"The total number of sequence buffer freed."
    ::= { urlMaintStats 18 }

urlMaintStatTotalDataBufAllocs OBJECT-TYPE
    SYNTAX  Counter32
    MAX-ACCESS  read-only
    STATUS  current
    DESCRIPTION
	"The total number of data buffers allocated to store client request."
    ::= { urlMaintStats 19 }

urlMaintStatTotalDataBufFrees OBJECT-TYPE
    SYNTAX  Counter32
    MAX-ACCESS  read-only
    STATUS  current
    DESCRIPTION
	"The total number of data buffers freed."
    ::= { urlMaintStats 20 }

urlMaintStatSeqBufAllocFails OBJECT-TYPE
    SYNTAX  Counter32
    MAX-ACCESS  read-only
    STATUS  current
    DESCRIPTION
	"The number of times sequence buffer allocation failed."
    ::= { urlMaintStats 21 }

urlMaintStatUBufAllocFails OBJECT-TYPE
    SYNTAX  Counter32
    MAX-ACCESS  read-only
    STATUS  current
    DESCRIPTION
	"The number of times URL data buffer allocation failed."
    ::= { urlMaintStats 22 }

urlMaintStatMaxSessPerBucket OBJECT-TYPE
    SYNTAX  Counter32
    MAX-ACCESS  read-only
    STATUS  current
    DESCRIPTION
	"The maximum number of items(sessions) allowed in the session table
         hash bucket chain."
    ::= { urlMaintStats 23 }

urlMaintStatMaxFramesPerSess OBJECT-TYPE
    SYNTAX  Counter32
    MAX-ACCESS  read-only
    STATUS  current
    DESCRIPTION
	"The maximum number of frames to be buffered per session."
    ::= { urlMaintStats 24 }

urlMaintStatMaxBytesBuffered OBJECT-TYPE
    SYNTAX  Counter32
    MAX-ACCESS  read-only
    STATUS  current
    DESCRIPTION
	"The maximum number of bytes buffered per session."
    ::= { urlMaintStats 25 }

urlMaintStatInvalidMethods OBJECT-TYPE
    SYNTAX  Counter32
    MAX-ACCESS  read-only
    STATUS  current
    DESCRIPTION
	"The total number of invalid method hits."
    ::= { urlMaintStats 26 }

urlMaintStatAgedSessions OBJECT-TYPE
    SYNTAX  Counter32
    MAX-ACCESS  read-only
    STATUS  current
    DESCRIPTION
	"The total number of aged delayed binding sessions."
    ::= { urlMaintStats 27 }

urlMaintStatLowestSPMemUnits OBJECT-TYPE
    SYNTAX  Gauge32
    MAX-ACCESS  read-only
    STATUS  current
    DESCRIPTION
	"The lowest available SP memory units."
    ::= { urlMaintStats 28 }

urlSpMaintStatsTable OBJECT-TYPE
    SYNTAX  SEQUENCE OF UrlSpMaintStatsTableEntry 
    MAX-ACCESS  not-accessible
    STATUS  current
    DESCRIPTION
        "The table of URL SP maintenance statistics."
    ::= { urlStats 4 }

urlSpMaintStatsTableEntry OBJECT-TYPE
    SYNTAX  UrlSpMaintStatsTableEntry
    MAX-ACCESS  not-accessible
    STATUS  current
    DESCRIPTION
        "A row in the URL SP maintenance statistics table."
    INDEX   { urlSpMaintStatsSpIndex }
    ::= { urlSpMaintStatsTable 1 }

UrlSpMaintStatsTableEntry ::= SEQUENCE {
    urlSpMaintStatsSpIndex          Integer32,
    urlSpMaintStatsCurMemUnits      Gauge32,
    urlSpMaintStatsLowestMemUnits   Gauge32
    }

urlSpMaintStatsSpIndex OBJECT-TYPE
    SYNTAX  Integer32
    MAX-ACCESS  read-only
    STATUS  current
    DESCRIPTION
        "The SP index."
    ::= { urlSpMaintStatsTableEntry 1 }

urlSpMaintStatsCurMemUnits OBJECT-TYPE
    SYNTAX  Gauge32
    MAX-ACCESS  read-only
    STATUS  current
    DESCRIPTION
	"The number of memory units available."
    ::= { urlSpMaintStatsTableEntry 2 }

urlSpMaintStatsLowestMemUnits OBJECT-TYPE
    SYNTAX  Gauge32
    MAX-ACCESS  read-only
    STATUS  current
    DESCRIPTION
	"The lowest number of memory units available."
    ::= { urlSpMaintStatsTableEntry 3 }

currOpenedServerConns OBJECT-TYPE
    SYNTAX  Counter32
    MAX-ACCESS  read-only
    STATUS  current
    DESCRIPTION
        "Specifies number of current opened server connections."
    ::= { connPoolingStats 1 }

activeServerConns OBJECT-TYPE
    SYNTAX  Gauge32
    MAX-ACCESS  read-only
    STATUS  current
    DESCRIPTION
        "Specifies number of active server connections."
    ::= { connPoolingStats 2 }

availServerConns OBJECT-TYPE
    SYNTAX Gauge32
    MAX-ACCESS  read-only
    STATUS  current
    DESCRIPTION
        "Specifies number of available server connections."
    ::= { connPoolingStats 3 }

agedOutClientConns OBJECT-TYPE
    SYNTAX  Counter32
    MAX-ACCESS  read-only
    STATUS  current
    DESCRIPTION
        "Specifies number of aged out client connection."
    ::= { connPoolingStats 4 }

agedOutServerConns OBJECT-TYPE
    SYNTAX  Counter32
    MAX-ACCESS  read-only
    STATUS  current
    DESCRIPTION
        "Specifies number of aged out server connection."
    ::= { connPoolingStats 5 }

slbStatEnhContRuleTable OBJECT-TYPE
    SYNTAX  SEQUENCE OF SlbStatEnhContRuleEntry
    MAX-ACCESS  not-accessible
    STATUS  current
    DESCRIPTION
        "The statistics table of instances that the content rule matched."
    ::= { layer7Stats 3 }

slbStatEnhContRuleEntry OBJECT-TYPE
    SYNTAX  SlbStatEnhContRuleEntry
    MAX-ACCESS  not-accessible
    STATUS  current
    DESCRIPTION
        "The content rule entry."
    INDEX   { slbStatEnhContVirtServIndex, slbStatEnhContVirtServiceIndex, slbStatEnhContRuleIndex }
    ::= { slbStatEnhContRuleTable 1 }

SlbStatEnhContRuleEntry ::= SEQUENCE {
    slbStatEnhContVirtServIndex         DisplayString,
    slbStatEnhContVirtServiceIndex      Integer32,
    slbStatEnhContRuleIndex            Integer32,
    slbStatEnhContRuleName            DisplayString,
    slbStatEnhContRuleContClass        DisplayString,
    slbStatEnhContRuleAction        INTEGER,
    slbStatEnhContRuleCurrSess        Integer32,
    slbStatEnhContRuleTotSess        Integer32,
    slbStatEnhContRuleHighSess        Integer32,
    slbStatEnhContRuleTotOcts        Integer32,
    slbStatEnhContRuleClientRtt      DisplayString,
    slbStatEnhContRuleServerRtt      DisplayString
    }

slbStatEnhContVirtServIndex OBJECT-TYPE
    SYNTAX DisplayString (SIZE(1..255))
    MAX-ACCESS read-only
    STATUS current
    DESCRIPTION
      "The virtual server id."
    ::= { slbStatEnhContRuleEntry 1 }

slbStatEnhContVirtServiceIndex OBJECT-TYPE
    SYNTAX Integer32
    MAX-ACCESS read-only
    STATUS current
    DESCRIPTION
        "Virtual service index."
    ::= { slbStatEnhContRuleEntry 2 }

slbStatEnhContRuleIndex OBJECT-TYPE
    SYNTAX Integer32
    MAX-ACCESS read-only
    STATUS current
    DESCRIPTION
        "The content rule index."
    ::= { slbStatEnhContRuleEntry 3 }

slbStatEnhContRuleName OBJECT-TYPE
    SYNTAX DisplayString
    MAX-ACCESS read-only
    STATUS current
    DESCRIPTION
        "The content rule name."
    ::= { slbStatEnhContRuleEntry 4 }

slbStatEnhContRuleContClass OBJECT-TYPE
    SYNTAX DisplayString
    MAX-ACCESS read-only
    STATUS current
    DESCRIPTION
        "The content rule content class."
    ::= { slbStatEnhContRuleEntry 5 }

slbStatEnhContRuleAction OBJECT-TYPE
    SYNTAX  INTEGER {
      group(1),
      appredir(2),
      discard(3),
      goto(4)
    }
    MAX-ACCESS read-only
    STATUS current
    DESCRIPTION
        "The content rule action."
    ::= { slbStatEnhContRuleEntry 6 }

slbStatEnhContRuleCurrSess OBJECT-TYPE
    SYNTAX Integer32
    MAX-ACCESS read-only
    STATUS current
    DESCRIPTION
       "The content rule current sessions."
    ::= { slbStatEnhContRuleEntry 7 }

slbStatEnhContRuleTotSess OBJECT-TYPE
    SYNTAX Integer32
    MAX-ACCESS read-only
    STATUS current
    DESCRIPTION
        "The content rule total sessions."
    ::= { slbStatEnhContRuleEntry 8 }

slbStatEnhContRuleHighSess OBJECT-TYPE
    SYNTAX Integer32
    MAX-ACCESS read-only
    STATUS current
    DESCRIPTION
        "The content rule highest sessions."
    ::= { slbStatEnhContRuleEntry 9 }

slbStatEnhContRuleTotOcts OBJECT-TYPE
    SYNTAX Integer32
    MAX-ACCESS read-only
    STATUS current
    DESCRIPTION
        "The content rule total octets."
    ::= { slbStatEnhContRuleEntry 10 }

slbStatEnhContRuleClientRtt OBJECT-TYPE
    SYNTAX  DisplayString (SIZE(1..255))
    MAX-ACCESS read-only
    STATUS current
    DESCRIPTION
        "The average ClientRTT in ms during the past collection interval."
    ::= { slbStatEnhContRuleEntry 11 }

slbStatEnhContRuleServerRtt OBJECT-TYPE
    SYNTAX  DisplayString (SIZE(1..255))
    MAX-ACCESS read-only
    STATUS current
    DESCRIPTION
        "The average ServerRTT in ms during the past collection interval."
    ::= { slbStatEnhContRuleEntry 12 }

slbStatEnhContRuleActionGroupTable OBJECT-TYPE
    SYNTAX  SEQUENCE OF SlbStatEnhContRuleActionPerRealEntry
    MAX-ACCESS  not-accessible
    STATUS  current
    DESCRIPTION
        "The statistics table of instances that the content rule matched."
    ::= { layer7Stats 4 }

slbStatEnhContRuleActionGroupEntry OBJECT-TYPE
    SYNTAX  SlbStatEnhContRuleActionPerRealEntry
    MAX-ACCESS  not-accessible
    STATUS  current
    DESCRIPTION
        "The content rule entry."
    INDEX   { slbStatEnhContActionVirtServIndex, slbStatEnhContActionVirtServiceIndex, slbStatEnhContRuleActionIndex, slbEnhContActionRealServerIndex}
    ::= { slbStatEnhContRuleActionGroupTable 1 }

SlbStatEnhContRuleActionPerRealEntry ::= SEQUENCE {
    slbStatEnhContActionVirtServIndex         	DisplayString,
    slbStatEnhContActionVirtServiceIndex      	Integer32,
    slbStatEnhContRuleActionIndex            	Integer32,
    slbEnhContActionRealServerIndex          	DisplayString,
    slbStatEnhContRuleActionGroupCurrSess       Integer32,
    slbStatEnhContRuleActionGroupTotSess        Integer32,
    slbStatEnhContRuleActionGroupHighSess       Integer32,
    slbStatEnhContRuleActionGroupTotOcts        Counter64,
    slbStatEnhContRuleActionGroupClientRtt      DisplayString,
    slbStatEnhContRuleActionGroupServerRtt      DisplayString,
    slbStatEnhContRuleActionGroupRealStatus     INTEGER,
    slbStatEnhContRuleActionGroupHcReason       DisplayString
    }

slbStatEnhContActionVirtServIndex OBJECT-TYPE
    SYNTAX DisplayString (SIZE(1..255))
    MAX-ACCESS read-only
    STATUS current
    DESCRIPTION
      "The virtual server id."
    ::= { slbStatEnhContRuleActionGroupEntry 1 }
slbStatEnhContActionVirtServiceIndex OBJECT-TYPE
    SYNTAX Integer32
    MAX-ACCESS read-only
    STATUS current
    DESCRIPTION
        "Virtual service index."
    ::= { slbStatEnhContRuleActionGroupEntry 2 }
slbStatEnhContRuleActionIndex OBJECT-TYPE
    SYNTAX Integer32
    MAX-ACCESS read-only
    STATUS current
    DESCRIPTION
        "The content rule index."
    ::= { slbStatEnhContRuleActionGroupEntry 3 }
slbEnhContActionRealServerIndex OBJECT-TYPE
    SYNTAX DisplayString (SIZE(1..255))
    MAX-ACCESS read-only
    STATUS current
    DESCRIPTION
      "The real server id."
    ::= { slbStatEnhContRuleActionGroupEntry 4 }

slbStatEnhContRuleActionGroupCurrSess OBJECT-TYPE
    SYNTAX Integer32
    MAX-ACCESS read-only
    STATUS current
    DESCRIPTION
       "The content rule current sessions per real server."
    ::= { slbStatEnhContRuleActionGroupEntry 5 }

slbStatEnhContRuleActionGroupTotSess OBJECT-TYPE
    SYNTAX Integer32
    MAX-ACCESS read-only
    STATUS current
    DESCRIPTION
        "The content rule total sessions per real server."
    ::= { slbStatEnhContRuleActionGroupEntry 6 }

slbStatEnhContRuleActionGroupHighSess OBJECT-TYPE
    SYNTAX Integer32
    MAX-ACCESS read-only
    STATUS current
    DESCRIPTION
        "The content rule highest sessions per real server."
    ::= { slbStatEnhContRuleActionGroupEntry 7 }

slbStatEnhContRuleActionGroupTotOcts OBJECT-TYPE
    SYNTAX Counter64
    MAX-ACCESS read-only
    STATUS current
    DESCRIPTION
        "The content rule total octets per real server."
    ::= { slbStatEnhContRuleActionGroupEntry 8 }

slbStatEnhContRuleActionGroupClientRtt OBJECT-TYPE
    SYNTAX  DisplayString (SIZE(1..255))
    MAX-ACCESS read-only
    STATUS current
    DESCRIPTION
        "The average ClientRTT in ms during the past collection interval."
    ::= { slbStatEnhContRuleActionGroupEntry 9 }

slbStatEnhContRuleActionGroupServerRtt OBJECT-TYPE
    SYNTAX  DisplayString (SIZE(1..255))
    MAX-ACCESS read-only
    STATUS current
    DESCRIPTION
        "The average ServerRTT in ms during the past collection interval."
    ::= { slbStatEnhContRuleActionGroupEntry 10 }

slbStatEnhContRuleActionGroupRealStatus OBJECT-TYPE
    SYNTAX  INTEGER {
        up(0),
        down(1),
        admindown(2),
        warning(3),
        shutdown(4),
	error(5) 
        }
    MAX-ACCESS  read-only
    STATUS  current
    DESCRIPTION
        "The real server status. (0)Up, (1)Down, (2)Admin-Down, 
				 (3)Warning, (4)Shutdown, (5)Error"
    ::= { slbStatEnhContRuleActionGroupEntry 11 }

slbStatEnhContRuleActionGroupHcReason OBJECT-TYPE
    SYNTAX  DisplayString (SIZE(1..128))
    MAX-ACCESS  read-only
    STATUS  current
    DESCRIPTION
        "Service health check failure reason."
    ::= { slbStatEnhContRuleActionGroupEntry 12 }


slbStatEnhServiceActionNonGroupTable OBJECT-TYPE
    SYNTAX  SEQUENCE OF SlbStatEnhServiceActionNonGroupEntry
    MAX-ACCESS  not-accessible
    STATUS  current
    DESCRIPTION
        "The statistics table of instances for service action non group."
    ::= { layer7Stats 5 }

slbStatEnhServiceActionNonGroupEntry OBJECT-TYPE
    SYNTAX  SlbStatEnhServiceActionNonGroupEntry
    MAX-ACCESS  not-accessible
    STATUS  current
    DESCRIPTION
        "The service action non group entry."
    INDEX   { slbStatEnhServiceActionNonGroupVirtServIndex, slbStatEnhServiceActionNonGroupVirtServiceIndex }
    ::= { slbStatEnhServiceActionNonGroupTable 1 }

SlbStatEnhServiceActionNonGroupEntry ::= SEQUENCE {
    slbStatEnhServiceActionNonGroupVirtServIndex         DisplayString,
    slbStatEnhServiceActionNonGroupVirtServiceIndex      Integer32,
    slbStatEnhServiceActionNonGroupCurrSess        Integer32,
    slbStatEnhServiceActionNonGroupTotSess        Integer32,
    slbStatEnhServiceActionNonGroupHighSess        Integer32,
    slbStatEnhServiceActionNonGroupTotOcts        Integer32
    }

slbStatEnhServiceActionNonGroupVirtServIndex OBJECT-TYPE
    SYNTAX DisplayString (SIZE(1..255))
    MAX-ACCESS read-only
    STATUS current
    DESCRIPTION
      "The virtual server id."
    ::= { slbStatEnhServiceActionNonGroupEntry 1 }

slbStatEnhServiceActionNonGroupVirtServiceIndex OBJECT-TYPE
    SYNTAX Integer32
    MAX-ACCESS read-only
    STATUS current
    DESCRIPTION
        "Virtual service index."
    ::= { slbStatEnhServiceActionNonGroupEntry 2 }

slbStatEnhServiceActionNonGroupCurrSess OBJECT-TYPE
    SYNTAX Integer32
    MAX-ACCESS read-only
    STATUS current
    DESCRIPTION
       "The service non group current sessions."
    ::= { slbStatEnhServiceActionNonGroupEntry 3 }

slbStatEnhServiceActionNonGroupTotSess OBJECT-TYPE
    SYNTAX Integer32
    MAX-ACCESS read-only
    STATUS current
    DESCRIPTION
        "The service non group total sessions."
    ::= { slbStatEnhServiceActionNonGroupEntry 4 }

slbStatEnhServiceActionNonGroupHighSess OBJECT-TYPE
    SYNTAX Integer32
    MAX-ACCESS read-only
    STATUS current
    DESCRIPTION
        "The service non group highest sessions."
    ::= { slbStatEnhServiceActionNonGroupEntry 5 }

slbStatEnhServiceActionNonGroupTotOcts OBJECT-TYPE
    SYNTAX Integer32
    MAX-ACCESS read-only
    STATUS current
    DESCRIPTION
        "The service non group total octets."
    ::= { slbStatEnhServiceActionNonGroupEntry 6 }

slbStatURLFilteringGroupTable OBJECT-TYPE
    SYNTAX  SEQUENCE OF SlbStatURLFilteringPreRealEntry
    MAX-ACCESS  not-accessible
    STATUS  current
    DESCRIPTION
        "The statistics table of URL Filtering."
    ::= { layer7Stats 6 }

slbStatURLFilteringGroupEntry OBJECT-TYPE
    SYNTAX  SlbStatURLFilteringPreRealEntry
    MAX-ACCESS  not-accessible
    STATUS  current
    DESCRIPTION
        "The statistics entry of URL Filtering."
    INDEX   { slbStatURLFilteringSubCategoryIndex }
    ::= { slbStatURLFilteringGroupTable 1 }

SlbStatURLFilteringPreRealEntry ::= SEQUENCE {
    slbStatURLFilteringSubCategoryIndex        Integer32,
    slbStatURLFilteringSubCategoryName         DisplayString,
    slbStatURLFilteringCategoryName            DisplayString,
    slbStatURLFilteringSubCategoryCount        Integer32
    }

slbStatURLFilteringSubCategoryIndex OBJECT-TYPE
    SYNTAX Integer32
    MAX-ACCESS read-only
    STATUS current
    DESCRIPTION
        "URL Filtering Sub Category count statistics."
    ::= { slbStatURLFilteringGroupEntry 1 }

slbStatURLFilteringSubCategoryName OBJECT-TYPE
    SYNTAX DisplayString (SIZE(1..64))
    MAX-ACCESS read-only
    STATUS current
    DESCRIPTION
        "URL Filtering Sub Category statistics."
    ::= { slbStatURLFilteringGroupEntry 2 }

slbStatURLFilteringCategoryName OBJECT-TYPE
    SYNTAX DisplayString (SIZE(1..32))
    MAX-ACCESS read-only
    STATUS current
    DESCRIPTION
        "URL Filtering Category statistics."
    ::= { slbStatURLFilteringGroupEntry 3 }

slbStatURLFilteringSubCategoryCount OBJECT-TYPE
    SYNTAX Integer32
    MAX-ACCESS read-only
    STATUS current
    DESCRIPTION
        "URL Filtering Sub Category count statistics."
    ::= { slbStatURLFilteringGroupEntry 4 }

slbStatOCSPServerTable OBJECT-TYPE
    SYNTAX  SEQUENCE OF SlbStatOCSPServerEntry
    MAX-ACCESS  not-accessible
    STATUS  current
    DESCRIPTION
        "The statistics table of OCSP servers."
    ::= { layer7Stats 7 }

slbStatOCSPServerEntry OBJECT-TYPE
    SYNTAX  SlbStatOCSPServerEntry
    MAX-ACCESS  not-accessible
    STATUS  current
    DESCRIPTION
        "The statistics entry of OCSP Servers."
    INDEX   { slbStatOCSPServerIndex }
    ::= { slbStatOCSPServerTable 1 }

SlbStatOCSPServerEntry ::= SEQUENCE {
      slbStatOCSPServerIndex            Integer32,
      slbStatOCSPServerAddress      	DisplayString,
      slbStatOCSPServerSentReq     	Counter64,
      slbStatOCSPServerFailedRetries    Counter64,
      slbStatOCSPServerFailedReq	Counter64,
      slbStatOCSPServerBadResponse      Counter64,
      slbStatOCSPServerRevokedResponse  Counter64,
      slbStatOCSPServerUnknownResponse  Counter64,
      slbStatOCSPServerInvalidAlgorithm Counter64,
      slbStatOCSPServerInvalidTime      Counter64,
      slbStatOCSPServerInvalidNonce     Counter64,
      slbStatOCSPServerIrrelevantResponse  Counter64,
      slbStatOCSPServerInvalidSignature  Counter64,
      slbStatOCSPServerSuccess      	Counter64,
      slbStatOCSPServerGeneralFailure   Counter64,
      slbStatOCSPServerRequestMethod    Integer32
    }
slbStatOCSPServerIndex OBJECT-TYPE
    SYNTAX Integer32
    MAX-ACCESS read-only
    STATUS current
    DESCRIPTION
        "OCSP Servers Address."
    ::= { slbStatOCSPServerEntry 1 }

slbStatOCSPServerAddress      		      OBJECT-TYPE
    SYNTAX DisplayString
    MAX-ACCESS read-only
    STATUS current
    DESCRIPTION
        "OCSP Servers statistic."
    ::= { slbStatOCSPServerEntry 2 }


slbStatOCSPServerSentReq     		         OBJECT-TYPE
    SYNTAX Counter64
    MAX-ACCESS read-only
    STATUS current
    DESCRIPTION
        "OCSP Servers statistic total sent req."
    ::= { slbStatOCSPServerEntry 3 }

slbStatOCSPServerFailedRetries           OBJECT-TYPE
    SYNTAX Counter64
    MAX-ACCESS read-only
    STATUS current
    DESCRIPTION
        "OCSP Servers statistic total failed retiries."
    ::= { slbStatOCSPServerEntry 4 }

slbStatOCSPServerFailedReq	             OBJECT-TYPE
    SYNTAX Counter64
    MAX-ACCESS read-only
    STATUS current
    DESCRIPTION
        "OCSP Servers statistic total failed requests."
    ::= { slbStatOCSPServerEntry 5 }

slbStatOCSPServerBadResponse        	 OBJECT-TYPE
    SYNTAX Counter64
    MAX-ACCESS read-only
    STATUS current
    DESCRIPTION
        "OCSP Servers statistic total bad response."
    ::= { slbStatOCSPServerEntry 6 }

slbStatOCSPServerRevokedResponse   OBJECT-TYPE
    SYNTAX Counter64
    MAX-ACCESS read-only
    STATUS current
    DESCRIPTION
        "OCSP Servers statistic total revoked responses."
    ::= { slbStatOCSPServerEntry 7 }

slbStatOCSPServerUnknownResponse  OBJECT-TYPE
    SYNTAX Counter64
    MAX-ACCESS read-only
    STATUS current
    DESCRIPTION
        "OCSP Servers statistic total unknown responses."
    ::= { slbStatOCSPServerEntry 8 }

slbStatOCSPServerInvalidAlgorithm      OBJECT-TYPE
    SYNTAX Counter64
    MAX-ACCESS read-only
    STATUS current
    DESCRIPTION
        "OCSP Servers statistic total invalid algorithm failed."
    ::= { slbStatOCSPServerEntry 9 }

slbStatOCSPServerInvalidTime      	    OBJECT-TYPE
    SYNTAX Counter64
    MAX-ACCESS read-only
    STATUS current
    DESCRIPTION
        "OCSP Servers statistic total invalid time failed."
    ::= { slbStatOCSPServerEntry 10 }

slbStatOCSPServerInvalidNonce      	   OBJECT-TYPE
    SYNTAX Counter64
    MAX-ACCESS read-only
    STATUS current
    DESCRIPTION
        "OCSP Servers statistic total invalid nonce failed."
    ::= { slbStatOCSPServerEntry 11 }

slbStatOCSPServerIrrelevantResponse  OBJECT-TYPE
    SYNTAX Counter64
    MAX-ACCESS read-only
    STATUS current
    DESCRIPTION
        "OCSP Servers statistic total irrelevant responses."
    ::= { slbStatOCSPServerEntry 12 }

slbStatOCSPServerInvalidSignature       OBJECT-TYPE
    SYNTAX Counter64
    MAX-ACCESS read-only
    STATUS current
    DESCRIPTION
        "OCSP Servers statistic total invalid signutre responses."
    ::= { slbStatOCSPServerEntry 13 }

slbStatOCSPServerSuccess      			   OBJECT-TYPE
    SYNTAX Counter64
    MAX-ACCESS read-only
    STATUS current
    DESCRIPTION
        "OCSP Servers statistic total success."
    ::= { slbStatOCSPServerEntry 14 }

slbStatOCSPServerGeneralFailure      	   OBJECT-TYPE
    SYNTAX Counter64
    MAX-ACCESS read-only
    STATUS current
    DESCRIPTION
        "OCSP Servers statistic total general failure responses."
    ::= { slbStatOCSPServerEntry 15 }

slbStatOCSPServerRequestMethod      	 OBJECT-TYPE
    SYNTAX Integer32
    MAX-ACCESS read-only
    STATUS current
    DESCRIPTION
        "OCSP Servers statistic 1- POST 2 - GET."
    ::= { slbStatOCSPServerEntry 16 }

ocspGeneralStats       OBJECT IDENTIFIER ::= { layer7Stats 8 }

ocspStatsNumOfOcsp OBJECT-TYPE
    SYNTAX  Counter64
    MAX-ACCESS  read-only
    STATUS  current
    DESCRIPTION
        "No of ocsp validations ."
    ::= { ocspGeneralStats 1 }

ocspStatsSentReq OBJECT-TYPE
    SYNTAX  Counter64
    MAX-ACCESS  read-only
    STATUS  current
    DESCRIPTION
        "No of ocsp requests sent ."
    ::= { ocspGeneralStats 2 }

ocspStatsFailedRetries OBJECT-TYPE
    SYNTAX  Counter64
    MAX-ACCESS  read-only
    STATUS  current
    DESCRIPTION
        "No of ocsp retries failed ."
    ::= { ocspGeneralStats 3 }

ocspStatsFailedReq OBJECT-TYPE
    SYNTAX  Counter64
    MAX-ACCESS  read-only
    STATUS  current
    DESCRIPTION
        "No of ocsp requests failed ."
    ::= { ocspGeneralStats 4 }

ocspStatsFailedOcsp OBJECT-TYPE
    SYNTAX  Counter64
    MAX-ACCESS  read-only
    STATUS  current
    DESCRIPTION
        "No of ocsp requests failed - any reason ."
    ::= { ocspGeneralStats 5 }

ocspStatsFromCache OBJECT-TYPE
    SYNTAX  Counter64
    MAX-ACCESS  read-only
    STATUS  current
    DESCRIPTION
        "No of ocsp responses from cache."
    ::= { ocspGeneralStats 6 }

ocspStatsFromStaple OBJECT-TYPE
    SYNTAX  Counter64
    MAX-ACCESS  read-only
    STATUS  current
    DESCRIPTION
        "No of ocsp staple responses we got ."
    ::= { ocspGeneralStats 7 }

ocspStatsNotStapled OBJECT-TYPE
    SYNTAX  Counter64
    MAX-ACCESS  read-only
    STATUS  current
    DESCRIPTION
        "how many we asked stapling but didnt get response ."
    ::= { ocspGeneralStats 8 }

ocspStatsBadResponse OBJECT-TYPE
    SYNTAX  Counter64
    MAX-ACCESS  read-only
    STATUS  current
    DESCRIPTION
        "No of ocsp bad responses we got ."
    ::= { ocspGeneralStats 9 }

ocspStatsRevokedResponse OBJECT-TYPE
    SYNTAX  Counter64
    MAX-ACCESS  read-only
    STATUS  current
    DESCRIPTION
        "No of ocsp revoked responses we got ."
    ::= { ocspGeneralStats 10 }

ocspStatsUnknownResponse OBJECT-TYPE
    SYNTAX  Counter64
    MAX-ACCESS  read-only
    STATUS  current
    DESCRIPTION
        "No of ocsp unknown responses we got ."
    ::= { ocspGeneralStats 11 }

ocspStatsInvalidAlgorithm OBJECT-TYPE
    SYNTAX  Counter64
    MAX-ACCESS  read-only
    STATUS  current
    DESCRIPTION
        "No of ocsp staple invalid algorithm responses we got ."
    ::= { ocspGeneralStats 12 }

ocspStatsInvalidTime OBJECT-TYPE
    SYNTAX  Counter64
    MAX-ACCESS  read-only
    STATUS  current
    DESCRIPTION
        "No of ocsp invalid time responses we got ."
    ::= { ocspGeneralStats 13 }

ocspStatsInvalidNonce OBJECT-TYPE
    SYNTAX  Counter64
    MAX-ACCESS  read-only
    STATUS  current
    DESCRIPTION
        "No of ocsp invalid nonce responses we got ."
    ::= { ocspGeneralStats 14 }

ocspStatsIrrelevantResponse OBJECT-TYPE
    SYNTAX  Counter64
    MAX-ACCESS  read-only
    STATUS  current
    DESCRIPTION
        "No of ocsp irrelevant responses we got ."
    ::= { ocspGeneralStats 15 }

ocspStatsInvalidSignature OBJECT-TYPE
    SYNTAX  Counter64
    MAX-ACCESS  read-only
    STATUS  current
    DESCRIPTION
        "No of ocsp invalid signutre responses we got ."
    ::= { ocspGeneralStats 16 }

ocspStatsSuccess OBJECT-TYPE
    SYNTAX  Counter64
    MAX-ACCESS  read-only
    STATUS  current
    DESCRIPTION
        "No of ocsp success responses we got ."
    ::= { ocspGeneralStats 17 }

ocspStatsGeneralFailure OBJECT-TYPE
    SYNTAX  Counter64
    MAX-ACCESS  read-only
    STATUS  current
    DESCRIPTION
        "No of ocsp general failer."
    ::= { ocspGeneralStats 18 }


slbParsingString OBJECT-TYPE
    SYNTAX  DisplayString (SIZE(0..78))
    MAX-ACCESS  read-write
    STATUS  current
    DESCRIPTION
        "The SLB Cookie to parse of length 8, 16, 24, 28 or 76 bytes and Cookie value should be in 0xXXXXXXXXXXXXXXXX format."
    ::= { slbParsing 1 }

slbParsingVip OBJECT-TYPE
    SYNTAX  DisplayString (SIZE(0..46))
    MAX-ACCESS  read-only
    STATUS  current
    DESCRIPTION
        "The Virtual IP address from parsed SLB Cookie."
    ::= { slbParsing 2 }

slbParsingRip OBJECT-TYPE
    SYNTAX  DisplayString (SIZE(0..46))
    MAX-ACCESS  read-only
    STATUS  current
    DESCRIPTION
        "The Real IP address from parsed SLB Cookie."
    ::= { slbParsing 3 }

slbParsingRport OBJECT-TYPE
    SYNTAX  INTEGER (1..65535)
    MAX-ACCESS  read-only
    STATUS  current
    DESCRIPTION
        "The Real Port Number from parsed SLB Cookie."
    ::= { slbParsing 4 }

slbParsingCip OBJECT-TYPE
    SYNTAX  DisplayString (SIZE(0..46))
    MAX-ACCESS  read-only
    STATUS  current
    DESCRIPTION
        "The Client IP address from parsed SLB Cookie."
    ::= { slbParsing 5 }

END

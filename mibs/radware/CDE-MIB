CDE-MIB DEFINITIONS ::= BEGIN

-- Title:      RADWARE
--             This Private MIB supports the configuration auto sync.
-- Version:    3.0
-- Date:       24 May 2016
-- By:         RMA (Radware MIB Authority)
-- E-mail:     US:            support@radware.com
--             International: support_int@radware.com
--
IMPORTS
       IpAddress
              FROM RFC1155-SMI
       Unsigned32
              FROM SNMPv2-SMI
       OBJECT-TYPE
              FROM RFC-1212
       PhysAddress
              FROM RFC1213-MIB
       TRAP-TYPE
              FROM RFC-1215
       TruthValue,
       rdwrConfigurationSync
              FROM RADWARE-MIB;
--
-- rdwrConfigurationSync OBJECT IDENTIFIER ::= {rsServerDispatcher 161 }

rdwrConfigurationSyncMonitor OBJECT IDENTIFIER ::= {rdwrConfigurationSync 1 }

rdwrConfSyncState OBJECT-TYPE
    SYNTAX	INTEGER
    {	
        syncOff(1),
        disconnected(2),
        synchronizing(3),
        inSync(4),
        incompatible(5),
        cannotSync(6),
        pendingVRRPSwitch(7),
        noMaster(8),
        masterConnected(9),
        outOfSync(10)
    }
    ACCESS	read-only
    STATUS	mandatory
    DESCRIPTION
	"The current state of the configuration synchronisation mechanism."
    ::= { rdwrConfigurationSyncMonitor 1 }

rdwrConfSyncIP OBJECT-TYPE
    SYNTAX	IpAddress
    ACCESS	read-only
    STATUS	mandatory
    DESCRIPTION
	"The current IP interface used for the communication with the
	 configuration peer."
    ::= { rdwrConfigurationSyncMonitor 2 }

rdwrConfSyncPeerIP OBJECT-TYPE
    SYNTAX	IpAddress
    ACCESS	read-only
    STATUS	mandatory
    DESCRIPTION
	"The current IP of the configuration peer."
    ::= { rdwrConfigurationSyncMonitor 3 }

rdwrConfSyncPeerBaseMac OBJECT-TYPE
    SYNTAX	PhysAddress
    ACCESS	read-write
    STATUS	mandatory
    DESCRIPTION
	"The base MAC of the configuration peer device that is currently logged
	 in or has last logged in."
     ::= { rdwrConfigurationSyncMonitor 4 }

rdwrConfSyncIncompatibilityReason OBJECT-TYPE
    SYNTAX	INTEGER
    {
        compatible(1),
        incompatibleHardware(2),
        incompatibleInstalledMemorySize(3),
        incompatibleLicense(4),
        incompatibleSoftwareVersion(5),
        incompatibleSlaveConfiguration(6),
        unknown(7),
        incompatibleAttackDb(8)
    }
    ACCESS	read-only
    STATUS	mandatory
    DESCRIPTION
	"The grounds for the incompatibilty between the primary device and the secondary device"
    ::= { rdwrConfigurationSyncMonitor 5 }

rdwrConfSyncLastConfSyncTime OBJECT-TYPE
    SYNTAX	Unsigned32
    ACCESS	read-only
    STATUS	mandatory
    DESCRIPTION
	"The last time the configuration was successfully propagated from the
	 master to the slave. The time is in seconds since epoch."
     ::= { rdwrConfigurationSyncMonitor 6 }

rdwrConfSyncLastConfFullSyncTime OBJECT-TYPE
    SYNTAX	Unsigned32
    ACCESS	read-only
    STATUS	mandatory
    DESCRIPTION
	"The last time a full configuration synchronisation was last
	 performed. The time is in seconds since epoch."
     ::= { rdwrConfigurationSyncMonitor 7 }

rdwrConfSyncNumOfFullSyncOperations OBJECT-TYPE
    SYNTAX	INTEGER
    ACCESS	read-only
    STATUS	mandatory
    DESCRIPTION
	"The number of full synchronisations successfully performed since the
	 automatic configuration synchronisation was last enabled, or since the
	 last reboot."
    ::= { rdwrConfigurationSyncMonitor 8 }

rdwrConfSyncNumOfSyncOperations OBJECT-TYPE
    SYNTAX	INTEGER
    ACCESS	read-only
    STATUS	mandatory
    DESCRIPTION
	"The number of synchronisations operations performed since the last
	 configuration full synchronisation, or since the last reboot."
    ::= { rdwrConfigurationSyncMonitor 9 }

rdwrConfSyncNumOfFailedSyncAttempts OBJECT-TYPE
    SYNTAX	INTEGER
    ACCESS	read-only
    STATUS	mandatory
    DESCRIPTION
	"The number of synchronisation operations (incremental or full) that
	 failed since the synchronisation was last enabled, or since the last
	 reboot."
    ::= { rdwrConfigurationSyncMonitor 10 }

rdwrConfSyncPeerConfigVersion OBJECT-TYPE
    SYNTAX	INTEGER
    ACCESS	read-only
    STATUS	mandatory
    DESCRIPTION
	"The configuration version the slave."
    ::= { rdwrConfigurationSyncMonitor 11 }

rdwrConfSyncConfigTimestamp OBJECT-TYPE
    SYNTAX	Unsigned32
    ACCESS	read-only
    STATUS	mandatory
    DESCRIPTION
	"Timestamp of the last configuration change in the machine."
    ::= { rdwrConfigurationSyncMonitor 12 }

rdwrConfSyncResetStatistics OBJECT-TYPE
    SYNTAX	INTEGER
    {
        reset(1)
    }
    ACCESS	read-write
    STATUS	mandatory
    DESCRIPTION
	"Reset the configuration synchronisation statistics."
    ::= { rdwrConfigurationSyncMonitor 13 }

rdwrConfSyncShouldReboot OBJECT-TYPE
    SYNTAX	TruthValue
    ACCESS	read-only
    STATUS	mandatory
    DESCRIPTION
	"Whether master/slave are waiting for reboot."
    ::= { rdwrConfigurationSyncMonitor 14 }

rdwrConfSyncNumOfConnects OBJECT-TYPE
    SYNTAX	INTEGER
    ACCESS	read-only
    STATUS	mandatory
    DESCRIPTION
	"Number of successful connections since last mode change or primary device reboot."
    ::= { rdwrConfigurationSyncMonitor 15 }

rdwrConfSyncNumOfDisconnects OBJECT-TYPE
    SYNTAX	INTEGER
    ACCESS	read-only
    STATUS	mandatory
    DESCRIPTION
	"Number of times the master disconnected from the peer since last mode
	change or reboot."
    ::= { rdwrConfigurationSyncMonitor 16 }

rdwrConfSyncIPString OBJECT-TYPE
    SYNTAX	OCTET STRING
    ACCESS	read-only
    STATUS	mandatory
    DESCRIPTION
	"The current IP interface used for the communication with the
	 configuration peer. Similar to rdwrConfSyncIP but in string format to enable IPv6 support"
    ::= { rdwrConfigurationSyncMonitor 18 }

rdwrConfSyncPeerIPString OBJECT-TYPE
    SYNTAX	OCTET STRING
    ACCESS	read-only
    STATUS	mandatory
    DESCRIPTION
	"The current IP of the configuration peer. Similar to rdwrConfSyncPeerIP but in string format to enable IPv6 support."
    ::= { rdwrConfigurationSyncMonitor 19 }

rdwrConfigurationSyncConf OBJECT IDENTIFIER ::= { rdwrConfigurationSync 2 }

rdwrConfSyncMode OBJECT-TYPE
    SYNTAX	INTEGER
    {
        master(1),
        slave(2),
        disabled(3)
    }
    ACCESS	read-write
    STATUS	mandatory
    DESCRIPTION
	"The role of the device inthe configuration synchronisation and whether
	 the feature is enabled."
    ::= { rdwrConfigurationSyncConf 1 }

rdwrConfSyncRetryTimeout OBJECT-TYPE
    SYNTAX	INTEGER (1..600)
    ACCESS	read-write
    STATUS	mandatory
    DESCRIPTION
	"Time in seconds between attempts to connect to configuration
	 slave. Must be in the range of 1 second to 10 minutes. Default is 5
	 seconds."
    ::= { rdwrConfigurationSyncConf 2 }

rdwrConfSyncKeepAlivePeriod OBJECT-TYPE
    SYNTAX	INTEGER (5..600)
    ACCESS	read-write
    STATUS	mandatory
    DESCRIPTION
	"Time in seconds between keep-alive messages to slave. Must be in the
	 range of 5 seconds to 10 minutes. Default is 10 seconds."
    ::= { rdwrConfigurationSyncConf 3 }

rdwrConfSyncRebootTimeout OBJECT-TYPE
    SYNTAX	INTEGER (1..600)
    ACCESS	read-write
    STATUS	mandatory
    DESCRIPTION
	"Time in seconds allowed for slave to reboot. After this time slave is
	considered disconnected. Must be in the range of 1 second to 10 minutes. Default
	is 4 minutes (240 seconds). Value is assigned in seconds."
    ::= { rdwrConfigurationSyncConf 4 }

rdwrConfSyncPeerDiscTrapDelay OBJECT-TYPE
    SYNTAX	INTEGER (0..3600)
    ACCESS	read-write
    STATUS	mandatory
    DESCRIPTION
	"Disconnected peer trap is only issued after this delay. If connection
	 is reestablished within this time period trap is deferred. Must be in
	 the range of 0 (immediate trap) to 1 hour. Default is 1 minute (60
	 seconds)."
    ::= { rdwrConfigurationSyncConf 5 }

rdwrConfSyncPeerResponseTimeout OBJECT-TYPE
    SYNTAX	INTEGER (1..600)
    ACCESS	read-write
    STATUS	mandatory
    DESCRIPTION
	"Time in seconds allowed for response to arrive from peer. If the
	timeout is exceeded, peer is considered disconnected. Must be in the range of 1 second to 10
	minutes. Default is 20 seconds. Value is assigned in seconds."
    ::= { rdwrConfigurationSyncConf 6 }

rdwrConfSyncMasterActivityTimeout OBJECT-TYPE
    SYNTAX	INTEGER (5..600)
    ACCESS	read-write
    STATUS	mandatory
    DESCRIPTION
	"Maximum time in seconds allowed by slave between master messages. If
	 the timeout is exceeded. Slave considers master as disconnected. This
	 value must be greater than keep alive frequency. Must be in the range
	 of 5 seconds to 10 minutes. Default is a minute (60 seconds)."
    ::= {rdwrConfigurationSyncConf 7 }

rdwrConfSyncAllowRebootActiveDevice OBJECT-TYPE
    SYNTAX	TruthValue
    ACCESS	read-write
    STATUS	mandatory
    DESCRIPTION
	"Allow master to reboot slave event if the slave is the VRRP active
	 device. Default value is false."
    ::= { rdwrConfigurationSyncConf 8 }

rdwrConfSyncRebootSlave OBJECT-TYPE
    SYNTAX	INTEGER
    {
        reboot(1)
    }
    ACCESS	read-write
    STATUS	mandatory
    DESCRIPTION
	"Manually reboot the secondary device."
    ::= { rdwrConfigurationSyncConf 9 }

rdwrConfSyncExcludeMgmtIP OBJECT-TYPE
    SYNTAX	TruthValue
    ACCESS	read-write
    STATUS	mandatory
    DESCRIPTION
	"Exclude the management ports IP interface from the
	synchronisations. When true the IPs have to be handled manually. Default
	value is false."
    ::= { rdwrConfigurationSyncConf 10 }

rdwrConfSyncExcludeMgmtCert OBJECT-TYPE
    SYNTAX	TruthValue
    ACCESS	read-write
    STATUS	mandatory
    DESCRIPTION
	"Exclude the WBM & SSH service configuration and the certificates
	 references from them from the synchronisations. When true, their
	 configuration has to be handled manually. Default value is false."
    ::= { rdwrConfigurationSyncConf 11 }

rdwrConfSyncDiscoverMngIPOnly OBJECT-TYPE
    SYNTAX	TruthValue
    ACCESS	read-write
    STATUS  obsolete
    DESCRIPTION
        " obsolete "
    ::= { rdwrConfigurationSyncConf 12 }

rdwrConfSyncFullSyncDelay OBJECT-TYPE
    SYNTAX	INTEGER (0..3600)
    ACCESS	read-write
    STATUS	mandatory
    DESCRIPTION
	"Time in seconds between the need to full sync is detected and the actual full sync operation.
         full sync will occure when this time is passed and the master wss idle (not configured).
	 range of 0 seconds to 1 hour. Default is 30 seconds."
    DEFVAL { 30 }
    ::= { rdwrConfigurationSyncConf 13 }

rdwrConfSyncFullSyncMaxDelay OBJECT-TYPE
    SYNTAX	INTEGER (0..3600)
    ACCESS	read-write
    STATUS	mandatory
    DESCRIPTION
	"Maximum time in seconds between the need to full sync is detected and the actual full sync operation.
         Full sync will occure if this time passed, even if the master has been configured.
	 range of 0 seconds to 1 hour. Default is 30 seconds."
    DEFVAL { 30 }
    ::= { rdwrConfigurationSyncConf 14 }

rdwrConfSyncCommunicationPassword OBJECT-TYPE
    SYNTAX	OCTET STRING
    ACCESS	read-write
    STATUS	mandatory
    DESCRIPTION
	"Sets the password for the synchronization session. This is mandatory before activating the module."
    ::= { rdwrConfigurationSyncConf 15 }

rdwrConfSyncConnectionPreference OBJECT-TYPE
    SYNTAX	OCTET STRING
    ACCESS	read-write
    STATUS	mandatory
    DESCRIPTION
	"Specifies the first choice of IP through which config-sync connects to peer. Can also be set to the values 'any' and 'any-mng-ip'."
    ::= { rdwrConfigurationSyncConf 16 }

rdwrConfSyncAlternateConnectionPreference OBJECT-TYPE
    SYNTAX	OCTET STRING
    ACCESS	read-write
    STATUS	mandatory
    DESCRIPTION
	"Specifies the second choice of IP through which config-sync connects to peer. Can also be set to the values 'any', 'any-mng-ip' and 'none'."
    ::= { rdwrConfigurationSyncConf 17 }

rdwrConfSyncReconnect OBJECT-TYPE
    SYNTAX	INTEGER
    {
        reconnect(1),
	doNothing(2)
    }
    ACCESS	read-write
    STATUS	mandatory
    DESCRIPTION
	"Manually reconnect the config-sync connection to the secondary device."
    ::= { rdwrConfigurationSyncConf 18 }

END

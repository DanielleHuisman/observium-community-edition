DEFENSEFLOW-MIB DEFINITIONS ::= BEGIN

-- Title:      RADWARE
-- Version:    0.1
-- Date:       01/01/2019
-- By:         RMA (Radware MIB Authority)
-- E-mail:     support@radware.com

IMPORTS
    enterprises
            FROM RFC1155-SMI
    OBJECT-TYPE
            FROM RFC-1212
    DisplayString
            FROM RFC-1213
    dskPercent
            FROM UCD-SNMP-MIB
    hrProcessorLoad
            FROM HOST-RESOURCES-MIB;

rnd                 OBJECT IDENTIFIER ::= { enterprises 89  }
rndApplications     OBJECT IDENTIFIER ::= { rnd 35 }
products            OBJECT IDENTIFIER ::= { rndApplications 10 }
defenseflow         OBJECT IDENTIFIER ::= { products 110 }

dfcHaStatus OBJECT-TYPE
    SYNTAX INTEGER {
        enabled(0),
        ha-one-node-down(1),
        disabled(2),
        error(100)
    }
    ACCESS read-only
    STATUS mandatory
    DESCRIPTION
        "The DefenseFlow High Availability status"
    ::= { defenseflow 1 }

dfcServiceStatus OBJECT-TYPE
    SYNTAX INTEGER {
        started(0),
        one-of-services-down(1),
        stopped(100)
    }
    ACCESS read-only
    STATUS mandatory
    DESCRIPTION
        "The DefenseFlow service status"
    ::= { defenseflow 2 }

dfcHaStatusTrap TRAP-TYPE
    ENTERPRISE  defenseflow
    VARIABLES   { dfcHaStatus }
    DESCRIPTION
    "The DefenseFlow High Availability status trap"
    ::= 1

dfcServiceStatusTrap TRAP-TYPE
    ENTERPRISE  defenseflow
    VARIABLES   { dfcServiceStatus }
    DESCRIPTION
    "The DefenseFlow service status trap"
    ::= 2

dfcDiskWarningTrap TRAP-TYPE
    ENTERPRISE  defenseflow
    VARIABLES   { dskPercent }
    DESCRIPTION
    "Disk capacity warning"
    ::= 3

dfcDiskErrorTrap TRAP-TYPE
    ENTERPRISE  defenseflow
    VARIABLES   { dskPercent }
    DESCRIPTION
    "Disk capacity error"
    ::= 4

dfcCpuWarningTrap TRAP-TYPE
    ENTERPRISE  defenseflow
    VARIABLES   { hrProcessorLoad }
    DESCRIPTION
    "CPU warning"
    ::= 5

dfcCpuErrorTrap TRAP-TYPE
    ENTERPRISE  defenseflow
    VARIABLES   { hrProcessorLoad }
    DESCRIPTION
    "CPU error"
    ::= 6


END

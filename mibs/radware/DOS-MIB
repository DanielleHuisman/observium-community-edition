DOS-MIB DEFINITIONS ::= BEGIN

-- Title:      RADWARE
--             This Private MIB supports the WSD/CSD/FP/LP
-- Version:    3.0
-- Date:       24 May 2016
-- By:         RMA (Radware MIB Authority)
-- E-mail:     US:            support@radware.com
--             International: support_int@radware.com
--
IMPORTS
       OBJECT-TYPE
                FROM RFC-1212
       TRAP-TYPE
                FROM RFC-1215
       rsDOS,
       rndErrorDesc,
       rndErrorSeverity
                FROM RADWARE-MIB;

-- Some MIB compilers require that the following 7 lines which define the path
-- to RND MIB are commented out:

-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }

rsDOSSamplingRatio OBJECT-TYPE
    SYNTAX INTEGER
    ACCESS  read-write
    STATUS  mandatory
    DESCRIPTION "Sampling ratio: one of how many packets is sampled."
	DEFVAL  {100}
    ::= {rsDOS 1}

rsDOSSamplerOverloadMode OBJECT-TYPE
    SYNTAX INTEGER {
        forward(1),
        discard(2)
    }
    ACCESS  read-write
    STATUS  mandatory
    DESCRIPTION "Overload mechanism mode: forward/discard excess traffic."
	DEFVAL  {forward}
    ::= {rsDOS 2}

-- Application-specific traps for DOS
-- Each enterprise-specific trap has two bound variables describing the exact nature of
-- the trap. rndErrorDesc provides a detailed description of the problem, including the
-- related interface number, board number or any other applicable variable.
-- rndErrorSeverity describes the severity of this problem.

-- Trap template
-- -------------
--    TRAP-TYPE
--       ENTERPRISE  rsServerDispatcher
--       VARIABLES   { rndErrorDesc, rndErrorSeverity }
--       DESCRIPTION
--             ""
--       ::=
-- -------------

-- obsolete
rsDOSOverloadTrap TRAP-TYPE
        ENTERPRISE rsDOS
        VARIABLES  { rndErrorDesc, rndErrorSeverity }
        DESCRIPTION
             "DOS overload indication."
		::=  1

END

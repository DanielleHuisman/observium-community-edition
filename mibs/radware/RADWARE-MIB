RADWARE-MIB DEFINITIONS ::= BEGIN

-- Title:      Radware common MIB
--             This Private MIB supports Radware products
-- Version:    11.0
-- Date:       9 May 2018
-- By:         RMA (Radware MIB Authority)
-- E-mail:     support@radware.com
--

IMPORTS
       NetworkAddress,
       IpAddress,
       Counter,
       Gauge,
       enterprises
              FROM RFC1155-SMI
      OBJECT-TYPE
              FROM RFC-1212
       DisplayString,
       PhysAddress,
       ipAddrEntry
              FROM RFC1213-MIB
       Ipv6Address                         
       		FROM IPV6-TC                     
       TRAP-TYPE
                    FROM RFC-1215
       TimeStamp
                FROM SNMPv2-TC
       ;


    TruthValue ::= INTEGER {
         true (1),
         false (2)
        }
    RowStatus ::= INTEGER {
        active(1),
        notInService(2),
        notReady(3),
        createAndGo(4),
        createAndWait(5),
        destroy(6)
        }

    FeatureStatus ::= INTEGER {
         enable(1),
         disable(2)
        }
    NetNumber ::=  OCTET STRING (SIZE(4))
    BitFlag ::= INTEGER
    VrId ::= INTEGER(1..255)

-- the RouteTag type represents the contents of the
-- Route Domain field in the packet header or route entry.
-- The use of the Route Domain is deprecated.

   RouteTag ::= OCTET STRING (SIZE (2))

-- Some MIB compilers require that the following 7 lines which define the path
-- to RND MIB are commented out:

-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }
 rnd            OBJECT IDENTIFIER ::= { enterprises 89  }

--   Objects in this MIB are arranged into groups:
--   rndMng        - Management/Action
--   rndDeviceParams- General parameters
--   rndBridge     - RND Bridge/Route parameters (Level 2)
--   rndInterface  - Interface table and RS232 interface parameters
--   rndSlot       - Structure of OpenGate (modular device)
--   rndIpRoute    - Routing Parameters (Level 3)
--   rndRouteSpf   - RND SPF Routing algorith
--   rndMaskTable  - RND Masking tables
--   rndBackup     - RND backup feature, Dial-up parameters.
--   rndFddi       - RND FDDI parameters
--   rndDECnet     - RND DECnet Router parameters
--   rndIPX        - Parameters for management of IPX router
--   rndTR         - Parameters for additional Token Ring support
--   rndTranslation- Parameters for translation between Ethernet, Token Ring
--                   and FDDI
--   rndPCDevices  - Parameters for management for RND PC-based devices
--   rndFACS       - Facility for Access Control and Security
--   rndSNAR       - SDLC/SNA Routing parameters
--   rndSRE        - Parameters for configuration of Source Routing and
--                   Source Routing Encapsulation algorithms
--   rndCOD        - Connect On Demande parameters.
--   rndSPS        - Parameters for configuration of SPS
--   rndBrgHub     _ Remot Bridge HUB paramenets
--   rndAdapter    - parameters for R_dapter, OG-Van
--   rndBootP      - BootP configurgaration.
--   rndOGLoadBalance - Load Balance configuration.
--   ipSpec        IP Specific for VGate, MRT and LRE
--   virtualLan    Virtual LAN definition
--   rsConf        Router Server Configuration
--   rsTunning     Tunning sub group
--   rndISDN       ISDN Parameters for  OG_RAN and Radptor,VAN ans WANgate.
--   rndPPP        PPP Parameters for IPX.
--   rndDial       Dial Parameters for V25 of OpenGate


-- At the end of the MIB there is a definition of all RND-specific traps.


-- rndMng group contains Management Variables for RND devices

rndMng   OBJECT IDENTIFIER ::= { rnd 1  }

rndSysId OBJECT-TYPE
    SYNTAX  INTEGER {
       reb(1),
       ceb(2),
       ceblb(3),
       xeb(4),
       xeb1(5),
       rebsx(6),
       rtb(7),
       ltb(8),
       lte(9),
       iprouter(10),
       ielb(11),
       leb(12),
       openGate12(13),
       openGate4(14),
       ran(15),
       itlb(16),
       gatelinx(17),
       openGate2(18),
       ogRanTR(19),
       stc(20),
       ftc(21),
       armon(22),
       fccs1004(23),    -- RADway
       fccs1012(24),    -- RADway
       rdapter(25),
       ogvan(26),
       wanGate(27),
       ogRubE(28),
       ogRubT(29),
       elX(30),
       vGate4(31),
       mrt(32),
       ogSrubET(33),
       vanXS(34),
       lre(35),
       vGate2(36),
       serverDispatcher4(37),
       serverDispatcher2(38),
       vGate2Fast(39),
       serverDispatcher2Fast(40),
       prt(41),
       mlm(42),
       prt11(43),
       quickOffice(44),
       apollo(45),
       radware(62)
     }
    ACCESS  read-only
    STATUS  mandatory
    DESCRIPTION
      "Identification of an RND device. The device type for each
      integer clarifies the sysObjectID in MIB - II."
    ::= { rndMng 1  }

rndAction OBJECT-TYPE
    SYNTAX  INTEGER {
       reset(1),
       sendNetworkTab(2),
       deleteNetworkTab(3),
       sendRoutingTab(4),    -- Level II
       deleteRoutingTab(5),
       sendLanTab(6),
       deleteLanTab(7),
       deleteArpTab(8),
       sendArpTab(9),
       deleteRouteTab(10),   -- Level III
       sendRouteTab(11),
       backupSPFRoutingTab(12),
       backupIPRoutingTab(13),
       backupNetworkTab(14),
       backupLanTab(15),
       backupArpTab(16),
       backupIPXRipTab(17),
       backupIPXSAPTab(18),
       resetCDB(19),
       eraseCDB(20),
       deleteZeroHopRoutingAllocTab(21),
       shutdown(22)
     }
    ACCESS  read-write
    STATUS  mandatory
    DESCRIPTION
      "This variable enables the operator to perform one of the
      specified actions on the tables maintained by the network device.
      Send actions require support of proprietery File exchange
      protocol."
   ::= { rndMng 2  }


rndFileName OBJECT-TYPE
    SYNTAX OCTET STRING -- SIZE 256
    ACCESS  read-write
    STATUS  mandatory
    DESCRIPTION
      "The name of the file used internally by RND for transferring
      tables maintained by network devices, using a prorietary File
      exchange protocol."
    ::=  { rndMng 3  }


removeViewTablePermissionReductionCheck OBJECT-TYPE
    SYNTAX      INTEGER {
			enabled(1),
			disabled(0) }
    ACCESS	read-write
    STATUS	mandatory
    DESCRIPTION
            "This is a True/False variable that determines whether the
	    user is able to change his own view permissions (originally it
	    wasn't allowed in order to prevent situations of permission reduction).
	    added for Fortis."
    ::= { rndMng 4 }

rsConfigurationAuditStatus  OBJECT-TYPE
    SYNTAX INTEGER {
                    enable(1),
                    disable(2)
                   }
    ACCESS  read-write
    STATUS  mandatory
    DESCRIPTION
        "Enable/Disable audit notifications."
--  DEFVAL { 2 }
    ::=  { rndMng 5 }

rsConfigurationAuditingType  OBJECT-TYPE
    SYNTAX INTEGER {
                    regular(1),
                    extended(2)
                   }
    ACCESS  read-write
    STATUS  mandatory
    DESCRIPTION
        "Sets audit notifications type."
--  DEFVAL { 2 }
    ::=  { rndMng 9 }	
	
-- rndDeviceParams group contains a number of general variables

rndDeviceParams       OBJECT IDENTIFIER ::= { rnd 2  }

rndBridgeType  OBJECT-TYPE
    SYNTAX  INTEGER {
       reb(1),
       ceb(2),
       ceblb(3),
       xeb(4),
       xeb1(5),
       rebsx(6),
       rtb(7),
       ltb(8),
       tre(9),
       rtre(10),      -- remote TRE
       xtb(11),
       ete(12),
       rete(13),      -- remote ETE
       ielb(30),
       leb(31),
       openGate12(32),
       openGate4(33),
       ran(34),
       itlb(35),
       gatelinx(36),
       openGate2(37),
       ogRanTR(38),
       rdapter(39),
       ogVan(40),
       wanGate(41),
       ogRubE(42),
       ogRubT(43),
       wanGateI(44),
       vGate4(45),
       lre(46),
       mrt(47),
       vGate2(48)
     }
    ACCESS  read-only
    STATUS  mandatory
    DESCRIPTION
      "Identification of the RND bridge type."
    ::= { rndDeviceParams 1  }


rndInactiveArpTimeOut OBJECT-TYPE
    SYNTAX INTEGER
    ACCESS  read-write
    STATUS  mandatory
    DESCRIPTION
      "This variable defines the maximum time period that can pass
       between ARP requests concerning an entry in the ARP table.
       After this time period, the entry is deleted from the table."
    ::= { rndDeviceParams 2  }

-- The following two variables define the format of RND specific
-- error messages issued by the RND devices

rndBridgeAlarm  OBJECT IDENTIFIER ::= { rndDeviceParams 3  }

rndErrorDesc OBJECT-TYPE
    SYNTAX DisplayString
    ACCESS  read-only
    STATUS  mandatory
    DESCRIPTION
       "A textual description of the enterprise-specific trap sent
        to the Network Management Station by the RND managed device."
    ::= { rndBridgeAlarm 1  }

rndErrorSeverity OBJECT-TYPE
    SYNTAX INTEGER
    ACCESS  read-only
    STATUS  mandatory
    DESCRIPTION
      "The severity type of the enterprise-specific trap sent to the
      Network Management Station by the RND managed device."
    ::= { rndBridgeAlarm 2  }

rndBrgVersion OBJECT-TYPE
    SYNTAX  DisplayString
    ACCESS  read-write
    STATUS  mandatory
    DESCRIPTION
      "The application software version."
   ::= { rndDeviceParams 4  }

rndBrgFeatures OBJECT-TYPE
    SYNTAX   OCTET STRING  -- SIZE 20
    ACCESS  read-only
    STATUS  mandatory
    DESCRIPTION
      "A bit mask that defines the features supported by a particular configuration
       of this network element:
       __________________________________________
       |  Byte 1|Byte 2 |Byte 3 | ....|Byte 20  |
       |87654321|                     | 87654321|
       |________|_______________________________|

 Byte1 :
      bit1: TX Block mask
      bit2: Source Routing Encapulation
      bit3: SNA/SDLC
      bit4: Frame Relay
      bit5: SNMP
      bit6: LAN Manager
      bit7: High Performance
      bit8: Translation
 Byte2 :
      bit1: DEC Router
      bit2: IPX Router
      bit3: IP  Router
 Byte3 :
      bit1: Dial Up Backup
      bit2: COD
      bit3: FACS
      bit4: Load Balance
      bit5: Remote Configuration
      bit6: RIP 2
      bit7: OSPF
      bit8: IPX RIP/SAP Filter
 Byte4 :
      bit1: BootP Server
      bit2: BootP Client
      bit3: Compression
      bit4: V25.bis
      bit5: ISDN
      bit6: CODv2
      bit7: NSPF
      bit8: UDP Relay

 Byte5
      bit1:VirtualLAN
      bit2:Static IP Multicast
      bit3:IP Redundancy
      bit4:CCM2
      bit5:ISDN Bonding
      bit6:Backup Link Selection -- for the  VAN/Rdapter ver 4.0
      bit7:IP/IPX Forwarding     -- for the  WANgate ver 4.0
      bit8:Improved COD

 Byte6
      bit1: Server Disptacher
      bit2: ISDN_US               -- for the  VANSX/WANGATE ver 5.0
      bit3: PPP
      bit4: IP Rip Filter       -- for Vgate3
      bit5: Zero Hop Routing    -- for Vgate3
      bit6: ISDN Japan

 Byte7
     bit1: With unmanaged Switch
     bit2: 2 LANs
     bit3: OSPF Ver 2.0
     bit4: FACS Ver 2.0
     bit5: Multiple WEB Farm
     bit6: Backup Server"

   ::= { rndDeviceParams 5  }

rndBrgLicense OBJECT-TYPE
    SYNTAX   OCTET STRING  -- SIZE 20
    ACCESS  read-write
    STATUS  mandatory
    DESCRIPTION
       "This parameter is used for entering a s/w license number for a device.
        A separate license number is supplied for each device."
   ::= { rndDeviceParams 6  }

-- IP Host Parameters

--All the new parameters under this section will be added to the
-- rndMng group, as rndIpHost sub-group.
--
rndIpHost  OBJECT IDENTIFIER   ::= { rndDeviceParams 7 }
--
--ICMP Transmission Enable\Disable
--The new variable will be


rndICMPTransmitionEnable   OBJECT-TYPE
   SYNTAX INTEGER {
      enable(1),
      disable(2)
   }
   ACCESS  read-write
   STATUS  mandatory
   DESCRIPTION
    "This variable controlls the ability to transmit ICMP frames"
    ::= { rndIpHost 1 }

rndCommunityTable OBJECT-TYPE
   SYNTAX SEQUENCE OF RndCommunityEntry
   ACCESS not-accessible
   STATUS mandatory
   DESCRIPTION
    "The community table of the agent"
     ::= { rndIpHost 2 }

rndCommunityEntry  OBJECT-TYPE
   SYNTAX RndCommunityEntry
   ACCESS not-accessible
   STATUS mandatory
   DESCRIPTION
       " The row definition for this table."
   INDEX { rndCommunityMngStationAddr,
           IMPLIED rndCommunityString }
   ::= { rndCommunityTable 1 }

RndCommunityEntry ::= SEQUENCE {
  rndCommunityMngStationAddr   IpAddress,
  rndCommunityString           DisplayString,
  rndCommunityAccess           INTEGER,
  rndCommunityTrapsEnable      INTEGER,
  rndCommunityStatus           INTEGER
  }


rndCommunityMngStationAddr OBJECT-TYPE
   SYNTAX IpAddress
   ACCESS   read-write
   STATUS mandatory
   DESCRIPTION
    "The management station that will be allowed to
    communicate with the agent IP address"
     ::=  { rndCommunityEntry 1 }

rndCommunityString OBJECT-TYPE
   SYNTAX DisplayString (SIZE(1..20))
   ACCESS read-write
   STATUS mandatory
   DESCRIPTION
    "The community string with which the management
     station will communicate with the agent"
     ::= { rndCommunityEntry 2 }

rndCommunityAccess OBJECT-TYPE
   SYNTAX INTEGER {
    readOnly(1),
    readWrite(2),
    super(3)
      }
   ACCESS read-write
   STATUS mandatory
   DESCRIPTION
    "The allowed access to this management station"
     ::= { rndCommunityEntry 3}

rndCommunityTrapsEnable OBJECT-TYPE
   SYNTAX INTEGER {
    trapsEnable(1),
    trapsDisable(2)
     }
   ACCESS   read-write
   STATUS mandatory
   DESCRIPTION
    "Should the agent send traps to the management station"
      ::= { rndCommunityEntry 4 }

rndCommunityStatus OBJECT-TYPE
   SYNTAX INTEGER {
    enable(1),
    invalid(2)
     }
   ACCESS read-write
   STATUS mandatory
   DESCRIPTION
    "The status of this entry. If the status is invalid the
    community entry will be deleted"
    ::= { rndCommunityEntry 5 }

rndManagedTime  OBJECT-TYPE
   SYNTAX DisplayString (SIZE(6))
   ACCESS read-write
   STATUS mandatory
   DESCRIPTION
    "The time will be sent in the format hhmmss"
   ::= { rndDeviceParams 8 }

rndManagedDate  OBJECT-TYPE
   SYNTAX DisplayString (SIZE(6..8))
   ACCESS read-write
   STATUS mandatory
   DESCRIPTION
    "The date will be sent in the format ddmmyyyy"
    ::= { rndDeviceParams 9 }


genGroup  OBJECT IDENTIFIER   ::= { rndDeviceParams 11 }
genGroupHWVersion OBJECT-TYPE
   SYNTAX  DisplayString
   ACCESS  read-only
   STATUS  mandatory
   DESCRIPTION
        "Defines the HW version of the product."
   ::= { genGroup 1 }

genGroupConfigurationSymbol OBJECT-TYPE
      SYNTAX  DisplayString (SIZE(1))
      ACCESS  read-only
      STATUS  mandatory
      DESCRIPTION
      "Defines the Configuration Symbol attached to any hardware module
      manufactured by LANNET. One single character A..Z defines the CS
      version."
      ::= { genGroup 2 }

genGroupHWStatus OBJECT-TYPE
      SYNTAX  INTEGER {
        ok(1),
        hardwareProblems(2),
        notSupported(255)
      }
      ACCESS  read-only
      STATUS  mandatory
      DESCRIPTION
      "This attribute describes the status of the group hardware as detected
      by the sensors software."
      ::= { genGroup 3 }

rndSerialNumber  OBJECT-TYPE
   SYNTAX DisplayString (SIZE(0..30))
   ACCESS read-write
   STATUS mandatory
   DESCRIPTION
    "The device's serial number. This parameter is sent with the device configuration but will
     not be set when the configuration is uploaded to the device."
    ::= { rndDeviceParams 12 }

rndApsoluteOSVersion OBJECT-TYPE
   SYNTAX DisplayString (SIZE(0..255))
   ACCESS read-only
   STATUS mandatory
   DESCRIPTION
    "The ApsoluteOS version."
    ::= { rndDeviceParams 13 }

rdwrDeviceType OBJECT-TYPE
   SYNTAX DisplayString (SIZE(0..255))
   ACCESS read-only
   STATUS mandatory
   DESCRIPTION
    "The Device Type."
    ::= { rndDeviceParams 14 }
    
rdwrDeviceNumberOfPorts OBJECT-TYPE
   SYNTAX INTEGER
   ACCESS read-only
   STATUS mandatory
   DESCRIPTION
    "The Device Number of Ports."
    ::= { rndDeviceParams 15 }
    
rdwrDevicePortsConfig OBJECT-TYPE
   SYNTAX DisplayString (SIZE(0..255))
   ACCESS read-only
   STATUS mandatory
   DESCRIPTION
    "The Device Ports Configuration."
    ::= { rndDeviceParams 16 }
    
rdwrDeviceThroughput OBJECT-TYPE
   SYNTAX DisplayString (SIZE(0..255))
   ACCESS read-only
   STATUS mandatory
   DESCRIPTION
    "The Device Throughput."
    ::= { rndDeviceParams 17 }
    
rdwrDeviceNetworkDriver OBJECT-TYPE
   SYNTAX DisplayString (SIZE(0..255))
   ACCESS read-only
   STATUS mandatory
   DESCRIPTION
    "The Device Network Driver."
    ::= { rndDeviceParams 18 }
    
rdwrDeviceCPUsNumber OBJECT-TYPE
   SYNTAX INTEGER
   ACCESS read-only
   STATUS mandatory
   DESCRIPTION
    "The Device number of CPU's."
    ::= { rndDeviceParams 19 }
    
rdwrDeviceActiveBoot OBJECT-TYPE
   SYNTAX DisplayString (SIZE(0..255))
   ACCESS read-only
   STATUS mandatory
   DESCRIPTION
    "The Device Active Boot."
    ::= { rndDeviceParams 20 }
    
rdwrDeviceSecondaryBoot OBJECT-TYPE
   SYNTAX DisplayString (SIZE(0..255))
   ACCESS read-only
   STATUS mandatory
   DESCRIPTION
    "The Device Secondary Boot."
    ::= { rndDeviceParams 21 }


rsCoresNumber OBJECT-TYPE 
       SYNTAX  INTEGER  (0..100)  
       ACCESS  read-only  
       STATUS  mandatory  
       DESCRIPTION  
         "Show cores number"  
       ::=  { rndDeviceParams 22 } 
        
rsCPUFrequency OBJECT-TYPE  
       SYNTAX  DisplayString  (SIZE(1..20))  
       ACCESS  read-only  
       STATUS  mandatory  
       DESCRIPTION  
         "Show CPU frequency"  
       ::=  { rndDeviceParams 23 } 

rndInterface OBJECT IDENTIFIER ::= { rnd 4  }

-- Channel & LAN Configuration

rndIfTable  OBJECT-TYPE
    SYNTAX SEQUENCE OF  RndIfEntry
    ACCESS  not-accessible
    STATUS  mandatory
    DESCRIPTION
      "RND-specific interface table.  Each table entry includes an
      index, Board number, Network Address, interface status, clock
      indicator and interface cost."
    ::= {  rndInterface 1  }


rndIfEntry  OBJECT-TYPE
    SYNTAX RndIfEntry
    ACCESS  not-accessible
    STATUS  mandatory
    DESCRIPTION
       " The row definition for this table."
    INDEX   { rndIfIndex  }
    ::= {  rndIfTable 1  }


RndIfEntry ::= SEQUENCE {
  rndIfIndex
     INTEGER,
  rndIfBoardNum
     INTEGER,
  rndIfNetAddress
     NetworkAddress,
  rndIfStatus
     INTEGER,
  rndIfClockType
     INTEGER,
 rndIfBaudRate
     INTEGER,
  rndIfCost
     INTEGER,
  rndIfCompression
     INTEGER,
  rndIfCompressionStatus
     INTEGER,
  rndIfCompressionRate
     INTEGER,
  rndIfLATCompression
     INTEGER,
  rndIfCompressionType
     INTEGER,
rndIfFilterMode
     INTEGER,
rndIfChannelType
     INTEGER,
rndIfBridge
     INTEGER,
rndHighPriorityIf    -- New Parameters
     INTEGER,
rndWanHeader   -- New Parameters
     INTEGER,
rndDuplexMode  -- New Parameters
     INTEGER
  }

rndIfIndex OBJECT-TYPE
    SYNTAX   INTEGER
    ACCESS  read-only
    STATUS  mandatory
    DESCRIPTION
     "Index to the RND Interface Table. The interface defined by a
     particular value of this index is the same interface as
     identified by the same value of ifIndex (MIBII)."
         ::= {  rndIfEntry 1  }

rndIfBoardNum OBJECT-TYPE
    SYNTAX   INTEGER
    ACCESS  read-only
    STATUS  mandatory
    DESCRIPTION
     "The interface defined by this entry correspTnds to the board
     defined by the same value of rndSlotBoardNum in the rndSlotTab."
    ::= {  rndIfEntry 2  }

rndIfNetAddress OBJECT-TYPE
    SYNTAX   NetworkAddress
    ACCESS  read-only
    STATUS  mandatory
    DESCRIPTION
     "The IP address of the interface defined by the particular value of
     rndIfIndex."
    ::= {  rndIfEntry 3  }

rndIfStatus  OBJECT-TYPE
    SYNTAX   INTEGER  {
       ok (1),
       okSingleBrg(2),
       okMultiBrg(3),
       connctFault(4),
       rxFault(5),
       txFault(6),
       channelLoopback(7),
       rxClockFault(8),
       t1Alarm(9)
    }
    ACCESS  read-only
    STATUS  mandatory
    DESCRIPTION
     "The current status of the interface."
     ::= {  rndIfEntry 4  }

rndIfClockType   OBJECT-TYPE
    SYNTAX  INTEGER {
       external(1),
       internal(2),
       t1(3),
       g703(4)
    }
    ACCESS  read-write
    STATUS  mandatory
    DESCRIPTION
     "rndIfClockType defines the type of clock each interface
     uses: internal or external."
    ::= {  rndIfEntry 5  }

rndIfBaudRate    OBJECT-TYPE          -- Level II routing
    SYNTAX   INTEGER   -- word
    ACCESS  read-write
    STATUS  mandatory
    DESCRIPTION
     " Defines the baud rate of use by the interface. The valid
      rates are determined by the type of the media for which this
      baud rate is defined."
    ::= { rndIfEntry 6  }


rndIfCost    OBJECT-TYPE          -- Level II routing
    SYNTAX   INTEGER   -- word
    ACCESS  read-write
    STATUS  mandatory
    DESCRIPTION
       "This variable assigns a transmission cost to the interface
        (channel or LAN). These costs are used in Level II routing. The
        costs aretypically inversly proportional to the channel quality."
    ::= { rndIfEntry 7  }

rndIfCompression   OBJECT-TYPE
    SYNTAX  INTEGER {
       enable(1),
       disable(2)
    }
    ACCESS  read-write
    STATUS  mandatory
    DESCRIPTION
       "Defines whether data compression is enabled or disabled for the
       interface."
    ::= {  rndIfEntry 8  }

  rndIfCompressionStatus  OBJECT-TYPE
  SYNTAX  INTEGER {
       not-inserted(1),
       active(2),
       not-active(3),
       disable(4)
    }
    ACCESS  read-only
    STATUS  mandatory
    DESCRIPTION
       "Defines the status of the compression component:
        not-inserted - Compression component is not in the device
        active -     Compression is enabled and operates correctly
        not-active - Compression is enables but does not operate.
                     The reason may be that there is no compression
                     component on the device connected to this interface.
        disabled   - Compression was disabled by management, using
                     variable rndCompression."
    ::= {  rndIfEntry 9  }

  rndIfCompressionRate  OBJECT-TYPE
    SYNTAX  INTEGER
    ACCESS  read-only
    STATUS  mandatory
    DESCRIPTION
  "Percentage of compression. This variable applies only
  if rndCompressionStatus is active."
    ::= {  rndIfEntry 10  }

  rndIfLATCompression  OBJECT-TYPE
    SYNTAX  INTEGER {
       enable(1),
       disable(2)
    }
    ACCESS  read-write
    STATUS  mandatory
    DESCRIPTION
  "Enable/Disable the LAT Compression."
    ::= {  rndIfEntry 11  }

  rndIfCompressionType  OBJECT-TYPE
    SYNTAX  INTEGER {
       none(1),
       lowSpeed(2),
       highSpeed(3)
    }
    ACCESS  read-only
    STATUS  mandatory
    DESCRIPTION
        "This parameter indicates the type of compression option available in the device.
         none(1)     - indicates that there is no compression option in the device
         lowSpeed(2) - indicates a compression option which is  operational up
                       to line speed sof 64 kbps.
         highSpeed(3)- indicates a compression option which is  operational up
                       to line speeds of 2 Mbps."
    ::= {  rndIfEntry 12  }

rndIfFilterMode  OBJECT-TYPE
    SYNTAX  INTEGER {
       destinationOnly(1),
       sourceAndDestination(2),
       none(3)
    }
    ACCESS  read-write
    STATUS  mandatory
    DESCRIPTION
         "This parameter indicates the type of filtering in the device. "
    ::= {  rndIfEntry 13 }

    rndIfChannelType OBJECT-TYPE
      SYNTAX  INTEGER {
         wanChannel(1),
         ogRanPort(2),
         routerToBridge(3),
         spsFramRelay(4),         -- Frame Relay with external SPS.
         dialBackup(5),
         snar(6),
         lan(7),
         spsX25(8),
         frameRelay1490(9),       -- Frame Relay with full  RFC1490 support.
         frameRelay1490CAR(10),   -- Frame Relay with CAR RFC1490 bridge encapsulation.
         frameRelayCAR(11),       -- Frame Relay with CAR and RND's encapsulation
         ppp(12)        -- New Value
        }
      ACCESS   read-write
      STATUS   mandatory
      DESCRIPTION
        " The type of the WAN channel "
   ::= { rndIfEntry 14 }

    rndIfBridge OBJECT-TYPE
      SYNTAX  INTEGER {
         enable(1),
         disable(2)
        }
      ACCESS   read-write
      STATUS   mandatory
      DESCRIPTION
        " This variable indicates  whether this interface forward Layer II pakages."
   ::= { rndIfEntry 15 }

    rndHighPriorityIf  OBJECT-TYPE
      SYNTAX  INTEGER {
         enable(1),
         disable(2)
        }
      ACCESS   read-write
      STATUS   mandatory
      DESCRIPTION
        " This variable indicates  whether this interface will forward pakages
        that fit HighPriority set by the manager."
       ::= { rndIfEntry 16}

    rndWanHeader  OBJECT-TYPE
      SYNTAX  INTEGER {
         regular(1),
         short(2)
        }
      ACCESS   read-write
      STATUS   mandatory
      DESCRIPTION
        " This variable indicates the RND WAN header type used for frames
          which pass through this interface. 'regular' specifies a 14 bytes
          header compatible with older OG versions and 'short' a 4 byte header
          compatible with the RND adapter product family."
       ::= { rndIfEntry 17}

    rndDuplexMode  OBJECT-TYPE
      SYNTAX  INTEGER {
         half(1),
         full(2)
        }
      ACCESS   read-write
      STATUS   mandatory
      DESCRIPTION
        " This variable indicates whether this interface operates in half duplex
          full duplex or auto negotiation mode."
       ::= { rndIfEntry 18}


-- rndIPX group defines the parameters for the IPX Router / removed 5.5.99

rndIPX   OBJECT IDENTIFIER ::= { rnd 12 }

-- This describes the - Facility for Access Control and Security
-- NEW VERSION  OF FACS MIB WITHOUT APP AND WITH SOKET Upgrade
--
rndFACS    OBJECT IDENTIFIER ::=  { rnd 16 }

rndFACSDefaultAction OBJECT-TYPE
  SYNTAX  INTEGER {
    block(1),
    forward(2),
    enable(3),
    disable(4),
    blockAndReport(129)
  }
  ACCESS  read-write
  STATUS  mandatory
  DESCRIPTION
         "Used to define the default action for the device, when no
                FACS statements applicable to a given frame are defined."

 DEFVAL  { 1 }
  ::= { rndFACS 1 }

rndFACSActTable OBJECT-TYPE
        SYNTAX  SEQUENCE OF RndFACSActEntry
        ACCESS  not-accessible
        STATUS  mandatory
        DESCRIPTION
               "The table of  FACS action."
        ::= { rndFACS 2 }

rndFACSActEntry OBJECT-TYPE
        SYNTAX  RndFACSActEntry
        ACCESS  not-accessible
        STATUS  mandatory
        DESCRIPTION
          "Each rndFACSActEntry consist of the following parameters"
        INDEX   {rndFACSActType,
                 rndFACSActIfIndex}
        ::= { rndFACSActTable 1 }

RndFACSActEntry ::= SEQUENCE {
        rndFACSActType
           INTEGER,
        rndFACSActIfIndex
           INTEGER,
        rndFACSAction
           INTEGER
                }

rndFACSActType OBJECT-TYPE
        SYNTAX  INTEGER {
              tx(1),
              rx(2),
              activeDB(4),
              tempDB(5)
            }
        ACCESS  read-only
        STATUS  mandatory
        DESCRIPTION
                "This parameter indicate on which FACS Table the FACS
                 action will preform."
        ::= { rndFACSActEntry 1 }

rndFACSActIfIndex OBJECT-TYPE
        SYNTAX  INTEGER
        ACCESS  read-only
        STATUS  mandatory
        DESCRIPTION
               "The interface to which this FACS entry is applicable."
        ::= { rndFACSActEntry 2 }


rndFACSAction OBJECT-TYPE
        SYNTAX  INTEGER {
                none(1),
                eraseIP(2),
                eraseDECnet(3),
                eraseIPX(4),
                eraseBrg(5),
                replaceIP(6),
                replaceIPX(8),
                replaceBrg(9),
                backupIP(10),
                backupIPX(12),
                backupBrg(13)
        }
        ACCESS  read-write
        STATUS  mandatory
        DESCRIPTION
               "The management station that sends a SET request for one of these actions
                with indexes  rndFACSType and rndFACSIfIndex defines the type and the
                interface  Id for which all FACS statements are to be erased.
                If no interface or no type  is specified, all FACS statements for a
                protocol are erased."
      DEFVAL  { 1 }
        ::= { rndFACSActEntry 3 }


rndFACSTable OBJECT-TYPE
  SYNTAX  SEQUENCE OF RndFACSEntry
  ACCESS  not-accessible
  STATUS  mandatory
  DESCRIPTION
         "The table of  FACS statment."
  ::= { rndFACS 3 }

rndFACSEntry OBJECT-TYPE
  SYNTAX  RndFACSEntry
  ACCESS  not-accessible
  STATUS  mandatory
  DESCRIPTION
         "Each FACS statment consist of the following parameters"
  INDEX  {rndFACSIfIndex,
          rndFACSProtocolType,
          rndFACSType,
          rndFACSIndex }
  ::= { rndFACSTable 1 }

RndFACSEntry ::= SEQUENCE {
     rndFACSIfIndex
        INTEGER,
     rndFACSProtocolType
        INTEGER,
     rndFACSType
        INTEGER,
     rndFACSIndex
        INTEGER,
     rndFACSSrcAdd
        OCTET STRING ,
     rndFACSSrcAddMask
        OCTET STRING,
     rndFACSDesAdd
        OCTET STRING,
     rndFACSDesAddMask
        OCTET STRING,
     rndFACSOperation
        INTEGER,
     rndFACSNetFiltering
        INTEGER,
     rndFACSSoketNum
        INTEGER,
     rndFACSMask1Id
        INTEGER,
     rndFACSMask2Id
        INTEGER,
     rndFACSStatus
        INTEGER
  }

rndFACSIfIndex OBJECT-TYPE
  SYNTAX  INTEGER
  ACCESS  read-only
  STATUS  mandatory
  DESCRIPTION
         "The interface to which this FACS entry is applicable."
  ::= { rndFACSEntry 1 }

rndFACSProtocolType OBJECT-TYPE
  SYNTAX  INTEGER{
                ip(1),
                ipx(2),
                dec(3),
                bridge(4)
        }
  ACCESS  read-only
  STATUS  mandatory
  DESCRIPTION
               "This parameter define the protocol the Security  Access Control
                is applicable."
  ::= { rndFACSEntry 2 }

rndFACSType OBJECT-TYPE
  SYNTAX  INTEGER {
              tx(1),
              rx(2),
              cod(3),
              activeDB(4),
              tempDB(5)
            }
  ACCESS  read-only
  STATUS  mandatory
  DESCRIPTION
                " The Mode of in which this FACS statement operates."
  ::= { rndFACSEntry 3 }

rndFACSIndex OBJECT-TYPE
  SYNTAX  INTEGER
  ACCESS  read-only
  STATUS  mandatory
  DESCRIPTION
               "Index to the FACS  Table. "
  ::= { rndFACSEntry 4 }

rndFACSSrcAdd OBJECT-TYPE
  SYNTAX  OCTET STRING
  ACCESS  read-write
  STATUS  mandatory
  DESCRIPTION
         "The size of the octet string will be according to the protocol type define in
          rndFACSProtocolType."
  ::= { rndFACSEntry 5 }

rndFACSSrcAddMask OBJECT-TYPE
  SYNTAX   OCTET STRING
  ACCESS  read-write
  STATUS  mandatory
  DESCRIPTION
         "Source-address mask ."
  ::= { rndFACSEntry 6 }

rndFACSDesAdd OBJECT-TYPE
        SYNTAX   OCTET STRING
        ACCESS  read-write
        STATUS  mandatory
        DESCRIPTION
           "Destination-address The size of the octet string will be according to the
           protocol type define in rndFACSProtocolType ."
        ::= { rndFACSEntry 7 }


rndFACSDesAddMask OBJECT-TYPE
        SYNTAX   OCTET STRING
        ACCESS  read-write
        STATUS  mandatory
        DESCRIPTION
               "Destination-address mask ."
        ::= { rndFACSEntry 8 }


rndFACSOperation OBJECT-TYPE
        SYNTAX  INTEGER {
               block(1),
               forward(2),
               permit(3),        -- For Connect On demand Only
               deny(4),          -- For Connect On demand Only
               blockZHRP(5),     -- Disable Zhrp for this FAXCS statement
               blockAndReport(129)
        }
        ACCESS  read-write
        STATUS  mandatory
        DESCRIPTION
               "... ."
        ::= { rndFACSEntry 9 }

rndFACSNetFiltering OBJECT-TYPE
        SYNTAX  INTEGER {
                none(1),
                l2multicast(2), --applicable for Bridge protocol
                arp(3),      --applicable for ip protocol
                icmp(4),     --applicable for ip protocol
                ip(5),       --applicable for ip protocol
                udp(6),      --applicable for ip protocol
                tcp(7),      --applicable for ip protocol
                decnet(8),   --applicable for decnet protocol
                ipx(9)      --applicable for ipx protocol
        }
        ACCESS  read-write
        STATUS  mandatory
        DESCRIPTION
               "... ."
        ::= { rndFACSEntry 10 }


rndFACSSoketNum OBJECT-TYPE   --applicable for ip,ipx protocol
        SYNTAX  INTEGER
         --   {none(1),
         --    ftp(21),
         --    telenet(23),
         --    smtp(25),
         --    tftp(69),
         --    snmp(161),
         --    snmpTrape(162),
         --    rip(520),
         --    saPipx(1106),
         --    ripIPX(1107)
         --  }
        ACCESS  read-write
        STATUS  mandatory
        DESCRIPTION
            " Port/socket  number for different applications
              0 is default meaning not applicable."
        ::= { rndFACSEntry 11}

rndFACSMask1Id OBJECT-TYPE
        SYNTAX  INTEGER
        ACCESS  read-write
        STATUS  mandatory
        DESCRIPTION
            " Index into RND mask table FACS/COD Type) ."
        ::= { rndFACSEntry 12}

rndFACSMask2Id OBJECT-TYPE
   SYNTAX  INTEGER
   ACCESS  read-write
   STATUS  mandatory
   DESCRIPTION
       " Index into RND mask table FACS/COD according to
       the value of rndFACSType ."
   ::= { rndFACSEntry 13}


rndFACSStatus OBJECT-TYPE
   SYNTAX  INTEGER {
     valid(1),
     createRequest(2),   --  future use
     underCreation(3),
     invalid(4)          -- logically deleted
   }
   ACCESS  read-write
   STATUS  mandatory
   DESCRIPTION
       "The status of a table entry."
   ::= { rndFACSEntry 14}

rndBootP    OBJECT IDENTIFIER ::=  { rnd 24 }

rndBootPServerAddress  OBJECT-TYPE
    SYNTAX IpAddress
    ACCESS read-write
    STATUS mandatory
    DESCRIPTION
     " The IPAddress of the BOOTP server. the OpenGate will act as a BootP relay if
       this parameter is not equale to 0.0.0.0."
    DEFVAL  {'00000000'H}
      ::= { rndBootP 1 }

rndBootPRelaySecThreshold OBJECT-TYPE
    SYNTAX INTEGER
    ACCESS read-write
    STATUS mandatory
    DESCRIPTION
       "BootP requests are relayed only if their SEC field is greater or
        equal to the threshold value in order to allow local BootP Servers
        to answer first."
    ::= { rndBootP 2 }

-- ip Specific group  Addition parameters to ip group in MIB-2

ipSpec      OBJECT IDENTIFIER ::= { rnd 26 }

rsIpAddrTable OBJECT-TYPE
    SYNTAX  SEQUENCE  OF RsIpAddrEntry
    ACCESS  not-accessible
    STATUS  mandatory
    DESCRIPTION
       "This table is parralel to MIB II IpAddrTable, and is used to
        add/delete entries to/from that table. In addition it contains
        private objects."
    ::=  { ipSpec 1 }

rsIpAddrEntry   OBJECT-TYPE
    SYNTAX  RsIpAddrEntry
    ACCESS  not-accessible
    STATUS  mandatory
    DESCRIPTION
            "The addressing information for one of this
            entity's IP addresses."
    INDEX  {rsIpAdEntAddr}
    ::=  { rsIpAddrTable 1 }

RsIpAddrEntry ::= SEQUENCE {
    rsIpAdEntAddr                IpAddress,
    rsIpAdEntIfIndex             INTEGER,
    rsIpAdEntNetMask             IpAddress,
    rsIpAdEntForwardIpBroadcast  INTEGER,
    rsIpAdEntReasmMaxSize        INTEGER,
    rsIpAdEntStatus              INTEGER,
    rsIpAdEntBcastAddr           INTEGER,
    rsIpAdEntVlanTag             INTEGER,
    rsIpAdEntOneIpMode           INTEGER,
    rsIpAdEntType		         INTEGER,
    rsIpAdEntPeerAddr		     IpAddress,
    rsIpAdEntPeerAddrStatus      INTEGER
    }

rsIpAdEntAddr OBJECT-TYPE
    SYNTAX  IpAddress
    ACCESS  read-only
    STATUS  mandatory
    DESCRIPTION
            "The IP address to which this entry's addressing
            information pertains."
    ::= { rsIpAddrEntry 1 }

rsIpAdEntIfIndex OBJECT-TYPE
    SYNTAX  INTEGER
    ACCESS  read-write
    STATUS  mandatory
    DESCRIPTION
            "The index value which uniquely identifies the
            interface to which this entry is applicable.  The
            interface identified by a particular value of this
            index is the same interface as identified by the
            same value of ifIndex."
    ::= { rsIpAddrEntry 2 }

rsIpAdEntNetMask OBJECT-TYPE
    SYNTAX  IpAddress
    ACCESS  read-write
    STATUS  mandatory
    DESCRIPTION
            "The subnet mask associated with the IP address of
            this entry.  The value of the mask is an IP
            address with all the network bits set to 1 and all
            the hosts bits set to 0."
    ::= { rsIpAddrEntry 3 }

rsIpAdEntForwardIpBroadcast OBJECT-TYPE
    SYNTAX INTEGER {
       enable(1),
       disable(2)
       }
    ACCESS  read-write
    STATUS  mandatory
    DESCRIPTION
        " This variable controls forwarding of IP (sub)net-directed
          broadcasts destined for an attached sub(net). "
    DEFVAL  { enable }
    ::=   { rsIpAddrEntry 4 }

rsIpAdEntReasmMaxSize OBJECT-TYPE
    SYNTAX  INTEGER (0..65535)
    ACCESS  read-only
    STATUS  mandatory
    DESCRIPTION
         "The size of the largest IP datagram which this
          entity can re-assemble from incoming IP fragmented
          datagrams received on this interface."
    ::= { rsIpAddrEntry 5 }

rsIpAdEntStatus OBJECT-TYPE
    SYNTAX INTEGER{
       valid(1),
       invalid(2)
       }
    ACCESS  read-write
    STATUS  mandatory
    DESCRIPTION
        " The validity of this entry. Invalid indicates that this entry is
          invalid in IpAddrTable (MIB II)."
    DEFVAL  { valid }
    ::=   { rsIpAddrEntry 6 }

rsIpAdEntBcastAddr OBJECT-TYPE
    SYNTAX INTEGER (0..1)
    ACCESS read-write
    STATUS mandatory
    DESCRIPTION
        " Indicates how the host part of ip subnet broadcast messages will be
          filled:
           0 - host part will be filled by 0
           1 - host part will be filled by 1."
    ::=   { rsIpAddrEntry 7 }

rsIpAdEntVlanTag OBJECT-TYPE
    SYNTAX  INTEGER
    ACCESS  read-write
    STATUS  mandatory
    DESCRIPTION
            "The vlan Tag value that represent this ip interface
             this filed include both vlna tag and vlan priority "
    ::= { rsIpAddrEntry 8 }


rsIpAdEntOneIpMode OBJECT-TYPE
    SYNTAX  INTEGER{
       enable(1),
       disable(2)
       }
    ACCESS  read-write
    STATUS  mandatory
    DESCRIPTION
            "the one-ip mode. Relevant only for LinkProof devices.
		disable - regular interface. Enable - the specific ip can be ip-to-me (to device) 
		and/or forwarding ip"
	DEFVAL  {disable}
    ::= { rsIpAddrEntry 9 }

rsIpAdEntType OBJECT-TYPE
    SYNTAX  INTEGER{
       static(1),
       dhcp(2),
       pppoe(3),
       pptp(4)
       }
    ACCESS  read-only
    STATUS  mandatory
    DESCRIPTION
            "Ip interface type. The way the ip-interface was set determine its type"
    ::= { rsIpAddrEntry 10 }

rsIpAdEntPeerAddr OBJECT-TYPE
    SYNTAX  IpAddress
    ACCESS  read-write
    STATUS  mandatory
    DESCRIPTION
            "IP of same interface on the peer device."
    ::= { rsIpAddrEntry 11 }

rsIpAdEntPeerAddrStatus OBJECT-TYPE
    SYNTAX  INTEGER{
		relevant(1),
        nonrelevant(2)
	   }
    ACCESS  read-write
    STATUS  mandatory
    DESCRIPTION
            "Indicating the relevancy of PeerAddr for this row"
    ::= { rsIpAddrEntry 12 }
	
icmpSpec               OBJECT IDENTIFIER ::= { ipSpec 2 }

rsIcmpGenErrMsgEnable   OBJECT-TYPE
    SYNTAX INTEGER {
       enable(1),
       disable(2)
   }
    ACCESS  read-write
    STATUS  mandatory
    DESCRIPTION
           "This variable controlls the ability to generate ICMP error messages"
    DEFVAL  { enable }
    ::= { icmpSpec 1 }

rsIcmpRdTable OBJECT-TYPE
    SYNTAX  SEQUENCE  OF RsIcmpRdEntry
    ACCESS  not-accessible
    STATUS  mandatory
    DESCRIPTION
       "This table contains ICMP Router Discovery parameters
        configurated per IP interface."
    ::=  {icmpSpec 2}

rsIcmpRdEntry   OBJECT-TYPE
    SYNTAX  RsIcmpRdEntry
    ACCESS  not-accessible
    STATUS  mandatory
    DESCRIPTION
           "The ICMP parameters configurated for IP interface."
    INDEX  {rsIcmpRdIpAddr}
    ::=  {rsIcmpRdTable 1}

RsIcmpRdEntry ::= SEQUENCE {
    rsIcmpRdIpAddr             IpAddress,
    rsIcmpRdIpAdvertAddr       IpAddress,
    rsIcmpRdMaxAdvertInterval  INTEGER,
    rsIcmpRdMinAdvertInterval  INTEGER,
    rsIcmpRdAdvertLifetime     INTEGER,
    rsIcmpRdAdvertise          INTEGER,
    rsIcmpRdPreferenceLevel    INTEGER,
    rsIcmpRdEntStatus          INTEGER
    }

rsIcmpRdIpAddr OBJECT-TYPE
    SYNTAX  IpAddress
    ACCESS  read-only
    STATUS  mandatory
    DESCRIPTION
            "The IP address to which this entry's information pertains."
    ::= {rsIcmpRdEntry 1}

rsIcmpRdIpAdvertAddr OBJECT-TYPE
    SYNTAX  IpAddress
    ACCESS  read-write
    STATUS  mandatory
    DESCRIPTION
            " The IP destination address to be used for multicast
              Router Advertisements sent from the interface. The
              only permissible values are the all-systems multicast
              address, 224.0.0.1, or the limited-broadcast address,
              255.255.255.255."
    DEFVAL  {'E0000001'H}
    ::= {rsIcmpRdEntry 2}

rsIcmpRdMaxAdvertInterval OBJECT-TYPE
    SYNTAX  INTEGER (4..1800)
    ACCESS  read-write
    STATUS  mandatory
    DESCRIPTION
            "The maximum time allowed between sending multicast
             Router Advertisements from the interface, in seconds.
             Must be no less than 4 seconds and no greater than 1800
             seconds."
    DEFVAL  {600}
    ::= {rsIcmpRdEntry 3}

rsIcmpRdMinAdvertInterval OBJECT-TYPE
    SYNTAX  INTEGER (3..1800)
    ACCESS  read-write
    STATUS  mandatory
    DESCRIPTION
            "The minimum time allowed between sending unsolicited
             multicast Router Advertisements from the interface, in
             seconds.  Must be no less than 3 seconds and no greater
             than rsIcmpRdMaxAdvertInterval.
             Default: 0.75 * rsIcmpRdMaxAdvertInterval."
    ::= {rsIcmpRdEntry 4}

rsIcmpRdAdvertLifetime OBJECT-TYPE
    SYNTAX  INTEGER (4..9000)
    ACCESS  read-write
    STATUS  mandatory
    DESCRIPTION
             "The maximum length of time that the advertised addresses
             are to be considered as valid. Must be no less than
             rsIcmpRdMaxAdvertInterval and no greater than 9000 seconds.
             Default: 3 * rsIcmpRdMaxAdvertInterval."
    ::= {rsIcmpRdEntry 5}

rsIcmpRdAdvertise OBJECT-TYPE
    SYNTAX  INTEGER {
       enable  (1),
       disable (2)
       }
    ACCESS  read-write
    STATUS  mandatory
    DESCRIPTION
             "A flag indicating whether or not the address is to be
              advertised."
    DEFVAL  {enable}
    ::= {rsIcmpRdEntry 6}

rsIcmpRdPreferenceLevel OBJECT-TYPE
    SYNTAX  INTEGER
    ACCESS  read-write
    STATUS  mandatory
    DESCRIPTION
             "The preferability of the address as a default router
             address, relative to other router addresses on the same
             subnet."
    DEFVAL  {0}
    ::= {rsIcmpRdEntry 7}

rsIcmpRdEntStatus  OBJECT-TYPE
    SYNTAX INTEGER
    ACCESS  read-write
    STATUS  mandatory
    DESCRIPTION
            "Setting of any value to this object set values of
             all fields to the default values."
    ::=   {rsIcmpRdEntry 8}


rip2Spec              OBJECT IDENTIFIER ::= { ipSpec  3 }

rsRip2IfConfTable OBJECT-TYPE
    SYNTAX  SEQUENCE  OF RsRip2IfConfEntry
    ACCESS  not-accessible
    STATUS  mandatory
    DESCRIPTION
           "This table is extension of rip2IfConfTable (RFC 1389 ,RIP 2)"
    ::=  { rip2Spec 1  }

rsRip2IfConfEntry   OBJECT-TYPE
    SYNTAX  RsRip2IfConfEntry
    ACCESS  not-accessible
    STATUS  mandatory
    DESCRIPTION " "
    INDEX  { rsRip2IfConfAddress }
    ::=  {  rsRip2IfConfTable 1  }

RsRip2IfConfEntry  ::= SEQUENCE {
    rsRip2IfConfAddress    IpAddress,
    rsRip2IfConfVirtualDis INTEGER,
    rsRip2IfConfAutoSend   INTEGER
    }

rsRip2IfConfAddress  OBJECT-TYPE
    SYNTAX IpAddress
    ACCESS  read-only
    STATUS  mandatory
    DESCRIPTION
      " The IP Address of this system on the indicated subnet. "
    ::=  { rsRip2IfConfEntry 1 }


rsRip2IfConfVirtualDis OBJECT-TYPE
    SYNTAX INTEGER
    ACCESS  read-write
    STATUS  mandatory
    DESCRIPTION
         "This variable defines the virtual number of hops assigned to
          the interface specified by rsIfIpAddrIndex. This enables
          fine-tuning of the RIP routing algorithm."
    DEFVAL  { 1 }
    ::=   { rsRip2IfConfEntry  2  }

rsRip2IfConfAutoSend OBJECT-TYPE
    SYNTAX  INTEGER {
       enable  (1),
       disable (2)
       }
    ACCESS  read-write
    STATUS  mandatory
    DESCRIPTION
         "This variable controls RIP automatic send behavior. If enabled
          and no routers were heard on the interface, RIP will only send
          default route with high metric. Otherwise RIP will send updates
          according to configuration. "
    DEFVAL  {disable}
     ::=   { rsRip2IfConfEntry  3  }

rdwrRip2IfConfTable OBJECT-TYPE
    SYNTAX   SEQUENCE OF RdwrRip2IfConfEntry
    ACCESS   not-accessible
    STATUS   mandatory
    DESCRIPTION
        "A list of subnets which require separate configuration in RIP. 
		This is a combination of rip2IfConfTable and rsRip2IfConfTable." 
    ::= { rip2Spec 2 }

rdwrRip2IfConfEntry OBJECT-TYPE
    SYNTAX   RdwrRip2IfConfEntry
    ACCESS   not-accessible
    STATUS   mandatory
    DESCRIPTION
        "A Single Routing Domain in a single Subnet."
    INDEX { rdwrRip2IfConfAddress }
    ::= { rdwrRip2IfConfTable 1 }

RdwrRip2IfConfEntry ::= SEQUENCE {
    rdwrRip2IfConfAddress           IpAddress,
    rdwrRip2IfConfDomain            RouteTag,
    rdwrRip2IfConfAuthType          INTEGER,
    rdwrRip2IfConfAuthKey           OCTET STRING (SIZE(0..16)),
    rdwrRip2IfConfSend              INTEGER,
    rdwrRip2IfConfReceive           INTEGER,
    rdwrRip2IfConfDefaultMetric     INTEGER,
    rdwrRip2IfConfStatus            INTEGER,
    rdwrRip2IfConfSrcAddress        IpAddress,
	rdwrRip2IfConfVirtualDis        INTEGER,
    rdwrRip2IfConfAutoSend          INTEGER
    }

rdwrRip2IfConfAddress OBJECT-TYPE
    SYNTAX   IpAddress
    ACCESS   read-only
    STATUS   mandatory
    DESCRIPTION
        "The IP Address of this system on the indicated
        subnet.  For unnumbered interfaces, the value 0.0.0.N,
        where the least significant 24 bits (N) is the ifIndex
        for the IP Interface in network byte order."
    ::= { rdwrRip2IfConfEntry 1 }

rdwrRip2IfConfDomain OBJECT-TYPE
    SYNTAX   RouteTag
    ACCESS   read-write
    STATUS   deprecated
    DESCRIPTION
        "Value inserted into the Routing Domain field
        of all RIP packets sent on this interface."
--  DEFVAL { '0000'h }
    ::= { rdwrRip2IfConfEntry 2 }

rdwrRip2IfConfAuthType OBJECT-TYPE
    SYNTAX   INTEGER {
                noAuthentication (1),
                simplePassword (2)
                }
    ACCESS   read-write
    STATUS   mandatory
    DESCRIPTION
        "The type of Authentication used on this
        interface."
--  DEFVAL { noAuthentication }
    ::= { rdwrRip2IfConfEntry 3 }

rdwrRip2IfConfAuthKey OBJECT-TYPE
    SYNTAX   OCTET STRING (SIZE(0..16))
    ACCESS   read-write
    STATUS   mandatory
    DESCRIPTION
        "The value to be used as the Authentication Key
        whenever the corresponding instance of
        rip2IfConfAuthType has the value simplePassword
        word.  A modification of the corresponding
        instance of rip2IfConfAuthType does not modify
        the rip2IfConfAuthKey value.  If a string shorter
        than 16 octets is supplied, it will be left-
        justified and padded to 16 octets, on the right,
        with nulls (0x00).
        Reading this object always results in an  OCTET
        STRING of length zero; authentication may not
        be bypassed by reading the MIB object."
--  DEFVAL { ''h }
    ::= { rdwrRip2IfConfEntry 4 }

rdwrRip2IfConfSend OBJECT-TYPE
    SYNTAX  INTEGER {
                doNotSend (1),
                ripVersion1 (2),
                rip1Compatible (3),
                ripVersion2 (4),
                ripV1Demand (5),
                ripV2Demand (6)
            }
    ACCESS   read-write
    STATUS   mandatory
    DESCRIPTION
        "What the router sends on this interface.
        ripVersion1 implies sending RIP updates compliant
        with  RFC  1058.   rip1Compatible implies
        broadcasting RIP-2 updates using RFC 1058 route
        subsumption rules.  ripVersion2 implies
        multicasting RIP-2 updates.  ripV1Demand indicates
        the use of Demand RIP on a WAN interface under RIP
        Version 1 rules.  ripV2Demand indicates the use of
        Demand RIP on a WAN interface under Version 2 rules."
--   DEFVAL { rip1Compatible }
::= { rdwrRip2IfConfEntry 5 }

rdwrRip2IfConfReceive OBJECT-TYPE
    SYNTAX  INTEGER {
                rip1 (1),
                rip2 (2),
                rip1OrRip2 (3),
                doNotRecieve (4)
            }
    ACCESS   read-write
    STATUS   mandatory
    DESCRIPTION
        "This indicates which version of RIP updates
        are to be accepted.  Note that rip2 and
        rip1OrRip2 implies reception of multicast
        packets."
--  DEFVAL { rip1OrRip2 }
    ::= { rdwrRip2IfConfEntry 6 }

rdwrRip2IfConfDefaultMetric OBJECT-TYPE
    SYNTAX   INTEGER ( 0..15 )
    ACCESS   read-write
    STATUS   mandatory
    DESCRIPTION
        "This variable indicates the metric that is to
        be used for the default route entry in RIP updates
        originated on this interface.  A value of zero
        indicates that no default route should be
        originated; in this case, a default route via
        another router may be propagated."
    ::= { rdwrRip2IfConfEntry 7 }
 
rdwrRip2IfConfStatus OBJECT-TYPE
    SYNTAX   INTEGER { 
                valid (1), 
				invalid (2) 
             }
    ACCESS   read-write
    STATUS   mandatory
    DESCRIPTION
        "Writing invalid has  the  effect  of  deleting
        this interface."
--  DEFVAL { valid }
    ::= { rdwrRip2IfConfEntry 8 }

rdwrRip2IfConfSrcAddress OBJECT-TYPE
    SYNTAX   IpAddress
    ACCESS   read-write
    STATUS   mandatory
    DESCRIPTION
       "The IP Address this system will use as a source
        address on this interface.  If it is a numbered
        interface, this MUST be the same value as
        rip2IfConfAddress.  On unnumbered interfaces,
        it must be the value of rip2IfConfAddress for
        some interface on the system."
	::= { rdwrRip2IfConfEntry 9 }
	 
rdwrRip2IfConfVirtualDis OBJECT-TYPE
    SYNTAX INTEGER
    ACCESS  read-write
    STATUS  mandatory
    DESCRIPTION
         "This variable defines the virtual number of hops assigned to
          the interface specified by rsIfIpAddrIndex. This enables
          fine-tuning of the RIP routing algorithm."
    DEFVAL  { 1 }
    ::=   { rdwrRip2IfConfEntry  10  }

rdwrRip2IfConfAutoSend OBJECT-TYPE
    SYNTAX  INTEGER {
       enable  (1),
       disable (2)
       }
    ACCESS  read-write
    STATUS  mandatory
    DESCRIPTION
         "This variable controls RIP automatic send behavior. If enabled
          and no routers were heard on the interface, RIP will only send
          default route with high metric. Otherwise RIP will send updates
          according to configuration. "
    DEFVAL  {disable}
     ::=   { rdwrRip2IfConfEntry  11  }

arpSpec                OBJECT IDENTIFIER ::= { ipSpec 4 }

rsArpDeleteTable OBJECT-TYPE
    SYNTAX  INTEGER
    ACCESS  read-write
    STATUS  mandatory
    DESCRIPTION
         "Setting this object to any not-null value has the effect of deleting
          all entries of the ARP table."
    ::= { arpSpec 1  }

rsArpInactiveTimeOut OBJECT-TYPE
    SYNTAX INTEGER
    ACCESS  read-write
    STATUS  mandatory
    DESCRIPTION
         "This variable defines the maximum time period (in second) that can
          pass between ARP requests concerning an entry in the ARP table.
          After this time period, the entry is deleted from the table."
    DEFVAL  { 60000 }
    ::= { arpSpec 2  }

rsArpProxy OBJECT-TYPE
    SYNTAX INTEGER {
       enable(1),
       disable(2)
    }
    ACCESS read-write
    STATUS mandatory
    DESCRIPTION
         "When ARP Proxy is enabled, the router can respond to
          ARP requests for nodes located on a different sub-net,
          provided they are it its network table. The router responds
          with its own MAC address.
          When ARP Proxy is disabled, the router responds only
          to ARP requests for its own IP addresses."
    DEFVAL  { disable }
    ::= { arpSpec 3  }

tftp     OBJECT IDENTIFIER ::= { ipSpec 5 }

rsTftpRetryTimeOut OBJECT-TYPE
    SYNTAX  INTEGER
    ACCESS  read-write
    STATUS  mandatory
    DESCRIPTION
        " General Retransmission time-out value (seconds) "
    DEFVAL  { 15 }
    ::= { tftp 1 }

rsTftpTotalTimeOut OBJECT-TYPE
    SYNTAX  INTEGER
    ACCESS  read-write
    STATUS  mandatory
    DESCRIPTION
        " Total Retransmission time-out value (seconds) "
    DEFVAL  { 60 }
    ::= { tftp 2 }

rsSendConfigFile OBJECT-TYPE
    SYNTAX DisplayString
    ACCESS  read-write
    STATUS  mandatory
    DESCRIPTION
        "The file name include path where the Router Server will put the full
         configuration. The default destination address will be the sender
         address."
    ::= { tftp 3 }

rsGetConfigFile OBJECT-TYPE
    SYNTAX DisplayString
    ACCESS  read-write
    STATUS  mandatory
    DESCRIPTION
        "The file name include path where the Router Server will get the
         configuration. The default source address will be the sender address."
    ::= { tftp 4 }

rsLoadSoftware OBJECT-TYPE
    SYNTAX DisplayString
    ACCESS  read-write
    STATUS  mandatory
    DESCRIPTION
        "The file name include path where the Router Server will get the
         software. The source address will the sender address."
    ::= { tftp 5 }
    
rsFileServerAddress OBJECT-TYPE
    SYNTAX  IpAddress
    ACCESS  read-write
    STATUS  mandatory
    DESCRIPTION
        "The IP address of the configuration / sw server."
        ::= { tftp 6 }

rsGetConfigFileAppend OBJECT-TYPE
    SYNTAX DisplayString
    ACCESS  read-write
    STATUS  mandatory
    DESCRIPTION
        "The file name include path where the Router Server will get the
         configuration commands file. The default source address will be the sender address."
	::= { tftp 8 }

rsGetConfigFileAppendReboot OBJECT-TYPE
    SYNTAX DisplayString
    ACCESS  read-write
    STATUS  mandatory
    DESCRIPTION
        "The file name include path where the Router Server will get the
         configuration commands file. The default source address will be the sender address."
	::= { tftp 9 }
	
rsGetConfigErrorLog OBJECT-TYPE
    SYNTAX DisplayString
    ACCESS  read-write
    STATUS  mandatory
    DESCRIPTION
        "The file name include path where the Router Server will get the
         configuration. The default source address will be the sender address."
    ::= { tftp 10 }

rsSendConfigFileBer OBJECT-TYPE
    SYNTAX DisplayString
    ACCESS  read-write
    STATUS  mandatory
    DESCRIPTION
        "The file name include path where the device puts the full configuration
	in BER format. The default destination address will be the sender address."
    ::= { tftp 11 }
    
rsIncludePrivateKeys OBJECT-TYPE
    SYNTAX FeatureStatus
    ACCESS read-write
    STATUS mandatory
    DESCRIPTION
        "Flags whether the configuration will include private keys."
    DEFVAL {disable}
    ::= { tftp 12 }

rsGetConfigFileType OBJECT-TYPE
    SYNTAX  INTEGER {
        regular (0),

-- active-active and active-backup are deprecated. They have been replaced by for-peer.
        active-active (1),
        active-backup (2),
        for-peer (3)
       }
    ACCESS read-write
    STATUS mandatory
    DESCRIPTION
        "Type of configuration to be downloaded."
    DEFVAL {regular}
    ::= { tftp 13 }

ipRedundancy    OBJECT IDENTIFIER ::= { ipSpec 6 }

ipRedundAdminStatus OBJECT-TYPE
    SYNTAX  INTEGER {
        enable(1),
        disable(2),
        vrrp(3)
       }
    ACCESS  read-write
    STATUS  mandatory
    DESCRIPTION
     "This variable controls the IP Redundancy method in the device.
      In case the value is enable, it means the ARP redundancy mechanism
      is running .If the value is vrrp, it means the former redundancy
      mechanism is disabled, and the vrrp mechanism is enabled.
      If the value is disable, both redundancy methods are disabled  "
    DEFVAL {disable }
    ::= { ipRedundancy 1 }

ipRedundOperStatus   OBJECT-TYPE
    SYNTAX INTEGER {
       active(1),
       inactive(2)
    }
    ACCESS  read-only
    STATUS  mandatory
    DESCRIPTION
        " obsolete "
    DEFVAL  {inactive}
    ::= { ipRedundancy 2 }

ipRedundRoutersTable OBJECT-TYPE
   SYNTAX SEQUENCE OF IpRedundRoutersEntry
   ACCESS not-accessible
   STATUS mandatory
   DESCRIPTION
    "List of IP addresses backed up by this router."
     ::= {ipRedundancy 3 }

ipRedundRoutersEntry  OBJECT-TYPE
   SYNTAX IpRedundRoutersEntry
   ACCESS not-accessible
   STATUS mandatory
   DESCRIPTION
       " The row definition for this table."
   INDEX {ipRedundRoutersIfAddr, ipRedundRoutersMainRouterAddr}
   ::= {ipRedundRoutersTable  1 }

IpRedundRoutersEntry ::= SEQUENCE {
      ipRedundRoutersIfAddr          IpAddress,
      ipRedundRoutersMainRouterAddr  IpAddress,
      ipRedundRoutersOperStatus      INTEGER,
      ipRedundRoutersPollInterval    INTEGER,
      ipRedundRoutersTimeout         INTEGER,
      ipRedundRoutersStatus          INTEGER
  }

ipRedundRoutersIfAddr OBJECT-TYPE
   SYNTAX IpAddress
   ACCESS read-only
   STATUS mandatory
   DESCRIPTION
    "The Ip address of the IP interface on which the redundancy feature
     is operational."
     ::=  { ipRedundRoutersEntry  1}

ipRedundRoutersMainRouterAddr OBJECT-TYPE
   SYNTAX IpAddress
   ACCESS read-only
   STATUS mandatory
   DESCRIPTION
    "The Ip address of the polled main router."
     ::=  { ipRedundRoutersEntry 2}

ipRedundRoutersOperStatus OBJECT-TYPE
   SYNTAX INTEGER { active(1), inactive(2) }
   ACCESS read-only
   STATUS mandatory
   DESCRIPTION
    "If active, the main router is considered inoperational and the IP
    interface operates as its backup."
     ::=  { ipRedundRoutersEntry 3 }

ipRedundRoutersPollInterval OBJECT-TYPE
   SYNTAX INTEGER
   ACCESS read-write
   STATUS mandatory
   DESCRIPTION
    "Polling interval for this router (in seconds). If 0 the router is not
     polled."
     DEFVAL  { 3 }
     ::=  { ipRedundRoutersEntry 4 }

ipRedundRoutersTimeout OBJECT-TYPE
   SYNTAX INTEGER
   ACCESS read-write
   STATUS mandatory
   DESCRIPTION
    "Interval in seconds during which the backed-up router must signal.
     If it does not signal, it is considered inoperational and the IP
     interface starts operating as backup."
     DEFVAL  { 12 }
     ::=  { ipRedundRoutersEntry  5}

ipRedundRoutersStatus OBJECT-TYPE
   SYNTAX INTEGER {
     active(1),
     notInService(2),
     notReady(3),
     createAndGo(4),
     createAndWait(5),
     destroy(6)
     }
   ACCESS read-write
   STATUS mandatory
   DESCRIPTION
    "Entry status"
     ::=  { ipRedundRoutersEntry 6}

rdwrRedunForceDownPorts OBJECT-TYPE
   SYNTAX INTEGER  (0..60)
   ACCESS  read-write
   STATUS  mandatory
   DESCRIPTION
      "the time that the forced ports will be electrically down. The value 0 means that the feature is disabled"
   DEFVAL  { 0 }
    ::=  {ipRedundancy 4 }

    
rdwrRedundancyInfoTable OBJECT-TYPE
    SYNTAX SEQUENCE OF RdwrRedundancyInfoEntry
    ACCESS not-accessible
    STATUS mandatory
    DESCRIPTION
      "Row holding the device redundancy information."
    ::=  {ipRedundancy 5 }

rdwrRedundancyInfoEntry OBJECT-TYPE
  SYNTAX RdwrRedundancyInfoEntry
  ACCESS not-accessible
  STATUS mandatory
  DESCRIPTION
    "Row definition for the table."
  INDEX { rdwrRedundancyInfoIdx }
  ::= { rdwrRedundancyInfoTable 1 }

RdwrRedundancyInfoEntry ::= SEQUENCE {
  rdwrRedundancyInfoIdx              INTEGER,
  rdwrRedundancyInfoInterface        INTEGER,  
  rdwrRedundancyInfoVRID             INTEGER,
  rdwrRedundancyInfoMode             INTEGER,
  rdwrRedundancyInfoMyAddress        IpAddress,
  rdwrRedundancyInfoNeighborAddress  IpAddress,
  rdwrRedundancyInfoStatus           INTEGER  
}

rdwrRedundancyInfoIdx OBJECT-TYPE
  SYNTAX INTEGER
  ACCESS read-only
  STATUS mandatory
  DESCRIPTION
    "The entry index. Starting from 1"
  ::= { rdwrRedundancyInfoEntry 1 }

rdwrRedundancyInfoInterface OBJECT-TYPE
  SYNTAX  INTEGER 
  ACCESS read-only
  STATUS mandatory
  DESCRIPTION
    "The entry attached interface"
  ::= { rdwrRedundancyInfoEntry 2 }
 
rdwrRedundancyInfoVRID OBJECT-TYPE
  SYNTAX  INTEGER 
  ACCESS read-only
  STATUS mandatory
  DESCRIPTION
    "Supporting VRRP, the entry indicates the entry VRID"
  ::= { rdwrRedundancyInfoEntry 3 }

rdwrRedundancyInfoMode OBJECT-TYPE
  SYNTAX  INTEGER {
    arp(1),
    not-used(2),
    vrrp(3)
  }
  ACCESS read-only
  STATUS mandatory
  DESCRIPTION
    "This variable indicates the IP Redundancy method in the device"
  ::= { rdwrRedundancyInfoEntry 4 }

rdwrRedundancyInfoMyAddress OBJECT-TYPE
  SYNTAX  IpAddress 
  ACCESS read-only
  STATUS mandatory
  DESCRIPTION
    "The entry indicates the device interfece address"
  ::= { rdwrRedundancyInfoEntry 5 }
    
rdwrRedundancyInfoNeighborAddress OBJECT-TYPE
  SYNTAX  IpAddress 
  ACCESS read-only
  STATUS mandatory
  DESCRIPTION
    "Acting as backup, the entry indicates the master associated address "
  ::= { rdwrRedundancyInfoEntry 6 }

rdwrRedundancyInfoStatus OBJECT-TYPE
   SYNTAX  INTEGER {
        active(1),
        backup(2)
  }
  ACCESS read-only
  STATUS mandatory
  DESCRIPTION
    "The redundancy entry status "
  ::= { rdwrRedundancyInfoEntry 7 }
    
    
    
ipRouteLeaking    OBJECT IDENTIFIER ::= { ipSpec 7 }

ipLeakStaticToRip   OBJECT-TYPE
    SYNTAX  INTEGER {
       enable  (1),
       disable (2)
       }
    ACCESS  read-write
    STATUS  mandatory
    DESCRIPTION
        "This parameter controls leaking (redistribution) of static routes
         to RIP. When enabled, all routes inserted to the IP routing table
         via SNMP are advertised into RIP."
    DEFVAL  {enable}
    ::= { ipRouteLeaking 1 }

ipLeakStaticToOspf   OBJECT-TYPE
    SYNTAX  INTEGER {
       enable  (1),
       disable (2)
       }
    ACCESS  read-write
    STATUS  mandatory
    DESCRIPTION
        "This parameter controls leaking (redistribution) of static routes
         into OSPF. When enabled, all routes inserted to the IP routing table
         via SNMP are advertised into OSPF as external routes."
    DEFVAL  {enable}
    ::= { ipRouteLeaking 2 }

ipLeakOspfToRip   OBJECT-TYPE
    SYNTAX  INTEGER {
       enable  (1),
       disable (2)
       }
    ACCESS  read-write
    STATUS  mandatory
    DESCRIPTION
        "This parameter controls leaking (redistribution) of routes
         from OSPF to RIP. If enabled, all routes learned via OSPF
         are advertised into RIP."
    DEFVAL  {disable}
    ::= { ipRouteLeaking 3 }

ipLeakRipToOspf   OBJECT-TYPE
    SYNTAX  INTEGER {
       enable  (1),
       disable (2)
       }
    ACCESS  read-write
    STATUS  mandatory
    DESCRIPTION
        "This parameter controls leaking (redistribution) of routes
         from RIP to OSPF. If enabled, all routes learned via RIP
         are advertised into OSPF as external routes."
    DEFVAL  {disable}
    ::= { ipRouteLeaking 4 }

ipLeakExtDirectToOspf   OBJECT-TYPE
    SYNTAX  INTEGER {
       enable  (1),
       disable (2)
       }
    ACCESS  read-write
    STATUS  mandatory
    DESCRIPTION
        "This parameter controls leaking (redistribution) into OSPF of
         direct routes external to OSPF, i.e. routes to local network
         corresponding to IP interfaces on which OSPF is disabled.
         When enabled, all such direct routes are advertised into OSPF
         as external routes."
    DEFVAL  {enable}
    ::= { ipRouteLeaking 5 }

ipLeakOverrideOSPFLeakonFailure OBJECT-TYPE
    SYNTAX  INTEGER {
      enable(1),
      disable(2)
    }
    ACCESS  read-write
    STATUS  mandatory
    DESCRIPTION
      "In case of OSPF:
	don't advertise the device as next hop router in case all load balanced devices are down."
        ::=  { ipRouteLeaking 6}

ipLeakAdvertiseOSPFAccordingtoPortRules OBJECT-TYPE
    SYNTAX  INTEGER {
      enable(1),
      disable(2)
    }
    ACCESS  read-write
    STATUS  mandatory
    DESCRIPTION
	"in OPSF: advertise routing according to the port rules"
        ::=  { ipRouteLeaking 7 }

ipRipFilter    OBJECT IDENTIFIER ::= { ipSpec 8 }

-- Global RIP filter is defined per IP router.

rsIpRipFilterGlbTable OBJECT-TYPE
   SYNTAX SEQUENCE OF RsIpRipFilterGlbEntry
   ACCESS  not-accessible
   STATUS  mandatory
   DESCRIPTION
      "The table of RIP global filters per IP router."
::= { ipRipFilter 1 }

rsIpRipFilterGlbEntry  OBJECT-TYPE
SYNTAX    RsIpRipFilterGlbEntry
ACCESS    not-accessible
STATUS    mandatory
DESCRIPTION
      " An entry in the RIP global filter table "
INDEX  { rsIpRipFilterGlbType,
         rsIpRipFilterGlbNumber }
::= { rsIpRipFilterGlbTable 1 }

RsIpRipFilterGlbEntry  ::= SEQUENCE {
      rsIpRipFilterGlbType            INTEGER,
      rsIpRipFilterGlbNumber          INTEGER,
      rsIpRipFilterGlbStatus          INTEGER,
      rsIpRipFilterGlbIpAddr          IpAddress,
      rsIpRipFilterGlbNetworkMaskBits INTEGER,
      rsIpRipFilterGlbMatchBits       INTEGER,
      rsIpRipFilterGlbAction          INTEGER
}

rsIpRipFilterGlbType  OBJECT-TYPE
SYNTAX INTEGER  {
    input(1),
    output(2)
}
ACCESS  read-only
STATUS  mandatory
DESCRIPTION
    " Type of filter - input/output "
::= {rsIpRipFilterGlbEntry 1}

rsIpRipFilterGlbNumber OBJECT-TYPE
SYNTAX  INTEGER
ACCESS  read-only
STATUS  mandatory
DESCRIPTION
   " Number of RIP filter. "
::= {rsIpRipFilterGlbEntry  2}

rsIpRipFilterGlbStatus OBJECT-TYPE
SYNTAX INTEGER  {
    valid (1),
    invalid (2),
    underCreation (3)
}
ACCESS read-write
STATUS mandatory
DESCRIPTION
   " The validity of this entry. Setting this value to invalid deletes
   the entry, and the entry may be actualy removed from the table."
DEFVAL  { valid }
::= {rsIpRipFilterGlbEntry 3}

rsIpRipFilterGlbIpAddr OBJECT-TYPE
SYNTAX IpAddress
ACCESS  read-write
STATUS  mandatory
DESCRIPTION
   " network prefix IP address, as in the forwarding table. "
DEFVAL {'00000000'H}
::= {rsIpRipFilterGlbEntry  4}

rsIpRipFilterGlbNetworkMaskBits  OBJECT-TYPE
SYNTAX  INTEGER
ACCESS  read-write
STATUS  mandatory
DESCRIPTION
   " the number of bits in the IP Network mask, called network-prefix-length
   in Router Requirements terminology. for example: the value 16 means
   mask 255.255.0.0 "
   DEFVAL {0}
::= {rsIpRipFilterGlbEntry 5}

rsIpRipFilterGlbMatchBits  OBJECT-TYPE
SYNTAX  INTEGER
ACCESS  read-write
STATUS  mandatory
DESCRIPTION
   " the number of bits to match in the Network IP address. A value
   smaller than 32 defines a wildcard. for example: the value 8 means
   all routes whose leftmost 8 bits are equal to those of the network IP
   address. If this variable has a value other than 32, than
   rsIpRipFilterGlbNetworkMaskBits must be 0 and is ignored. "
   DEFVAL {32}
::= {rsIpRipFilterGlbEntry 6}

rsIpRipFilterGlbAction OBJECT-TYPE
SYNTAX INTEGER {
   deny(1),
   permit(2)
}
ACCESS  read-write
STATUS  mandatory
DESCRIPTION
   " Filter action - permit/deny for this network"
DEFVAL { permit }
::= {rsIpRipFilterGlbEntry  7}


-- Intf RIP filter is defined per IP Interface

rsIpRipFilterLclTable OBJECT-TYPE
SYNTAX SEQUENCE OF RsIpRipFilterLclEntry
ACCESS  not-accessible
STATUS  mandatory
DESCRIPTION
   "Table of input/output  RIP filters used per IP Interface."
::= { ipRipFilter 2 }

rsIpRipFilterLclEntry  OBJECT-TYPE
SYNTAX RsIpRipFilterLclEntry
ACCESS not-accessible
STATUS mandatory
DESCRIPTION
   " An entry in the Intf RIP filter table"
INDEX  {rsIpRipFilterLclIpIntf,
        rsIpRipFilterLclType,
        rsIpRipFilterLclNumber}
::= { rsIpRipFilterLclTable 1 }

RsIpRipFilterLclEntry  ::= SEQUENCE {
      rsIpRipFilterLclIpIntf          IpAddress,
      rsIpRipFilterLclType            INTEGER,
      rsIpRipFilterLclNumber          INTEGER,
      rsIpRipFilterLclStatus          INTEGER,
      rsIpRipFilterLclIpAddr          IpAddress,
      rsIpRipFilterLclNetworkMaskBits INTEGER,
      rsIpRipFilterLclMatchBits       INTEGER,
      rsIpRipFilterLclAction          INTEGER
}

rsIpRipFilterLclIpIntf  OBJECT-TYPE
SYNTAX IpAddress
ACCESS  read-only
STATUS  mandatory
DESCRIPTION
   " The IP address identifying the RIP interface for this filter.
   This value corresponds to rsIpAdEntAddr. "
::= {rsIpRipFilterLclEntry 1}


rsIpRipFilterLclType  OBJECT-TYPE
SYNTAX INTEGER  {
   input(1),
   output(2)
}
ACCESS read-only
STATUS mandatory
DESCRIPTION
   " Type of filter - input/output "
::= {rsIpRipFilterLclEntry 2}

rsIpRipFilterLclNumber OBJECT-TYPE
SYNTAX INTEGER
ACCESS read-only
STATUS mandatory
DESCRIPTION
   " Number of RIP filter for this Interface"
::= {rsIpRipFilterLclEntry  3}

rsIpRipFilterLclStatus   OBJECT-TYPE
SYNTAX INTEGER  {
   valid (1),
   invalid (2),
   underCreation (3)
}
ACCESS read-write
STATUS mandatory
DESCRIPTION
   " The validity of this entry. Setting this value to invalid deletes
   the entry, and the entry may be actualy removed from the table."
DEFVAL  { valid }
::= {rsIpRipFilterLclEntry  4}

rsIpRipFilterLclIpAddr OBJECT-TYPE
SYNTAX IpAddress
ACCESS  read-write
STATUS  mandatory
DESCRIPTION
   " network prefix IP address, as in the forwarding table. "
DEFVAL {'00000000'H}
::= {rsIpRipFilterLclEntry  5}

rsIpRipFilterLclNetworkMaskBits  OBJECT-TYPE
SYNTAX  INTEGER
ACCESS  read-write
STATUS  mandatory
DESCRIPTION
   " the number of bits in the IP Network mask, called network-prefix-length
   in Router Requirements terminology. for example: the value 16 means
   mask 255.255.0.0 "
DEFVAL {0}
::= {rsIpRipFilterLclEntry 6}

rsIpRipFilterLclMatchBits  OBJECT-TYPE
SYNTAX  INTEGER
ACCESS  read-write
STATUS  mandatory
DESCRIPTION
   " the number of bits to match in the Network IP address. A value
   smaller than 32 defines a wildcard. for example: the value 8 means
   all routes whose leftmost 8 bits are equal to those of the network IP
   address. If this variable has a value other than 32, than
   rsIpRipFilterLclNetworkMaskBits must be 0 and is ignored. "
DEFVAL {32}
::= {rsIpRipFilterLclEntry 7}

rsIpRipFilterLclAction OBJECT-TYPE
SYNTAX INTEGER  {
   deny(1),
   permit(2)
}
ACCESS read-write
STATUS mandatory
DESCRIPTION
   " Filter action - permit/deny "
DEFVAL { permit }
::= {rsIpRipFilterLclEntry  8}


rsRipEnable OBJECT-TYPE
    SYNTAX  INTEGER {
      enable(1),
      disable(2)
   }
    ACCESS  read-write
    STATUS  mandatory
    DESCRIPTION
           "Enables or disables RIP."
    ::=  { ipSpec 9 }

lreBoxAgentIP OBJECT-TYPE
    SYNTAX IpAddress
    ACCESS  read-write
    STATUS  mandatory
    DESCRIPTION
           ""
    ::=  { ipSpec 10 }

--
-- Proprietary IPv6-supporting Adress table MIB
--
ipIfTable OBJECT-TYPE
    SYNTAX  SEQUENCE  OF IpIfEntry
    ACCESS  not-accessible
    STATUS  mandatory
    DESCRIPTION
       "This table is parralel to IPv6 MIB (RFC4293) ipIfTable, and is 
used to

        add/delete entries to/from that table. In addition it contains
        private objects."
    ::=  { ipSpec 11 }

	
ipIfEntry   OBJECT-TYPE
    SYNTAX  IpIfEntry
    ACCESS  not-accessible
    STATUS  mandatory
    DESCRIPTION
            "The addressing information for one of this
            entity's IP addresses."
    INDEX  {ipIfAddr}
    ::=  {ipIfTable 1 }    
	
IpIfEntry ::= SEQUENCE {
        ipIfAddr                        Ipv6Address,
	ipIfPrefix                      INTEGER,
	ipIfIndex                       INTEGER,
	ipIfFwdBroadcast                INTEGER,
	ipIfBcastAddr                   INTEGER,
	ipIfVlanTag                     INTEGER,
	ipIfLabel                       DisplayString, 
	ipIfEntryStatus                 RowStatus,
	ipIfBackupAddr                  Ipv6Address
    }
	
ipIfAddr OBJECT-TYPE
    SYNTAX  Ipv6Address
    ACCESS  read-only
    STATUS  mandatory
    DESCRIPTION
            "The IP address to which this entry's addressing
            information pertains."
    ::= { ipIfEntry 1 }
	
ipIfPrefix OBJECT-TYPE
    SYNTAX  INTEGER (0..128)
    ACCESS  read-write
    STATUS  mandatory
    DESCRIPTION
            "The IP address's prefix."
    ::= { ipIfEntry 2 }

ipIfIndex OBJECT-TYPE
    SYNTAX  INTEGER
    ACCESS  read-write
    STATUS  mandatory
    DESCRIPTION
            "The index value which uniquely identifies the
            interface to which this entry is applicable.  The
            interface identified by a particular value of this
            index is the same interface as identified by the
            same value of ifIndex."
    ::= { ipIfEntry 3 }	
	
ipIfFwdBroadcast OBJECT-TYPE
    SYNTAX INTEGER {
       enable(1),
       disable(2)
       }
    ACCESS  read-write
    STATUS  mandatory
    DESCRIPTION
        " This variable controls forwarding of IP (sub)net-directed
          broadcasts destined for an attached sub(net). "
    DEFVAL  { enable }
    ::=   { ipIfEntry 4}

ipIfBcastAddr OBJECT-TYPE
    SYNTAX INTEGER (0..1)
    ACCESS read-write
    STATUS mandatory
    DESCRIPTION
        " Indicates how the host part of ip subnet broadcast messages will be
          filled:
           0 - host part will be filled by 0
           1 - host part will be filled by 1."
    ::=   { ipIfEntry 5 }	

ipIfVlanTag OBJECT-TYPE
    SYNTAX  INTEGER
    ACCESS  read-write
    STATUS  mandatory
    DESCRIPTION
            "The vlan Tag value that represent this ip interface
             this filed include both vlna tag and vlan priority "
    ::= { ipIfEntry 6 }
	

ipIfLabel OBJECT-TYPE
    SYNTAX DisplayString (SIZE(0..20))
    ACCESS  read-write
    STATUS  mandatory
    DESCRIPTION
            "User textual dscription of the ip interface."
    ::= {ipIfEntry 7}

ipIfEntryStatus OBJECT-TYPE
   SYNTAX  RowStatus
   ACCESS  read-write
   STATUS  mandatory
   DESCRIPTION
         "It is used to delete an entry"
    ::=   { ipIfEntry 8 }
ipIfBackupAddr OBJECT-TYPE
    SYNTAX  Ipv6Address
    ACCESS  read-write
    STATUS  mandatory
    DESCRIPTION
            "The ip address of the peer address. It is used by CDE and High Availability."
    ::= { ipIfEntry 9 }

ipSpecRouteTable OBJECT-TYPE
   SYNTAX     SEQUENCE OF IpSpecRouteEntry
   ACCESS     not-accessible 
   STATUS     mandatory
   DESCRIPTION
          "This entity's IP Routing table."
   ::= { ipSpec 12 }

ipSpecRouteEntry OBJECT-TYPE
   SYNTAX     IpSpecRouteEntry
   ACCESS     not-accessible
   STATUS     mandatory
   DESCRIPTION
          "A particular route to a particular destination, under a
           particular policy (as reflected in the ipSpecRoutePolicy object).

           Dynamically created rows will survive an agent reboot.

           Implementers need to be aware that if the total number
           of elements (octets or sub-identifiers) in
           ipSpecRouteDest, and
           ipSpecRouteNextHop exceeds 111, then OIDs of column
           instances in this table will have more than 128 sub-
           identifiers and cannot be accessed using SNMPv1,
           SNMPv2c, or SNMPv3."
   INDEX {
       ipSpecRouteDest,
       ipSpecRoutePfxLen,
       ipSpecRouteNextHop
       }
   ::= { ipSpecRouteTable 1 }

IpSpecRouteEntry ::= SEQUENCE {
       ipSpecRouteDest         Ipv6Address,
       ipSpecRoutePfxLen       INTEGER,
       ipSpecRouteNextHop      Ipv6Address,
       ipSpecRoutePort         INTEGER,
       ipSpecRouteMetric       INTEGER,
       ipSpecRouteLabel        DisplayString(SIZE(0..20)),
       ipSpecRouteStatus       RowStatus
   }

ipSpecRouteDest OBJECT-TYPE
   SYNTAX     Ipv6Address
   ACCESS     read-write
   STATUS     mandatory
   DESCRIPTION
          "The destination IP address of this route.

           The values for the index objects ipSpecRouteDest and
           ipSpecRoutePfxLen must be consistent.  When the value
           of ipSpecRouteDest (excluding the zone index, if one
           is present) is x, then the bitwise logical-AND
           of x with the value of the mask formed from the
           corresponding index object ipSpecRoutePfxLen MUST be
           equal to x.  If not, then the index pair is not
           consistent and an inconsistentName error must be
           returned on SET or CREATE requests."

   ::= { ipSpecRouteEntry 1 }

ipSpecRoutePfxLen OBJECT-TYPE
   SYNTAX  INTEGER (0..128)
   ACCESS     read-write
   STATUS     mandatory
   DESCRIPTION
          "The prefix length. For IPv4 must be <=32, for IPv6 <= 128.

           The values for the index objects ipSpecRouteDest and
           ipSpecRoutePfxLen must be consistent. For IPv4 must be 
           <=32, for IPv6 <= 128. If not, then the index pair is not
           consistent and an inconsistentName error must be
           returned on SET or CREATE requests."

   ::= { ipSpecRouteEntry 2 }

ipSpecRouteNextHop OBJECT-TYPE
   SYNTAX     Ipv6Address
   ACCESS     read-write
   STATUS     mandatory
   DESCRIPTION
          "On remote routes, the address of the next system en
           route.  For non-remote routes, a zero length string.

           The type of this address is determined by the value of
           the ipSpecRouteNextHopType object."
   ::= { ipSpecRouteEntry 3 }


ipSpecRouteMetric OBJECT-TYPE
   SYNTAX     INTEGER (1..9999)
   ACCESS read-write
   STATUS     mandatory
   DESCRIPTION
          "The primary routing metric for this route.  The
           semantics of this metric are determined by the routing-
           protocol specified in the route's ipSpecRouteProto
           value.  The default value is 1."
   DEFVAL { 1 }
   ::= { ipSpecRouteEntry 4 }

ipSpecRoutePort OBJECT-TYPE
   SYNTAX     INTEGER
   ACCESS     read-only
   STATUS     mandatory
   DESCRIPTION
          "The Port value that identifies the local port/interface
           through which the next hop of this route should be
           reached. "
   ::= { ipSpecRouteEntry 5 }

ipSpecRouteLabel OBJECT-TYPE
   SYNTAX     DisplayString(SIZE(0..20))
   ACCESS     read-only
   STATUS     mandatory
   DESCRIPTION
          "User defined data."
   ::= { ipSpecRouteEntry 6 }

ipSpecRouteStatus OBJECT-TYPE
   SYNTAX     RowStatus
   ACCESS read-write
   STATUS     mandatory
   DESCRIPTION
          "The row status variable, used according to row
           installation and removal conventions.

           A row entry cannot be modified when the status is
           marked as active(1)."
   ::= { ipSpecRouteEntry 7 }

--
--	Neighbor Discovery table
--
ip6NetToMediaTable OBJECT-TYPE
   SYNTAX     SEQUENCE OF Ip6NetToMediaEntry
   ACCESS     not-accessible 
   STATUS     mandatory
   DESCRIPTION
          "This entity's ND table."
   ::= { ipSpec 13 }

ip6NetToMediaEntry   OBJECT-TYPE
    SYNTAX  Ip6NetToMediaEntry
    ACCESS  not-accessible
    STATUS  mandatory
    DESCRIPTION
            "The addressing information for one of this
            entity's ND addresses."
    INDEX  {ip6NetToMediaIfIndex, ip6NetToMediaNetAddress}
    ::=  {ip6NetToMediaTable 1 }    


Ip6NetToMediaEntry ::= SEQUENCE {
	ip6NetToMediaIfIndex		INTEGER,
	ip6NetToMediaPhysAddress	PhysAddress,
	ip6NetToMediaNetAddress 	Ipv6Address,
	ip6NetToMediaType 		INTEGER
	}

	
ip6NetToMediaIfIndex OBJECT-TYPE
    SYNTAX  INTEGER
    ACCESS  read-write
    STATUS  mandatory
    DESCRIPTION
            "The interface on which this entry's equivalence
                      is effective.  The interface identified by a
                      particular value of this index is the same
                      interface as identified by the same value of
                      ifIndex."
    ::= { ip6NetToMediaEntry 1 }

ip6NetToMediaPhysAddress OBJECT-TYPE
    SYNTAX  PhysAddress
    ACCESS  read-write
    STATUS  mandatory
    DESCRIPTION
            "The media-dependent `physical' address."
    ::= { ip6NetToMediaEntry 2 }

ip6NetToMediaNetAddress OBJECT-TYPE
    SYNTAX  Ipv6Address
    ACCESS  read-write
    STATUS  mandatory
    DESCRIPTION
            "The IpAddress corresponding to the media-
                      dependent `physical' address."
    ::= { ip6NetToMediaEntry 3 }

ip6NetToMediaType OBJECT-TYPE
              SYNTAX  INTEGER {
                          other(1),        -- none of the following
                          invalid(2),      -- an invalidated mapping
                          dynamic(3),
                          static(4)
                      }
              ACCESS  read-write
              STATUS  mandatory
              DESCRIPTION
                      "The type of mapping.

                      Setting this object to the value invalid(2) has
                      the effect of invalidating the corresponding entry
                      in the ipNetToMediaTable.  That is, it effectively
                      dissasociates the interface identified with said
                      entry from the mapping identified with said entry.
                      It is an implementation-specific matter as to
                      whether the agent removes an invalidated entry
                      from the table.  Accordingly, management stations
                      must be prepared to receive tabular information
                      from agents that corresponds to entries not
                      currently in use.  Proper interpretation of such
                      entries requires examination of the relevant
                      ipNetToMediaType object."
              ::= { ip6NetToMediaEntry 4 }


ndSpec                OBJECT IDENTIFIER ::= { ipSpec 14 }	

rsNetNdInactiveTimeOut OBJECT-TYPE
    SYNTAX INTEGER
    ACCESS  read-write
    STATUS  mandatory
    DESCRIPTION
         "This variable defines the maximum time period (in second) that can
          pass between Neighbor-discovery requests concerning an entry in the Neighbor-discovery table.
          After this time period, the entry is deleted from the table.
		  This timer is common for both IPv6 Neighbor-discovery and IPv4 ARP."
    DEFVAL  { 60000 }
    ::= { ndSpec 1  }

virtualLan  OBJECT IDENTIFIER ::= { rnd 27 }

--
--  virtualLanTable
--
virtualLanTable  OBJECT-TYPE
   SYNTAX  SEQUENCE OF VirtualLanEntry
   ACCESS  not-accessible
   STATUS  mandatory
   DESCRIPTION
         "An entry of this table specifies an new ifIndex with a type of
          propVirtual(53)."
   ::= { virtualLan 1 }

virtualLanEntry OBJECT-TYPE
   SYNTAX  VirtualLanEntry
   ACCESS  not-accessible
   STATUS  mandatory
   DESCRIPTION
         "A list of information for each virtual LAN."
   INDEX  { vlIfIndex}
   ::= { virtualLanTable 1 }

VirtualLanEntry   ::= SEQUENCE {
     vlIfIndex          INTEGER,
     vlProto            INTEGER,
     vlAutoConfigEnable TruthValue,
     vlStatus           RowStatus,
     vlType             INTEGER
   }

vlIfIndex OBJECT-TYPE
   SYNTAX  INTEGER
   ACCESS  read-write
   STATUS  mandatory
   DESCRIPTION
         "An logical interface number, corresponded this VL"
   ::= { virtualLanEntry 1 }

vlProto  OBJECT-TYPE
   SYNTAX  INTEGER {
      other(1),
      ip(2),
      ipmulticast(3),
      ipxRaw(4),
      ipxET(5),
      ipxLLC(6),
      ipxSNAP(7),
      decNET(8),
      decLAT(9),
      netBios(10),
      appleTalk(11),
      xns(12),
      sna(13),
      userDefined(14)
      }
   ACCESS  read-write
   STATUS  mandatory
   DESCRIPTION
         "The protocol, supported by this VL. The meanings of the values are:
      other: none of the following. This VL includes any protocol except the
             following protocols. It  is a bridging VL. RS relies on
             a third-party router to exchange traffic between nodes on different
             virtual LANs of this type.
      IP:    This is a routing VL, RS will route between nodes on
             different virtual LANs.
      IPmulticast: RS will broadcast the message to all  the VL's ports. Used for
             video-conferencing applications.
      ipxRaw: This is a Routing VL, RS will route between nodes on
             different virtual LANs.
      ipxET: This is a routing VL, RS will route between nodes on
             different virtual LANs.
      ipxLLC: This is a routing VL, RS will route between nodes on
             different virtual LANs.
      ipxSNAP: This is a routing VL, RS will route between nodes on
             different virtual LANs.
      decNET: This is a bridging VL, RS relies on a third-party router
             to exchange traffic between nodes on different DECnet virtual
             LANs of this type.
      netBios: This is a Bridging VL, RS relies on a third-party router
             to exchange traffic between nodes on different NetBIOS virtual
             LANs of this type.
      appleTalk: This is a bridging VL, RS relies on a third-party router
             to exchange traffic between nodes on different AppleTalk virtual
             LANs of this type."
   ::= { virtualLanEntry 2 }

vlAutoConfigEnable  OBJECT-TYPE
   SYNTAX  TruthValue
   ACCESS  read-write
   STATUS  mandatory
   DESCRIPTION
         "It is used only in the case of IP. The meanings of the values are:
      true(1):  Autolearning is used for this VL
      false(2): Autolearning isn't used for this VL from ports, specified in
                the table virtualLanAutoConfTable."
   ::= { virtualLanEntry 3 }

vlStatus  OBJECT-TYPE
   SYNTAX  RowStatus
   ACCESS  read-write
   STATUS  mandatory
   DESCRIPTION
         "It is used to delete an entry"
   ::= { virtualLanEntry 4 }

vlType OBJECT-TYPE
   SYNTAX INTEGER {
        regular(1),
        specBroadcast(2),
        specArpReq(3),
        specBroadcastAndUnicast(4),
        specArpReqAndUnicast(5)
        }
   ACCESS  read-write
   STATUS  mandatory
   DESCRIPTION
       "regular       - ordinary type
        specBroadcast - for switches that support VLANs as a set of ports and
                        only as a broadcast domain: broadcast frames do not
                        cross VLAN's bounders, but unicast frames may be
                        transmitted between different VLANs. Permits passing
                        of broadcast frames between Vgate's VLANs.
        specArpReq -    for switches that support VLANs as a set of ports and
                        only as a broadcast domain: broadcast frames do not
                        cross VLAN's bounders, but unicast frames may be
                        transmitted between different VLANs. Permits passing
                        of ARP request frames between Vgate's VLANs.
        specBroadcastAndUnicast -
                        for switches that support VLANs as a set of ports
                        but no frame crosses VLAN's bounders. Permits passing
                        of IP/ARP request broadcast and IP unicast frames
                        between Vgate's VLANs.
        specArpReqAndUnicast -
                        for switches that support VLANs as a set of ports
                        but no frame crosses VLAN's bounders. Permits passing
                        of ARP request broadcast and IP unicast frames between
                        Vgate's VLANs. This type can be used only for IP VLANs."
   ::= { virtualLanEntry 5 }

--
--   virtualLanPortsTable
--
virtualLanPortsTable  OBJECT-TYPE
   SYNTAX SEQUENCE OF VirtualLanPortEntry
   ACCESS  not-accessible
   STATUS  mandatory
   DESCRIPTION
         "For each VL (a ifIndex with a type of propVirtual(53)) an entry of  this
           table specifies a set of ports, which it contains."
   ::= { virtualLan 2 }

virtualLanPortEntry   OBJECT-TYPE
   SYNTAX  VirtualLanPortEntry
   ACCESS  not-accessible
   STATUS  mandatory
   DESCRIPTION
         "A entry of this table specifies a  VL and a port belonging to it"
   INDEX  { vLIfIndex, vLPortIfIndex}
   ::= { virtualLanPortsTable 1 }

VirtualLanPortEntry  ::= SEQUENCE {
     vLIfIndex      INTEGER,
     vLPortIfIndex  INTEGER,
     vLPortType     INTEGER,
     vLPortStatus   RowStatus
   }

vLIfIndex  OBJECT-TYPE
   SYNTAX  INTEGER
   ACCESS  read-write
   STATUS  mandatory
   DESCRIPTION
        "An logical interface number, corresponding to this VL"
   ::= { virtualLanPortEntry 1 }

vLPortIfIndex  OBJECT-TYPE
   SYNTAX  INTEGER
   ACCESS  read-write
   STATUS  mandatory
   DESCRIPTION
         "A physical port belonging to the VL specified by vlIfIndex."
   ::= { virtualLanPortEntry 2 }

vLPortType   OBJECT-TYPE
   SYNTAX  INTEGER {static(1), dynamic(2) }
   ACCESS  read-only
   STATUS  mandatory
   DESCRIPTION
         "static means configured by user dynamic means autoconfigured by the RS"
   ::= { virtualLanPortEntry 3}

vLPortStatus  OBJECT-TYPE
   SYNTAX  RowStatus
   ACCESS  read-write
   STATUS  mandatory
   DESCRIPTION
         "It is used to delete an entry"
   ::= { virtualLanPortEntry 4}

--
--   virtualLanAutoConfTable
--
virtualLanAutoConfTable  OBJECT-TYPE
   SYNTAX SEQUENCE OF VirtualLanAutoConfEntry
   ACCESS  not-accessible
   STATUS  mandatory
   DESCRIPTION
         "This table specifies per a routing protocol a set of ports, from which
           RS will automatically  learning VL in accordance with rules, defined
           by the protocol."
   ::= { virtualLan 3 }

virtualLanAutoConfEntry   OBJECT-TYPE
   SYNTAX  VirtualLanAutoConfEntry
   ACCESS  not-accessible
   STATUS  mandatory
   DESCRIPTION
       "One port, specified by vlAutoConfPortIfIndex, for which the RS will
        automatically  learn its VL in accordance with rules, defined
        by  the protocol specified in vlAutoConfProto."
   INDEX  {vlAutoConfPortIfIndex,
           vlAutoConfProto}
   ::= { virtualLanAutoConfTable 1 }

VirtualLanAutoConfEntry ::= SEQUENCE {
   vlAutoConfProto        INTEGER,
   vlAutoConfPortIfIndex  INTEGER,
   vlAutoConfStatus       RowStatus
   }
vlAutoConfPortIfIndex OBJECT-TYPE
   SYNTAX  INTEGER
   ACCESS  read-write
   STATUS  mandatory
   DESCRIPTION
         "Port on which the autoconfig option should be supported"
   ::= { virtualLanAutoConfEntry 1 }

vlAutoConfProto OBJECT-TYPE
   SYNTAX  INTEGER {
      ip(2)
      }
   ACCESS  read-only
   STATUS  mandatory
   DESCRIPTION
         "Protocol for which the autoconfig option is supported for the port
          specified by vlAutoConfPortIfIndex  "
   ::= {virtualLanAutoConfEntry 2 }

vlAutoConfStatus  OBJECT-TYPE
   SYNTAX  RowStatus
   ACCESS  read-write
   STATUS  mandatory
   DESCRIPTION
         "It is used to delete an entry"
   ::= { virtualLanAutoConfEntry 3 }

virtualLanAutoConfAgingTimeout  OBJECT-TYPE
   SYNTAX  INTEGER
   ACCESS  read-write
   STATUS  mandatory
   DESCRIPTION
         "The units of this MIB object is seconds.
          Its value can be either 0 or in range 10..65535 ."
   DEFVAL  { 3600 }
   ::= { virtualLan 4 }

virtualLanProtocolVlan  OBJECT IDENTIFIER ::= { virtualLan 5 }

virtualLanUserEtherType  OBJECT-TYPE
   SYNTAX OCTET STRING(SIZE(2))
   ACCESS  read-write
   STATUS  mandatory
   DESCRIPTION
         ""
   ::= { virtualLanProtocolVlan 1}

virtualLanUserMask  OBJECT-TYPE
   SYNTAX OCTET STRING(SIZE(2))
   ACCESS  read-write
   STATUS  mandatory
   DESCRIPTION
         ""
   ::= { virtualLanProtocolVlan 2}

--

rsConf  OBJECT IDENTIFIER ::= { rnd 28 }

-- The following MIB group is used by the Management/Configuration
-- station to configure the device interfaces,
-- physicals as well as virtuals Networks..
-- Each entry in the rsConfTable should have one of
-- the extended rsIfType.
-- It will also have a corresponding entry in the standard iftable.
-- The implementation uses these inputs to build the interface
-- layer of the device. The output is reflected in the
-- ifTable and ifStackTable which are implementation dependent.

RsIfType ::= INTEGER
--      STATUS  current
--       DESCRIPTION
--           "This type defines what type of sub-layer is used
--            in each entry of rsIfConfTable.
--            It should contain values from IANAifType
--            type for standard sub-layer, and values (starting from 500
--            decimal) for private sub-layers.
--            The values of ifType field in ifTable should be taken
--            from this type for ifTable entries which have full correlation
--            with entries in rsIfConfTable.
--            Other entries in ifTable should have other
--            ifType values (defined by other type) depend on the specific
--            implementation."
           {
            ppp(23),             -- From IANAifType
            frameRelay(32),      --     "
            virtualNet(500),
            rndWan(1000),        -- Rad/Rnd private
            cod(1001),               --      "
            backup(1002),         --      "
            fr1490(1003),          --      "
            b1isdn(1010),
            b2isdn(1011),
            unknown(1100)
           }


rsIfConfTable OBJECT-TYPE
   SYNTAX SEQUENCE OF RsIfConfEntry
   ACCESS  not-accessible
   STATUS  mandatory
   DESCRIPTION
        "This table enable the user to add interface  to the RS.
           RS will automatically  add the new interface to the interface Table "
   ::= { rsConf 1 }

rsIfConfEntry OBJECT-TYPE
       SYNTAX RsIfConfEntry
       ACCESS  not-accessible
       STATUS  mandatory
       DESCRIPTION
           "Each entry defines a configured interface."
       INDEX { rsIfConfIndex }
      ::= { rsIfConfTable 1 }


RsIfConfEntry ::= SEQUENCE {
   rsIfConfIndex  INTEGER,
   rsIfConfType   RsIfType,
   rsIfConfName   DisplayString,
   rsIfConfStatus RowStatus
      }
rsIfConfIndex OBJECT-TYPE
   SYNTAX  INTEGER
   ACCESS  read-only
   STATUS  mandatory
   DESCRIPTION
       "This variable uniquely identifies the interface.
       It is used as a cross reference in other system tables"
   ::= { rsIfConfEntry 1 }

rsIfConfType  OBJECT-TYPE
   SYNTAX  RsIfType
   ACCESS  read-write
   STATUS  mandatory
   DESCRIPTION
       "This variable identifies the type of the specific
       entry in the rsIfConfTable.
       This field is writable only at creation time
       (i.e., when value of status is underCreation)."
   ::= { rsIfConfEntry 2 }

rsIfConfName  OBJECT-TYPE
   SYNTAX  DisplayString
   ACCESS  read-write
   STATUS  mandatory
   DESCRIPTION
       "This variable provides a logical name to a specific entry in
       rsIfConfTable"
   ::= { rsIfConfEntry 3 }

rsIfConfStatus  OBJECT-TYPE
   SYNTAX  RowStatus
   ACCESS  read-write
   STATUS  mandatory
   DESCRIPTION
       "The status of the ConfigEntry.  The choices are those
       defined in SNMPv2-TC. Only: active, createAndWait, and destroy
       will be used.
       active - The conceptual row is available for use by the managed device.
       createAndWait - A new instance of a conceptual row is desired, but
       not to have it available for use by the managed device.
       destroy - Delete all instances associated with an existing conceptual row."
   ::= { rsIfConfEntry 4 }

rsTunning  OBJECT IDENTIFIER ::= { rnd 29 }

rsHighPriority OBJECT-TYPE
    SYNTAX INTEGER
    ACCESS  read-write
    STATUS  mandatory
    DESCRIPTION
      "This variable indicates the time interval the forwarding task inside the
      RS works in High Priority Mode."
    ::=  { rsTunning 1  }

rsLowPriority OBJECT-TYPE
    SYNTAX INTEGER
    ACCESS  read-write
    STATUS  mandatory
    DESCRIPTION
      "This variable indicates the time interval the forwarding task inside the
      RS works in Low Priority Mode."
    ::=  { rsTunning 2  }

rsDbgLevel OBJECT-TYPE
    SYNTAX INTEGER
    ACCESS  read-write
    STATUS  mandatory
    DESCRIPTION
      "This variable indicates the debug level the Router Server works.
       the range of this variable is 1..100 "
    ::=  { rsTunning 3  }

rsDiagnostic  OBJECT-TYPE
    SYNTAX DisplayString
    ACCESS  read-only
    STATUS  mandatory
    DESCRIPTION
      "This variable  will contain some dignostic information in case on a
       problem ocurs in the RS functinality."
    ::=  { rsTunning 4 }

rsConfirmMessagTab  OBJECT-TYPE
    SYNTAX INTEGER
    ACCESS  read-write
    STATUS  mandatory
    DESCRIPTION
      "This variable  enables the operator to confirm all the message in the
       event Message Table."
    ::=  { rsTunning 5 }

eventMessageTable OBJECT-TYPE
   SYNTAX SEQUENCE OF EventMessageEntry
   ACCESS not-accessible
   STATUS mandatory
   DESCRIPTION
    "The Event Message table of the agent"
     ::= { rsTunning 6 }

eventMessageEntry  OBJECT-TYPE
   SYNTAX EventMessageEntry
   ACCESS not-accessible
   STATUS mandatory
   DESCRIPTION
       " The row definition for this table."
   INDEX { eventNum }
   ::= {eventMessageTable 1}

EventMessageEntry  ::= SEQUENCE {
   eventNum        INTEGER,
   eventDesc       DisplayString
   }

eventNum OBJECT-TYPE
   SYNTAX INTEGER
   ACCESS read-only
   STATUS mandatory
   DESCRIPTION
      "The event number,the index of this table."
   ::= {eventMessageEntry 1}

eventDesc  OBJECT-TYPE
   SYNTAX DisplayString
   ACCESS read-only
   STATUS mandatory
   DESCRIPTION
      "The event discription, this text will include time and severity."
  ::= {eventMessageEntry 2}

reaTunning OBJECT IDENTIFIER ::= { rsTunning 7 }

reaIpRemoteAgingTime OBJECT-TYPE
    SYNTAX INTEGER
    ACCESS  read-write
    STATUS  mandatory
    DESCRIPTION
      "This variable specifies aging time used by the REA for remote
       entries in the Ip Fast Forwarding Table."
    ::=  { reaTunning 1 }

reaFftHashMaxChain OBJECT-TYPE
    SYNTAX INTEGER
    ACCESS  read-write
    STATUS  mandatory
    DESCRIPTION
      "This variable specifies the maximum length of hash chains in
       the Fast Forwarding Tables."
    ::=  { reaTunning 2 }

reaMltcstBitOn OBJECT-TYPE
    SYNTAX INTEGER {
        on  (1),
        off (2)
    }
    ACCESS  read-write
    STATUS  mandatory
    DESCRIPTION
      ""
    ::=  { reaTunning 3 }

reaIpForwardEnable OBJECT-TYPE
    SYNTAX INTEGER {
        enable  (1),
        disable (2)
    }
    ACCESS  read-write
    STATUS  mandatory
    DESCRIPTION
      "The Platform will perform fast IP forwarding if only if this
       variable's value is enable."
    ::=  { reaTunning 4 }

reaIpxForwardEnable OBJECT-TYPE
    SYNTAX INTEGER {
        enable  (1),
        disable (2)
    }
    ACCESS  read-write
    STATUS  mandatory
    DESCRIPTION
      "The Platform will perform fast IPX forwarding if only if this
       variable's value is enable."
    ::=  { reaTunning 5 }

reaBridgeEnable OBJECT-TYPE
    SYNTAX INTEGER {
        enable  (1),
        disable (2)
    }
    ACCESS  read-write
    STATUS  mandatory
    DESCRIPTION
      "The Platform will perform bridging if only if this
       variable's value is enable."
    ::=  { reaTunning 6 }

reaFacsEnable OBJECT-TYPE
    SYNTAX INTEGER {
        enable  (1),
        disable (2)
    }
    ACCESS  read-write
    STATUS  mandatory
    DESCRIPTION
      "The RS and Platform will perform FASC if only if this
       variable's value is enable."
    ::=  { reaTunning 7 }

reaIpForwardDatagrams OBJECT-TYPE
    SYNTAX Counter
    ACCESS  read-only
    STATUS  mandatory
    DESCRIPTION
      "The number of IP datagrams have been forwarded by the Platform."
    ::=  { reaTunning 8 }

reaIpInDiscards OBJECT-TYPE
    SYNTAX Counter
    ACCESS  read-only
    STATUS  mandatory
    DESCRIPTION
      "The number of IP datagrams have been dicarded by the Platform."
    ::=  { reaTunning 9 }

reaIpxForwardDatagrams OBJECT-TYPE
    SYNTAX Counter
    ACCESS  read-only
    STATUS  mandatory
    DESCRIPTION
      "The number of IPX datagrams have been forwarded by the Platform."
    ::=  { reaTunning 10 }

reaIpxInDiscards OBJECT-TYPE
    SYNTAX Counter
    ACCESS  read-only
    STATUS  mandatory
    DESCRIPTION
      "The number of IP datagrams have been dicarded by the Platform."
    ::=  { reaTunning 11 }

reaBridgeFftTable OBJECT-TYPE
    SYNTAX SEQUENCE OF ReaBridgeFftEntry
    ACCESS not-accessible
    STATUS mandatory
    DESCRIPTION
      "The Bridge Fast Forwarding Table"
    ::=  { reaTunning 12 }

reaBridgeFftEntry  OBJECT-TYPE
   SYNTAX ReaBridgeFftEntry
   ACCESS not-accessible
   STATUS mandatory
   DESCRIPTION
       " The row definition for this table."
   INDEX { reaBrgFftEntryNum }
   ::= { reaBridgeFftTable 1 }

ReaBridgeFftEntry ::= SEQUENCE {
        reaBrgFftEntryNum           INTEGER,
        reaBrgFftMacAddr            PhysAddress,    -- from RFC1213
        reaBrgFftReNum              INTEGER,        -- 1..N
        reaBrgFftPortNum            INTEGER,        -- 1..N
        reaBrgFftFacsSrcIndex       INTEGER,
        reaBrgFftFacsDstIndex       INTEGER
   }

reaBrgFftEntryNum OBJECT-TYPE
   SYNTAX INTEGER
   ACCESS   read-only
   STATUS mandatory
   DESCRIPTION
       ""
   ::=  { reaBridgeFftEntry 1 }

reaBrgFftMacAddr OBJECT-TYPE
   SYNTAX PhysAddress
   ACCESS   read-only
   STATUS mandatory
   DESCRIPTION
       ""
   ::=  { reaBridgeFftEntry 2 }

reaBrgFftReNum OBJECT-TYPE
   SYNTAX INTEGER
   ACCESS   read-only
   STATUS mandatory
   DESCRIPTION
       ""
   ::=  { reaBridgeFftEntry 3 }

reaBrgFftPortNum OBJECT-TYPE
   SYNTAX INTEGER
   ACCESS   read-only
   STATUS mandatory
   DESCRIPTION
       ""
   ::=  { reaBridgeFftEntry 4 }

reaBrgFftFacsSrcIndex OBJECT-TYPE
   SYNTAX INTEGER
   ACCESS   read-only
   STATUS mandatory
   DESCRIPTION
       ""
   ::=  { reaBridgeFftEntry 5 }

reaBrgFftFacsDstIndex OBJECT-TYPE
   SYNTAX INTEGER
   ACCESS   read-only
   STATUS mandatory
   DESCRIPTION
       ""
   ::=  { reaBridgeFftEntry 6 }

reaBrgDiscards OBJECT-TYPE
    SYNTAX Counter
    ACCESS  read-only
    STATUS  mandatory
    DESCRIPTION
      "The number of bridging datagrams have been discarded by the Platform."
    ::=  { reaTunning 13 }

reaBrgForwards OBJECT-TYPE
    SYNTAX Counter
    ACCESS  read-only
    STATUS  mandatory
    DESCRIPTION
      "The number of bridging datagrams have been forwarded by the Platform."
    ::=  { reaTunning 14 }

reaIpFftTable OBJECT-TYPE
    SYNTAX SEQUENCE OF ReaIpFftEntry
    ACCESS not-accessible
    STATUS mandatory
    DESCRIPTION
      "The IP Fast Forwarding Table"
    ::=  { reaTunning 15 }

reaIpFftEntry  OBJECT-TYPE
   SYNTAX ReaIpFftEntry
   ACCESS not-accessible
   STATUS mandatory
   DESCRIPTION
       " The row definition for this table."
   INDEX { reaIpFftEntryNum }
   ::= { reaIpFftTable 1 }

ReaIpFftEntry ::= SEQUENCE {
        reaIpFftEntryNum            INTEGER,
        reaIpFftDstIpAddr           IpAddress,
        reaIpFftDstIpMask           IpAddress,
        reaIpFftRangeType           INTEGER,
        reaIpFftSrcMacAddr          PhysAddress,
        reaIpFftDstMacAddr          PhysAddress,
        reaIpFftReNum               INTEGER,        -- 1..N
        reaIpFftPortNum             INTEGER,        -- 1..N
        reaIpFftFacsSrcIndex        INTEGER,
        reaIpFftFacsDstIndex        INTEGER,
        reaIpFftApplFlags           OCTET STRING
   }

reaIpFftEntryNum OBJECT-TYPE
   SYNTAX INTEGER
   ACCESS   read-only
   STATUS mandatory
   DESCRIPTION
       ""
   ::=  { reaIpFftEntry 1 }

reaIpFftDstIpAddr OBJECT-TYPE
   SYNTAX IpAddress
   ACCESS   read-only
   STATUS mandatory
   DESCRIPTION
       ""
   ::=  { reaIpFftEntry 2 }

reaIpFftDstIpMask OBJECT-TYPE
   SYNTAX IpAddress
   ACCESS   read-only
   STATUS mandatory
   DESCRIPTION
       ""
   ::=  { reaIpFftEntry 3 }

reaIpFftRangeType OBJECT-TYPE
   SYNTAX INTEGER {
        direct (1),
        remote (2)
   }
   ACCESS   read-only
   STATUS mandatory
   DESCRIPTION
       ""
   ::=  { reaIpFftEntry 4 }

reaIpFftSrcMacAddr OBJECT-TYPE
   SYNTAX PhysAddress
   ACCESS   read-only
   STATUS mandatory
   DESCRIPTION
       ""
   ::=  { reaIpFftEntry 5 }

reaIpFftDstMacAddr OBJECT-TYPE
   SYNTAX PhysAddress
   ACCESS   read-only
   STATUS mandatory
   DESCRIPTION
       ""
   ::=  { reaIpFftEntry 6 }

reaIpFftReNum OBJECT-TYPE
   SYNTAX INTEGER
   ACCESS   read-only
   STATUS mandatory
   DESCRIPTION
       ""
   ::=  { reaIpFftEntry 7 }

reaIpFftPortNum OBJECT-TYPE
   SYNTAX INTEGER
   ACCESS   read-only
   STATUS mandatory
   DESCRIPTION
       ""
   ::=  { reaIpFftEntry 8 }

reaIpFftFacsSrcIndex OBJECT-TYPE
   SYNTAX INTEGER
   ACCESS   read-only
   STATUS mandatory
   DESCRIPTION
       ""
   ::=  { reaIpFftEntry 9 }

reaIpFftFacsDstIndex OBJECT-TYPE
   SYNTAX INTEGER
   ACCESS   read-only
   STATUS mandatory
   DESCRIPTION
       ""
   ::=  { reaIpFftEntry 10 }

reaIpFftApplFlags OBJECT-TYPE
   SYNTAX OCTET STRING (SIZE(4))
   ACCESS read-only
   STATUS mandatory
   DESCRIPTION
      "A bit mask that defines the applications associated with this entry:
       __________________________________________
       |  Byte 1|Byte 2 |Byte 3 | ....|Byte 20  |
       |87654321|                     | 87654321|
       |________|_______________________________|

 Byte1 :
      bit1: Server Dispatcher Client"
   ::=  { reaIpFftEntry 11 }

reaIpxFftTable OBJECT-TYPE
    SYNTAX SEQUENCE OF ReaIpxFftEntry
    ACCESS not-accessible
    STATUS mandatory
    DESCRIPTION
      "The IPX Fast Forwarding Table"
    ::=  { reaTunning 16 }

reaIpxFftEntry  OBJECT-TYPE
   SYNTAX ReaIpxFftEntry
   ACCESS not-accessible
   STATUS mandatory
   DESCRIPTION
       " The row definition for this table."
   INDEX { reaIpxFftEntryNum }
   ::= { reaIpxFftTable 1 }

ReaIpxFftEntry ::= SEQUENCE {
        reaIpxFftEntryNum             INTEGER,
        reaIpxFftDstNetid             INTEGER,
        reaIpxFftRangeType            INTEGER,
        reaIpxFftSrcMacAddr           PhysAddress,
        reaIpxFftDstMacAddr           PhysAddress,
        reaIpxFftReNum                INTEGER,        -- 1..N
        reaIpxFftPortNum              INTEGER,        -- 1..N
        reaIpxFftFacsSrcIndex         INTEGER,
        reaIpxFftFacsDstIndex         INTEGER
   }

reaIpxFftEntryNum OBJECT-TYPE
   SYNTAX INTEGER
   ACCESS   read-only
   STATUS mandatory
   DESCRIPTION
       ""
   ::=  { reaIpxFftEntry 1 }

reaIpxFftDstNetid OBJECT-TYPE
   SYNTAX INTEGER
   ACCESS   read-only
   STATUS mandatory
   DESCRIPTION
       ""
   ::=  { reaIpxFftEntry 2 }

reaIpxFftRangeType OBJECT-TYPE
   SYNTAX INTEGER {
        direct (1),
        remote (2)
   }
   ACCESS   read-only
   STATUS mandatory
   DESCRIPTION
       ""
   ::=  { reaIpxFftEntry 3 }

reaIpxFftSrcMacAddr OBJECT-TYPE
   SYNTAX PhysAddress
   ACCESS   read-only
   STATUS mandatory
   DESCRIPTION
       ""
   ::=  { reaIpxFftEntry 4 }

reaIpxFftDstMacAddr OBJECT-TYPE
   SYNTAX PhysAddress
   ACCESS   read-only
   STATUS mandatory
   DESCRIPTION
       ""
   ::=  { reaIpxFftEntry 5 }

reaIpxFftReNum OBJECT-TYPE
   SYNTAX INTEGER
   ACCESS   read-only
   STATUS mandatory
   DESCRIPTION
       ""
   ::=  { reaIpxFftEntry 6 }

reaIpxFftPortNum OBJECT-TYPE
   SYNTAX INTEGER
   ACCESS   read-only
   STATUS mandatory
   DESCRIPTION
       ""
   ::=  { reaIpxFftEntry 7 }

reaIpxFftFacsSrcIndex OBJECT-TYPE
   SYNTAX INTEGER
   ACCESS   read-only
   STATUS mandatory
   DESCRIPTION
       ""
   ::=  { reaIpxFftEntry 8 }

reaIpxFftFacsDstIndex OBJECT-TYPE
   SYNTAX INTEGER
   ACCESS   read-only
   STATUS mandatory
   DESCRIPTION
       ""
   ::=  { reaIpxFftEntry 9 }

lreVnResposibilityTable OBJECT-TYPE
    SYNTAX SEQUENCE OF LreVnResposibilityEntry
    ACCESS not-accessible
    STATUS mandatory
    DESCRIPTION
      "The Bridge Responsibility Table"
    ::=  { reaTunning 17 }

lreVnResposibilityEntry  OBJECT-TYPE
   SYNTAX LreVnResposibilityEntry
   ACCESS not-accessible
   STATUS mandatory
   DESCRIPTION
       " The row definition for this table."
   INDEX { lreVnRespVn }
   ::= { lreVnResposibilityTable 1 }

LreVnResposibilityEntry ::= SEQUENCE {
        lreVnRespVn             INTEGER,
        lreVnRespStatus         RowStatus
   }

lreVnRespVn OBJECT-TYPE
   SYNTAX INTEGER
   ACCESS   read-write
   STATUS mandatory
   DESCRIPTION
       ""
   ::=  { lreVnResposibilityEntry 1 }

lreVnRespStatus OBJECT-TYPE
   SYNTAX RowStatus
   ACCESS read-write
   STATUS mandatory
   DESCRIPTION
       ""
   ::=  { lreVnResposibilityEntry 2 }

reaSrcViolationEnable OBJECT-TYPE
    SYNTAX INTEGER {
        enable  (1),
        disable (2)
    }
    ACCESS  read-write
    STATUS  mandatory
    DESCRIPTION
      "The Platform will perform the Source Port Violation Procedure
       if only if this variable's value is enable."
    ::=  { reaTunning 18 }

reaSrcViolationTrapEnable OBJECT-TYPE
    SYNTAX INTEGER {
        enable  (1),
        disable (2)
    }
    ACCESS  read-write
    STATUS  mandatory
    DESCRIPTION
      "The RS will send the Source Port Violation TRAP messages
       if only if this variable's value is enable."
    ::=  { reaTunning 19 }

reaSrcAddrValidationEnable OBJECT-TYPE
    SYNTAX INTEGER {
        enable  (1),
        disable (2)
    }
    ACCESS  read-write
    STATUS  mandatory
    DESCRIPTION
      "The Platform will verify the source address of incoming
       IP datagram."
    ::=  { reaTunning 20 }

reaRsQueueDiscards OBJECT-TYPE
    SYNTAX Counter
    ACCESS read-only
    STATUS mandatory
    DESCRIPTION
      ""
    ::=  { reaTunning 21 }

reaBufFree OBJECT-TYPE
    SYNTAX  INTEGER
    ACCESS  read-only
    STATUS  mandatory
    DESCRIPTION
      "The number of free buffers."
    ::=  { reaTunning 22 }

lreResetDstMacBit46 OBJECT-TYPE
    SYNTAX  INTEGER {
      enable(1),
      disable(2)
   }
    ACCESS  read-write
    STATUS  mandatory
    DESCRIPTION
      ""
    ::=  { reaTunning 23 }

lreQueSourceSelect OBJECT-TYPE
    SYNTAX  INTEGER {
      vNET(1),
      dstMac(2)
   }
    ACCESS  read-write
    STATUS  mandatory
    DESCRIPTION
      ""
    ::=  { reaTunning 24 }

lreResetDstMacBit47 OBJECT-TYPE
    SYNTAX  INTEGER {
      enable(1),
      disable(2)
   }
    ACCESS  read-write
    STATUS  mandatory
    DESCRIPTION
      ""
    ::=  { reaTunning 25 }

rsMaxEntriesTuning OBJECT IDENTIFIER ::= { rsTunning 8 }

rsMaxBridgeForwardingEntriesTuning OBJECT IDENTIFIER ::= { rsMaxEntriesTuning 1}

rsMaxBrgFrwEntries OBJECT-TYPE
    SYNTAX INTEGER
    ACCESS  read-only
    STATUS  mandatory
    DESCRIPTION
      "Maximal number of entries in bridge forwarding table."
    ::=  { rsMaxBridgeForwardingEntriesTuning 1 }

rsMaxBrgFrwEntriesAfterReset OBJECT-TYPE
    SYNTAX INTEGER
    ACCESS  read-write
    STATUS  mandatory
    DESCRIPTION
      "Future maximal number of entries in bridge forwarding table."
    ::=  { rsMaxBridgeForwardingEntriesTuning 2 }

rsMaxIpForwardingEntriesTuning OBJECT IDENTIFIER ::= { rsMaxEntriesTuning 2}

rsMaxIpFrwEntries OBJECT-TYPE
    SYNTAX INTEGER
    ACCESS  read-only
    STATUS  mandatory
    DESCRIPTION
      "Maximal number of entries in Ip forwarding table."
    ::=  { rsMaxIpForwardingEntriesTuning 1 }

rsMaxIpFrwEntriesAfterReset OBJECT-TYPE
    SYNTAX INTEGER
    ACCESS  read-write
    STATUS  mandatory
    DESCRIPTION
      "Future maximal number of entries in Ip forwarding table."
    ::=  { rsMaxIpForwardingEntriesTuning 2 }

rsMaxArpEntriesTuning OBJECT IDENTIFIER ::= { rsMaxEntriesTuning 3}

rsMaxArpEntries OBJECT-TYPE
    SYNTAX INTEGER
    ACCESS  read-only
    STATUS  mandatory
    DESCRIPTION
      "Maximal number of entries in Arp forwarding table."
    ::=  { rsMaxArpEntriesTuning 1 }

rsMaxArpEntriesAfterReset OBJECT-TYPE
    SYNTAX INTEGER
    ACCESS  read-write
    STATUS  mandatory
    DESCRIPTION
      "Future maximal number of entries in Arp forwarding table."
    ::=  { rsMaxArpEntriesTuning 2 }

rsMaxIpxForwardingEntriesTuning OBJECT IDENTIFIER ::= { rsMaxEntriesTuning 4}

rsMaxIpxFrwEntries OBJECT-TYPE
    SYNTAX INTEGER
    ACCESS  read-only
    STATUS  mandatory
    DESCRIPTION
      "Maximal number of entries in Ipx forwarding table."
    ::=  { rsMaxIpxForwardingEntriesTuning 1 }

rsMaxIpxFrwEntriesAfterReset OBJECT-TYPE
    SYNTAX INTEGER
    ACCESS  read-write
    STATUS  mandatory
    DESCRIPTION
      "Future maximal number of entries in Ipx forwarding table."
    ::=  { rsMaxIpxForwardingEntriesTuning 2 }

rsMaxIpxSapEntriesTuning OBJECT IDENTIFIER ::= { rsMaxEntriesTuning 5}

rsMaxIpxSapEntries OBJECT-TYPE
    SYNTAX INTEGER
    ACCESS  read-only
    STATUS  mandatory
    DESCRIPTION
      "Maximal number of entries in IpxSap table."
    ::=  { rsMaxIpxSapEntriesTuning 1 }

rsMaxIpxSapEntriesAfterReset OBJECT-TYPE
    SYNTAX INTEGER
    ACCESS  read-write
    STATUS  mandatory
    DESCRIPTION
      "Future maximal number of entries in IpxSap table."
    ::=  { rsMaxIpxSapEntriesTuning 2 }

rsMaxDspClntEntriesTuning OBJECT IDENTIFIER ::= { rsMaxEntriesTuning 6}

rsMaxDspClntEntries OBJECT-TYPE
    SYNTAX INTEGER
    ACCESS  read-only
    STATUS  mandatory
    DESCRIPTION
      "Maximal number of entries in rsSdClientsTable."
    ::=  { rsMaxDspClntEntriesTuning 1 }

rsMaxDspClntEntriesAfterReset OBJECT-TYPE
    SYNTAX INTEGER
    ACCESS  read-write
    STATUS  mandatory
    DESCRIPTION
      "Future maximal number of entries in rsSdClientsTable."
    ::=  { rsMaxDspClntEntriesTuning 2 }

rsMaxZeroHopRoutEntriesTuning OBJECT IDENTIFIER ::= { rsMaxEntriesTuning 7}

rsMaxZhrConns OBJECT-TYPE
    SYNTAX INTEGER
    ACCESS  read-only
    STATUS  mandatory
    DESCRIPTION
      "The current maximal number of direct Zero-hop routing
       connections."
    ::= { rsMaxZeroHopRoutEntriesTuning 1 }

rsMaxZhrConnsAfterReset OBJECT-TYPE
    SYNTAX INTEGER
    ACCESS  read-write
    STATUS  mandatory
    DESCRIPTION
      "The future (after reset) maximal number of direct Zero-hop routing
       connections."
    ::= { rsMaxZeroHopRoutEntriesTuning 2 }

rsMaxDspFrmEntriesTuning OBJECT IDENTIFIER ::= { rsMaxEntriesTuning 8}

rsMaxDspFrmEntries OBJECT-TYPE
    SYNTAX INTEGER
    ACCESS  read-only
    STATUS  mandatory
    DESCRIPTION
      "Maximal number of entries in rsSdClientsTable."
    ::=  { rsMaxDspFrmEntriesTuning 1 }

rsMaxDspFrmEntriesAfterReset OBJECT-TYPE
    SYNTAX INTEGER
    ACCESS  read-write
    STATUS  mandatory
    DESCRIPTION
      "Future maximal number of entries in rsSdClientsTable."
    ::=  { rsMaxDspFrmEntriesTuning 2 }

rsMaxRoutingEntriesTuning OBJECT IDENTIFIER ::= { rsMaxEntriesTuning 9}

rsMaxRoutingEntries OBJECT-TYPE
    SYNTAX INTEGER
    ACCESS  read-only
    STATUS  mandatory
    DESCRIPTION
      "Maximal number of entries in the routing table."
    ::=  { rsMaxRoutingEntriesTuning 1 }

rsMaxRoutingEntriesAfterReset OBJECT-TYPE
    SYNTAX INTEGER
    ACCESS  read-write
    STATUS  mandatory
    DESCRIPTION
      "Future maximal number of entries in the routing table."
    ::=  { rsMaxRoutingEntriesTuning 2 }

rsMaxRadiusEntriesTuning OBJECT IDENTIFIER ::= { rsMaxEntriesTuning 10}

rsMaxRadiusUsersEntries OBJECT-TYPE
    SYNTAX INTEGER
    ACCESS  read-only
    STATUS  mandatory
    DESCRIPTION
      "Maximal number of entries in the radius users table."
    ::=  { rsMaxRadiusEntriesTuning 1 }

rsMaxRadiusUsersEntriesAfterReset OBJECT-TYPE
    SYNTAX INTEGER
    ACCESS  read-write
    STATUS  mandatory
    DESCRIPTION
      "Future maximal number of entries in the radius users table."
    ::=  { rsMaxRadiusEntriesTuning 2 }

rsMaxRadiusNasAuthEntries OBJECT-TYPE
    SYNTAX INTEGER
    ACCESS  read-only
    STATUS  mandatory
    DESCRIPTION
      "Maximal number of entries in the NAS Authenticators table."
    ::=  { rsMaxRadiusEntriesTuning 3 }

rsMaxRadiusNasAuthEntriesAfterReset OBJECT-TYPE
    SYNTAX INTEGER
    ACCESS  read-write
    STATUS  mandatory
    DESCRIPTION
      "Future maximal number of entries in the NAS Authenticators table."
    ::=  { rsMaxRadiusEntriesTuning 4 }


rsTuneCheckMemory OBJECT-TYPE
    SYNTAX INTEGER {
      enoughMemory(1),
      notEnoughMemory(2)
    }
    ACCESS read-only
    STATUS mandatory
    DESCRIPTION
      "Shows whether the requested number of entries in the after-reset tuning
       variables can be successfully allocated."
    ::= { rsTunning 9 }

rsTuneLastCheckResult OBJECT-TYPE
    SYNTAX INTEGER
    ACCESS read-only
    STATUS mandatory
    DESCRIPTION
      "Number of Kbytes missing in request for new table sizes."
    ::= { rsTunning 10 }


rndApplications  OBJECT IDENTIFIER ::= { rnd 35 }
rsServerDispatcher  OBJECT IDENTIFIER ::= { rndApplications 1}


-- rndMidLevelManagement group contains variables which direct the mid-level
-- management stations how to monitor and manage their domains.

rndMidLevelManagement  OBJECT IDENTIFIER ::= { rndApplications 2} -- NEW Group

-- rndHighLevelNms  OBJECT IDENTIFIER ::= { rndMidLevelManagement 1}

-- rndHighLevelNmsIpAddress OBJECT-TYPE
--    SYNTAX IpAddress
--    ACCESS read-write
--    STATUS mandatory
--    DESCRIPTION
--     "The IP address of the high-level network management station to which the
--      mid-level management station should report"
--      ::=  { rndHighLevelNms 1 }

-- rndHighLevelNmsCommunity OBJECT-TYPE
--    SYNTAX OCTET STRING(SIZE(1..20))
--    ACCESS read-write
--    STATUS mandatory
--    DESCRIPTION
--     "The community of the high-level network management station that should be used
--      by the mid-level management station when reporting"
--  ::=  { rndHighLevelNms 2 }

rndAlarmOptions  OBJECT IDENTIFIER ::= { rndMidLevelManagement 2}

rndAlarmEnabling OBJECT-TYPE
    SYNTAX INTEGER {
        enabled(1),
        disabled(2)
        }
    ACCESS read-write
    STATUS mandatory
    DESCRIPTION
        "Indicates whether alarms should be issued to the high-level
         NMS "
     ::=  { rndAlarmOptions 1 }

rndAlarmInterval OBJECT-TYPE
    SYNTAX INTEGER
    ACCESS read-write
    STATUS mandatory
    DESCRIPTION
        "Indicates the minimal period of time which must pass after issuing
         an alarm before issuing the same alarm again."
     ::=  { rndAlarmOptions 2 }

rndMonitoredElementsTable  OBJECT-TYPE
   SYNTAX SEQUENCE OF RndMonitoredElementEntry
   ACCESS not-accessible
   STATUS mandatory
   DESCRIPTION
    "The table of monitored elements of the network"
    ::= {rndMidLevelManagement 3}

rndMonitoredElementEntry  OBJECT-TYPE
   SYNTAX RndMonitoredElementEntry
   ACCESS not-accessible
   STATUS mandatory
   DESCRIPTION
       " The row definition for this table."
   INDEX { rndMonitoredElementAddress }
    ::= {rndMonitoredElementsTable 1}

RndMonitoredElementEntry ::= SEQUENCE {

rndMonitoredElementAddress    IpAddress,
rndMonitoredElementCommunity  DisplayString(SIZE(1..20)),
rndMonitoredElementLabel      DisplayString(SIZE(1..20)),
rndDefaultPollingInterval     INTEGER,
rndDefaultLogFile             DisplayString,
rndMonitoredElementStatus     RowStatus
}
rndMonitoredElementAddress OBJECT-TYPE
   SYNTAX IpAddress
   ACCESS read-only
   STATUS mandatory
   DESCRIPTION
    "The IP address of the monitored element"
     ::=  {rndMonitoredElementEntry  1 }

rndMonitoredElementCommunity OBJECT-TYPE
   SYNTAX DisplayString(SIZE(1..20))
   ACCESS read-write
   STATUS mandatory
   DESCRIPTION
    "The community of the monitored element"
     ::=  {rndMonitoredElementEntry 2  }

rndMonitoredElementLabel OBJECT-TYPE
   SYNTAX DisplayString(SIZE(1..20))
   ACCESS read-write
   STATUS mandatory
   DESCRIPTION
    "The label assigned by the network manager to the monitored element"
     ::=  {rndMonitoredElementEntry 3}

rndDefaultPollingInterval OBJECT-TYPE
   SYNTAX INTEGER
   ACCESS read-write
   STATUS mandatory
   DESCRIPTION
    "The default period of time between two consecutive pollings of the
     monitored element for the value of an object instance. If no other polling
     interval is specifically assigned to the monitored object instance, this
     one will be used"
     ::=  {rndMonitoredElementEntry 4}

rndDefaultLogFile OBJECT-TYPE
   SYNTAX DisplayString
   ACCESS read-write
   STATUS mandatory
   DESCRIPTION
    "The default file path of the log-file which will contain the polling
     results for the monitored element. If no other file path is specifically
     assigned to the monitored object instance, this log-file will be used."

     ::=  {rndMonitoredElementEntry  5}

rndMonitoredElementStatus OBJECT-TYPE
   SYNTAX RowStatus
   ACCESS read-write
   STATUS mandatory
   DESCRIPTION
         "It is used to manage the monitored elements table and indicates
          the current monitoring status of an element."
     ::=  {rndMonitoredElementEntry  6}

rndMonitoringTable  OBJECT-TYPE
   SYNTAX SEQUENCE OF RndMonitoringEntry
   ACCESS not-accessible
   STATUS mandatory
   DESCRIPTION
    "The table of monitored object instances. Each monitored object instance
     belongs to a monitored element previously entered in the
     rndMonitoredElementsTable. "
    ::= {rndMidLevelManagement 4}

rndMonitoringEntry OBJECT-TYPE
   SYNTAX RndMonitoringEntry
   ACCESS not-accessible
   STATUS mandatory
   DESCRIPTION
       " The row definition for this table."
   INDEX { rndMonitoredElement, rndMonitoredObjectInstanceLabel }
    ::= {rndMonitoringTable 1}

RndMonitoringEntry ::= SEQUENCE {

rndMonitoredElement             DisplayString(SIZE(1..20)),
rndMonitoredObjectInstanceLabel DisplayString,
rndMonitoredObjectName          DisplayString,
rndMonitoredObjectIdentifier    OBJECT IDENTIFIER,
rndMonitoredObjectInstance      OBJECT IDENTIFIER,
rndMonitoredObjectSyntax        INTEGER,
rndMonitoringInterval           INTEGER,
rndAlarmMaxTreshold             INTEGER,
rndAlarmMinTreshold             INTEGER,
rndMonitoringLogfile            DisplayString,
rndMonitoringEntryStatus        RowStatus
}

rndMonitoredElement OBJECT-TYPE
   SYNTAX DisplayString(SIZE(1..20))
   ACCESS read-only
   STATUS mandatory
   DESCRIPTION
    "A label assigned by the network manager to a monitored element to
     which this monitored object instance belongs. This label must have
     been previously entered in an instance of rndMonitoredElementLabel"
    ::=  {rndMonitoringEntry  1}

rndMonitoredObjectInstanceLabel OBJECT-TYPE
   SYNTAX DisplayString(SIZE(1..20))
   ACCESS read-only
   STATUS mandatory
   DESCRIPTION
    "The label assigned by the network manager to the monitored object instance"
    ::=  {rndMonitoringEntry  2}

rndMonitoredObjectName OBJECT-TYPE
   SYNTAX DisplayString(SIZE(0..20))
   ACCESS read-write
   STATUS mandatory
   DESCRIPTION
    "The symbolic object type name of the object to which the monitored object
     instance belongs (as it appears the MIB module definition). In case of
     ambiguity the <MIB module name> : <object type name> format should be used.
     An instance of rndMonitoredObjectName need not be assigned any value, if
     the corresponding instance of rndMonitoredObjectIdentifier is assigned a
     value, since any one of these, together with the object instance
     identifier, suffices to unambigously identify the monitored object
     instance."

    ::=  {rndMonitoringEntry  3}

rndMonitoredObjectIdentifier OBJECT-TYPE
   SYNTAX OBJECT IDENTIFIER
   ACCESS read-write
   STATUS mandatory
   DESCRIPTION
    "The object identifier of the object to which the monitored object
     instance belongs.
     An instance of rndMonitoredObjectIdentifier need not be assigned any value, if
     the corresponding instance of rndMonitoredObjectName is assigned a value,
     since any one of these, together with the object instance identifier,
     suffices to unambigously identify the monitored object instance."

    ::=  {rndMonitoringEntry  4}

rndMonitoredObjectInstance OBJECT-TYPE
   SYNTAX OBJECT IDENTIFIER
   ACCESS read-write
   STATUS mandatory
   DESCRIPTION
        "The instance identifier (key) of the monitored object instance."
    ::=  {rndMonitoringEntry  5}

rndMonitoredObjectSyntax OBJECT-TYPE
   SYNTAX INTEGER {
       integer(1),
       octet-string(2),
       ip-address(3),
       object-identifier(4)
     }

   ACCESS read-write
   STATUS mandatory
   DESCRIPTION
    "The syntax of the monitored object instance (i.e., the syntax of the object
     type of the object to which the monitored instance belongs).
     Need not be assigned any value if the corresponding instance of
     rndMonitoredObjectName has been assigned a value"
    ::=  {rndMonitoringEntry  6}

rndMonitoringInterval OBJECT-TYPE
   SYNTAX INTEGER
   ACCESS read-write
   STATUS mandatory
   DESCRIPTION
    "The period of time between two consecutive retrievals of the monitored
     object instance's value."
    ::=  {rndMonitoringEntry  7}


rndAlarmMaxTreshold OBJECT-TYPE
   SYNTAX INTEGER
   ACCESS read-write
   STATUS mandatory
   DESCRIPTION
    "The value of the monitored object instance, the exceeding of which
     will cause the generation of an alarm to the high-level management
     station."
    ::=  {rndMonitoringEntry 8}

rndAlarmMinTreshold OBJECT-TYPE
   SYNTAX INTEGER
   ACCESS read-write
   STATUS mandatory
   DESCRIPTION
    "If the value of the monitored object instance falls below the value
     assigned to rndAlarmMinTreshold, an alarm to the high-level management
     station will be issued."
    ::=  {rndMonitoringEntry  9}


rndMonitoringLogfile OBJECT-TYPE
   SYNTAX DisplayString
   ACCESS read-write
   STATUS mandatory
   DESCRIPTION
    "The entire path of the file in which the results of the monitoring
     of this object instance should be recorded."
    ::=  {rndMonitoringEntry  10}

rndMonitoringEntryStatus OBJECT-TYPE
   SYNTAX RowStatus
   ACCESS read-write
   STATUS mandatory
   DESCRIPTION
         "It is used to manage the monitored object instances table and
          indicates the current monitoring status of an object instance."
    ::=  {rndMonitoringEntry  11}

rndMibFilesTable  OBJECT-TYPE
   SYNTAX SEQUENCE OF RndMibFileEntry
   ACCESS not-accessible
   STATUS mandatory
   DESCRIPTION
    "The table of monitored object instances. Each monitored object instance
     belongs to a monitored element previously entered in the
     rndMonitoredElementsTable. "
    ::= {rndMidLevelManagement 5}

rndMibFileEntry OBJECT-TYPE
   SYNTAX RndMibFileEntry
   ACCESS not-accessible
   STATUS mandatory
   DESCRIPTION
       " The row definition for this table."
   INDEX { rndMibFileIndex }
    ::= {rndMibFilesTable 1}

RndMibFileEntry ::= SEQUENCE {

rndMibFileIndex                 INTEGER,
rndMibFilePath                  DisplayString,
rndMibFileRefresh               INTEGER,
rndMibFileEntryStatus           RowStatus
}
rndMibFileIndex OBJECT-TYPE
   SYNTAX INTEGER
   ACCESS read-only
   STATUS mandatory
   DESCRIPTION
    "The number of the MIB file in the list MIB files supported by the
     Mid-Level management station. The order of the MIB files in this
     list must reflect the the IMPORT relation between the MIBS contained
     in the MIB files, i.e., if MIB A IMPORTS FROM MIB B, the file containing
     MIB A must have a lesser index in this table than the file containing
     MIB B."
    ::=  {rndMibFileEntry  1}


rndMibFilePath OBJECT-TYPE
   SYNTAX DisplayString
   ACCESS read-write
   STATUS mandatory
   DESCRIPTION
    "The path of the MIB file in the MIB file server."
    ::=  {rndMibFileEntry  2}

rndMibFileRefresh OBJECT-TYPE
   SYNTAX INTEGER {
      no(1),
      yes(2)
   }
   ACCESS read-write
   STATUS mandatory
   DESCRIPTION
    "Indicates if the file should be fetched after setting this entry from the
     MIB file server."
    ::=  {rndMibFileEntry  3}

rndMibFileEntryStatus OBJECT-TYPE
   SYNTAX RowStatus
   ACCESS read-write
   STATUS mandatory
   DESCRIPTION
         "It is used to manage the MIB files table."
    ::=  {rndMibFileEntry  4}

rndHardwareConfiguration OBJECT-TYPE
    SYNTAX TruthValue
    ACCESS read-write
    STATUS mandatory
    DESCRIPTION
        "Indicates whether the current SET SNMP PDU contains hardware
         configuration (i.e., normally read-only variables). SET of such
         variables in the Mid-level management station will be allowed only
         if this variable is included in the SNMP PDU and its value is true.
         Its value as returned in  a GET SNMP PDU will always be false."
    ::= {rndMidLevelManagement 6}

rndEraseSimulatedConfiguration OBJECT-TYPE
    SYNTAX INTEGER {
        eraseSimulatedConfiguration(1),
        simulatedConfigurationPresent(2),
        simulatedConfigurationErased(3)
        }
    ACCESS read-write
    STATUS mandatory
    DESCRIPTION
        "eraseSimulatedConfiguration instructs the MLNMS to erase all the
         simulated configuration from its configuration data-base (CDB). This
         the only accepted value for SNMP SET statements and will never be
         returned in SNMP GET statements.
         simulatedConfigurationPresent indicates that the MLNMS currently has
         a simulated configuration.
         simulatedConfigurationErased indicates that the MLNMS currently has
         no simulated configuration."
    ::= {rndMidLevelManagement 7}

rndDeleteValuesTable  OBJECT-TYPE
   SYNTAX SEQUENCE OF RndDeleteValuesEntry
   ACCESS not-accessible
   STATUS mandatory
   DESCRIPTION
    "This table indicates which MIB variables are row status fields which
     control the status of the entry to which they belong. This table also
     indicates which (integer!) value of these MIB variables will cause, if
     present in a SNMP SET PDU, the deletion of the conceptual row instance
     to which the SET MIB variable instance belongs."
    ::= {rndMidLevelManagement 8}

rndDeleteValuesEntry  OBJECT-TYPE
   SYNTAX RndDeleteValuesEntry
   ACCESS not-accessible
   STATUS mandatory
   DESCRIPTION
       " The row definition for the rndDeleteValuesTable table."
   INDEX { IMPLIED rndRowStatusVariableName }
    ::= {rndDeleteValuesTable 1}

RndDeleteValuesEntry ::= SEQUENCE {

rndRowStatusVariableName    DisplayString,
rndRowStatusObjectId        OBJECT IDENTIFIER,
rndRowDeleteValue           INTEGER,
rndDeleteValueEntryStatus   RowStatus
}

rndRowStatusVariableName OBJECT-TYPE
   SYNTAX DisplayString(SIZE(1..80))
--   ACCESS read-only
   ACCESS read-write
   STATUS mandatory
   DESCRIPTION
    "The name of the row status field. This name may not necessarily be any
     name which is present in the MIBs loaded into the MLNMS station."

     ::=  {rndDeleteValuesEntry 1}

rndRowStatusObjectId OBJECT-TYPE
   SYNTAX OBJECT IDENTIFIER
   ACCESS read-write
   STATUS mandatory
   DESCRIPTION
    "The object id of the row status field. If the rndRowStatusVariableName is
     a name present in the MIBs loaded into the MLNMS, this MIB
     variable is not required, but if given, it must match the object id known
     to the MLNMS.
     The variable identified by rndRowStatusVariableName and/or rndRowStatusObjectId
     must be a read-write MIB variable of type INTEGER which belongs to an
     entry (i.e, is a child of a MIB variable of type SEQUENCE)."

     ::=  {rndDeleteValuesEntry 2}

rndRowDeleteValue OBJECT-TYPE
   SYNTAX INTEGER
   ACCESS read-write
   STATUS mandatory
   DESCRIPTION
    "The value of the variable identified by rndRowStatusVariableName and/or
     rndRowStatusObjectId, which, if present in a SNMP SET PDU, will cause
     the deletion of the conceptual row instance which the SET MIB variable
     instance belongs."
     ::=  {rndDeleteValuesEntry 3}

rndDeleteValueEntryStatus  OBJECT-TYPE
   SYNTAX  RowStatus
   ACCESS  read-write
   STATUS  mandatory
   DESCRIPTION
         "It is used to delete an entry from this table."
     ::=  {rndDeleteValuesEntry 4}

-- rndVisionDriver group contains variables which deal with the Vision Driver files.
rndVisionDriver  OBJECT IDENTIFIER ::= { rndMidLevelManagement 9 }

rndVisionDriverActiveName OBJECT-TYPE
   SYNTAX DisplayString(SIZE(1..100))
   ACCESS read-only
   STATUS mandatory
   DESCRIPTION
    "The name of the active vision driver stored on the device."

   ::= { rndVisionDriver 1 }

rndVisionDriverRestoreFromBackup OBJECT-TYPE
    SYNTAX INTEGER {
        activate(1)
    }
    ACCESS  read-write
    STATUS  mandatory
    DESCRIPTION "Restores the backup vision driver"
    ::= { rndVisionDriver 2 }

rndSmartFan  OBJECT IDENTIFIER ::= { rndMidLevelManagement 10 }

rndSmartFanStatus OBJECT-TYPE
   SYNTAX INTEGER {
      enable(1),
      disable(2)
   }
   ACCESS read-write
   STATUS mandatory
   DESCRIPTION
    "Smart Fan Status"
   DEFVAL  {disable}
   ::= { rndSmartFan 1 }

rsIpZeroHopRouting  OBJECT IDENTIFIER ::= { rndApplications 3} -- NEW Group

rsIpZhrGeneralStatus  OBJECT-TYPE
    SYNTAX  INTEGER  {
   enable(1),
   disable(2)
}
    ACCESS  read-write
    STATUS  mandatory
    DESCRIPTION
        "This parameter enables or disables the IP Zero Hop Routing feature
         for all IP interfaces. The IP Zero Hop Routing feature can also be
         enabled or disabled on each IP interface through the
         rsIpZhrStatusTable."
    DEFVAL  {2}
    ::= { rsIpZeroHopRouting 1 }

rsIpZhrAgingTimeout   OBJECT-TYPE
    SYNTAX  INTEGER
    ACCESS  read-write
    STATUS  mandatory
    DESCRIPTION
        "This parameter controls the aging time-out in seconds of direct
         connections which were allocated. The virtual IP address of a direct
         connection whose time-out has expired is eligible for allocation to a
         different connection."
    DEFVAL  {600}
    ::= { rsIpZeroHopRouting 2 }

rsIpZhrStatusTable OBJECT-TYPE
SYNTAX SEQUENCE OF RsIpZhrStatusEntry
ACCESS  not-accessible
STATUS  mandatory
DESCRIPTION
      "The administrative status of the ZHR feature per ip interface."
::= { rsIpZeroHopRouting 3 }


rsIpZhrStatusEntry  OBJECT-TYPE
SYNTAX    RsIpZhrStatusEntry
ACCESS    not-accessible
STATUS    mandatory
DESCRIPTION
      " An entry in the ZHR status table.  "
INDEX  { rsIpZhrStatusIpIntf}
::= { rsIpZhrStatusTable 1 }


RsIpZhrStatusEntry  ::= SEQUENCE {
      rsIpZhrStatusIpIntf                    IpAddress,
      rsIpZhrAdminStatus                     INTEGER
}


rsIpZhrStatusIpIntf       OBJECT-TYPE
SYNTAX IpAddress
ACCESS  read-only
STATUS  mandatory
DESCRIPTION
   " The Ip interface whose ZHR feature status is accessed. "
::= {rsIpZhrStatusEntry  1}

 rsIpZhrAdminStatus OBJECT-TYPE
 SYNTAX INTEGER {
    enable (1),
    disable(2)
}
ACCESS read-write
STATUS mandatory
DESCRIPTION
         "It is used to control whether ZHR will operate on the interface. "
DEFVAL {1}
::=  {rsIpZhrStatusEntry  2}


rsIpZhrVirtAddressTable OBJECT-TYPE
SYNTAX SEQUENCE OF RsIpZhrVirtAddressEntry
ACCESS  not-accessible
STATUS  mandatory
DESCRIPTION
      "The table of free virtual IP addresses which may be allocated
       to establish direct connections   -  Per IP Interface."
::= { rsIpZeroHopRouting 4 }

rsIpZhrVirtAddressEntry  OBJECT-TYPE
SYNTAX    RsIpZhrVirtAddressEntry
ACCESS    not-accessible
STATUS    mandatory
DESCRIPTION
      " An entry in the ZHR virtual IP addresses table "
INDEX  { rsIpZhrVirtAddressIpIntf,
         rsIpZhrVirtAddressTo }
::= { rsIpZhrVirtAddressTable 1 }

RsIpZhrVirtAddressEntry  ::= SEQUENCE {
      rsIpZhrVirtAddressIpIntf         IpAddress,
      rsIpZhrVirtAddressTo             IpAddress,
      rsIpZhrVirtAddressFrom           IpAddress,
      rsIpZhrVirtAddressStatus         RowStatus
}

rsIpZhrVirtAddressIpIntf OBJECT-TYPE
SYNTAX IpAddress
ACCESS  read-only
STATUS  mandatory
DESCRIPTION
   " The Ip Interface to which the IP addresses in this entry are allocated."
::= {rsIpZhrVirtAddressEntry  1}

rsIpZhrVirtAddressTo OBJECT-TYPE
SYNTAX IpAddress
ACCESS  read-only
STATUS  mandatory
DESCRIPTION
   " The last free IP address in the block. "
::= {rsIpZhrVirtAddressEntry  2}

rsIpZhrVirtAddressFrom OBJECT-TYPE
SYNTAX IpAddress
ACCESS  read-write
STATUS  mandatory
DESCRIPTION
   " The first free IP address in the block. "
::= {rsIpZhrVirtAddressEntry  3}

 rsIpZhrVirtAddressStatus OBJECT-TYPE
 SYNTAX RowStatus
ACCESS read-write
STATUS mandatory
DESCRIPTION
         "It is used to manage the virtual address table.
          The supported actions will be active, createAndGo and destroy. "
::=  {rsIpZhrVirtAddressEntry  4}

rsIpZhrConnectionsTable OBJECT-TYPE
SYNTAX SEQUENCE OF RsIpZhrConnectionEntry
ACCESS  not-accessible
STATUS  mandatory
DESCRIPTION
   "Table of the currently active direct connections."
::= { rsIpZeroHopRouting 5}

rsIpZhrConnectionEntry  OBJECT-TYPE
SYNTAX RsIpZhrConnectionEntry
ACCESS not-accessible
STATUS mandatory
DESCRIPTION
   " An entry in the ZHR Connection table"
INDEX  {rsIpZhrConnectionIpIntf,
        rsIpZhrConnectionSrcIp,
        rsIpZhrConnectionDestIp}
::= { rsIpZhrConnectionsTable 1 }

RsIpZhrConnectionEntry  ::= SEQUENCE {
      rsIpZhrConnectionIpIntf          IpAddress,
      rsIpZhrConnectionSrcIp           IpAddress,
      rsIpZhrConnectionDestIp          IpAddress,
      rsIpZhrConnectionVirtualIp       IpAddress,
      rsIpZhrConnectionType            INTEGER,
      rsIpZhrConnectionAge             INTEGER,
      rsIpZhrConnectionStatus          RowStatus
}

rsIpZhrConnectionIpIntf  OBJECT-TYPE
SYNTAX IpAddress
ACCESS  read-only
STATUS  mandatory
DESCRIPTION
   " The IP Interface for which this direct connection was established. "
::= {rsIpZhrConnectionEntry 1}

rsIpZhrConnectionSrcIp   OBJECT-TYPE
SYNTAX IpAddress
ACCESS  read-only
STATUS  mandatory
DESCRIPTION
   " The source IP Address of this direct connection. "
::= {rsIpZhrConnectionEntry 2}


rsIpZhrConnectionDestIp  OBJECT-TYPE
SYNTAX IpAddress
ACCESS  read-only
STATUS  mandatory
DESCRIPTION
   " The destination IP Address of this direct connection. "
::= {rsIpZhrConnectionEntry 3}

rsIpZhrConnectionVirtualIp OBJECT-TYPE
SYNTAX IpAddress
ACCESS  read-only
STATUS  mandatory
DESCRIPTION
   " The virtual IP address allocated for this direct connection. "
::= {rsIpZhrConnectionEntry 4}


rsIpZhrConnectionType   OBJECT-TYPE
SYNTAX INTEGER  {
   static(1),
   dynamic(2),
   disabled(3)
    }
ACCESS  read-only
STATUS  mandatory
DESCRIPTION
   " The type of this direct connection.
     dynamic  - established by the RS.
     disabled - established by the RS.
                The RS detected that the virtual address is already used as
                destination by the source BEFORE its allocation, and therefore
                marked this connection as 'disabled' to prevent a future
                allocation of this virtual address to this source.
     static   - established by user."
 ::= {rsIpZhrConnectionEntry 5}

rsIpZhrConnectionAge   OBJECT-TYPE
SYNTAX INTEGER
ACCESS  read-only
STATUS  mandatory
DESCRIPTION
   " The age of the connection in seconds."
::= {rsIpZhrConnectionEntry 6}

rsIpZhrConnectionStatus OBJECT-TYPE
 SYNTAX RowStatus
ACCESS read-write
STATUS mandatory
DESCRIPTION
         "It is used to manage the connections table.
          The supported actions will be active, createAndGo and destroy. "
::=  {rsIpZhrConnectionEntry  7}


-- Enterprise-specific traps for RND
-- Each enterprise-specific trap has two bound variables describing the exact nature of
-- the trap. rndErrorDesc provides a detailed description of the problem, including the
-- related interface number, board number or any other applicable variable.
-- rndErrorSeverity describes the severity of this problem.

-- Trap template
-- -------------
--    TRAP-TYPE
--       ENTERPRISE  rnd
--       VARIABLES   { rndErrorDesc, rndErrorSeverity }
--       DESCRIPTION
--             ""
--       ::=
-- -------------

routeTableOverflow TRAP-TYPE
       ENTERPRISE  rnd
       VARIABLES   { rndErrorDesc, rndErrorSeverity }
       DESCRIPTION
             "An overflow condition has occurred in the Routing Table. The Routing
              Table is used for IP routing algorithm (RIP)."
       ::= 5

fanNotWorking TRAP-TYPE
       ENTERPRISE rnd
       VARIABLES   { rndErrorDesc, rndErrorSeverity }
       DESCRIPTION
             "Fan Failure was detected"
       ::= 7

resetRequired TRAP-TYPE
       ENTERPRISE  rnd
       VARIABLES   { rndErrorDesc, rndErrorSeverity }
       DESCRIPTION
             "This trap indicates that in order to perform the last SET request, a reset operation
              of the router/bridge is required. This occurs when the layer 2 routing algorithm is
              changed between SPF and Spanning Tree. The reset can be performed manually or
              using the variable rndAction."
       ::=  10

endTftp  TRAP-TYPE
       ENTERPRISE  rnd
       VARIABLES   { rndErrorDesc, rndErrorSeverity }
       DESCRIPTION
             "This trap indicates that in the device finished a TFTP
             transaction with the management station.
             variable rndErrorDesc and rndErrorSeverity provides the actual message
             text and severity respectively."
       ::= 12

abortTftp TRAP-TYPE
       ENTERPRISE  rnd
       VARIABLES   { rndErrorDesc, rndErrorSeverity }
       DESCRIPTION
             "This trap indicates that in the device aborted a TFTP session with the management station.
              variable rndErrorDesc  and rndErrorSeverity  provides the actual  message text  and
              severity  respectively."
       ::= 13

startTftp TRAP-TYPE
       ENTERPRISE  rnd
       VARIABLES   { rndErrorDesc, rndErrorSeverity }
       DESCRIPTION
             "Informational trap indicating that the device has intiated a
             TFTP session. rndErrorDesc will contain the file type in
             question"
       ::=  14

deviceTemperatureNormal TRAP-TYPE
       ENTERPRISE rnd
       VARIABLES   { rndErrorDesc, rndErrorSeverity }
       DESCRIPTION
             "Sent whenever the temperature changes back to normal"
       ::= 15

deviceTemperatureHigh TRAP-TYPE
       ENTERPRISE rnd
       VARIABLES   { rndErrorDesc, rndErrorSeverity }
       DESCRIPTION
             "Sent whenever the temperature changes to high"
       ::= 16

deviceTemperatureCritical TRAP-TYPE
       ENTERPRISE rnd
       VARIABLES   { rndErrorDesc, rndErrorSeverity }
       DESCRIPTION
             "Sent whenever the temperature changes to critical"
       ::= 17

ipxRipTblOverflow    TRAP-TYPE
       ENTERPRISE  rnd
       VARIABLES   { rndErrorDesc, rndErrorSeverity }
       DESCRIPTION
             "This trap indicates that in an OpenGate IPX RIP table overflow.
             The bound variable rndErrorDesc, rndErrorSeverity
             provides the actual  message text and severity respectively."
       ::=  36

ipxSapTblOverflow  TRAP-TYPE
       ENTERPRISE  rnd
       VARIABLES   { rndErrorDesc, rndErrorSeverity }
       DESCRIPTION
             "This trap indicates that in an OpenGate IPX SAP table overflow.
             The bound variable rndErrorDesc, rndErrorSeverity
             provides the actual  message text and severity respectively."
       ::= 37

 facsAccessVoilation TRAP-TYPE
       ENTERPRISE  rnd
       VARIABLES   { rndErrorDesc, rndErrorSeverity }
       DESCRIPTION
           "This trap indicates that message that fits FACS statenebt with operation
            blockAndReport was forward to the interface.The bound variable rndErrorDesc,
               rndErrorSeverity(== info ) and interface Number."
           ::= 49

 autoConfigurationCompleted TRAP-TYPE
       ENTERPRISE  rnd
       VARIABLES   { rndErrorDesc, rndErrorSeverity }
       DESCRIPTION
         "This trap indicates that auto comfiguration completetd succssefully.
           The bound variable rndErrorDesc, rndErrorSeverity(== info )"
           ::= 50

 forwardingTabOverflow  TRAP-TYPE
       ENTERPRISE  rnd
       VARIABLES   { rndErrorDesc, rndErrorSeverity }
       DESCRIPTION
         "This trap indicates that an overflow condition has occurred in the
           layer II Forward Table.
           The bound variable rndErrorDesc, rndErrorSeverity(== warning )"
           ::= 51

errorsDuringInit  TRAP-TYPE
       ENTERPRISE  rnd
       VARIABLES   { rndErrorDesc, rndErrorSeverity }
       DESCRIPTION
             ""
       ::=  61

vlanDynPortAdded  TRAP-TYPE
       ENTERPRISE  rnd
       VARIABLES   { rndErrorDesc, rndErrorSeverity }
       DESCRIPTION
             ""
       ::=  66

vlanDynPortRemoved  TRAP-TYPE
       ENTERPRISE  rnd
       VARIABLES   { rndErrorDesc, rndErrorSeverity }
       DESCRIPTION
             ""
       ::=  67

rsSDclientsTableOverflow  TRAP-TYPE
       ENTERPRISE  rnd
       VARIABLES   { rndErrorDesc, rndErrorSeverity }
       DESCRIPTION
             "This warning is generated when an overflow occurs in the clients table."
       ::=  68

rsSDinactiveServer  TRAP-TYPE
       ENTERPRISE  rnd
       VARIABLES   { rndErrorDesc, rndErrorSeverity }
       DESCRIPTION
             "This warning is generated when a server does not respond to the dispatchers polling
              and is thought to be inactive."
       ::=  69

rsIpZhrConnectionsTableOverflow TRAP-TYPE
       ENTERPRISE  rnd
       VARIABLES   { rndErrorDesc, rndErrorSeverity }
       DESCRIPTION
             "The Zero Hop Routing connections Table has been overflown."
       ::= 70

rsIpZhrReqStaticConnNotAccepted TRAP-TYPE
       ENTERPRISE  rnd
       VARIABLES   { rndErrorDesc, rndErrorSeverity }
       DESCRIPTION
             "The requested static connection was not accepted because there is
              no available IP virtual address to allocate to it."
       ::= 71

rsIpZhrVirtualIpAsSource TRAP-TYPE
       ENTERPRISE  rnd
       VARIABLES   { rndErrorDesc, rndErrorSeverity }
       DESCRIPTION
             "The virtual IP address appeared as a source IP.
              All the connections using it will be deleted and
              it will not be further allocated to new connections."
       ::=  72

rsIpZhrNotAllocVirtualIp TRAP-TYPE
       ENTERPRISE  rnd
       VARIABLES   { rndErrorDesc, rndErrorSeverity }
       DESCRIPTION
             "The source IP address sent an ARP specifying a virtual IP
              which was not allocated for this source.
              This virtual IP will not be allocated to connections of this
              specific source IP."
       ::= 73

rsSnmpSetRequestInSpecialCfgState TRAP-TYPE
       ENTERPRISE  rnd
       VARIABLES   { rndErrorDesc, rndErrorSeverity }
       DESCRIPTION
             "An incoming SNMP SET request was rejected because no such
              requests (except action requests) are accepted after start of
              new configuration reception or during sending the current
              configuration to an NMS."
       ::= 74

rsConfigurationAuditEvent TRAP-TYPE
       ENTERPRISE  rnd
       VARIABLES   { rndErrorDesc, rndErrorSeverity }
       DESCRIPTION
             "Triggered by an audit event."
       ::= 75

rdwrFanNotWorking TRAP-TYPE
       ENTERPRISE  rnd
       VARIABLES   { rndErrorDesc, rndErrorSeverity }
       DESCRIPTION
             "Triggered by fan failure."
       ::= 76

rdwrFanInfo TRAP-TYPE
       ENTERPRISE  rnd
       VARIABLES   { rndErrorDesc, rndErrorSeverity }
       DESCRIPTION
             "Triggered by fan information."
       ::= 77
       
rdwrCertExpiration TRAP-TYPE
       ENTERPRISE  rnd
       VARIABLES   { rndErrorDesc, rndErrorSeverity }
       DESCRIPTION
             "Certificate expiration notification."
       ::= 78

cdeResyncronizing TRAP-TYPE
       ENTERPRISE  rnd
       VARIABLES   { rndErrorDesc, rndErrorSeverity }
       DESCRIPTION
             "Config Sync primary device Resyncronize with secondary device."
       ::= 79

cdeCannotSync TRAP-TYPE
       ENTERPRISE  rnd
       VARIABLES   { rndErrorDesc, rndErrorSeverity }
       DESCRIPTION
             "Config Sync Cannot sync."
       ::= 80

cdeConnected TRAP-TYPE
       ENTERPRISE  rnd
       VARIABLES   { rndErrorDesc, rndErrorSeverity }
       DESCRIPTION
             "Config Sync primary device Connected to secondary device"
       ::= 81

cdeConfigUpdateFailed TRAP-TYPE
       ENTERPRISE  rnd
       VARIABLES   { rndErrorDesc, rndErrorSeverity }
       DESCRIPTION
             "Config Sync primary device Failed to update the secondary device with a specific change."
       ::= 82

cdeSlaveReboot TRAP-TYPE
       ENTERPRISE  rnd
       VARIABLES   { rndErrorDesc, rndErrorSeverity }
       DESCRIPTION
             "Config Sync primary device Send reboot command to the secondary device"
       ::= 83


cdeSlaveRebootFailed TRAP-TYPE
       ENTERPRISE  rnd
       VARIABLES   { rndErrorDesc, rndErrorSeverity }
       DESCRIPTION
             "Config Sync Secondary Device Reboot has failed."
       ::= 84

cdeEnterOutOfSync TRAP-TYPE
       ENTERPRISE  rnd
       VARIABLES   { rndErrorDesc, rndErrorSeverity }
       DESCRIPTION
             "Config Sync enters out-of-sync state."
       ::= 85

cdeSlaveRebootPending TRAP-TYPE
       ENTERPRISE  rnd
       VARIABLES   { rndErrorDesc, rndErrorSeverity }
       DESCRIPTION
             "Config Sync Secondary Device Reboot is pending."
       ::= 86

cdeDisconnected TRAP-TYPE
       ENTERPRISE  rnd
       VARIABLES   { rndErrorDesc, rndErrorSeverity }
       DESCRIPTION
             "Config Sync enters disconnected state."
       ::= 87

cdeInSync TRAP-TYPE
       ENTERPRISE  rnd
       VARIABLES   { rndErrorDesc, rndErrorSeverity }
       DESCRIPTION
             "Config Sync enters in-sync state."
       ::= 88

cdeIncompatible TRAP-TYPE
       ENTERPRISE  rnd
       VARIABLES   { rndErrorDesc, rndErrorSeverity }
       DESCRIPTION
             "Config Sync enters incompatible state."
       ::= 89

cdeNoMaster TRAP-TYPE
       ENTERPRISE  rnd
       VARIABLES   { rndErrorDesc, rndErrorSeverity }
       DESCRIPTION
             "Config Sync enters no-master state."
       ::= 90

cdeMasterConnected TRAP-TYPE
       ENTERPRISE  rnd
       VARIABLES   { rndErrorDesc, rndErrorSeverity }
       DESCRIPTION
             "Config Sync enters master-connected state."
       ::= 91

diagnosticCapture TRAP-TYPE
       ENTERPRISE  rnd
       VARIABLES   { rndErrorDesc, rndErrorSeverity }
       DESCRIPTION
             "Diagnostic Caputre related information traps."
       ::= 92

controllerDisabledAppsec TRAP-TYPE
       ENTERPRISE  rnd
       VARIABLES   { rndErrorDesc, rndErrorSeverity }
       DESCRIPTION
             "Controller Disabled Appsec related traps."
       ::= 93

vcpuLicenseTrap TRAP-TYPE
       ENTERPRISE  rnd
       VARIABLES   { rndErrorDesc, rndErrorSeverity }
       DESCRIPTION
             "Vcpu License related traps."
       ::= 94

sslNetworkPolicies TRAP-TYPE
       ENTERPRISE  rnd
       VARIABLES   { rndErrorDesc, rndErrorSeverity }
       DESCRIPTION
             "PSSLO delete disable related traps."
       ::= 95

rsIDSslPssoWithoutCertificateTrap TRAP-TYPE
        ENTERPRISE rnd
        VARIABLES  { rndErrorDesc, rndErrorSeverity }
        DESCRIPTION
             "Protected Server without certificate is now disabled"
       ::=  96

rsIDinterfaceGroupDownInfo TRAP-TYPE
        ENTERPRISE rnd
        VARIABLES  { rndErrorDesc, rndErrorSeverity }
        DESCRIPTION
             "Interface group port is now disabled"
       ::=  97
accessListBuildError TRAP-TYPE
       ENTERPRISE rnd
       VARIABLES  { rndErrorDesc, rndErrorSeverity }
       DESCRIPTION "Accesslist build failed. Using previous configuration."
       ::=  98

rsPortStatusChangedLACPInfo TRAP-TYPE
       ENTERPRISE rnd
       VARIABLES  { rndErrorDesc, rndErrorSeverity }
       DESCRIPTION
             "Indicates when physical port belongs or not to the trunk based on LACP."
       ::=  99

antiscanUtilizationAboveInfoTrap TRAP-TYPE
       ENTERPRISE rnd
       VARIABLES  { rndErrorDesc, rndErrorSeverity }
       DESCRIPTION "Antiscan table utilziation info."
       ::=  100

antiscanUtilizationBelowInfoTrap TRAP-TYPE
       ENTERPRISE rnd
       VARIABLES  { rndErrorDesc, rndErrorSeverity }
       DESCRIPTION "Antiscan table utilziation info."
       ::=  101

 rsDPCACPUDataReadFailure TRAP-TYPE
       ENTERPRISE  rnd
       VARIABLES   { rndErrorDesc, rndErrorSeverity }
       DESCRIPTION
             "DPCA CPU Data Read Failure"
       ::= 102

 rsDPCACPUUtilExceededWarningStartThresh TRAP-TYPE
       ENTERPRISE  rnd
       VARIABLES   { rndErrorDesc, rndErrorSeverity }
       DESCRIPTION
             "DPCA CPU Util Exceeded Warning Start Thresh"
       ::= 103

 rsDPCACPUUtilDecreasedBelowWarningStopThresh TRAP-TYPE
       ENTERPRISE  rnd
       VARIABLES   { rndErrorDesc, rndErrorSeverity }
       DESCRIPTION
             "DPCA CPU Util Decreased Below Warning Stop Thresh"
       ::= 104

 rsEngCPUUtilExceededWarningStartThresh TRAP-TYPE
       ENTERPRISE  rnd
       VARIABLES   { rndErrorDesc, rndErrorSeverity }
       DESCRIPTION
             "Eng CPU Util Exceeded Warning Start Thresh"
       ::= 105

 rsEngCPUUtilDecreasedBelowWarningStopThresh TRAP-TYPE
       ENTERPRISE  rnd
       VARIABLES   { rndErrorDesc, rndErrorSeverity }
       DESCRIPTION
             "Eng CPU Util Decreased Below Warning Stop Thresh"
       ::= 106

rsDPCACPUUtilExceededErrorStartThresh TRAP-TYPE
       ENTERPRISE  rnd
       VARIABLES   { rndErrorDesc, rndErrorSeverity }
       DESCRIPTION
             "DPCA CPU Util Exceeded Error Start Thresh"
       ::= 107

 rsDPCACPUUtilDecreasedBelowErrorStopThresh TRAP-TYPE
       ENTERPRISE  rnd
       VARIABLES   { rndErrorDesc, rndErrorSeverity }
       DESCRIPTION
             "DPCA CPU Util Decreased Below Error Stop Thresh"
       ::= 108

 rsEngCPUUtilExceededErrorStartThresh TRAP-TYPE
       ENTERPRISE  rnd
       VARIABLES   { rndErrorDesc, rndErrorSeverity }
       DESCRIPTION
             "Eng CPU Util Exceeded Error Start Thresh"
       ::= 109

 rsEngCPUUtilDecreasedBelowErrorStopThresh TRAP-TYPE
       ENTERPRISE  rnd
       VARIABLES   { rndErrorDesc, rndErrorSeverity }
       DESCRIPTION
             "Eng CPU Util Decreased Below Error Stop Thresh"
       ::= 110

rsWSDRedundancySwitch TRAP-TYPE
  ENTERPRISE rnd
  VARIABLES   { rndErrorDesc, rndErrorSeverity }
  DESCRIPTION "Whenever main server fails and backup takes over or server comes
               up after failure a trap of this type is issued."
     ::= 141

axConfigFailed TRAP-TYPE
       ENTERPRISE  rnd
       VARIABLES   { rndErrorDesc, rndErrorSeverity }
       DESCRIPTION "Failed to configure the on-device SSL engine. SSL decryption and encryption is disabled."               
       ::= 142

trafficFiltersRulesError TRAP-TYPE
       ENTERPRISE  rnd
       VARIABLES   { rndErrorDesc, rndErrorSeverity }
       DESCRIPTION "Traffic filters rules traps issues."               
       ::= 143


-- Some MIB compilers require that the following 7 lines which define the path
-- to RND MIB are commented out:

-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }

rsWSDServerStatTable OBJECT-TYPE
   SYNTAX SEQUENCE OF RsWSDServerStatEntry
   ACCESS not-accessible
   STATUS mandatory
   DESCRIPTION
          "In this table the WSD collects statistics per servers."
   ::= {rsServerDispatcher 12}

rsWSDServerStatEntry OBJECT-TYPE
    SYNTAX RsWSDServerStatEntry
    ACCESS not-accessible
    STATUS  mandatory
    DESCRIPTION
       " The row definition for this table."
   INDEX  {rsWSDSerStatName}
   ::= {rsWSDServerStatTable 1}

RsWSDServerStatEntry  ::= SEQUENCE {
  rsWSDSerStatName                     DisplayString,
  rsWSDSerStatAttUsersNum              INTEGER,
  rsWSDSerStatPeakLoad                 INTEGER,
  rsWSDSerStatFramesRate               INTEGER,
  rsWSDSerStatFramesLoad               Counter,
  rsWSDSerStatRecoveryTime             INTEGER,
  rsWSDSerStatWarmUpTime               INTEGER,
  rsWSDSerStatConnectionLimit          INTEGER,
  rsWSDSerStatAdminStatus              INTEGER,
  rsWSDSerStatConnectionLimitReached   INTEGER
  }

rsWSDSerStatName OBJECT-TYPE
    SYNTAX DisplayString (SIZE(1..30))
    ACCESS  read-only
    STATUS  mandatory
    DESCRIPTION
    "This variable indicate the name assigned by the user to the serve."
    ::= {rsWSDServerStatEntry 1}

rsWSDSerStatAttUsersNum OBJECT-TYPE
    SYNTAX INTEGER
    ACCESS  read-only
    STATUS  mandatory
    DESCRIPTION
      "The total number of currently active users attached to this server."
   ::= {rsWSDServerStatEntry 2}

rsWSDSerStatPeakLoad OBJECT-TYPE
    SYNTAX INTEGER
    ACCESS  read-only
    STATUS  mandatory
    DESCRIPTION
      "Maximal number of frames per second dispatched to server
       since last reset."
   ::= {rsWSDServerStatEntry 3}

rsWSDSerStatFramesRate OBJECT-TYPE
    SYNTAX INTEGER
    ACCESS  read-only
    STATUS  mandatory
    DESCRIPTION
     "Number of frames per second dispatched to server."
   ::= {rsWSDServerStatEntry 4}

rsWSDSerStatFramesLoad OBJECT-TYPE
    SYNTAX Counter
    ACCESS  read-only
    STATUS  mandatory
    DESCRIPTION
      "Number of frames per second dispatched to server."
   ::= {rsWSDServerStatEntry 5}

rsWSDSerStatRecoveryTime OBJECT-TYPE
    SYNTAX INTEGER
    ACCESS  read-write
    STATUS  mandatory
    DESCRIPTION
      "Number of seconds after server initialization during which ISD won't
       send any requests."
   ::= {rsWSDServerStatEntry 6}

rsWSDSerStatWarmUpTime OBJECT-TYPE
    SYNTAX INTEGER
    ACCESS  read-write
    STATUS  mandatory
    DESCRIPTION
      "Number of seconds after server recovery during which the server will get
       less requests than permitted by his weight and load."
   ::= {rsWSDServerStatEntry 7}

rsWSDSerStatConnectionLimit OBJECT-TYPE
    SYNTAX INTEGER
    ACCESS  read-write
    STATUS  mandatory
    DESCRIPTION
      "The maximal number of client sessions which can be opened on this sever."
-- DEFVAL {0}
   ::= {rsWSDServerStatEntry 8}

   rsWSDSerStatAdminStatus  OBJECT-TYPE
    SYNTAX INTEGER {
            enable(1),
            connectionsShutdown(2),
      	    sessionsShutdown(3)
    }
    ACCESS  read-write
    STATUS  mandatory
    DESCRIPTION
    "Administrative status of physical server.
     enable -   activates the server.
                The rsADServerOperStatus will change to active.
     connectionsShutdown - gracefully shuts down connections to the server by allowing existing connections to complete,
                           while new connections are not forwarded to this server.
                  	       The rsADServerOperStatus will change to noNewSessions.
     sessionsShutdown - gracefully shuts down sessions to the server by allowing existing sessions to complete
			            (new connections that match existing sessions on this server are still forwarded to the server), while new sessions are not forwarded to this server. 
                  	    The rsADServerOperStatus will change to noNewSessions."
    DEFVAL {1}
    ::=  { rsWSDServerStatEntry  9}

   rsWSDSerStatConnectionLimitReached  OBJECT-TYPE
    SYNTAX  INTEGER
    ACCESS  read-only
    STATUS  mandatory
    DESCRIPTION
    "Connection limit reached flag."
    ::=  { rsWSDServerStatEntry  10}


wsdRedundTable OBJECT-TYPE
   SYNTAX SEQUENCE OF WsdRedundEntry
   ACCESS not-accessible
   STATUS mandatory
   DESCRIPTION
      "List of Farm IP addresses backed up by this router."
   ::= {rsServerDispatcher 16}

wsdRedundEntry  OBJECT-TYPE
   SYNTAX WsdRedundEntry
   ACCESS not-accessible
   STATUS mandatory
   DESCRIPTION
      "The row definition for this table."
   INDEX {wsdRedundFarmAddr, wsdRedundMainWsdAddr}
   ::= {wsdRedundTable  1 }

WsdRedundEntry ::= SEQUENCE {
   wsdRedundFarmAddr          IpAddress,
   wsdRedundMainWsdAddr   IpAddress,
   wsdRedundOperStatus         INTEGER,
   wsdRedundPollInterval        INTEGER,
   wsdRedundTimeout             INTEGER,
   wsdRedundStatus                 INTEGER
   }

wsdRedundFarmAddr OBJECT-TYPE
   SYNTAX IpAddress
   ACCESS read-only
   STATUS mandatory
   DESCRIPTION
      "The Farm Virtual Ip address on which the redundancy feature operates."
   ::=  { wsdRedundEntry  1}

wsdRedundMainWsdAddr OBJECT-TYPE
   SYNTAX IpAddress
   ACCESS read-only
   STATUS mandatory
   DESCRIPTION
      "The Ip address of the polled main wsd."
   ::=  { wsdRedundEntry 2}

wsdRedundOperStatus OBJECT-TYPE
   SYNTAX INTEGER { active(1), inactive(2) }
   ACCESS read-only
   STATUS mandatory
   DESCRIPTION
      "If active, the main wsd is considered inactive and the IP interface operates as its backup."
   ::=  { wsdRedundEntry 3 }

wsdRedundPollInterval OBJECT-TYPE
   SYNTAX INTEGER
   ACCESS read-write
   STATUS mandatory
   DESCRIPTION
      "Polling interval for the main wsd (in seconds). If 0 the wsd is not
       polled."
-- DEFVAL  { 3 }
   ::=  { wsdRedundEntry 4 }

wsdRedundTimeout OBJECT-TYPE
   SYNTAX INTEGER
   ACCESS read-write
   STATUS mandatory
   DESCRIPTION
      "Interval in seconds during which the backed-up wsd must signal.
       If it does not signal, it is considered inactive and the IP
       interface starts operating as backup."
-- DEFVAL  { 12 }
   ::=  { wsdRedundEntry  5}

wsdRedundStatus OBJECT-TYPE
   SYNTAX INTEGER {
                   active(1),
                   notInService(2),
                   notReady(3),
                   createAndGo(4),
                   createAndWait(5),
                   destroy(6)
                  }
   ACCESS read-write
   STATUS mandatory
   DESCRIPTION
      "Entry status"
   ::=  { wsdRedundEntry 6}


rsWSDNewEntryOnSourcePort OBJECT-TYPE
    SYNTAX INTEGER {
      enable(1),
      disable(2)
   }
    ACCESS  read-write
    STATUS  mandatory
    DESCRIPTION
      "Check source port and if different open new client entry."
-- DEFVAL  { disable }
    ::=  {rsServerDispatcher 19}

rsWSDSelectServerOnSourcePort OBJECT-TYPE
    SYNTAX INTEGER {
      enable(1),
      disable(2)
   }
    ACCESS  read-write
    STATUS  mandatory
    DESCRIPTION
      "Check source port and if different select a new server."
-- DEFVAL  { disable }
    ::=  {rsServerDispatcher 20}

rsWSDRedundancyMode OBJECT-TYPE
    SYNTAX INTEGER {
        enable(1),
        disable(2)
    }
    ACCESS  read-write
    STATUS  mandatory
    DESCRIPTION
        "Defines whether interface grouping functionality is enabled on the device."
--  DEFVAL { disable }
    ::=  { rsServerDispatcher 21}

rsNsdMode OBJECT-TYPE
    SYNTAX INTEGER {
        slowMode(1),
        fastMode(2)
    }
    ACCESS  read-write
    STATUS  mandatory
    DESCRIPTION
        "The Topology chosen for the NSD.
         Slow mode keeps the servers behind the NSD.
         Fast mode uses retargeting to connect clients directly
         to servers."
--  DEFVAL  {1}
    ::=  {rsServerDispatcher 22}

rsNsdWINSAddr OBJECT-TYPE
    SYNTAX IpAddress
    ACCESS  read-write
    STATUS  mandatory
    DESCRIPTION
        "NetBIOS Name Server IP Address."
    ::=  {rsServerDispatcher 23}

rsWSDSyslogStatus  OBJECT-TYPE
    SYNTAX INTEGER {
                    enable(1),
                    disable(2)
                   }
    ACCESS  read-write
    STATUS  mandatory
    DESCRIPTION
        "Enable/Disable syslog message sending to remote station."
--  DEFVAL { 2 }
    ::=  {rsServerDispatcher 26}

rsWSDSyslogAddress OBJECT-TYPE
    SYNTAX IpAddress
    ACCESS  read-write
    STATUS  mandatory
    DESCRIPTION
        "The IP Address of the syslog station."
    ::= {rsServerDispatcher 27}

rsWSDNTCheckTable OBJECT-TYPE
   SYNTAX SEQUENCE OF RsWSDNTCheckEntry
   ACCESS not-accessible
   STATUS mandatory
   DESCRIPTION
       "In this table the WSD collects NT statistics per servers."
   ::= {rsServerDispatcher 28}

rsWSDNTCheckEntry OBJECT-TYPE
   SYNTAX RsWSDNTCheckEntry
   ACCESS not-accessible
   STATUS  mandatory
   DESCRIPTION
       " The row definition for this table."
   INDEX  {rsWSDNTSerialNum}
   ::= {rsWSDNTCheckTable 1}

RsWSDNTCheckEntry ::= SEQUENCE {
     rsWSDNTSerialNum             INTEGER,
     rsWSDNTFrequentCheckPeriod   INTEGER,
     rsWSDNTOpenSessionsWeight    INTEGER,
     rsWSDNTIncomingTrafficWeight INTEGER,
     rsWSDNTOutgoingTrafficWeight INTEGER,
     rsWSDNTRegularCheckPeriod    INTEGER,
     rsWSDNTAvResponseWeight      INTEGER,
     rsWSDNTUsersLimitWeight      INTEGER,
     rsWSDNTTCPLimitWeight        INTEGER,
     rsWSDNTRetries               INTEGER,
     rsWSDNTCommunity             DisplayString
}

rsWSDNTSerialNum OBJECT-TYPE
   SYNTAX INTEGER
   ACCESS  read-only
   STATUS  mandatory
   DESCRIPTION
       "The serial number of the algorithm."
   ::= {rsWSDNTCheckEntry 1}

rsWSDNTFrequentCheckPeriod OBJECT-TYPE
   SYNTAX INTEGER
   ACCESS  read-write
   STATUS  mandatory
   DESCRIPTION
       "The period for getting the frequent NT variables."
-- DEFVAL {10}
   ::= {rsWSDNTCheckEntry 2}

rsWSDNTOpenSessionsWeight OBJECT-TYPE
   SYNTAX INTEGER
   ACCESS  read-write
   STATUS  mandatory
   DESCRIPTION
       "The weight for currently open sessions consideration."
-- DEFVAL {0}
   ::= {rsWSDNTCheckEntry 3}

rsWSDNTIncomingTrafficWeight OBJECT-TYPE
   SYNTAX INTEGER
   ACCESS  read-write
   STATUS  mandatory
   DESCRIPTION
       "The weight for incoming traffic consideration."
-- DEFVAL {0}
   ::= {rsWSDNTCheckEntry 4}

rsWSDNTOutgoingTrafficWeight OBJECT-TYPE
   SYNTAX INTEGER
   ACCESS  read-write
   STATUS  mandatory
   DESCRIPTION
       "The weight for outgoing traffic consideration."
-- DEFVAL {0}
   ::= {rsWSDNTCheckEntry 5}

rsWSDNTRegularCheckPeriod OBJECT-TYPE
   SYNTAX INTEGER
   ACCESS  read-write
   STATUS  mandatory
   DESCRIPTION
       "The period for getting the regular NT variables."
-- DEFVAL {300}
   ::= {rsWSDNTCheckEntry 6}

rsWSDNTAvResponseWeight   OBJECT-TYPE
   SYNTAX INTEGER
   ACCESS  read-write
   STATUS  mandatory
   DESCRIPTION
       "The weight for average response time."
-- DEFVAL {0}
   ::= {rsWSDNTCheckEntry 7}

rsWSDNTUsersLimitWeight OBJECT-TYPE
   SYNTAX INTEGER
   ACCESS  read-write
   STATUS  mandatory
   DESCRIPTION
       "The weight for the users limit on the server."
-- DEFVAL {0}
   ::= {rsWSDNTCheckEntry 8}

rsWSDNTTCPLimitWeight OBJECT-TYPE
   SYNTAX INTEGER
   ACCESS  read-write
   STATUS  mandatory
   DESCRIPTION
       "The weight for the TCP connections limit on the server."
-- DEFVAL {0}
   ::= {rsWSDNTCheckEntry 9}

rsWSDNTRetries OBJECT-TYPE
   SYNTAX INTEGER
   ACCESS  read-write
   STATUS  mandatory
   DESCRIPTION
       "The number of retries before issuing a trap."
-- DEFVAL {3}
   ::= {rsWSDNTCheckEntry 10}

rsWSDNTCommunity OBJECT-TYPE
    SYNTAX DisplayString (SIZE(1..30))
    ACCESS  read-write
    STATUS  mandatory
    DESCRIPTION
    "The SNMP community name with which we access the servers."
    ::= {rsWSDNTCheckEntry 11}


rsWSDPrivateCheckTable OBJECT-TYPE
   SYNTAX SEQUENCE OF RsWSDPrivateCheckEntry
   ACCESS not-accessible
   STATUS mandatory
   DESCRIPTION
       "In this table the WSD collects private statistics per server."
   ::= {rsServerDispatcher 29}

rsWSDPrivateCheckEntry OBJECT-TYPE
   SYNTAX RsWSDPrivateCheckEntry
   ACCESS not-accessible
   STATUS  mandatory
   DESCRIPTION
       " The row definition for this table."
   INDEX  {rsWSDPrivateSerialNum}
   ::= {rsWSDPrivateCheckTable 1}

RsWSDPrivateCheckEntry  ::= SEQUENCE {
               rsWSDPrivateSerialNum           INTEGER,
               rsWSDPrivateSpecialCheckPeriod  INTEGER,
               rsWSDPrivateExtraVar1ID         OBJECT IDENTIFIER,
               rsWSDPrivateExtraVar1Weight     INTEGER,
               rsWSDPrivateExtraVar2ID         OBJECT IDENTIFIER,
               rsWSDPrivateExtraVar2Weight     INTEGER,
               rsWSDPrivateRetries             INTEGER,
               rsWSDPrivateCommunity           DisplayString,
               rsWSDPrivateExtraVar1Mode       INTEGER,
               rsWSDPrivateExtraVar2Mode       INTEGER
}

rsWSDPrivateSerialNum OBJECT-TYPE
   SYNTAX INTEGER
   ACCESS  read-only
   STATUS  mandatory
   DESCRIPTION
       "The serial number of the algorithm."
   ::= {rsWSDPrivateCheckEntry 1}

rsWSDPrivateSpecialCheckPeriod OBJECT-TYPE
   SYNTAX INTEGER
   ACCESS  read-write
   STATUS  mandatory
   DESCRIPTION
       "The period for getting the private variables."
-- DEFVAL {30}
   ::= {rsWSDPrivateCheckEntry 2}

rsWSDPrivateExtraVar1ID OBJECT-TYPE
   SYNTAX OBJECT IDENTIFIER
   ACCESS read-write
   STATUS mandatory
   DESCRIPTION
       "This MIB variable will be retrieved from the server."
   ::= {rsWSDPrivateCheckEntry 3}

rsWSDPrivateExtraVar1Weight OBJECT-TYPE
   SYNTAX INTEGER
   ACCESS read-write
   STATUS  mandatory
   DESCRIPTION
       "The weight for variable number 1."
-- DEFVAL {3}
   ::= {rsWSDPrivateCheckEntry 4}

rsWSDPrivateExtraVar2ID OBJECT-TYPE
   SYNTAX OBJECT IDENTIFIER
   ACCESS  read-write
   STATUS  mandatory
   DESCRIPTION
       "This MIB variable will be retrieved from the server."
   ::= {rsWSDPrivateCheckEntry 5}

rsWSDPrivateExtraVar2Weight OBJECT-TYPE
   SYNTAX INTEGER
   ACCESS  read-write
   STATUS  mandatory
   DESCRIPTION
       "The weight for variable number 2."
-- DEFVAL {3}
   ::= {rsWSDPrivateCheckEntry 6}

rsWSDPrivateRetries OBJECT-TYPE
  SYNTAX INTEGER
  ACCESS  read-write
  STATUS  mandatory
  DESCRIPTION
      "The number of retries before issuing a trap."
  ::= {rsWSDPrivateCheckEntry 7}

rsWSDPrivateCommunity OBJECT-TYPE
    SYNTAX DisplayString (SIZE(1..30))
    ACCESS  read-write
    STATUS  mandatory
    DESCRIPTION
    "The SNMP community name with which we access the servers."
    ::= {rsWSDPrivateCheckEntry 8}


rsWSDPrivateExtraVar1Mode OBJECT-TYPE
    SYNTAX INTEGER {
      ascending(1),
      descending(2)
   }
    ACCESS  read-write
    STATUS  mandatory
    DESCRIPTION
      "Specify the type of parameter. Ascending means that the value of 100 is the best (Idle CPU percentage). Descending means that the value of 0 is the best (CPU utilization percentage)"
    ::=  {rsWSDPrivateCheckEntry 9}

rsWSDPrivateExtraVar2Mode OBJECT-TYPE
    SYNTAX INTEGER {
      ascending(1),
      descending(2)
   }
    ACCESS  read-write
    STATUS  mandatory
    DESCRIPTION
      "Specify the type of parameter. Ascending means that the value of 100 is the best (Idle CPU percentage). Descending means that the value of 0 is the best (CPU utilization percentage)"
    ::=  {rsWSDPrivateCheckEntry 10}



rsWSDDNSResolution  OBJECT-TYPE
   SYNTAX INTEGER {
                   enable(1),
                   disable(2),
                   proximity(3)
                  }
   ACCESS  read-write
   STATUS  mandatory
   DESCRIPTION
       "Enable/Disable DNS resolution for Farm Addresses. In proximity mode, the WSD will give the best proximity address for the farm."
-- DEFVAL { 2 }
   ::=  {rsServerDispatcher 31}

rsWSDUserPassword  OBJECT-TYPE
    	SYNTAX DisplayString (SIZE(1..8))
    	ACCESS  read-write
   	STATUS  mandatory
   	DESCRIPTION
     	 "Software download user provided password."
   	::=  {rsServerDispatcher 33}

rsWSDUserVersion  OBJECT-TYPE
    	SYNTAX DisplayString (SIZE(1..6))
    	ACCESS  read-write
   	STATUS  mandatory
   	DESCRIPTION
     	 "Software download user provided version."
   	::=  {rsServerDispatcher 34}

rsWSDNatStatus  OBJECT-TYPE
    SYNTAX INTEGER {
                    enable(1),
                    disable(2)
                   }
    ACCESS  read-write
    STATUS  mandatory
    DESCRIPTION
        "Enable/Disable NAT - to hide the address of the server in messages send ."
--  DEFVAL { 2 }
    ::=  {rsServerDispatcher 35}


rsWSDRedundancyTakeback  OBJECT-TYPE
   SYNTAX INTEGER {
        automatic(1),
        manual(2)
   }
   ACCESS  read-write
   STATUS  mandatory
   DESCRIPTION
       "Whether to take the interfaces when coming up from redundancy failure automatically or wait for manual terminal command"
-- DEFVAL { 1 }
   ::=  {rsServerDispatcher 37}

rsMLB  OBJECT IDENTIFIER ::= { rsServerDispatcher 38 }

rsCSD  OBJECT IDENTIFIER ::= { rsServerDispatcher 39 }

rsNWSD  OBJECT IDENTIFIER ::= { rsServerDispatcher 40 }


rsWSDIfTable  OBJECT-TYPE
    SYNTAX SEQUENCE OF  RsWSDIfEntry
    ACCESS  not-accessible
    STATUS  mandatory
    DESCRIPTION
      "RND-specific interface table.  Each table entry includes an
      index, Board number, Network Address, interface status, clock
      indicator and interface cost."
    ::= {  rsServerDispatcher  41  }


rsWSDIfEntry  OBJECT-TYPE
    SYNTAX RsWSDIfEntry
    ACCESS  not-accessible
    STATUS  mandatory
    DESCRIPTION
       " The row definition for this table."
    INDEX   { rsWSDIfIndex  }
    ::= {  rsWSDIfTable 1  }


RsWSDIfEntry ::= SEQUENCE {
  rsWSDIfIndex
     INTEGER,
  rsWSDIfBoardNum
     INTEGER,
  rsWSDIfNetAddress
     NetworkAddress,
  rsWSDIfStatus
     INTEGER,
  rsWSDIfClockType
     INTEGER,
 rsWSDIfBaudRate
     INTEGER,
  rsWSDIfCost
     INTEGER,
  rsWSDIfCompression
     INTEGER,
  rsWSDIfCompressionStatus
     INTEGER,
  rsWSDIfCompressionRate
     INTEGER,
  rsWSDIfLATCompression
     INTEGER,
  rsWSDIfCompressionType
     INTEGER,
rsWSDIfFilterMode
     INTEGER,
rsWSDIfChannelType
     INTEGER,
rsWSDIfBridge
     INTEGER,
rsWSDHighPriorityIf    -- New Parameters
     INTEGER,
rsWSDWanHeader   -- New Parameters
     INTEGER,
rsWSDDuplexMode  -- New Parameters
     INTEGER
  }

rsWSDIfIndex OBJECT-TYPE
    SYNTAX   INTEGER
    ACCESS  read-only
    STATUS  mandatory
    DESCRIPTION
     "Index to the RND Interface Table. The interface defined by a
     particular value of this index is the same interface as
     identified by the same value of ifIndex (MIBII)."
         ::= {  rsWSDIfEntry 1  }

rsWSDIfBoardNum OBJECT-TYPE
    SYNTAX   INTEGER
    ACCESS  read-only
    STATUS  mandatory
    DESCRIPTION
     "The interface defined by this entry correspTnds to the board
     defined by the same value of rndSlotBoardNum in the rndSlotTab."
    ::= {  rsWSDIfEntry 2  }

rsWSDIfNetAddress OBJECT-TYPE
    SYNTAX   NetworkAddress
    ACCESS  read-only
    STATUS  mandatory
    DESCRIPTION
     "The IP address of the interface defined by the particular value of
     rsWSDIfIndex."
    ::= {  rsWSDIfEntry 3  }

rsWSDIfStatus  OBJECT-TYPE
    SYNTAX   INTEGER  {
       ok (1),
       okSingleBrg(2),
       okMultiBrg(3),
       connctFault(4),
       rxFault(5),
       txFault(6),
       channelLoopback(7),
       rxClockFault(8),
       t1Alarm(9)
    }
    ACCESS  read-only
    STATUS  mandatory
    DESCRIPTION
     "The current status of the interface."
     ::= {  rsWSDIfEntry 4  }

rsWSDIfClockType   OBJECT-TYPE
    SYNTAX  INTEGER {
       external(1),
       internal(2),
       t1(3),
       g703(4)
    }
    ACCESS  read-write
    STATUS  mandatory
    DESCRIPTION
     "rsWSDIfClockType defines the type of clock each interface
     uses: internal or external."
    ::= {  rsWSDIfEntry 5  }

rsWSDIfBaudRate    OBJECT-TYPE          -- Level II routing
    SYNTAX   INTEGER   -- word
    ACCESS  read-write
    STATUS  mandatory
    DESCRIPTION
     " Defines the baud rate of use by the interface. The valid
      rates are determined by the type of the media for which this
      baud rate is defined."
    ::= { rsWSDIfEntry 6  }


rsWSDIfCost    OBJECT-TYPE          -- Level II routing
    SYNTAX   INTEGER   -- word
    ACCESS  read-write
    STATUS  mandatory
    DESCRIPTION
       "This variable assigns a transmission cost to the interface
        (channel or LAN). These costs are used in Level II routing. The
        costs aretypically inversly proportional to the channel quality."
    ::= { rsWSDIfEntry 7  }

rsWSDIfCompression   OBJECT-TYPE
    SYNTAX  INTEGER {
       enable(1),
       disable(2)
    }
    ACCESS  read-write
    STATUS  mandatory
    DESCRIPTION
       "Defines whether data compression is enabled or disabled for the
       interface."
    ::= {  rsWSDIfEntry 8  }

  rsWSDIfCompressionStatus  OBJECT-TYPE
  SYNTAX  INTEGER {
       not-inserted(1),
       active(2),
       not-active(3),
       disable(4)
    }
    ACCESS  read-only
    STATUS  mandatory
    DESCRIPTION
       "Defines the status of the compression component:
        not-inserted - Compression component is not in the device
        active -     Compression is enabled and operates correctly
        not-active - Compression is enables but does not operate.
                     The reason may be that there is no compression
                     component on the device connected to this interface.
        disabled   - Compression was disabled by management, using
                     variable rndCompression."
    ::= {  rsWSDIfEntry 9  }

  rsWSDIfCompressionRate  OBJECT-TYPE
    SYNTAX  INTEGER
    ACCESS  read-only
    STATUS  mandatory
    DESCRIPTION
  "Percentage of compression. This variable applies only
  if rndCompressionStatus is active."
    ::= {  rsWSDIfEntry 10  }

  rsWSDIfLATCompression  OBJECT-TYPE
    SYNTAX  INTEGER {
       enable(1),
       disable(2)
    }
    ACCESS  read-write
    STATUS  mandatory
    DESCRIPTION
  "Enable/Disable the LAT Compression."
    ::= {  rsWSDIfEntry 11  }

  rsWSDIfCompressionType  OBJECT-TYPE
    SYNTAX  INTEGER {
       none(1),
       lowSpeed(2),
       highSpeed(3)
    }
    ACCESS  read-only
    STATUS  mandatory
    DESCRIPTION
        "This parameter indicates the type of compression option available in the device.
         none(1)     - indicates that there is no compression option in the device
         lowSpeed(2) - indicates a compression option which is  operational up
                       to line speed sof 64 kbps.
         highSpeed(3)- indicates a compression option which is  operational up
                       to line speeds of 2 Mbps."
    ::= {  rsWSDIfEntry 12  }

rsWSDIfFilterMode  OBJECT-TYPE
    SYNTAX  INTEGER {
       destinationOnly(1),
       sourceAndDestination(2),
       none(3)
    }
    ACCESS  read-write
    STATUS  mandatory
    DESCRIPTION
         "This parameter indicates the type of filtering in the device. "
    ::= {  rsWSDIfEntry 13 }

    rsWSDIfChannelType OBJECT-TYPE
      SYNTAX  INTEGER {
         wanChannel(1),
         ogRanPort(2),
         routerToBridge(3),
         spsFramRelay(4),         -- Frame Relay with external SPS.
         dialBackup(5),
         snar(6),
         lan(7),
         spsX25(8),
         frameRelay1490(9),       -- Frame Relay with full  RFC1490 support.
         frameRelay1490CAR(10),   -- Frame Relay with CAR RFC1490 bridge encapsulation.
         frameRelayCAR(11),       -- Frame Relay with CAR and RND's encapsulation
         ppp(12)        -- New Value
        }
      ACCESS   read-write
      STATUS   mandatory
      DESCRIPTION
        " The type of the WAN channel "
   ::= { rsWSDIfEntry 14 }

    rsWSDIfBridge OBJECT-TYPE
      SYNTAX  INTEGER {
         enable(1),
         disable(2)
        }
      ACCESS   read-write
      STATUS   mandatory
      DESCRIPTION
        " This variable indicates  whether this interface forward Layer II pakages."
   ::= { rsWSDIfEntry 15 }

    rsWSDHighPriorityIf  OBJECT-TYPE
      SYNTAX  INTEGER {
         enable(1),
         disable(2)
        }
      ACCESS   read-write
      STATUS   mandatory
      DESCRIPTION
        " This variable indicates  whether this interface will forward pakages
        that fit HighPriority set by the manager."
       ::= { rsWSDIfEntry 16}

    rsWSDWanHeader  OBJECT-TYPE
      SYNTAX  INTEGER {
         regular(1),
         short(2)
        }
      ACCESS   read-write
      STATUS   mandatory
      DESCRIPTION
        " This variable indicates the RND WAN header type used for frames
          which pass through this interface. 'regular' specifies a 14 bytes
          header compatible with older OG versions and 'short' a 4 byte header
          compatible with the RND adapter product family."
       ::= { rsWSDIfEntry 17}

    rsWSDDuplexMode  OBJECT-TYPE
      SYNTAX  INTEGER {
         half(1),
         full(2),
         auto(3)
        }
      ACCESS   read-write
      STATUS   mandatory
      DESCRIPTION
        " This variable indicates whether this interface operates in half duplex
          full duplex or auto negotiation mode."
       ::= { rsWSDIfEntry 18}

-- The following definitions are applicable for the mirroring

rsWSDClientMirrorPercentage OBJECT-TYPE
    SYNTAX  INTEGER  (1..100)
    ACCESS  read-write
    STATUS  mandatory
    DESCRIPTION
      "The percent of client entries to back up."
--  DEFVAL  { 100 }
    ::=  {rsServerDispatcher 42}

rsWSDMirrorStatus OBJECT-TYPE
    SYNTAX  INTEGER {
      enable(1),
      disable(2)
    }
    ACCESS  read-write
    STATUS  mandatory
    DESCRIPTION
      "Enable/Disable mirroring. This enables the allocation of the mirror tables."
    ::=  {rsServerDispatcher 43}

rsWSDMirrorProtocolMode OBJECT-TYPE
    SYNTAX  INTEGER {
      enable(1),
      disable(2)
    }
    ACCESS  read-write
    STATUS  mandatory
    DESCRIPTION
      "Enable/Disable of the mirror protocol. That is whether to send the mirror
       messages."
    ::=  {rsServerDispatcher 44}

rsWSDApplicationMirrorTable OBJECT-TYPE
    SYNTAX SEQUENCE OF RsWSDApplicationMirrorEntry
    ACCESS not-accessible
    STATUS  mandatory
    DESCRIPTION
      "Table containing the list of active mirror entries."
    ::=  {rsServerDispatcher 45}

rsWSDApplicationMirrorEntry OBJECT-TYPE
    SYNTAX RsWSDApplicationMirrorEntry
    ACCESS not-accessible
    STATUS  mandatory
    DESCRIPTION
       "The row definition for this table."
   INDEX { rsWSDMirrorActiveAddress }
    ::=  { rsWSDApplicationMirrorTable 1 }

RsWSDApplicationMirrorEntry ::= SEQUENCE {
  rsWSDMirrorActiveAddress IpAddress,
  rsWSDMirrorActiveStatus  INTEGER
  }

rsWSDMirrorActiveAddress OBJECT-TYPE
    SYNTAX  IpAddress
    ACCESS  read-only
    STATUS  mandatory
    DESCRIPTION
      "The IP address of the active device."
    ::=  {rsWSDApplicationMirrorEntry 1}

rsWSDMirrorActiveStatus OBJECT-TYPE
    SYNTAX INTEGER {
              active(1),
              notInService(2),
              notReady(3),
              createAndGo(4),
              createAndWait(5),
              destroy(6) }
    ACCESS  read-write
    STATUS  mandatory
    DESCRIPTION
       "This variable indicates the administrative status of this entry.
        Used to delete an entry of this table."
    ::=  { rsWSDApplicationMirrorEntry 2 }


rsWSDClientMirrorPollingTime OBJECT-TYPE
    SYNTAX  INTEGER
    ACCESS  read-write
    STATUS  mandatory
    DESCRIPTION
      "The polling time for sending the client entries."
--  DEFVAL  { 10 }
    ::=  {rsServerDispatcher 46}

rsPlatformIdentifier OBJECT-TYPE
   SYNTAX  INTEGER {
        vgate(1),
        vgfe(2),
        onecpu(3),
        onecpuh(4),
        boomer(5),
        cougar(6),
        argo(7),
        kitty(8),
        voyager(9),
        galaxy(10),
        ninia(11),
        mecong(12),
        congo(13),
        ods1(14),
        ods2(15),
        ods3(16),
        ods3S1(17),
        ods3S2(18),
        vl(19),
        ods-ht(20),
        virtual(21),
        ods-htqe(22),
        ods-mrxl(23),
        dp-100(24),
        dp-200(25),
        dp-400(26),
        dp-20(27),
        dp-60(28),
        dp-6(29)
   }
   ACCESS  read-only
   STATUS  mandatory
   DESCRIPTION
        "An administratively-assigned value that identifies managed device platform."
   ::= { rsServerDispatcher 47 }

rsConfigurationIdentifier OBJECT-TYPE
   SYNTAX  INTEGER {
        twoPorts(1),
        fourPorts(2),
        fixed-2(3),
        fixed-8(4),
        fixed-8-2(5),
        fixed-16-5(6),
        chassis(7),
        fixed-7(8),
        fixed-16-7-1(9),
        fixed-9-1(10),
        fixed-8cg-9fg-2fxg(11),
        fixed-12cg-8fg(12),
        fixed-3cg(13),
        fixed-4-2(14),
        fixed-12-4-2(15),
        fixed-2-8-9(16),
        fixed-4-4-8-2(17),
        fixed-4-8-2(18),
        fixed-6(19),
        fixed-6-2(20),
        fixed-4-20-2(21),
        fixed-2-1(22),
        fixed-4-4-20-2(23),
        fixed-24-2(24),
        fixed-2-6-2(25)
   }
   ACCESS  read-only
   STATUS  mandatory
   DESCRIPTION
        "An administratively-assigned value that identifies managed device configuration.
         cg - copper gig, fg - fiber gig, fxg - fiber 10gig."
   ::= { rsServerDispatcher 48 }

rsSWPasswordStatus OBJECT-TYPE
   SYNTAX  INTEGER {
        statusUnset(1),
        passwordOK(2),
        wrongPassword(3)
   }
   ACCESS  read-write
   STATUS  mandatory
   DESCRIPTION
        "Software download password status."
   DEFVAL {statusUnset}
   ::= { rsServerDispatcher 49 }

rsWSDFlashSize OBJECT-TYPE
   SYNTAX  INTEGER
   ACCESS  read-only
   STATUS  mandatory
   DESCRIPTION
        "Flash Size"
   ::= { rsServerDispatcher 50 }

rsWSDDRAMSize OBJECT-TYPE
   SYNTAX  INTEGER
   ACCESS  read-only
   STATUS  mandatory
   DESCRIPTION
        "DRAM Size"
   ::= { rsServerDispatcher 51 }

rsWSDVLANRedundOperStatus OBJECT-TYPE
    SYNTAX  INTEGER {
        blockBroadcast(1),
        forwardTraffic(2),
	blockAll (3)
    }
    ACCESS  read-write
    STATUS  mandatory
    DESCRIPTION
    "Sets the backup redundant device for a VLAN.
     blockBroadcast - blocks only the broadcast traffic
     forwardTraffic - forwards the traffic
     blockAll - blocks broadcast and unicast traffic"
    ::=  { rsServerDispatcher 52 }

rsWSDResourceUtilization OBJECT-TYPE
    SYNTAX  INTEGER  (0..100)
    ACCESS  read-only
    STATUS  mandatory
    DESCRIPTION
      "Highest Utilization of controller and engines"
    DEFVAL  { 0 }
    ::=  { rsServerDispatcher 53 }

rsWSDRSResourceUtilization OBJECT-TYPE
    SYNTAX  INTEGER  (0..100)
    ACCESS  read-only
    STATUS  mandatory
    DESCRIPTION
      "DefensePro Controller utilization"
    DEFVAL  { 0 }
    ::=  { rsServerDispatcher 54 }

rsWSDREResourceUtilization OBJECT-TYPE
    SYNTAX  INTEGER  (0..100)
    ACCESS  read-only
    STATUS  mandatory
    DESCRIPTION
      "Resource Utilization of network utilization"
    DEFVAL  { 0 }
    ::=  { rsServerDispatcher 55 }

rsWSDBuildNumber OBJECT-TYPE
    SYNTAX  DisplayString
    ACCESS  read-write
    STATUS  mandatory
    DESCRIPTION
      "Build number"
    ::=  { rsServerDispatcher 56 }

rsWSDUseOneTrap OBJECT-TYPE
    SYNTAX  INTEGER {
        enable(1),
        disable(2)
    }
    ACCESS  read-write
    STATUS  mandatory
    DESCRIPTION
      "When enabled, a single trap is used to indicate server failure. When disabled,
        continuous traps are sent."
    DEFVAL { 2 }
    ::=  { rsServerDispatcher 57 }

rsWSDSecuredComm  OBJECT IDENTIFIER ::= { rsServerDispatcher 58 }

rsWSDSCProtcolsTable OBJECT-TYPE
    SYNTAX SEQUENCE OF RsWSDSCProtcolsEntry
    ACCESS not-accessible
    STATUS mandatory
    DESCRIPTION
      "Table containing the list of ports/protocols for secured (encrypted)
       communication between the device and the management station or other device."
    ::=  { rsWSDSecuredComm 1 }

rsWSDSCProtcolsEntry OBJECT-TYPE
    SYNTAX RsWSDSCProtcolsEntry
    ACCESS not-accessible
    STATUS  mandatory
    DESCRIPTION
       "The row definition for protocol table."
    INDEX { rsWSDSCProtocol }
    ::=  { rsWSDSCProtcolsTable 1}

RsWSDSCProtcolsEntry ::= SEQUENCE {
    rsWSDSCProtocol       INTEGER,
    rsWSDSCProtocolStatus INTEGER
}

rsWSDSCProtocol OBJECT-TYPE
    SYNTAX INTEGER {
      snmp(1),
      tftp(2),
      lrp(3),
      prp(4),
      srp(5),
      mirror(6)
    }
    ACCESS  read-only
    STATUS  mandatory
    DESCRIPTION
      "The protocol that should work in secured mode."
    ::=  { rsWSDSCProtcolsEntry 1}

rsWSDSCProtocolStatus OBJECT-TYPE
    SYNTAX INTEGER {
      encrypted(1),
      notEncrypted(2)
    }
    ACCESS  read-write
    STATUS  mandatory
    DESCRIPTION
      "The status (secured or not secured) of the protocol."
--  DEFVAL  { 2 }
    ::=  { rsWSDSCProtcolsEntry 2}

rsWSDSNMPPortsTable OBJECT-TYPE
    SYNTAX SEQUENCE OF RsWSDSNMPPortsEntry
    ACCESS not-accessible
    STATUS mandatory
    DESCRIPTION
      "The table contains all the physical ports. Each port can be set to
       allow/block SNMP operations to the device."
    ::= { rsServerDispatcher 59 }

rsWSDSNMPPortsEntry OBJECT-TYPE
  SYNTAX RsWSDSNMPPortsEntry
  ACCESS not-accessible
  STATUS mandatory
  DESCRIPTION
    "Row definition for the table."
  INDEX { rsWSDSNMPPhysicalPortNumber }
  ::= { rsWSDSNMPPortsTable 1 }

RsWSDSNMPPortsEntry ::= SEQUENCE {
  rsWSDSNMPPhysicalPortNumber INTEGER,
  rsWSDSNMPPhysicalPortState  INTEGER,
  rsWSDSNMPPhysicalPortTelnetState INTEGER,
  rsWSDSNMPPhysicalPortSSHState INTEGER,
  rsWSDSNMPPhysicalPortWebState INTEGER,
  rsWSDSNMPPhysicalPortSSLState INTEGER
}

rsWSDSNMPPhysicalPortNumber OBJECT-TYPE
  SYNTAX INTEGER
  ACCESS read-only
  STATUS mandatory
  DESCRIPTION
    "Physical port number."
  ::= { rsWSDSNMPPortsEntry 1 }

rsWSDSNMPPhysicalPortState OBJECT-TYPE
  SYNTAX INTEGER {
    enable(1),
    disable(2)
  }
  ACCESS read-write
  STATUS mandatory
  DESCRIPTION
    "enable - accept SNMP operations on the physical port. disable -
     ignore SNMP opertaions on the physical port."
  DEFVAL { 1 }
  ::= { rsWSDSNMPPortsEntry 2 }

rsWSDSNMPPhysicalPortTelnetState OBJECT-TYPE
  SYNTAX INTEGER {
    enable(1),
    disable(2)
  }
  ACCESS read-write
  STATUS mandatory
  DESCRIPTION
    "enable - accept Telnet operations on the physical port. disable -
     ignore Telnet opertaions on the physical port."
  DEFVAL { 1 }
  ::= { rsWSDSNMPPortsEntry 3 }

rsWSDSNMPPhysicalPortSSHState OBJECT-TYPE
  SYNTAX INTEGER {
    enable(1),
    disable(2)
  }
  ACCESS read-write
  STATUS mandatory
  DESCRIPTION
    "enable - accept SSH operations on the physical port. disable -
     ignore SSH opertaions on the physical port."
  DEFVAL { 1 }
  ::= { rsWSDSNMPPortsEntry 4 }



rsWSDSNMPPhysicalPortWebState OBJECT-TYPE
  SYNTAX INTEGER {
    enable(1),
    disable(2)
  }
  ACCESS read-write
  STATUS mandatory
  DESCRIPTION
    "enable - accept Web operations on the physical port. disable -
     ignore Web opertaions on the physical port."
  DEFVAL { 1 }
  ::= { rsWSDSNMPPortsEntry 5 }

rsWSDSNMPPhysicalPortSSLState OBJECT-TYPE
  SYNTAX INTEGER {
    enable(1),
    disable(2)
  }
  ACCESS read-write
  STATUS mandatory
  DESCRIPTION
    "enable - accept SSL operations on the physical port. disable -
     ignore SSL opertaions on the physical port."
  DEFVAL { 1 }
  ::= { rsWSDSNMPPortsEntry 6 }
  


rsSendPortUnreachableStatus OBJECT-TYPE
  SYNTAX INTEGER {
    enable(1),
    disable(2)
  }
  ACCESS read-write
  STATUS mandatory
  DESCRIPTION
    "enable - send port unreachable (UDP) or reset (TCP) when port not available. disable -
     don't send a response, just discard the received packet."
  DEFVAL { 1 }
  ::= { rsServerDispatcher 175 }

rsSysUtilControllerCpuWarningAlertStartThreshold OBJECT-TYPE
   SYNTAX INTEGER (0..100)
   ACCESS  read-write
   STATUS  mandatory
   DESCRIPTION
       "Specifies the warning alert-start threshold for high utilization of the controller CPU"
    DEFVAL {80}
	::=  { rsServerDispatcher 200 }

rsSysUtilControllerCpuWarningAlertStopThreshold OBJECT-TYPE
   SYNTAX INTEGER (0..100)
   ACCESS  read-write
   STATUS  mandatory
   DESCRIPTION
       "Specifies the warning alert-stop threshold for high utilization of the controller CPU"
    DEFVAL {75}
	::=  { rsServerDispatcher 201 }

rsSysUtilAnyEngineCpuWarningAlertStartThreshold OBJECT-TYPE
   SYNTAX INTEGER (0..100)
   ACCESS  read-write
   STATUS  mandatory
   DESCRIPTION
       "Specifies the warning alert-start threshold for high utilization of any flow-engine CPU"
    DEFVAL {80}
	::=  { rsServerDispatcher 202 }

rsSysUtilAnyEngineCpuWarningAlertStopThreshold OBJECT-TYPE
   SYNTAX INTEGER (0..100)
   ACCESS  read-write
   STATUS  mandatory
   DESCRIPTION
       "Specifies the warning alert-stop threshold for high utilization of any flow-engine CPU"
	DEFVAL {75}  
    ::=  { rsServerDispatcher 203 }

rsSysUtilControllerCpuErrorAlertStartThreshold OBJECT-TYPE
   SYNTAX INTEGER (0..100)
   ACCESS  read-write
   STATUS  mandatory
   DESCRIPTION
       "Specifies the error alert-start threshold for high utilization of the controller CPU"
   DEFVAL {90}  
   ::=  { rsServerDispatcher 204 }

rsSysUtilControllerCpuErrorAlertStopThreshold OBJECT-TYPE
   SYNTAX INTEGER (0..100)
   ACCESS  read-write
   STATUS  mandatory
   DESCRIPTION
       "Specifies the error alert-stop threshold for high utilization of the controller CPU"
    DEFVAL {85}
	::=  { rsServerDispatcher 205 }

rsSysUtilAnyEngineCpuErrorAlertStartThreshold OBJECT-TYPE
   SYNTAX INTEGER (0..100)
   ACCESS  read-write
   STATUS  mandatory
   DESCRIPTION
       "Specifies the error alert-start threshold for high utilization of any flow-engine CPU"
   DEFVAL {90}
    ::=  { rsServerDispatcher 206 }

rsSysUtilAnyEngineCpuErrorAlertStopThreshold OBJECT-TYPE
   SYNTAX INTEGER (0..100)
   ACCESS  read-write
   STATUS  mandatory
   DESCRIPTION
       "Specifies the error alert-stop threshold for high utilization of any flow-engine CPU"
   DEFVAL {85}
    ::=  { rsServerDispatcher 207 }
	
rsSysUtilCpuAlertsStatus OBJECT-TYPE
   SYNTAX INTEGER {
      enable(1),
      disable(2)
   }
   ACCESS  read-write
   STATUS  mandatory
   DESCRIPTION
       "CPU alerts status"
   DEFVAL  {disable}
    ::=  { rsServerDispatcher 208 }	

rsBWM  OBJECT IDENTIFIER ::= { rsServerDispatcher 60 }


rsWSDTelnetUserTable OBJECT-TYPE
  SYNTAX  SEQUENCE OF RsWSDTelnetUserEntry
  ACCESS  not-accessible
  STATUS  mandatory
  DESCRIPTION
    "A table containing the users authorized to use TELNET."
  ::= {rsServerDispatcher 61}

rsWSDTelnetUserEntry OBJECT-TYPE
  SYNTAX  RsWSDTelnetUserEntry
  ACCESS  not-accessible
  STATUS  mandatory
  DESCRIPTION
    "Information about a particular Telnet user."
  INDEX   { rsWSDTelnetUserName }
  ::= { rsWSDTelnetUserTable 1 }

RsWSDTelnetUserEntry ::= SEQUENCE {
    rsWSDTelnetUserName     DisplayString,
    rsWSDTelnetUserPassword DisplayString,
    rsWSDTelnetUserEAddr    DisplayString,
    rsWSDTelnetUserSeverity INTEGER,
    rsWSDTelnetUserStatus   RowStatus,
    rsWSDTelnetUserGroup    DisplayString,
    rsWSDTelnetUserConfigurationTraceStatus INTEGER,
    rsWSDTelnetUserConfigurationTraceInf INTEGER,
    rsWSDTelnetUserWebAccessLevel INTEGER,
    rsWSDTelnetUserSshPublicKeyName DisplayString
  }

rsWSDTelnetUserName OBJECT-TYPE
    SYNTAX DisplayString (SIZE(0..30))
    ACCESS  read-write
    STATUS  mandatory
    DESCRIPTION
    "User Name."
    ::= {rsWSDTelnetUserEntry 1}

rsWSDTelnetUserPassword OBJECT-TYPE
    SYNTAX DisplayString (SIZE(0..64))
    ACCESS  read-write
    STATUS  mandatory
    DESCRIPTION
    "User password."
    ::= {rsWSDTelnetUserEntry 2}

rsWSDTelnetUserEAddr OBJECT-TYPE
    SYNTAX DisplayString (SIZE(0..63))
    ACCESS  read-write
    STATUS  mandatory
    DESCRIPTION
    "User email address."
    ::= {rsWSDTelnetUserEntry 3}

rsWSDTelnetUserSeverity OBJECT-TYPE
   SYNTAX INTEGER {
      none(1),
      info(2),
      warning(3),
      error(4),
      fatal(5)
   }
   ACCESS read-write
   STATUS mandatory
   DESCRIPTION
      "minimum failure severity to be notified by mail"
   ::=  { rsWSDTelnetUserEntry 4}

rsWSDTelnetUserStatus OBJECT-TYPE
   SYNTAX RowStatus
   ACCESS read-write
   STATUS mandatory
   DESCRIPTION
      "Entry status"
   ::=  { rsWSDTelnetUserEntry 5}

rsWSDTelnetUserGroup OBJECT-TYPE
	SYNTAX DisplayString (SIZE(0..30))
	ACCESS read-write
	STATUS mandatory
	DESCRIPTION
		"The group to which that user belongs."
	::= { rsWSDTelnetUserEntry 6}

rsWSDTelnetUserConfigurationTraceStatus OBJECT-TYPE
   SYNTAX INTEGER {
      enable(1),
      disable(2)
   }
   ACCESS read-write
   STATUS mandatory
   DESCRIPTION
      "enable mail trace of configuration change"
   DEFVAL { disable }
   ::=  { rsWSDTelnetUserEntry 7}


rsWSDTelnetUserConfigurationTraceInf OBJECT-TYPE
   SYNTAX INTEGER {
      all(1),
      webBased(2),
      terminal(3),
      snmp(4),
      telnetSSH(5),
      ftp(6),
      ftpSSH(7)
   }
   ACCESS read-write
   STATUS mandatory
   DESCRIPTION
      "specify configuration interfaces via which changes in configuration should be informed"
   DEFVAL { all }
   ::=  { rsWSDTelnetUserEntry 8}

rsWSDTelnetUserWebAccessLevel OBJECT-TYPE
   SYNTAX INTEGER {
      readwrite(1),
      readonly(2),
      none(3)
   }
   ACCESS read-write
   STATUS mandatory
   DESCRIPTION
      "Defines access level for web based management. Either read-write, read-only or no access."
   DEFVAL { readwrite }
   ::=  { rsWSDTelnetUserEntry 9}

rsWSDTelnetUserSshPublicKeyName OBJECT-TYPE
    SYNTAX DisplayString (SIZE(0..63))
    ACCESS  read-write
    STATUS  mandatory
    DESCRIPTION
		"The name of the Certificate Entry where the ssh public key resides."
    ::= {rsWSDTelnetUserEntry 10}

rsWSDTelnetParams OBJECT IDENTIFIER ::= {rsServerDispatcher 62 }

rsWSDTelnetPort OBJECT-TYPE
    SYNTAX  INTEGER (1..65535)
    ACCESS  read-write
    STATUS  mandatory
    DESCRIPTION
      "The Telnet Server Port."
--  DEFVAL  { 23 }
    ::=  {rsWSDTelnetParams 1}


rsWSDTelnetStatus OBJECT-TYPE
   SYNTAX  INTEGER {
        enable(1),
      	disable(2)
   }
   ACCESS  read-write
   STATUS  mandatory
   DESCRIPTION
        "Telnet Status. Enable/Disable Telnet Terminal operation."
--  DEFVAL  { disable }
   ::= { rsWSDTelnetParams 2 }

rsSSD  OBJECT IDENTIFIER ::= { rsServerDispatcher 63 }

rsSSDvirtualLan  OBJECT IDENTIFIER ::= { rsSSD 1 }

--
--  rsSSDvirtualLanTable
--
rsSSDvirtualLanTable  OBJECT-TYPE
   SYNTAX  SEQUENCE OF RsSSDvirtualLanEntry
   ACCESS  not-accessible
   STATUS  mandatory
   DESCRIPTION
         "An entry of this table specifies an new ifIndex with a type of
          propVirtual(53)."
   ::= { rsSSDvirtualLan 1 }

rsSSDvirtualLanEntry OBJECT-TYPE
   SYNTAX  RsSSDvirtualLanEntry
   ACCESS  not-accessible
   STATUS  mandatory
   DESCRIPTION
         "A list of information for each virtual LAN."
   INDEX  { rsSSDvlIfIndex}
   ::= { rsSSDvirtualLanTable 1 }

RsSSDvirtualLanEntry   ::= SEQUENCE {
     rsSSDvlIfIndex          		INTEGER,
     rsSSDvlProto            		INTEGER,
     rsSSDvlAutoConfigEnable 		TruthValue,
     rsSSDvlStatus           		RowStatus,
     rsSSDvlType             		INTEGER,
     rsSSDvlTag                         INTEGER,
     rsSSDvlPriority                INTEGER,
     rsSSDvlUpCriterion             INTEGER,
     rsSSDvlDownCriterion           INTEGER
   }

rsSSDvlIfIndex OBJECT-TYPE
   SYNTAX  INTEGER
   ACCESS  read-write
   STATUS  mandatory
   DESCRIPTION
         "An logical interface number, corresponded this VL"
   ::= { rsSSDvirtualLanEntry 1 }

rsSSDvlProto  OBJECT-TYPE
   SYNTAX  INTEGER {
      other(1),
      ip(2),
      ipmulticast(3),
      ipxRaw(4),
      ipxET(5),
      ipxLLC(6),
      ipxSNAP(7),
      decNET(8),
      decLAT(9),
      netBios(10),
      appleTalk(11),
      xns(12),
      sna(13),
      userDefined(14),
      swVlan(15)
      }
   ACCESS  read-write
   STATUS  mandatory
   DESCRIPTION
         "The protocol, supported by this VL. The meanings of the values are:
      other: none of the following. This VL includes any protocol except the
             following protocols. It  is a bridging VL. RS relies on
             a third-party router to exchange traffic between nodes on different
             virtual LANs of this type.
      IP:    This is a routing VL, RS will route between nodes on
             different virtual LANs.
      IPmulticast: RS will broadcast the message to all  the VL's ports. Used for
             video-conferencing applications.
      ipxRaw: This is a Routing VL, RS will route between nodes on
             different virtual LANs.
      ipxET: This is a routing VL, RS will route between nodes on
             different virtual LANs.
      ipxLLC: This is a routing VL, RS will route between nodes on
             different virtual LANs.
      ipxSNAP: This is a routing VL, RS will route between nodes on
             different virtual LANs.
      decNET: This is a bridging VL, RS relies on a third-party router
             to exchange traffic between nodes on different DECnet virtual
             LANs of this type.
      netBios: This is a Bridging VL, RS relies on a third-party router
             to exchange traffic between nodes on different NetBIOS virtual
             LANs of this type.
      appleTalk: This is a bridging VL, RS relies on a third-party router
             to exchange traffic between nodes on different AppleTalk virtual
             LANs of this type.
      swVlan: This is a Bridging and routing VL (switch VL) , Bridging is
             done on the Hertz/Uhaul level , and the RS route between nodes on
             different virtual LANs and/or between nodes of the switch VL."

   ::= { rsSSDvirtualLanEntry 2 }

rsSSDvlAutoConfigEnable  OBJECT-TYPE
   SYNTAX  TruthValue
   ACCESS  read-write
   STATUS  mandatory
   DESCRIPTION
         "It is used only in the case of IP. The meanings of the values are:
      true(1):  Autolearning is used for this VL
      false(2): Autolearning isn't used for this VL from ports, specified in
                the table virtualLanAutoConfTable."
   ::= { rsSSDvirtualLanEntry 3 }

rsSSDvlStatus  OBJECT-TYPE
   SYNTAX  RowStatus
   ACCESS  read-write
   STATUS  mandatory
   DESCRIPTION
         "It is used to delete an entry"
   ::= { rsSSDvirtualLanEntry 4 }

rsSSDvlType OBJECT-TYPE
   SYNTAX INTEGER {
        regular(1),
        specBroadcast(2),
        specArpReq(3),
        specBroadcastAndUnicast(4),
        specArpReqAndUnicast(5),
	specSwitch(6)
        }
   ACCESS  read-write
   STATUS  mandatory
   DESCRIPTION
       "regular       - ordinary type
        specBroadcast - for switches that support VLANs as a set of ports and
                        only as a broadcast domain: broadcast frames do not
                        cross VLAN's bounders, but unicast frames may be
                        transmitted between different VLANs. Permits passing
                        of broadcast frames between Vgate's VLANs.
        specArpReq -    for switches that support VLANs as a set of ports and
                        only as a broadcast domain: broadcast frames do not
                        cross VLAN's bounders, but unicast frames may be
                        transmitted between different VLANs. Permits passing
                        of ARP request frames between Vgate's VLANs.
        specBroadcastAndUnicast -
                        for switches that support VLANs as a set of ports
                        but no frame crosses VLAN's bounders. Permits passing
                        of IP/ARP request broadcast and IP unicast frames
                        between Vgate's VLANs.
        specArpReqAndUnicast -
                        for switches that support VLANs as a set of ports
                        but no frame crosses VLAN's bounders. Permits passing
                        of ARP request broadcast and IP unicast frames between
                        Vgate's VLANs. This type can be used only for IP VLANs.
	specSwitch -
        		for switches that support VLANs as a set of ports.
                        This VLAN type is for switching when packets do not have
                        to get to the cpu except when an IP interface defined on the VLAN.
                        In Switch VLAN the cpu don't interfere in the bridging action
                        this is done on the Herzts level (L2)."
   ::= { rsSSDvirtualLanEntry 5 }


rsSSDvlTag OBJECT-TYPE
   SYNTAX  INTEGER
   ACCESS  read-write
   STATUS  mandatory
   DESCRIPTION
         "A VLAN tag, used for this VLAN on tagged ports.
          If it's 0, then a value of (rsSSDvlIfIndex-100000+1) is used"
   DEFVAL { 0 }
   ::= { rsSSDvirtualLanEntry 6 }

rsSSDvlPriority OBJECT-TYPE
   SYNTAX  INTEGER {
        low(1),
        high(2)
   }
   ACCESS  read-write
   STATUS  mandatory
   DESCRIPTION
         "A user priority, used for this VLAN on tagged ports."
   DEFVAL { 1 }
   ::= { rsSSDvirtualLanEntry 7 }

rsSSDvlUpCriterion OBJECT-TYPE
   SYNTAX  INTEGER {
        defaultByType(1),
        onePort(2),
        allPorts(3)
   }
   ACCESS  read-write
   STATUS  mandatory
   DESCRIPTION
         "The criterion according to which the vlan interface is considered to be up 
		  for interface grouping."
   DEFVAL { 1 }
   ::= { rsSSDvirtualLanEntry 8 }

rsSSDvlDownCriterion OBJECT-TYPE
   SYNTAX  INTEGER {
        defaultByType(1),
        onePort(2),
        allPorts(3)
   }
   ACCESS  read-write
   STATUS  mandatory
   DESCRIPTION
         "The criterion according to which the vlan interface is considered to be down 
		  for interface grouping."
   DEFVAL { 1 }
   ::= { rsSSDvirtualLanEntry 9 }

--
--   rsSSDvirtualLanPortsTable
--

rsSSDvirtualLanPortsTable  OBJECT-TYPE
   SYNTAX SEQUENCE OF RsSSDvirtualLanPortEntry
   ACCESS  not-accessible
   STATUS  mandatory
   DESCRIPTION
         "For each VL (a ifIndex with a type of propVirtual(53)) an entry of  this
           table specifies a set of ports, which it contains."
   ::= { rsSSDvirtualLan 2 }

rsSSDvirtualLanPortEntry   OBJECT-TYPE
   SYNTAX  RsSSDvirtualLanPortEntry
   ACCESS  not-accessible
   STATUS  mandatory
   DESCRIPTION
         "A entry of this table specifies a  VL and a port belonging to it"
   INDEX  { rsSSDvLIfIndex, rsSSDvLPortIfIndex}
   ::= { rsSSDvirtualLanPortsTable 1 }

RsSSDvirtualLanPortEntry  ::= SEQUENCE {
     rsSSDvLIfIndex      INTEGER,
     rsSSDvLPortIfIndex  INTEGER,
     rsSSDvLPortType     INTEGER,
     rsSSDvLPortStatus   RowStatus,
     rsSSDvLPortTag                     INTEGER,
     rsSSDvLPortInterfaceGroupingState  INTEGER
 }


rsSSDvLIfIndex  OBJECT-TYPE
   SYNTAX  INTEGER
   ACCESS  read-write
   STATUS  mandatory
   DESCRIPTION
        "An logical interface number, corresponding to this VL"
   ::= { rsSSDvirtualLanPortEntry 1 }

rsSSDvLPortIfIndex  OBJECT-TYPE
   SYNTAX  INTEGER
   ACCESS  read-write
   STATUS  mandatory
   DESCRIPTION
         "A physical port belonging to the VL specified by rsSSDvlIfIndex."
   ::= { rsSSDvirtualLanPortEntry 2 }

rsSSDvLPortType   OBJECT-TYPE
   SYNTAX  INTEGER {
        static(1),
        dynamic(2)
   }
   ACCESS  read-only
   STATUS  mandatory
   DESCRIPTION
         "static means configured by user dynamic means autoconfigured by the RS"
   ::= { rsSSDvirtualLanPortEntry 3}

rsSSDvLPortStatus  OBJECT-TYPE
   SYNTAX  RowStatus
   ACCESS  read-write
   STATUS  mandatory
   DESCRIPTION
         "It is used to delete an entry"
   ::= { rsSSDvirtualLanPortEntry 4}

rsSSDvLPortTag  OBJECT-TYPE
    SYNTAX INTEGER {
        untag(1),
        tag(2)
    }
    ACCESS  read-write
    STATUS  mandatory
    DESCRIPTION
        "This variable indicate if the port is tagged or untagged "
--  DEFVAL { 1 }
    ::= { rsSSDvirtualLanPortEntry 5 }

rsSSDvLPortInterfaceGroupingState OBJECT-TYPE
  SYNTAX INTEGER {
    included(1),
    excluded(2)
  }
  ACCESS read-write
  STATUS mandatory
  DESCRIPTION
    "included- the port effects the VLAN Up/Down decision for interface grouping. 
     excluded- the port does not effect the VLAN Up/Down decision for interface grouping."
  DEFVAL { 1 }
  ::= { rsSSDvirtualLanPortEntry 6 }

rsWSDThresholdWarnings  OBJECT IDENTIFIER ::= { rsServerDispatcher 64 }

rsWSDThreshTrapFloodDelay OBJECT-TYPE
    SYNTAX INTEGER (0..3600)
    ACCESS  read-write
    STATUS  mandatory
    DESCRIPTION
       "This variable defines how far (in seconds) will 2 Threshold Warning Traps be
        spaced for the same Threshold Warning Type. Default = 0, i.e. DISABLED"
--  DEFVAL {0}
    ::= { rsWSDThresholdWarnings 1 }

rsWSDCriticalTrapFloodDelay OBJECT-TYPE
    SYNTAX INTEGER (1..3600)
    ACCESS  read-write
    STATUS  mandatory
    DESCRIPTION
       "This variable defines how far (in seconds) will 2 Critical Warning Traps be
        spaced (of any type). Default = 20 seconds."
--  DEFVAL {20}
    ::= { rsWSDThresholdWarnings 2 }

rsIDS OBJECT IDENTIFIER ::= { rsServerDispatcher 65 }

rsWSDLicense OBJECT-TYPE
    SYNTAX DisplayString (SIZE(1..80))
    ACCESS  read-write
    STATUS  mandatory
    DESCRIPTION "The new licence for the device"
--    DEFVAL
    ::=  {rsServerDispatcher 66}

rsErrMailParams OBJECT IDENTIFIER ::= {rsServerDispatcher 67 }


rsErrMailEnable OBJECT-TYPE
   SYNTAX INTEGER {
      enable(1),
      disable(2)
   }
    ACCESS  read-write
    STATUS  mandatory
    DESCRIPTION
      "Send email on errors enable"
--  DEFVAL  { 2 }
    ::=  {rsErrMailParams 1}


rsErrMailGateway OBJECT-TYPE
    SYNTAX IpAddress
    ACCESS  read-write
    STATUS  mandatory
    DESCRIPTION
      "primary SMTP gateway for error mail"
    ::=  {rsErrMailParams 2}

rsErrMailSrcAddress OBJECT-TYPE
   SYNTAX DisplayString (SIZE(1..64))
   ACCESS read-write
   STATUS mandatory
   DESCRIPTION
    "source address to be used by device for outgoing mail"
     ::= {rsErrMailParams 3}

rsErrMailToFieldText OBJECT-TYPE
   SYNTAX DisplayString (SIZE(0..255))
   ACCESS read-write
   STATUS mandatory
   DESCRIPTION
    "Display name in 'TO:' field used by device for outgoing 
	 mail. When empty the text in the To field is generated 
	 by the device according to the message severity."
     ::= {rsErrMailParams 4}



rsWSDWebParams OBJECT IDENTIFIER ::= {rsServerDispatcher 68 }

rsWSDWebPort OBJECT-TYPE
    SYNTAX  INTEGER (1..65535)
    ACCESS  read-write
    STATUS  mandatory
    DESCRIPTION
      "The Web Server Port."
--  DEFVAL  { 80 }
    ::=  {rsWSDWebParams 1}


rsWSDWebStatus OBJECT-TYPE
   SYNTAX  INTEGER {
        enable(1),
      	disable(2)
   }
   ACCESS  read-write
   STATUS  mandatory
   DESCRIPTION
        "Web Status. Enable/Disable Web operation."
--  DEFVAL  { disable }
   ::= { rsWSDWebParams 2 }

rsWSDWebHelpLocation OBJECT-TYPE
   SYNTAX  DisplayString (SIZE(0..80))
   ACCESS  read-write
   STATUS  mandatory
   DESCRIPTION
        "Location of the help files directory."
   ::= { rsWSDWebParams 3 }

rsWSDWebSSLPort OBJECT-TYPE
   SYNTAX  INTEGER (1..65535)
   ACCESS  read-write
   STATUS  mandatory
   DESCRIPTION
        "SSL Port"
   DEFVAL { 443 }
   ::= { rsWSDWebParams 4 }

rsWSDWebSSLStatus OBJECT-TYPE
   SYNTAX  INTEGER {
        enable(1),
      	disable(2)
   }
   ACCESS  read-write
   STATUS  mandatory
   DESCRIPTION
        "Web SSL Status. Enable/Disable Web SSL operation."
   DEFVAL  { disable }
   ::= { rsWSDWebParams 5 }

rsWSDWebSSLPrivateKeyFile OBJECT-TYPE
   SYNTAX  DisplayString (SIZE(0..80))
   ACCESS  read-write
   STATUS  mandatory
   DESCRIPTION
        "File name of the private key file used by the web server."
   ::= { rsWSDWebParams 6 }

rsWSDWebSSLCertificateFile OBJECT-TYPE
   SYNTAX  DisplayString (SIZE(0..80))
   ACCESS  read-write
   STATUS  mandatory
   DESCRIPTION
        "File name of the certificate file used by the web server."
   ::= { rsWSDWebParams 7 }

rsWSDWebSSLCaFile OBJECT-TYPE
   SYNTAX  DisplayString (SIZE(0..80))
   ACCESS  read-write
   STATUS  mandatory
   DESCRIPTION
        "File name of the CAfile used by the web server."
   ::= { rsWSDWebParams 8 }

rsWSDWebSSLCaPath OBJECT-TYPE
   SYNTAX  DisplayString (SIZE(0..80))
   ACCESS  read-write
   STATUS  mandatory
   DESCRIPTION
        "Directory where the CA certificates are stored."
   ::= { rsWSDWebParams 9 }

rsWSDWebSSLClientAuthentication OBJECT-TYPE
   SYNTAX  INTEGER {
        password(1),
      	certificate(2)
   }
   ACCESS  read-write
   STATUS  mandatory
   DESCRIPTION
        "Type of client authentication."
   DEFVAL  { password }
   ::= { rsWSDWebParams 10 }

rsWSDWebAccessLevel OBJECT-TYPE
   SYNTAX  INTEGER {
        readOnly(1),
        readWrite(2)
   }
   ACCESS  read-write
   STATUS  mandatory
   DESCRIPTION
        "Determines whether web server allows read-only or also write access. In read-only mode some
         pages will not be available."
   DEFVAL  { readWrite }
   ::= { rsWSDWebParams 11 }

rsWSDWebSoapSupportStatus OBJECT-TYPE
    SYNTAX INTEGER {
        enable(1),
        disable(2)
    }
    ACCESS  read-write
    STATUS  mandatory
    DESCRIPTION
        "Whether the devices support of web services is enabled or not."
   DEFVAL  { disable }
   ::= { rsWSDWebParams 12 }

rsWSDWebSSLWeakCiphersSupportStatus OBJECT-TYPE
    SYNTAX INTEGER {
        enable(1),
        disable(2)
    }
    ACCESS  read-write
    STATUS  mandatory
    DESCRIPTION
        "Determines whether the secure web server allows SSL connections using weak ciphers security access."
   DEFVAL  { enable }
   ::= { rsWSDWebParams 13 }

rsWSDSysParams OBJECT IDENTIFIER ::= {rsServerDispatcher 69 }

rsWSDSysFlashSize OBJECT-TYPE
    SYNTAX  INTEGER
    ACCESS  read-only
    STATUS  mandatory
    DESCRIPTION
      "The flash size of the device in mega bytes."
--  DEFVAL  { 8 }
    ::=  {rsWSDSysParams 1}


rsWSDSysUpTime OBJECT-TYPE
   SYNTAX  DisplayString
   ACCESS  read-only
   STATUS  mandatory
   DESCRIPTION
        "Time since the system was last reinitialized in a convenient format."
--  DEFVAL  { 0 }
   ::= { rsWSDSysParams 2 }


rsWSDSysManagedTime  OBJECT-TYPE
   SYNTAX DisplayString (SIZE(0..80))
   ACCESS read-write
   STATUS mandatory
   DESCRIPTION
    "The time will be sent in the format hh:mm:ss"
   ::= { rsWSDSysParams 3 }

rsWSDSysManagedDate  OBJECT-TYPE
   SYNTAX DisplayString (SIZE(0..80))
   ACCESS read-write
   STATUS mandatory
   DESCRIPTION
    "The date will be sent in the format dd/mm/yyyy"
    ::= { rsWSDSysParams 4 }

rsWSDSysBaseMACAddress  OBJECT-TYPE
   SYNTAX DisplayString (SIZE(17))
   ACCESS read-write
   STATUS mandatory
   DESCRIPTION
    "Base MAC address of the device"
    ::= { rsWSDSysParams 5 }

rdwrDualPowerSupplyParams OBJECT IDENTIFIER ::= {rsWSDSysParams 6 }

rdwrPowerSupply1Status  OBJECT-TYPE
   SYNTAX INTEGER {
      active(1),
      notInService(2),
      invalid(3)
   }
   ACCESS read-only
   STATUS mandatory
   DESCRIPTION
    "Status of power supply 1. Relevant only for dual power supply devices.
     On single power supply devices the status returned is invalid."
   ::= { rdwrDualPowerSupplyParams 1 }

rdwrPowerSupply2Status  OBJECT-TYPE
   SYNTAX INTEGER {
      active(1),
      notInService(2),
      invalid(3)
   }
   ACCESS read-only
   STATUS mandatory
   DESCRIPTION
    "Status of power supply 2. Relevant only for dual power supply devices.
     On single power supply devices the status returned is invalid."
   ::= { rdwrDualPowerSupplyParams 2 }

rdwrPowerSupplyTrapStatus  OBJECT-TYPE
   SYNTAX FeatureStatus
   ACCESS read-write
   STATUS mandatory
   DESCRIPTION
    "Enables the user to disable the sending of traps for the power supply status"
   ::= { rdwrDualPowerSupplyParams 3 }

rdwrPowerSupplyStatus  OBJECT-TYPE
   SYNTAX INTEGER {
      singlePowerSupplyOk(1),
      firstPowerSupplyFailed(2),
      secondPowerSupplyFailed(3),
      doublePowerSupplyOk(4),
      unknownPowerSupplyFailed(5)
   }
   ACCESS read-only
   STATUS mandatory
   DESCRIPTION
    "The status of the power supply"
   ::= { rdwrDualPowerSupplyParams 4 }

rsWSDLicenseID OBJECT-TYPE
   SYNTAX DisplayString (SIZE(1..80))
   ACCESS  read-only
   STATUS  mandatory
   DESCRIPTION
    "License ID used for license downgrade"
    ::= { rsServerDispatcher 70 }

rsWSDSendFakeArp OBJECT-TYPE
   SYNTAX  INTEGER {
        enable(1),
      	disable(2)
   }
   ACCESS  read-write
   STATUS  mandatory
   DESCRIPTION
        "Controls whether a backup will send a fake ARP, advertising the main box's
         interfaces and VIPs, when the main box returns to service."
--  DEFVAL  { disable }
   ::= { rsServerDispatcher 71 }

rsWSDNTP OBJECT IDENTIFIER ::= { rsServerDispatcher 72 }

rsWSDNTPServerAddr  OBJECT-TYPE
    SYNTAX  IpAddress
    ACCESS  read-write
    STATUS  mandatory
    DESCRIPTION
      "Server IP address."
	::=  { rsWSDNTP 1 }

rsWSDNTPInterval OBJECT-TYPE
    SYNTAX INTEGER
    ACCESS read-write
    STATUS mandatory
    DESCRIPTION
      "Time update interval."
	::=  { rsWSDNTP 2 }

rsWSDNTPStatus OBJECT-TYPE
    SYNTAX INTEGER {
      enable(1),
      disable(2)
    }
    ACCESS read-write
    STATUS mandatory
    DESCRIPTION
      "Enable status for NTP synchronization."
	::=  { rsWSDNTP 3 }

rsWSDNTPTimeZone OBJECT-TYPE
    SYNTAX DisplayString (SIZE(1..6))
    ACCESS read-write
    STATUS mandatory
    DESCRIPTION
      "Offset from Greenwich time (format hh:mm)."
	::=  { rsWSDNTP 4 }

rsWSDNTPPort OBJECT-TYPE
    SYNTAX INTEGER
    ACCESS read-write
    STATUS mandatory
    DESCRIPTION
      " A UDP Port number."
	::=  { rsWSDNTP 5 }

rsWSDNTPServerUrl  OBJECT-TYPE
    SYNTAX  DisplayString (SIZE(0..64))
    ACCESS  read-write
    STATUS  mandatory
    DESCRIPTION
      "NTP Server URL or IP address."
	::=  { rsWSDNTP 6 }

rsStatistics OBJECT IDENTIFIER ::= { rsServerDispatcher 73 }

rsPhysPortMirrorTable OBJECT-TYPE
    SYNTAX SEQUENCE OF RsPhysPortMirrorEntry
    ACCESS not-accessible
    STATUS mandatory
    DESCRIPTION
      "Table containing the list of copy ports "
    ::=  { rsServerDispatcher 74 }

rsPhysPortMirrorEntry OBJECT-TYPE
    SYNTAX RsPhysPortMirrorEntry
    ACCESS not-accessible
    STATUS  mandatory
    DESCRIPTION
       " The row definition for physical copy port table."
   INDEX { rsPhysPortMirrorSrcInf, rsPhysPortMirrorDstPort }
    ::=  { rsPhysPortMirrorTable 1 }

RsPhysPortMirrorEntry ::= SEQUENCE {
    rsPhysPortMirrorSrcInf           INTEGER,
    rsPhysPortMirrorDstPort          INTEGER,
    rsPhysPortMirrorRxTx             INTEGER,
    rsPhysPortMirrorRxBroadCast      INTEGER,
    rsPhysPortMirrorStatus           RowStatus,
    rsPhysPortMirrorBackupDstPort    INTEGER,
    rsPhysPortMirrorDstStatus        INTEGER,
    rsPhysPortMirrorBackupStatus     INTEGER,
    rsPhysPortMirrorActiveDstPort    INTEGER,
    rsPhysPortMirrorMode	     INTEGER,
    rsPhysPortMirrorThreshold	     INTEGER,
    rsPhysPortMirrorThresholdStatus  INTEGER
  }

rsPhysPortMirrorSrcInf OBJECT-TYPE
    SYNTAX  INTEGER
    ACCESS  read-only
    STATUS  mandatory
    DESCRIPTION
      "The port under sniffing"
    ::= { rsPhysPortMirrorEntry 1 }

rsPhysPortMirrorDstPort OBJECT-TYPE
    SYNTAX  INTEGER
    ACCESS  read-only
    STATUS  mandatory
    DESCRIPTION
      "The destination port - the target sniffer port"
    ::= { rsPhysPortMirrorEntry 2 }

rsPhysPortMirrorRxTx OBJECT-TYPE
    SYNTAX INTEGER {
        copyRxTx(1),
        copyRxOnly(2),
        copyTxOnly (3)
    }
    ACCESS  read-write
    STATUS  mandatory
    DESCRIPTION
       "Copy Rx/Tx traffic to the copy port ."
--  DEFVAL  { copyRxTx }
    ::=  { rsPhysPortMirrorEntry 3 }

rsPhysPortMirrorRxBroadCast OBJECT-TYPE
    SYNTAX INTEGER {
      enable(1),
      disable(2)
    }
    ACCESS  read-write
    STATUS  mandatory
    DESCRIPTION
      "The copy will include broadcast/unknown or not"
--  DEFVAL  { enable }
    ::=  { rsPhysPortMirrorEntry 4 }

rsPhysPortMirrorStatus OBJECT-TYPE
    SYNTAX  RowStatus
    ACCESS  read-write
    STATUS  mandatory
    DESCRIPTION
       "Used to delete an entry of this table."
    ::=  { rsPhysPortMirrorEntry 5 }

rsPhysPortMirrorBackupDstPort OBJECT-TYPE
    SYNTAX  INTEGER
    ACCESS  read-write
    STATUS  mandatory
    DESCRIPTION
      "The destination port - the target sniffer port"
    ::= { rsPhysPortMirrorEntry 6 }

rsPhysPortMirrorDstStatus OBJECT-TYPE
    SYNTAX INTEGER {
      active(1),
      portDown(2),
      checkIDSFail(3),
      checkIDSFailAndPortDown(4)
    }
    ACCESS  read-only
    STATUS  mandatory
    DESCRIPTION
      "The status of the dest-port according to the health check:
        active - the port is ok and can be used as a destination port for copy-port
        portDown - the port has been recognized as physically DOWN and therefore the traffic
                            will not be copied to this port until it will be recognized as physically UP
        checkIDSFail - the connectivty check of the monitoring port of the IDS failed and therefore
                        the traffic will not be copied to this port until the check will recognize differently
        checkIDSFailAnd PortDown - both the connectivty check on the IDS failed and the port has
                        been recognized as physically DOWN."
    ::=  { rsPhysPortMirrorEntry 7 }

rsPhysPortMirrorBackupStatus OBJECT-TYPE
    SYNTAX INTEGER {
      active(1),
      portDown(2),
      checkIDSFail(3),
      checkIDSFailAndPortDown(4),
      none(5)
    }
    ACCESS  read-only
    STATUS  mandatory
    DESCRIPTION
      " The status of the backup-port according to the health check:
        Active - the port is ok and can be used as a destination port for copy-port
        PortDown - the port has been recognized as physically DOWN and therefore the traffic
                            will not be copied to this port until it will be recognized as physically UP
        CheckIDSFail - the connectivty check of the monitoring port of the IDS failed and therefore
                        the traffic will not be copied to this port until the check will recognize differently
        CheckIDSFailAnd PortDown - both the connectivty check on the IDS failed and the port has
                        been recognized as physically DOWN
         None - for the case there is no defined backup port."
    ::=  { rsPhysPortMirrorEntry 8 }

rsPhysPortMirrorActiveDstPort OBJECT-TYPE
    SYNTAX INTEGER {
      dstPort(1),
      backupPort(2),
      none(3)
    }
    ACCESS  read-only
    STATUS  mandatory
    DESCRIPTION
      "The active dest-port at a certain time, if it is the dest-port or the backup-port or none of
        them."
    ::=  { rsPhysPortMirrorEntry 9 }
    
rsPhysPortMirrorMode OBJECT-TYPE
    SYNTAX INTEGER {
      enabled(1),
      traffic-rate(2)
    }
    ACCESS  read-write
    STATUS  mandatory
    DESCRIPTION
      "Always copy or copy according to threshold "
    DEFVAL  { enabled }
    ::=  { rsPhysPortMirrorEntry 10 }

rsPhysPortMirrorThreshold OBJECT-TYPE
    SYNTAX INTEGER
    ACCESS  read-write
    STATUS  mandatory
    DESCRIPTION
      "The copy threshold "
    DEFVAL  { 0 }
    ::=  { rsPhysPortMirrorEntry 11 }
    
rsPhysPortMirrorThresholdStatus OBJECT-TYPE
    SYNTAX INTEGER {
      waiting(1),
      active(2),
      elapsed(3),
      none(4)
    }
    ACCESS  read-only
    STATUS  mandatory
    DESCRIPTION
      "The threshold status "
    ::=  { rsPhysPortMirrorEntry 12 }
    
rsPhysPortMirrorThresholdUnits OBJECT-TYPE
    SYNTAX INTEGER {
      pps(1),
      kbps(2)
    }
    ACCESS  read-write
    STATUS  mandatory
    DESCRIPTION
      "Units used to measure port-mirroring threshold."
    DEFVAL { pps }
    ::=  { rsServerDispatcher 126 }
    
rsPhysPortMirrorThresholdInterval OBJECT-TYPE
    SYNTAX INTEGER
    ACCESS  read-write
    STATUS  mandatory
    DESCRIPTION
      "Time interval in which port mirroring will be active, if the mode is threshold"
    ::=  { rsServerDispatcher 127 }

rsPhysPortMirrorThresholdReset OBJECT-TYPE
    SYNTAX INTEGER {
      reset(1),
      no-reset(2)      
    }
    ACCESS  read-write
    STATUS  mandatory
    DESCRIPTION
      "Reset the port mirroring threshold"
    ::=  { rsServerDispatcher 128 }

rsCP OBJECT IDENTIFIER ::= { rsServerDispatcher 75 }

rsVWSD OBJECT IDENTIFIER ::= {rsServerDispatcher 76 }

rsVWSDDataPermissionsTable OBJECT-TYPE
	SYNTAX SEQUENCE OF RsVWSDDataPermissionsTableEntry
	ACCESS not-accessible
	STATUS mandatory
	DESCRIPTION
    "Table containing the list of data items to which Farm administrators
    of the virtual wsd has permissions."
	::= { rsVWSD 1 }

rsVWSDDataPermissionsTableEntry OBJECT-TYPE
   SYNTAX RsVWSDDataPermissionsTableEntry
   ACCESS not-accessible
   STATUS mandatory
   DESCRIPTION
       " The row definition for this table."
	INDEX { rsVWSDUserGroup, rsVWSDDataType, rsVWSDDataItems}
  ::= {rsVWSDDataPermissionsTable 1}

RsVWSDDataPermissionsTableEntry ::= SEQUENCE {
	rsVWSDUserGroup    DisplayString,
	rsVWSDDataType     OCTET STRING,
	rsVWSDDataItems    OCTET STRING,
  rsVWSDDataStatus   RowStatus
}

rsVWSDUserGroup OBJECT-TYPE
	SYNTAX DisplayString (SIZE(1..30))
    	ACCESS  read-only
    	STATUS  mandatory
    	DESCRIPTION
    		"The Group of users for whom data permission is given."
	::= { rsVWSDDataPermissionsTableEntry 1}

rsVWSDDataType OBJECT-TYPE
	SYNTAX OCTET STRING (SIZE(1..80))
	ACCESS read-only
	STATUS mandatory
	DESCRIPTION
		"Holds a string that identifies the table of the index by which the
    data filtering is done."
	::= { rsVWSDDataPermissionsTableEntry 2}

rsVWSDDataItems OBJECT-TYPE
	SYNTAX OCTET STRING (SIZE(1..80))
	ACCESS read-only
	STATUS mandatory
	DESCRIPTION
		"The Value(s) of the index column for the data item to which permission is set."
	::= { rsVWSDDataPermissionsTableEntry 3}

rsVWSDDataStatus OBJECT-TYPE
  SYNTAX RowStatus
  ACCESS read-write
  STATUS mandatory
  DESCRIPTION
    "The row status for the table"
  ::= { rsVWSDDataPermissionsTableEntry 4}

rsWSDManagementPorts OBJECT-TYPE
    SYNTAX INTEGER {
        outOfPath(1),
        switch(2),
        promiscuous(3)
    }
    ACCESS  read-write
    STATUS  mandatory
    DESCRIPTION "The entry indicates the functionality of the device.
    outOfPath implies that the device will be able to have a management
    port, and the rest of the ports will be used for sniffing. switch
    implies the regular functionality of the device (router or VLAN).
    promiscuous will have static port mappings for forwarding."
--  DEFVAL  {switch}
    ::= { rsServerDispatcher 77 }

rsWSDManagementPortsTable OBJECT-TYPE
    SYNTAX SEQUENCE OF RsWSDManagementPortsEntry
    ACCESS not-accessible
    STATUS  mandatory
    DESCRIPTION
      "Table containing the operation of each port.."
    ::= { rsServerDispatcher 78 }

rsWSDManagementPortsEntry OBJECT-TYPE
    SYNTAX RsWSDManagementPortsEntry
    ACCESS not-accessible
    STATUS mandatory
    DESCRIPTION
       "The row definition for this table."
    INDEX { rsWSDPortIndex }
    ::=  { rsWSDManagementPortsTable 1 }

RsWSDManagementPortsEntry ::= SEQUENCE {
    rsWSDPortIndex INTEGER,
    rsWSDPortOperation INTEGER
}

rsWSDPortIndex OBJECT-TYPE
    SYNTAX INTEGER
    ACCESS read-only
    STATUS mandatory
    DESCRIPTION
      "The index of the physical ports."
    ::=  { rsWSDManagementPortsEntry 1 }

rsWSDPortOperation OBJECT-TYPE
    SYNTAX INTEGER {
        management (1),
        sniffer (2)
    }
    ACCESS read-only
    STATUS mandatory
    DESCRIPTION
      "The operation of the particular port."
    DEFVAL { sniffer }
    ::=  { rsWSDManagementPortsEntry 2 }

rsCCK  OBJECT IDENTIFIER ::= { rsServerDispatcher 79 }

rsWSDSshParams OBJECT IDENTIFIER ::= {rsServerDispatcher 80 }

rsWSDSshPort OBJECT-TYPE
    SYNTAX  INTEGER (1..65535)
    ACCESS  read-write
    STATUS  mandatory
    DESCRIPTION
      "The SSH Server Port."
--  DEFVAL  { 22 }
    ::=  {rsWSDSshParams 1}


rsWSDSshStatus OBJECT-TYPE
   SYNTAX  INTEGER {
        enable(1),
      	disable(2)
   }
   ACCESS  read-write
   STATUS  mandatory
   DESCRIPTION
        "SSH Status. Enable/Disable SSH operation."
--  DEFVAL  { disable }
   ::= { rsWSDSshParams 2 }

rsWSDSshAllowPwdAndPubKey OBJECT-TYPE
   SYNTAX  INTEGER {
        enable(1),
      	disable(2)
   }
   ACCESS  read-write
   STATUS  mandatory
   DESCRIPTION
        "SSH allow the use of password for user with public key."
   DEFVAL  { disable }
   ::= { rsWSDSshParams 3 }


rsWSDHttpsParams OBJECT IDENTIFIER ::= {rsServerDispatcher 81 }

rsWSDHttpsPort OBJECT-TYPE
    SYNTAX  INTEGER (1..65535)
    ACCESS  read-write
    STATUS  mandatory
    DESCRIPTION
      "The Https Server Port."
--  DEFVAL  { 443 }
    ::=  {rsWSDHttpsParams 1}


rsWSDHttpsStatus OBJECT-TYPE
   SYNTAX  INTEGER {
        enable(1),
      	disable(2)
   }
   ACCESS  read-write
   STATUS  mandatory
   DESCRIPTION
        "Https Status. Enable/Disable Https operation."
--  DEFVAL  { disable }
   ::= { rsWSDHttpsParams 2 }


rsWSDStaticForwardingTable OBJECT-TYPE
    SYNTAX SEQUENCE OF RsWSDStaticForwardingEntry
    ACCESS not-accessible
    STATUS  mandatory
    DESCRIPTION
      "Table containing the static fowarding configration."
    ::= { rsServerDispatcher 82 }

rsWSDStaticForwardingEntry OBJECT-TYPE
    SYNTAX RsWSDStaticForwardingEntry
    ACCESS not-accessible
    STATUS mandatory
    DESCRIPTION
       "The row definition for this table."
    INDEX { rsWSDStaticSourcePort }
    ::=  { rsWSDStaticForwardingTable 1 }

RsWSDStaticForwardingEntry ::= SEQUENCE {
    rsWSDStaticSourcePort INTEGER,
    rsWSDStaticDestinationPort INTEGER,
    rsWSDStaticPortOperation INTEGER,
    rsWSDStaticStatus RowStatus,
    rsWSDStaticFailureMode INTEGER,
    rsWSDStaticInPort INTEGER
}

rsWSDStaticSourcePort OBJECT-TYPE
    SYNTAX INTEGER
    ACCESS read-only
    STATUS mandatory
    DESCRIPTION
      "The index of the source port."
    ::=  { rsWSDStaticForwardingEntry 1 }

rsWSDStaticDestinationPort OBJECT-TYPE
    SYNTAX INTEGER
    ACCESS read-write
    STATUS mandatory
    DESCRIPTION
      "The destination port."
    ::=  { rsWSDStaticForwardingEntry 2 }

rsWSDStaticPortOperation OBJECT-TYPE
    SYNTAX INTEGER {
        process(1),
        forward(2),
	bypass(3)
    }
    ACCESS read-write
    STATUS mandatory
    DESCRIPTION
      "The operation for the specific port. process implies that the packets
      will be processed (analyzed, filtered etc.) prior to being forwarded.
      forward implies that the packets will be forwarded."
    ::=  { rsWSDStaticForwardingEntry 3 }

rsWSDStaticStatus OBJECT-TYPE
    SYNTAX RowStatus
    ACCESS read-write
    STATUS mandatory
    DESCRIPTION
       "This variable indicates the administrative status of this entry.
        Used to delete an entry of this table."
    ::=  { rsWSDStaticForwardingEntry 4 }

rsWSDStaticFailureMode OBJECT-TYPE
    SYNTAX INTEGER {
        fail-close(1),
        fail-open(2)
    }
    ACCESS read-write
    STATUS mandatory
    DESCRIPTION
      "The link state in case the device fails.
        fail-open: allow traffic to continue to flow unimpeded
        fail-close: traffic is blocked."
    DEFVAL  { fail-close }
    ::=  { rsWSDStaticForwardingEntry 5 }
    
rsWSDStaticInPort OBJECT-TYPE

    SYNTAX INTEGER {

        source(1),

        destination(2)

	}

	ACCESS read-write
    STATUS mandatory
    DESCRIPTION
      "This field is needed for Apsolute Vision."
    DEFVAL  { source }
    ::=  { rsWSDStaticForwardingEntry 6 }



rsRadiusServer OBJECT IDENTIFIER ::= {rsServerDispatcher 83 }


rsRadiusMainServerAddr OBJECT-TYPE
    SYNTAX IpAddress
    ACCESS  read-write
    STATUS  mandatory
    DESCRIPTION
      "The IP Address of the radius main server."
    ::= {rsRadiusServer 1}

rsRadiusMainServerPort OBJECT-TYPE
    SYNTAX INTEGER
    ACCESS  read-write
    STATUS  mandatory
    DESCRIPTION
       "The port on which the radius main server listens"
--  DEFVAL { 1812 }
    ::= {rsRadiusServer 2}

rsRadiusMainServerSecret OBJECT-TYPE
    SYNTAX  DisplayString (SIZE(0..100))
    ACCESS  read-write
    STATUS  mandatory
    DESCRIPTION
       "The key with which the user's password is encrypted."
    ::= {rsRadiusServer 3}

rsRadiusBackupServerAddr OBJECT-TYPE
    SYNTAX IpAddress
    ACCESS  read-write
    STATUS  mandatory
    DESCRIPTION
      "The IP Address of the backup radius server."
    ::= {rsRadiusServer 4}

rsRadiusBackupServerPort OBJECT-TYPE
    SYNTAX INTEGER
    ACCESS  read-write
    STATUS  mandatory
    DESCRIPTION
       "The port on which the radius backup server listens"
--  DEFVAL { 1812 }
    ::= {rsRadiusServer 5}

rsRadiusBackupServerSecret OBJECT-TYPE
    SYNTAX DisplayString (SIZE(0..100))
    ACCESS  read-write
    STATUS  mandatory
    DESCRIPTION
       "The key with which the user's password is encrypted."
    ::= {rsRadiusServer 6}

rsAuthenticationMethod OBJECT-TYPE
    SYNTAX INTEGER {
        userTable(1),
        radiusAndUserTable(2),
        tacacsAndUserTable(3)}
    ACCESS  read-write
    STATUS  mandatory
    DESCRIPTION
      "Radius authentication method."
--  DEFVAL { 1 }
    ::=  {rsRadiusServer 7}

rsRadiusServerTimeout OBJECT-TYPE
    SYNTAX  INTEGER (1..10)
    ACCESS  read-write
    STATUS  mandatory
    DESCRIPTION
      "Number of seconds to wait for reply from the radius server before
	   retransmitting the request."
--  DEFVAL  { 1 }
    ::=  {rsRadiusServer 8}

rsRadiusServerRetries OBJECT-TYPE
    SYNTAX  INTEGER (1..3)
    ACCESS  read-write
    STATUS  mandatory
    DESCRIPTION
      "Minimal number of unanswered request attempts before considering the radius
	   server disconnected."
--  DEFVAL  { 2 }
    ::=  {rsRadiusServer 9}

rsLockUserAfterLoginFailure OBJECT-TYPE
    SYNTAX  INTEGER (0..10)
    ACCESS  read-write
    STATUS  mandatory
    DESCRIPTION
      "Number of failed access attempts after which the user is locked out and cannot
       manage the device. 0 - never lock users."
    DEFVAL  { 0 }
    ::=  {rsRadiusServer 10}

rsRadiusClientLifeTime OBJECT-TYPE
    SYNTAX INTEGER (15..3600)
    ACCESS  read-write
    STATUS  mandatory
    DESCRIPTION
      "Number of seconds for which radius authentication replies are cached. During this
       time the device will use the cached response and not issue authentication
       requests for the user."
    DEFVAL  { 30 }
    ::=  {rsRadiusServer 11}

rsRadiusMainServerUrl OBJECT-TYPE
    SYNTAX	DisplayString (SIZE(0..64))
    ACCESS  read-write
    STATUS  mandatory
    DESCRIPTION
      "The URL or IP Address of the radius main server."
    ::= {rsRadiusServer 12}

rsRadiusBackupServerUrl OBJECT-TYPE
    SYNTAX	DisplayString (SIZE(0..64))
    ACCESS  read-write
    STATUS  mandatory
    DESCRIPTION
      "The URL or IP Address of the backup radius server."
    ::= {rsRadiusServer 13}


rspRadiusParameters  OBJECT IDENTIFIER ::= { rsRadiusServer 14 }

rspRadiusPrimaryAddr  OBJECT-TYPE
    SYNTAX  DisplayString (SIZE(0..64))
    ACCESS  read-write
    STATUS  mandatory
    DESCRIPTION
      "Primary Radius server URL or IP address."
    ::=  {rspRadiusParameters 1}

rspRadiusPrimaryAuthPort  OBJECT-TYPE
    SYNTAX  INTEGER
    ACCESS  read-write
    STATUS  mandatory
    DESCRIPTION
      "Primary Radius server authentication port."
    ::=  {rspRadiusParameters 2}

rspRadiusPrimaryAccPort  OBJECT-TYPE
    SYNTAX  INTEGER
    ACCESS  read-write
    STATUS  mandatory
    DESCRIPTION
      "Primary Radius server accounting port."
    ::=  {rspRadiusParameters 3}

rspRadiusPrimarySecret  OBJECT-TYPE
    SYNTAX  DisplayString(SIZE(0..64))
    ACCESS  read-write
    STATUS  mandatory
    DESCRIPTION
      "CID and Primary Radius shared secret"
    ::=  {rspRadiusParameters 4}

rspRadiusAltAddr  OBJECT-TYPE
    SYNTAX  DisplayString (SIZE(0..64))
    ACCESS  read-write
    STATUS  mandatory
    DESCRIPTION
      "Alternate Radius server URL or IP address."
    ::=  {rspRadiusParameters 5}

rspRadiusAltAuthPort  OBJECT-TYPE
    SYNTAX  INTEGER
    ACCESS  read-write
    STATUS  mandatory
    DESCRIPTION
      " Alternate Radius server authentication port."
    ::=  {rspRadiusParameters 6}

rspRadiusAltAccPort  OBJECT-TYPE
    SYNTAX  INTEGER
    ACCESS  read-write
    STATUS  mandatory
    DESCRIPTION
      " Alternate Radius server accounting port."
    ::=  {rspRadiusParameters 7}

rspRadiusAltSecret  OBJECT-TYPE
    SYNTAX  DisplayString(SIZE(0..64))
    ACCESS  read-write
    STATUS  mandatory
    DESCRIPTION
      "CID and Alternate Radius shared secret"
    ::=  {rspRadiusParameters 8}

rspRadiusOwnAuthPort  OBJECT-TYPE
    SYNTAX  INTEGER
    ACCESS  read-write
    STATUS  mandatory
    DESCRIPTION
      "Own Radius proxy authentication port."
    ::=  {rspRadiusParameters 9}

rspRadiusOwnAccPort  OBJECT-TYPE
    SYNTAX  INTEGER
    ACCESS  read-write
    STATUS  mandatory
    DESCRIPTION
      "Own Radius proxy accounting port."
    ::=  {rspRadiusParameters 10}

rspRadiusEnable  OBJECT-TYPE
    SYNTAX INTEGER {
      enable(1),
      disable(2)
    }
    ACCESS  read-write
    STATUS  mandatory
    DESCRIPTION
      "Proxy Radius resolution enable."
    DEFVAL { 2 }
    ::=  { rspRadiusParameters 11}

rspRadiusTransparentEnable  OBJECT-TYPE
    SYNTAX INTEGER {
      enable(1),
      disable(2)
    }
    ACCESS  read-write
    STATUS  mandatory
    DESCRIPTION
      "Proxy Radius transparent mode resolution enable."
    DEFVAL { 2 }
    ::=  { rspRadiusParameters 12}

rspRadiusRuleTable OBJECT-TYPE
    SYNTAX SEQUENCE OF RspRadiusRuleEntry
    ACCESS not-accessible
    STATUS  mandatory
    DESCRIPTION
	"The attribute action table"
    ::=  { rspRadiusParameters 13}

rspRadiusRuleEntry OBJECT-TYPE
    SYNTAX RspRadiusRuleEntry
    ACCESS not-accessible
    STATUS  mandatory
    DESCRIPTION
       " The row definition for this table."
    INDEX { rspRadiusattId,
			rspRadiusattValue,
			rspRadiusNetworkName }
    ::=  { rspRadiusRuleTable 1}

RspRadiusRuleEntry ::= SEQUENCE {
    rspRadiusattId			INTEGER,
    rspRadiusattValue			DisplayString,
    rspRadiusNetworkName		DisplayString,
    rspRadiusrowStatus		RowStatus
    }

rspRadiusattId  OBJECT-TYPE
    SYNTAX  INTEGER
    ACCESS  read-only
    STATUS  mandatory
    DESCRIPTION
      "Attribute ID of the message to/from the RADIUS"
    ::=  {rspRadiusRuleEntry 1}


rspRadiusattValue  OBJECT-TYPE
    SYNTAX  DisplayString(SIZE(1..64))
    ACCESS  read-only
    STATUS  mandatory
    DESCRIPTION
      "Attribute value of the message to/from the RADIUS"
    ::=  {rspRadiusRuleEntry 2}

rspRadiusNetworkName  OBJECT-TYPE
    SYNTAX  DisplayString(SIZE(1..64))
    ACCESS  read-only
    STATUS  mandatory
    DESCRIPTION
      "The name of the network that the rule applied to"
    ::=  {rspRadiusRuleEntry 3}

rspRadiusrowStatus OBJECT-TYPE
    SYNTAX RowStatus
    ACCESS  read-write
    STATUS  mandatory
    DESCRIPTION
     "Administrative status."
    ::=  { rspRadiusRuleEntry 4}


rspRadiusNasTable OBJECT-TYPE
    SYNTAX SEQUENCE OF RspRadiusNasEntry
    ACCESS not-accessible
    STATUS  mandatory
    DESCRIPTION
	"The NAS IP/Secret table"
    ::=  { rspRadiusParameters 14}

rspRadiusNasEntry OBJECT-TYPE
    SYNTAX RspRadiusNasEntry
    ACCESS not-accessible
    STATUS  mandatory
    DESCRIPTION
       " The row definition for this table."
    INDEX { rspRadiusNasIp }
    ::=  { rspRadiusNasTable 1}

RspRadiusNasEntry ::= SEQUENCE {
    rspRadiusNasIp			IpAddress,
    rspRadiusNasSecret		DisplayString,
    rspRadiusNasrowStatus		RowStatus
    }


rspRadiusNasIp OBJECT-TYPE
    SYNTAX IpAddress
    ACCESS  read-only
    STATUS  mandatory
    DESCRIPTION
     "The IP of this NAS"
    ::=  { rspRadiusNasEntry 1}

rspRadiusNasSecret OBJECT-TYPE
    SYNTAX DisplayString(SIZE(0..64))
    ACCESS  read-write
    STATUS  mandatory
    DESCRIPTION
     "The secret of this NAS"
    ::=  { rspRadiusNasEntry 2}

rspRadiusNasrowStatus OBJECT-TYPE
    SYNTAX RowStatus
    ACCESS  read-write
    STATUS  mandatory
    DESCRIPTION
     "Administrative status."
    ::=  { rspRadiusNasEntry 3}

rspRadiusUserMirrorProtocolMode OBJECT-TYPE
    SYNTAX  INTEGER {
      enable(1),
      disable(2)
    }
    ACCESS  read-write
    STATUS  mandatory
    DESCRIPTION
      "The status of the mirroring for Radius proxy."
    ::=  {rspRadiusParameters 15}

rspRadiusUserMirrorPollingTime OBJECT-TYPE
    SYNTAX  INTEGER
    ACCESS  read-write
    STATUS  mandatory
    DESCRIPTION
      "The polling time of the Radius users table."
	DEFVAL  { 10 }
    ::=  {rspRadiusParameters 16}

rspRadiusNetworkUpdatePolicy OBJECT-TYPE
    SYNTAX  INTEGER {
      replace(1),
      add(2)
    } 
    ACCESS  read-write
    STATUS  mandatory
    DESCRIPTION
      "Define the way the device treats new user network. 
      Replace - the device replaces current network and update the user policy. 
      Add -the device adds the network to the user entry. 
      The device supports up to fine simultaneous networks for each entry "
    DEFVAL  { 1 }
    ::=  {rspRadiusParameters 17}
    
rsTacacsServer OBJECT IDENTIFIER ::= {rsServerDispatcher 180 }

rsTacacsPrimaryServerAddr OBJECT-TYPE
    SYNTAX IpAddress
    ACCESS  read-write
    STATUS  mandatory
    DESCRIPTION
      "Defines the primary TACACS+ server address."
    ::= {rsTacacsServer 1}
rsTacacsPrimaryServerSecret OBJECT-TYPE
    SYNTAX  DisplayString (SIZE(0..99))
    ACCESS  read-write
    STATUS  mandatory
    DESCRIPTION
       "Defines the shared secret between the switch and the primary TACACS+ server."
    ::= {rsTacacsServer 2}
rsTacacsPrimaryServerPort OBJECT-TYPE
    SYNTAX INTEGER (1..65000)
    ACCESS  read-write
    STATUS  mandatory
    DESCRIPTION
       "The port on which the TACACS+ primary server listens."
    DEFVAL { 49 }
    ::= {rsTacacsServer 3}
rsTacacsSecondaryServerAddr OBJECT-TYPE
    SYNTAX IpAddress
    ACCESS  read-write
    STATUS  mandatory
    DESCRIPTION
      "Defines the secondary TACACS+ server address."
    ::= {rsTacacsServer 4}
rsTacacsSecondaryServerSecret OBJECT-TYPE
    SYNTAX  DisplayString (SIZE(0..99))
    ACCESS  read-write
    STATUS  mandatory
    DESCRIPTION
       "Defines the shared secret between the switch and the secondary TACACS+ server."
    ::= {rsTacacsServer 5}
rsTacacsSecondaryServerPort OBJECT-TYPE
    SYNTAX INTEGER (1..65000)
    ACCESS  read-write
    STATUS  mandatory
    DESCRIPTION
       "The port on which the TACACS+ secondary server listens."
    DEFVAL { 49 }
    ::= {rsTacacsServer 6}
rsTacacsServerRetries OBJECT-TYPE
    SYNTAX  INTEGER (1..3)
    ACCESS  read-write
    STATUS  mandatory
    DESCRIPTION
      "Defines the number of failed authentication requests before switching to a different TACACS+ server. 
      The default is 2 requests."
    DEFVAL  { 2 }
    ::=  {rsTacacsServer 7}
rsTacacsServerTimeout OBJECT-TYPE
    SYNTAX  INTEGER (1..10)
    ACCESS  read-write
    STATUS  mandatory
    DESCRIPTION
      "Defines the amount of time, in seconds, before a TACACS+ server authentication attempt is considered to have failed. 
      The default is 1 second."
    DEFVAL  { 1 }
    ::=  {rsTacacsServer 8}
rsTacacsCommandLoggingStatus  OBJECT-TYPE
    SYNTAX FeatureStatus
    ACCESS  read-write
    STATUS  mandatory
    DESCRIPTION
        "Enable/disable TACACS+ command logging. 
	When enabled, device sends command log messages to TACACS+ server."
    DEFVAL { disable }
    ::=  { rsTacacsServer 9 }
rsTacacsCommandAuthorizationStatus  OBJECT-TYPE
    SYNTAX FeatureStatus
    ACCESS  read-write
    STATUS  mandatory
    DESCRIPTION
        "Enable/disable TACACS+ command authorization."
    DEFVAL { disable }
    ::=  { rsTacacsServer 10 }
rsTacacsClientAging OBJECT-TYPE
    SYNTAX  INTEGER
    ACCESS  read-write
    STATUS  mandatory
    DESCRIPTION
      "Number of seconds for which tacacs+ authentication and authorization replies are cached. During this
       time the device will use the cached response and not issue requests for the user."
    DEFVAL  { 0 }
    ::=  {rsTacacsServer 11}

rsIfTable OBJECT-TYPE
    SYNTAX SEQUENCE OF RsIfEntry
    ACCESS not-accessible
    STATUS  mandatory
    DESCRIPTION
      "Device physical interface table"
    ::=  {rsServerDispatcher 84}

rsIfEntry OBJECT-TYPE
    SYNTAX RsIfEntry
    ACCESS not-accessible
    STATUS  mandatory
    DESCRIPTION
       "The row definition for this table"
   INDEX { rsIfIndex }
    ::=  {rsIfTable 1}

RsIfEntry ::= SEQUENCE {
  rsIfIndex         INTEGER,
  rsIfSpeed         INTEGER,
  rsIfDuplex        INTEGER,
  rsIfAutoNegotiate INTEGER,
  rsIfAutoNegotiateCfg INTEGER,
  rsIfFEC		INTEGER
  }

rsIfIndex OBJECT-TYPE
    SYNTAX  INTEGER
    ACCESS read-only
    STATUS  mandatory
    DESCRIPTION
      "interface's index"
    ::=  {rsIfEntry 1}

rsIfSpeed OBJECT-TYPE
    SYNTAX  INTEGER {
       auto(0),
       eth10(1),
       fe100(2),
       ge1000(3),
	   xg10000(4),
	   qxg10000(5),
	   hg100000(6)
    }
    ACCESS read-write
    STATUS  mandatory
    DESCRIPTION
      "interface's speed"
    ::=  {rsIfEntry 2}

rsIfDuplex OBJECT-TYPE
    SYNTAX  INTEGER {
       half(1),
       full(2)
    }
    ACCESS read-write
    STATUS  mandatory
    DESCRIPTION
      "interface's duplex"
    ::=  {rsIfEntry 3}

rsIfAutoNegotiate OBJECT-TYPE
    SYNTAX  INTEGER {
       auto(0),
       on(1),
       off(2)
    }
    ACCESS read-only
    STATUS  mandatory
    DESCRIPTION
      "interface's autonegotiation status"
    ::=  {rsIfEntry 4}

rsIfAutoNegotiateCfg OBJECT-TYPE
    SYNTAX  INTEGER {
       auto(0),
       on(1),
       off(2)
    }
    ACCESS read-write
    STATUS  mandatory
    DESCRIPTION
      "interface's autonegotiation status"
    ::=  {rsIfEntry 5}

rsIfFEC OBJECT-TYPE
    SYNTAX  INTEGER {
       disable(0),
       enable(1),
       auto(2)
    }
    ACCESS read-write
    STATUS  mandatory
    DESCRIPTION
      "interface's FEC status"
    ::=  {rsIfEntry 6}


rsWSDDeviceOperationMode OBJECT-TYPE
    SYNTAX INTEGER {
        trafficRedirection(1),
        staticForwarding(2),
        transparentForwarding(3)
    }
    ACCESS  read-write
    STATUS  mandatory
    DESCRIPTION
      "Device operation mode: redirection (load balancing) or static
      forwarding (Dos Shield), or transparent forwarding (for IDS load
      balancing)."
    DEFVAL  {trafficRedirection}
    ::= {rsServerDispatcher 85}

rsWSDVersionStatus OBJECT-TYPE
    SYNTAX INTEGER {
        open(1),
        final(2)
    }
    ACCESS  read-only
    STATUS  mandatory
    DESCRIPTION
      "Indicates whether the current version is closed or still open (under development)."
    ::= {rsServerDispatcher 86}

rsWSDSyslogFacility OBJECT-TYPE
    SYNTAX INTEGER {
        kernelMsg(0),
        userLevelMsg(1),
        mailSystem(2),
        systemDaemons(3),
        authorization(4),
        syslogdMessages(5),
        linePrinter(6),
        networkNews(7),
        uucp(8),
        clockDaemon1(9),
        security(10),
        ftpDaemon(11),
        ntpSubsystem(12),
        logAudit(13),
        logAlert(14),
        clockDaemon2(15),
        local0(16),
        local1(17),
        local2(18),
        local3(19),
        local4(20),
        local5(21),
        local6(22),
        local7(23)
    }
    ACCESS  read-write
    STATUS  mandatory
    DESCRIPTION
      "The SYSLOG Priority value is calculated by multiplying the Facility
       number by 8 and then adding the numerical value of the Severity."
    DEFVAL { local6 }
    ::= {rsServerDispatcher 87}

rsACC OBJECT IDENTIFIER ::= {rsServerDispatcher 88 }

rsWSDPingPortsTable OBJECT-TYPE
    SYNTAX SEQUENCE OF RsWSDPingPortsEntry
    ACCESS not-accessible
    STATUS mandatory
    DESCRIPTION
      "The table contains all the physical ports. Each port can be set to
       allow/block Ping operations to the device."
    ::= { rsServerDispatcher 89 }

rsWSDPingPortsEntry OBJECT-TYPE
  SYNTAX RsWSDPingPortsEntry
  ACCESS not-accessible
  STATUS mandatory
  DESCRIPTION
    "Row definition for the table."
  INDEX { rsWSDPingPhysicalPortNumber }
  ::= { rsWSDPingPortsTable 1 }

RsWSDPingPortsEntry ::= SEQUENCE {
  rsWSDPingPhysicalPortNumber INTEGER,
  rsWSDPingPhysicalPortState INTEGER
}

rsWSDPingPhysicalPortNumber OBJECT-TYPE
  SYNTAX INTEGER
  ACCESS read-only
  STATUS mandatory
  DESCRIPTION
    "Physical port number."
  ::= { rsWSDPingPortsEntry 1 }

rsWSDPingPhysicalPortState OBJECT-TYPE
  SYNTAX INTEGER {
    enable(1),
    disable(2)
  }
  ACCESS read-write
  STATUS mandatory
  DESCRIPTION
    "enable - accept Ping operations on the physical port. disable -
     ignore Ping opertaions on the physical port."
  DEFVAL { 1 }
  ::= { rsWSDPingPortsEntry 2 }

rsWSDBackupInterfaceGrouping OBJECT-TYPE
    SYNTAX INTEGER {
        enable(1),
        disable(2)
    }
    ACCESS  read-write
    STATUS  mandatory
    DESCRIPTION
        "When Backup Interface Grouping is enabled, the backup will take all interfaces when all of the main's
         interfaces are down. It will also release all interfaces at the same time when all the main's are up."
    DEFVAL { enable }
    ::=  { rsServerDispatcher 90}

rsRegistrationStatus OBJECT-TYPE
    SYNTAX INTEGER {
        registered(1),
        notRegistered(2)
    }
    ACCESS  read-write
    STATUS  mandatory
    DESCRIPTION
        "Indicates whether the device has been registered. The NMS is expected to set it after
         successful registration."
    DEFVAL { notRegistered }
    ::=  { rsServerDispatcher 91}

rsCT100 OBJECT IDENTIFIER ::= {rsServerDispatcher 92 }

rsFloatingPacketOffset OBJECT-TYPE
    SYNTAX INTEGER {
        enable(1),
        disable(2)
    }
    ACCESS  read-write
    STATUS  mandatory
    DESCRIPTION
        "Indicates whether the incoming packet offset may be changed by the application. This is not needed in
         most cases but is required for tagging of outgoing packets (802.1q) and packet encapsulation."
    DEFVAL { disable }
    ::=  { rsServerDispatcher 93}

rsDnsParameters OBJECT IDENTIFIER ::= { rsServerDispatcher 94 }
rsDnsrParameters OBJECT IDENTIFIER ::= { rsDnsParameters 1 }

rsDnsrPrimaryAddr  OBJECT-TYPE
    SYNTAX  IpAddress
    ACCESS  read-write
    STATUS  mandatory
    DESCRIPTION
      "Primary DNS server IP address."
    ::=  {rsDnsrParameters 1}

rsDnsrAlternateAddr  OBJECT-TYPE
    SYNTAX  IpAddress
    ACCESS  read-write
    STATUS  mandatory
    DESCRIPTION
      "Alternate DNS server IP address."
    ::=  {rsDnsrParameters 2}

rsDnsrEnable  OBJECT-TYPE
    SYNTAX INTEGER {
      enable(1),
      disable(2)
    }
    ACCESS  read-write
    STATUS  mandatory
    DESCRIPTION
      "DNS resolution enable."
    DEFVAL { 2 }
    ::=  {rsDnsrParameters 3}

rsDnsrStaticResTable OBJECT-TYPE
    SYNTAX SEQUENCE OF RsDnsrStaticResEntry
    ACCESS not-accessible
    STATUS  mandatory
    DESCRIPTION
	"DNS Static resolution table. The table containing URL/IP Pairs.
	 The DNS resolver use this table in the resolution process."
    ::=  { rsDnsrParameters 4}

rsDnsrStaticResEntry OBJECT-TYPE
    SYNTAX RsDnsrStaticResEntry
    ACCESS not-accessible
    STATUS  mandatory
    DESCRIPTION
       " The row definition for this table."
    INDEX {rsDnsrSUrl}
    ::=  { rsDnsrStaticResTable 1}

RsDnsrStaticResEntry ::= SEQUENCE {
    rsDnsrSUrl				DisplayString,
    rsDnsrSIp				IpAddress,
    rsDnsrSrowStatus		RowStatus
    }

rsDnsrSUrl OBJECT-TYPE
    SYNTAX DisplayString (SIZE(1..49))
    ACCESS  read-only
    STATUS  mandatory
    DESCRIPTION
      "The URL string in the static URL/IP resolution table."
    ::=  { rsDnsrStaticResEntry 1}

rsDnsrSIp OBJECT-TYPE
    SYNTAX IpAddress
    ACCESS  read-write
    STATUS  mandatory
    DESCRIPTION
      "The IP Address in the static URL/IP resolution table."
    ::= { rsDnsrStaticResEntry 2}

rsDnsrSrowStatus OBJECT-TYPE
    SYNTAX RowStatus
    ACCESS  read-write
    STATUS  mandatory
    DESCRIPTION
     "Administrative status."
    ::=  { rsDnsrStaticResEntry 3}

rsDnsServerParameters OBJECT IDENTIFIER ::= { rsDnsParameters 2 }

rsDnsServerEnable  OBJECT-TYPE
    SYNTAX INTEGER {
      enable(1),
      disable(2)
    }
    ACCESS  read-write
    STATUS  mandatory
    DESCRIPTION
      "DNS server enable."
    DEFVAL { 2 }
    ::=  {rsDnsServerParameters 1}

rsDnsServerStaticResTable OBJECT-TYPE
    SYNTAX SEQUENCE OF RsDnsServerStaticResEntry
    ACCESS not-accessible
    STATUS  mandatory
    DESCRIPTION
	"DNS Static resolution table. The table containing URL/IP Pairs.
	 The DNS server use this table to look form farms IP."
    ::=  { rsDnsServerParameters 2}

rsDnsServerStaticResEntry OBJECT-TYPE
    SYNTAX RsDnsServerStaticResEntry
    ACCESS not-accessible
    STATUS  mandatory
    DESCRIPTION
       " The row definition for this table."
    INDEX {rsDnsServerSUrl}
    ::=  { rsDnsServerStaticResTable 1}

RsDnsServerStaticResEntry ::= SEQUENCE {
    rsDnsServerSUrl				DisplayString,
    rsDnsServerSIp				IpAddress,
	rsDnsServerSEnable			INTEGER,
    rsDnsServerSrowStatus		RowStatus
    }

rsDnsServerSUrl OBJECT-TYPE
    SYNTAX DisplayString (SIZE(1..80))
    ACCESS  read-only
    STATUS  mandatory
    DESCRIPTION
      "The URL string in the static URL/IP resolution table."
    ::=  { rsDnsServerStaticResEntry 1}

rsDnsServerSIp OBJECT-TYPE
    SYNTAX IpAddress
    ACCESS  read-write
    STATUS  mandatory
    DESCRIPTION
      "The IP Address in the static URL/IP resolution table."
    ::= { rsDnsServerStaticResEntry 2}

rsDnsServerSEnable OBJECT-TYPE
    SYNTAX INTEGER {
      enable(1),
      disable(2)
    }
    ACCESS  read-write
    STATUS  mandatory
    DESCRIPTION
      "Mark if the entry is enabled for the DNS server."
    ::= { rsDnsServerStaticResEntry 3}

rsDnsServerSrowStatus OBJECT-TYPE
    SYNTAX RowStatus
    ACCESS  read-write
    STATUS  mandatory
    DESCRIPTION
     "Administrative status."
    ::=  { rsDnsServerStaticResEntry 4}


rsPrivateCheckSNMPPort OBJECT-TYPE
    SYNTAX INTEGER (1..65535)
    ACCESS  read-write
    STATUS  mandatory
    DESCRIPTION
        "Destination SNMP port used for private and NT checks."
    DEFVAL { 161 }
    ::=  { rsServerDispatcher 95}

rsVlanTagHandling OBJECT-TYPE
    SYNTAX  INTEGER {
      retain (1),
      overwrite (2)
    }
    ACCESS  read-write
    STATUS  mandatory
    DESCRIPTION
      "Determine how to handle incoming tagged packets: forward them with the original tags or
       overwrite the tags with new ones before forwarding. Note that overwrite may in some
       cases simply remove the tag."
    DEFVAL { overwrite }
    ::=  { rsServerDispatcher 96 }

rsSmtpParameters OBJECT IDENTIFIER ::= { rsServerDispatcher 97 }

rsSmtpPrimaryAddr  OBJECT-TYPE
    SYNTAX  DisplayString (SIZE(0..64))
    ACCESS  read-write
    STATUS  mandatory
    DESCRIPTION
      "Primary SMTP server address."
    ::=  {rsSmtpParameters 1}

rsSmtpAlternateAddr  OBJECT-TYPE
    SYNTAX  DisplayString (SIZE(0..64))
    ACCESS  read-write
    STATUS  mandatory
    DESCRIPTION
      "Alternate SMTP server address."
    ::=  {rsSmtpParameters 2}

rsSmtpEnable  OBJECT-TYPE
    SYNTAX INTEGER {
      enable(1),
      disable(2)
    }
    ACCESS  read-write
    STATUS  mandatory
    DESCRIPTION
      "SMTP task enable."
    DEFVAL { 2 }
    ::=  {rsSmtpParameters 3}

rsSmtpOwnAddr OBJECT-TYPE
    SYNTAX DisplayString (SIZE(0..64))
    ACCESS  read-write
    STATUS  mandatory
    DESCRIPTION
      "Our own Email address"
    ::=  { rsSmtpParameters 4}

rsSmtpBackupOwnAddr OBJECT-TYPE
    SYNTAX DisplayString (SIZE(0..64))
    ACCESS  read-write
    STATUS  mandatory
    DESCRIPTION
      "Backup device own Email address"
    ::=  { rsSmtpParameters 5}


rsWSDSyslogUrl OBJECT-TYPE
    SYNTAX  DisplayString(SIZE(0..64))
    ACCESS  read-write
    STATUS  mandatory
    DESCRIPTION
        "The URL/IP Address of the syslog station."
    ::= {rsServerDispatcher 98}


rsFileSystem  OBJECT IDENTIFIER ::= { rsServerDispatcher 99 }

--
--  rsFSapplList
--
rsFSapplList  OBJECT-TYPE
   SYNTAX  SEQUENCE OF RsFSapplEntry
   ACCESS  not-accessible
   STATUS  mandatory
   DESCRIPTION
         "An entry of this table specifies an an application on the compact flash."
   ::= { rsFileSystem 1 }

rsFSapplEntry OBJECT-TYPE
   SYNTAX  RsFSapplEntry
   ACCESS  not-accessible
   STATUS  mandatory
   DESCRIPTION
         "A list of information for each application."
   INDEX  { rsFSapplName }
   ::= { rsFSapplList 1 }

RsFSapplEntry   ::= SEQUENCE {
     rsFSapplName             DisplayString,
     rsFSapplIndex 	          INTEGER,
     rsFSapplValid            TruthValue,
     rsFSapplActive           TruthValue,
     rsFSapplVersion          DisplayString,
     rsFSapplStartup 	      TruthValue,
     rsFSapplStatus           RowStatus,
     rsFSapplVersionOS        DisplayString,
     rsFSapplVersionDP        DisplayString,     
     rsFSapplVersionDME       DisplayString,
     rsFSapplVersionDD        DisplayString
   }

rsFSapplName OBJECT-TYPE
   SYNTAX  DisplayString (SIZE(1..60))
   ACCESS  read-only
   STATUS  mandatory
   DESCRIPTION
         "The application name"
   ::= { rsFSapplEntry 1 }

rsFSapplIndex OBJECT-TYPE
   SYNTAX  INTEGER
   ACCESS  read-only
   STATUS  mandatory
   DESCRIPTION
         "The application index number as appears on the compact flash."
   ::= { rsFSapplEntry 2 }

rsFSapplValid  OBJECT-TYPE
   SYNTAX  TruthValue
   ACCESS  read-only
   STATUS  mandatory
   DESCRIPTION
         "Indicate whether the application is valid or not:
      true(1) : Application is valid - can be set to active
      false(2): Application is invalid - indicates a problem in the
		upgrade process or installation, user should download a new version."
   ::= { rsFSapplEntry 3 }

rsFSapplActive  OBJECT-TYPE
   SYNTAX  TruthValue
   ACCESS  read-write
   STATUS  mandatory
   DESCRIPTION
         "Indicate or set the application as the current active application:
      true(1):  active application
      false(2): not the active application."
   ::= { rsFSapplEntry 4 }

rsFSapplVersion OBJECT-TYPE
   SYNTAX  DisplayString (SIZE(1..20))
   ACCESS  read-only
   STATUS  mandatory
   DESCRIPTION
         "The major version of the application."
   ::= { rsFSapplEntry 5 }

rsFSapplStartup  OBJECT-TYPE
   SYNTAX  TruthValue
   ACCESS  read-only
   STATUS  mandatory
   DESCRIPTION
         "Indicate whether the application is the startup application:
      true(1) : startup application
      false(2): not the startup application."
   ::= { rsFSapplEntry 6 }

rsFSapplStatus OBJECT-TYPE
   SYNTAX  RowStatus
   ACCESS  read-write
   STATUS  mandatory
   DESCRIPTION
         "delete/update an entry"
   ::= { rsFSapplEntry 7 }

rsFSapplVersionOS OBJECT-TYPE
   SYNTAX  DisplayString (SIZE(1..30))
   ACCESS  read-only
   STATUS  mandatory
   DESCRIPTION
         "The OS version"
   ::= { rsFSapplEntry 8 }

rsFSapplVersionDP OBJECT-TYPE
   SYNTAX  DisplayString (SIZE(1..30))
   ACCESS  read-only
   STATUS  mandatory
   DESCRIPTION
         "The DP version"
   ::= { rsFSapplEntry 9 }

rsFSapplVersionDME OBJECT-TYPE
   SYNTAX  DisplayString (SIZE(1..30))
   ACCESS  read-only
   STATUS  mandatory
   DESCRIPTION
         "The DME version"
   ::= { rsFSapplEntry 10 }

rsFSapplVersionDD OBJECT-TYPE
   SYNTAX  DisplayString (SIZE(1..30))
   ACCESS  read-only
   STATUS  mandatory
   DESCRIPTION
         "The DeviceDriver version"
   ::= { rsFSapplEntry 11 }   

rsFSinstallNew  OBJECT-TYPE
    SYNTAX INTEGER {
                    enable(1),
                    disable(2)
                   }
    ACCESS  read-write
    STATUS  mandatory
    DESCRIPTION
        "Enable/Disable - automatic make new downloaded application the default."
    DEFVAL { 1 }
    ::=  {rsFileSystem 2}






rdwrConfigurationFileTable  OBJECT-TYPE
   SYNTAX  SEQUENCE OF RdwrConfigurationFileEntry
   ACCESS  not-accessible
   STATUS  mandatory
   DESCRIPTION
         "A table holding information about configuration files."
   ::= { rsFileSystem 3 }


rdwrConfigurationFileEntry OBJECT-TYPE
   SYNTAX  RdwrConfigurationFileEntry
   ACCESS  not-accessible
   STATUS  mandatory
   DESCRIPTION
         "An entry in the table of configuration files"
   INDEX  {rdwrConfigurationFileApp,rdwrConfigurationFileName}
   ::= { rdwrConfigurationFileTable 1 }

RdwrConfigurationFileEntry   ::= SEQUENCE {
     rdwrConfigurationFileApp              DisplayString,
     rdwrConfigurationFileName             DisplayString,
     rdwrConfigurationFileRunning          TruthValue,
     rdwrConfigurationFileInstalled        TruthValue,
     rdwrConfigurationFilePath             DisplayString,
     rdwrConfigurationFileAction           INTEGER,
     rdwrConfigurationFileStatus           RowStatus
   }

rdwrConfigurationFileApp OBJECT-TYPE
   SYNTAX  DisplayString (SIZE(1..128))
   ACCESS  read-only
   STATUS  mandatory
   DESCRIPTION
         "The application the configuration file belongs to."
   ::= { rdwrConfigurationFileEntry 1 }

rdwrConfigurationFileName OBJECT-TYPE
   SYNTAX  DisplayString (SIZE(1..128))
   ACCESS  read-only
   STATUS  mandatory
   DESCRIPTION
         "The name of the configuration file relative to a predefined directory holding
          all configuration files for a specific application."
   ::= { rdwrConfigurationFileEntry 2 }


rdwrConfigurationFileRunning  OBJECT-TYPE
   SYNTAX  TruthValue
   ACCESS  read-only
   STATUS  mandatory
   DESCRIPTION
         "Indicate whether this is the currently running configuration."
   ::= { rdwrConfigurationFileEntry 3 }

rdwrConfigurationFileInstalled  OBJECT-TYPE
   SYNTAX  TruthValue
   ACCESS  read-only
   STATUS  mandatory
   DESCRIPTION
         "Indicate whether this is the currently installed configuration, i.e. the configuration
          which will be associated to it's application after reset."
   ::= { rdwrConfigurationFileEntry 4 }


rdwrConfigurationFilePath OBJECT-TYPE
   SYNTAX  DisplayString (SIZE(0..128))
   ACCESS  read-write
   STATUS  mandatory
   DESCRIPTION
         "The absolute path of the configuration file. When creating a new entry in this table
          the path must be present and indicates where the file is to be taken from."
   ::= { rdwrConfigurationFileEntry 5 }


rdwrConfigurationFileAction  OBJECT-TYPE
    SYNTAX INTEGER {
           none(1),
           add(2),
           install(3),
           delete(4)
    }
    ACCESS  read-write
    STATUS  mandatory
    DESCRIPTION
        "The required operation needed on the configuration file."
    DEFVAL { 1 }
    ::=  {rdwrConfigurationFileEntry 6}

rdwrConfigurationFileStatus OBJECT-TYPE
   SYNTAX  RowStatus
   ACCESS  read-write
   STATUS  mandatory
   DESCRIPTION
         "Operation to be performed on a specific configuration file."
   ::= { rdwrConfigurationFileEntry 7 }


rdwrDefCfg OBJECT IDENTIFIER ::= { rsFileSystem 4 }

rdwrDefCfgIpAddress OBJECT-TYPE
   SYNTAX IpAddress
   ACCESS   read-write
   STATUS mandatory
   DESCRIPTION
    "The default IP address of the device"
     ::=  { rdwrDefCfg 1 }

rdwrDefCfgIpMask OBJECT-TYPE
   SYNTAX IpAddress
   ACCESS   read-write
   STATUS mandatory
   DESCRIPTION
    "The default IP mask of the device"
     ::=  { rdwrDefCfg 2 }

rdwrDefCfgPort OBJECT-TYPE
   SYNTAX INTEGER
   ACCESS   read-write
   STATUS mandatory
   DESCRIPTION
    "The default port number of the device"
     ::=  { rdwrDefCfg 3 }


rdwrDefCfgGateway OBJECT-TYPE
   SYNTAX IpAddress
   ACCESS   read-write
   STATUS mandatory
   DESCRIPTION
    "The default gatewary address of the device"
     ::=  { rdwrDefCfg 4 }


rdwrDefCfgUserName OBJECT-TYPE
   SYNTAX DisplayString (SIZE(0..30))
   ACCESS read-write
   STATUS mandatory
   DESCRIPTION
    "The default root user name"
     ::= { rdwrDefCfg 5 }


rdwrDefCfgUserPassword OBJECT-TYPE
   SYNTAX DisplayString (SIZE(0..64))
   ACCESS read-write
   STATUS mandatory
   DESCRIPTION
    "The default root user password"
     ::= { rdwrDefCfg 6 }

rdwrDefCfgCommunity OBJECT-TYPE
   SYNTAX DisplayString (SIZE(0..64))
   ACCESS read-write
   STATUS mandatory
   DESCRIPTION
    "The default community string for SNMP v1 and SNMP v2 access."
     ::= { rdwrDefCfg 7 }




rdwrApplicationFileTable  OBJECT-TYPE
   SYNTAX  SEQUENCE OF RdwrApplicationFileEntry
   ACCESS  not-accessible
   STATUS  mandatory
   DESCRIPTION
         "A table holding information about Application files."
   ::= { rsFileSystem 5 }


rdwrApplicationFileEntry OBJECT-TYPE
   SYNTAX  RdwrApplicationFileEntry
   ACCESS  not-accessible
   STATUS  mandatory
   DESCRIPTION
         "An entry in the table of Application files"
   INDEX  {rdwrApplicationFileName}
   ::= { rdwrApplicationFileTable 1 }

RdwrApplicationFileEntry   ::= SEQUENCE {
     rdwrApplicationFileName             DisplayString,
     rdwrApplicationFileRunning          TruthValue,
     rdwrApplicationFileSelected         TruthValue,
     rdwrApplicationFileValid	         TruthValue,
     rdwrApplicationFileStartup          TruthValue,
     rdwrApplicationFileVersion          DisplayString,
     rdwrApplicationFileAction           INTEGER,
     rdwrApplicationFileStatus           RowStatus
   }

rdwrApplicationFileName OBJECT-TYPE
   SYNTAX  DisplayString (SIZE(1..128))
   ACCESS  read-only
   STATUS  mandatory
   DESCRIPTION
         "The application name."
   ::= { rdwrApplicationFileEntry 1 }

rdwrApplicationFileRunning  OBJECT-TYPE
   SYNTAX  TruthValue
   ACCESS  read-only
   STATUS  mandatory
   DESCRIPTION
         "Indicate whether this is the currently running application."
   ::= { rdwrApplicationFileEntry 2 }

rdwrApplicationFileSelected  OBJECT-TYPE
   SYNTAX  TruthValue
   ACCESS  read-only
   STATUS  mandatory
   DESCRIPTION
         "Indicate whether this is the currently selected application, i.e. the application
          which will be running after reset."
   ::= { rdwrApplicationFileEntry 3 }


rdwrApplicationFileValid  OBJECT-TYPE
   SYNTAX  TruthValue
   ACCESS  read-only
   STATUS  mandatory
   DESCRIPTION
         "Indicate whether the application is valid or not:
      true(1) : Application is valid - can be set to active
      false(2): Application is invalid - indicates a problem in the
		upgrade process or installation, user should download a new version."
   ::= { rdwrApplicationFileEntry 4 }


rdwrApplicationFileStartup  OBJECT-TYPE
   SYNTAX  TruthValue
   ACCESS  read-only
   STATUS  mandatory
   DESCRIPTION
         "Indicate whether the application is the startup application:
      true(1) : startup application
      false(2): not the startup application."
   ::= { rdwrApplicationFileEntry 5 }


rdwrApplicationFileVersion OBJECT-TYPE
   SYNTAX  DisplayString (SIZE(1..20))
   ACCESS  read-only
   STATUS  mandatory
   DESCRIPTION
         "The major version of the application."
   ::= { rdwrApplicationFileEntry 6 }


rdwrApplicationFileAction  OBJECT-TYPE
    SYNTAX INTEGER {
           none(1),
           add(2),
           select(3),
           delete(4)
    }
    ACCESS  read-write
    STATUS  mandatory
    DESCRIPTION
        "Add/Select(install)/Delete an application name."
    DEFVAL { 1 }
    ::=  {rdwrApplicationFileEntry 7}

rdwrApplicationFileStatus OBJECT-TYPE
   SYNTAX  RowStatus
   ACCESS  read-write
   STATUS  mandatory
   DESCRIPTION
         "The SNMP Operation to be performed on a specific application file."
   ::= { rdwrApplicationFileEntry 8 }






rsWSDHardwareLicense OBJECT-TYPE
    SYNTAX DisplayString (SIZE(1..80))
    ACCESS  read-write
    STATUS  mandatory
    DESCRIPTION "The new licence for the device"
--    DEFVAL
    ::=  {rsServerDispatcher 100}

rsWSDHardwareLicenseID OBJECT-TYPE
   SYNTAX DisplayString (SIZE(1..80))
   ACCESS  read-only
   STATUS  mandatory
   DESCRIPTION
    "License ID used for license downgrade"
    ::= { rsServerDispatcher 101 }

rsWSDThroughputLicense OBJECT-TYPE
    SYNTAX DisplayString (SIZE(1..80))
    ACCESS  read-write
    STATUS  mandatory
    DESCRIPTION "The new licence for the device"
--    DEFVAL
    ::=  {rsServerDispatcher 141}

rsWSDThroughputLicenseID OBJECT-TYPE
   SYNTAX DisplayString (SIZE(1..80))
   ACCESS  read-only
   STATUS  mandatory
   DESCRIPTION
    "License ID used for license downgrade"
    ::= { rsServerDispatcher 142 }

rsWSDThroughputLicenseIP OBJECT-TYPE
   SYNTAX DisplayString (SIZE(1..80))
   ACCESS  read-only
   STATUS  mandatory
   DESCRIPTION
    "License IP "
    ::= { rsServerDispatcher 143 }

rsWSDThroughputLicenseMethod OBJECT-TYPE
   SYNTAX DisplayString (SIZE(1..80))
   ACCESS  read-only
   STATUS  mandatory
   DESCRIPTION
    "License Method "
    ::= { rsServerDispatcher 144 }

rsWSDVcpuLicense OBJECT-TYPE
    SYNTAX DisplayString (SIZE(1..80))
    ACCESS  read-write
    STATUS  mandatory
    DESCRIPTION "The vCPU licence"
--    DEFVAL
    ::=  {rsServerDispatcher 193}


rsWSDVcpuLicenseID  OBJECT-TYPE
   SYNTAX DisplayString (SIZE(1..80))
   ACCESS  read-only
   STATUS  mandatory
   DESCRIPTION
    "VCPU License ID used for license downgrade"
    ::= { rsServerDispatcher 194}


rsWSDVcpuLicenseIP OBJECT-TYPE
  SYNTAX DisplayString (SIZE(1..80))
  ACCESS  read-only
   STATUS  mandatory
   DESCRIPTION
    "VCPU License IP "
    ::= { rsServerDispatcher 195 }

rsWSDVcpuLicenseMethod OBJECT-TYPE
   SYNTAX DisplayString (SIZE(1..80))
   ACCESS  read-only
  STATUS  mandatory
   DESCRIPTION
    "VCPU License Method "
    ::= { rsServerDispatcher 196 }

rdwrSnmpParameters OBJECT IDENTIFIER ::= { rsServerDispatcher 102 }

rdwrSnmpSupportedVersions OBJECT-TYPE
    SYNTAX  INTEGER
    ACCESS  read-only
    STATUS  mandatory
    DESCRIPTION
      "The currently supported SNMP versions as a bit mask. "
    ::=  { rdwrSnmpParameters 1}

rdwrSnmpSupportedVersionsAfterReset OBJECT-TYPE
    SYNTAX  INTEGER
    ACCESS  read-write
    STATUS  mandatory
    DESCRIPTION
      "The bit mask of supported SNMP versions after resetting the device."
    ::=  { rdwrSnmpParameters 2}

rdwrSnmpPort OBJECT-TYPE
    SYNTAX  INTEGER
    ACCESS  read-write
    STATUS  mandatory
    DESCRIPTION
      "The Snmp Port."
--  DEFVAL  { 161 }
    ::=  {rdwrSnmpParameters 3}


rdwrSnmpStatus OBJECT-TYPE
   SYNTAX  INTEGER {
        enable(1),
      	disable(2)
   }
   ACCESS  read-write
   STATUS  mandatory
   DESCRIPTION
        "Snmp Status. Enable/Disable Snmp operation."
--  DEFVAL  { enable }
   ::= { rdwrSnmpParameters 4 }


rdwrSnmpConfigFileFormat OBJECT-TYPE
    SYNTAX  INTEGER {
      cli(1),
      ber(2),
      ascii(3)
    }
    ACCESS  read-write
    STATUS  mandatory
    DESCRIPTION
	"The format of the configuration file."
-- DEFVAL { ber }
        ::=  { rdwrSnmpParameters 5 }



rdwrSnmpErrorIndex OBJECT-TYPE
    SYNTAX  INTEGER
    ACCESS  read-only
    STATUS  mandatory
    DESCRIPTION
      "The index of the field in the PDU which caused the error. 
       Values as in the reply PDU starting with 1."
    ::=  {rdwrSnmpParameters 6}

rdwrSnmpErrorStatus OBJECT-TYPE
    SYNTAX  INTEGER
    ACCESS  read-only
    STATUS  mandatory
    DESCRIPTION
      "The status returned in the Reply PDU."
    ::=  {rdwrSnmpParameters 7}

rdwrSnmpErrorDescription OBJECT-TYPE
    SYNTAX DisplayString (SIZE(0..255))
    ACCESS  read-only
    STATUS  mandatory
    DESCRIPTION
      "The description of the error."
    ::=  {rdwrSnmpParameters 8}


rdwrSnmpErrorRequestId OBJECT-TYPE
    SYNTAX  INTEGER
    ACCESS  read-only
    STATUS  mandatory
    DESCRIPTION
      "The requestId of the request which caused the last error."
    ::=  {rdwrSnmpParameters 9}

rdwrSnmpErrorTbTable OBJECT-TYPE
    SYNTAX SEQUENCE OF RdwrSnmpErrorTbEntry
    ACCESS not-accessible
    STATUS  mandatory
    DESCRIPTION
      "Table containing the list of errors occured"
    ::=  {rdwrSnmpParameters 10}

rdwrSnmpErrorTbEntry OBJECT-TYPE
    SYNTAX RdwrSnmpErrorTbEntry
    ACCESS not-accessible
    STATUS  mandatory
    DESCRIPTION
       "The row definition for this table."
    INDEX {	rdwrSnmpErrorTbRequestId
}
    ::=  { rdwrSnmpErrorTbTable 1 }

RdwrSnmpErrorTbEntry ::= SEQUENCE {
	rdwrSnmpErrorTbRequestId		INTEGER,
   	rdwrSnmpErrorTbVarId			OBJECT IDENTIFIER,
	rdwrSnmpErrorTbDescription		DisplayString,
    	rdwrSnmpErrorTbErrorIndex		INTEGER,
    	rdwrSnmpErrorTbType			INTEGER,
    	rdwrSnmpErrorTbStatus			INTEGER,
	rdwrSnmpErrorTbFieldInEntry		INTEGER,
	rdwrSnmpErrorTbTime			DisplayString,
	rdwrSnmpErrorTbDate			DisplayString
}

rdwrSnmpErrorTbRequestId OBJECT-TYPE
    SYNTAX INTEGER
    ACCESS  read-only
    STATUS  mandatory
    DESCRIPTION
       "This variable indicates the requestId of the request which caused the error."
    ::=  { rdwrSnmpErrorTbEntry 1 }

rdwrSnmpErrorTbVarId OBJECT-TYPE
    SYNTAX OBJECT IDENTIFIER
    ACCESS  read-only
    STATUS  mandatory
    DESCRIPTION
       "This variable indicates the variable Oid"
    ::=  { rdwrSnmpErrorTbEntry 2 }

rdwrSnmpErrorTbDescription OBJECT-TYPE
    SYNTAX DisplayString (SIZE(0..255))
    ACCESS  read-only
    STATUS  mandatory
    DESCRIPTION
       "This variable indicates the description of the error"
    ::=  { rdwrSnmpErrorTbEntry 3 }

rdwrSnmpErrorTbErrorIndex OBJECT-TYPE
    SYNTAX INTEGER
    ACCESS  read-only
    STATUS  mandatory
    DESCRIPTION
       "This variable indicates the index of the field in the PDU which caused the error (start at 1)"
    ::=  { rdwrSnmpErrorTbEntry 4 }

rdwrSnmpErrorTbType OBJECT-TYPE
    SYNTAX INTEGER {
    	    ok(0),
	    application(1),
	    internalRange(2),
	    internalGeneral(3)}
    ACCESS  read-only
    STATUS  mandatory
    DESCRIPTION
       "This variable indicates the type of error."
    ::=  { rdwrSnmpErrorTbEntry 5 }
    
rdwrSnmpErrorTbStatus OBJECT-TYPE
    SYNTAX INTEGER {
    	    ok(0),
	    tooBig(1),
	    noSuchName(2),
	    badValue(3),
	    readOnly(4),
	    genErr(5)}
    ACCESS  read-only
    STATUS  mandatory
    DESCRIPTION
       "This variable indicates the type of error."
    ::=  { rdwrSnmpErrorTbEntry 6 }

rdwrSnmpErrorTbFieldInEntry OBJECT-TYPE
    SYNTAX INTEGER 
    ACCESS  read-only
    STATUS  mandatory
    DESCRIPTION
       "This variable indicates the index of the field in an entry (0 for scalar)"
    ::=  { rdwrSnmpErrorTbEntry 7 }

rdwrSnmpErrorTbTime  OBJECT-TYPE
   SYNTAX DisplayString (SIZE(9))
   ACCESS read-only
   STATUS mandatory
   DESCRIPTION
    "This variable indicates the time the error occurred, the time will be in the format hh:mm:ss"
   ::= { rdwrSnmpErrorTbEntry 8 }

rdwrSnmpErrorTbDate  OBJECT-TYPE
   SYNTAX DisplayString (SIZE(11))
   ACCESS read-only
   STATUS mandatory
   DESCRIPTION
     "This variable indicates the time the error occurred, the date will be in the format dd/mm/yyyy"
    ::= { rdwrSnmpErrorTbEntry 9 }


rdwrSnmpErrorTbTableReset OBJECT-TYPE
    SYNTAX  INTEGER {
      	    reset(1) }
   ACCESS  read-write
   STATUS  mandatory
   DESCRIPTION
      "Reset the SNMP error table"
    ::=  {rdwrSnmpParameters 11}

 
rdwrLastConfigurationChangesTable OBJECT-TYPE
    SYNTAX SEQUENCE OF RdwrLastConfigurationChangesEntry
    ACCESS not-accessible
    STATUS  mandatory
    DESCRIPTION
      "Table containing the list of last configuration changes occured."
    ::=  {rdwrSnmpParameters 12}
    
rdwrLastConfigurationChangesEntry OBJECT-TYPE
    SYNTAX RdwrLastConfigurationChangesEntry
    ACCESS not-accessible
    STATUS  mandatory
    DESCRIPTION
       "The row definition for this table."
    INDEX {rdwrLastConfigurationChangesID }
    ::= {rdwrLastConfigurationChangesTable 1}
    
RdwrLastConfigurationChangesEntry ::= SEQUENCE {
      	rdwrLastConfigurationChangesID				INTEGER,
      	rdwrLastConfigurationChangesStatus			RowStatus,
      	rdwrLastConfigurationChangesMibOid 			OBJECT IDENTIFIER,
      	rdwrLastConfigurationChangesChangeType 		INTEGER,
      	rdwrLastConfigurationChangesKeys 			DisplayString
}

rdwrLastConfigurationChangesID OBJECT-TYPE
   SYNTAX INTEGER 
   ACCESS read-only
   STATUS mandatory
   DESCRIPTION
    "This variable indicates the change ID"
     ::=  { rdwrLastConfigurationChangesEntry 1}
     
rdwrLastConfigurationChangesStatus OBJECT-TYPE
   SYNTAX RowStatus
   ACCESS read-write
   STATUS mandatory
   DESCRIPTION
      "Entry status. It is used to delete an entry"
   ::=  { rdwrLastConfigurationChangesEntry 2}

rdwrLastConfigurationChangesMibOid OBJECT-TYPE
   SYNTAX OBJECT IDENTIFIER
   ACCESS read-only
   STATUS mandatory
   DESCRIPTION
    "This variable indicates Mib OID."
     ::=  { rdwrLastConfigurationChangesEntry 3}

rdwrLastConfigurationChangesChangeType OBJECT-TYPE
   SYNTAX INTEGER {add(1), modify(2), delete(3), configurationFileLoaded(4), tableNotUpdated(5), refreshTable(6), updatePolicies(7)}
   ACCESS read-only
   STATUS mandatory
   DESCRIPTION
    "This variable indicates ChangeType "
     ::=  { rdwrLastConfigurationChangesEntry 4}

rdwrLastConfigurationChangesKeys OBJECT-TYPE
   SYNTAX DisplayString
   ACCESS read-only
   STATUS mandatory
   DESCRIPTION
    "This variable indicates Keys."
     ::=  { rdwrLastConfigurationChangesEntry 5}
     
rdwrLastConfigurationChangesTableReset OBJECT-TYPE
   SYNTAX  INTEGER {reset(1)}
   ACCESS  read-write
   STATUS  mandatory
   DESCRIPTION
    "Reset the Last Configuration Changes table"
   ::=  {rdwrSnmpParameters 13}

rdwrLastConfigurationChangesTimestamp OBJECT-TYPE
   SYNTAX      TimeStamp
   ACCESS      read-only
   STATUS      mandatory
   DESCRIPTION
           "The value of sysUpTime at the last configuration change."
   ::= { rdwrSnmpParameters 14 }

rdwrLastConfigurationChangesTime OBJECT-TYPE
   SYNTAX      INTEGER
   ACCESS      read-only 
   STATUS      mandatory
   DESCRIPTION
           "Last configuration change time, time since 00:00:00 GMT, Jan. 1, 1970, measured in seconds."
   ::= { rdwrSnmpParameters 15 }


     
rsWSDSyslogSourcePort OBJECT-TYPE
    SYNTAX  INTEGER (514 | 1024..65535)
    ACCESS  read-write
    STATUS  mandatory
    DESCRIPTION
      "Determines the source port with which Syslog packets will be sent."
    DEFVAL { 514 }
    ::=  { rsServerDispatcher 103 }
    
rsWSDSyslogDestinationPort OBJECT-TYPE
    SYNTAX  INTEGER (514 | 1024..65535)
    ACCESS  read-write
    STATUS  mandatory
    DESCRIPTION
      "Determines the destination port with which Syslog packets will be sent."
    DEFVAL { 514 }
    ::=  { rsServerDispatcher 124 }    

rsSESSION OBJECT IDENTIFIER ::= { rsServerDispatcher 104 }

-- -------------------------------------------------------------
-- Radware - Enterprise
-- -------------------------------------------------------------

rsLinkAggregationHash OBJECT IDENTIFIER ::= { rsServerDispatcher 105 }

rsLinkAggregationL2Hash OBJECT-TYPE
    SYNTAX INTEGER {
      none(1),
      source(2),
	  detination(3),
	  both(4)
    }
    ACCESS  read-write
    STATUS  mandatory
    DESCRIPTION
      "Layer 2 addresses usage in the hash function"
    DEFVAL { 1 }
    ::=  {rsLinkAggregationHash 1}


rsLinkAggregationL3Hash OBJECT-TYPE
    SYNTAX INTEGER {
      none(1),
      source(2),
	  detination(3),
	  both(4)
    }
    ACCESS  read-write
    STATUS  mandatory
    DESCRIPTION
      "Layer 3 addresses usage in the hash function"
    DEFVAL { 1 }
    ::=  {rsLinkAggregationHash 2}


rsLinkAggregationL4Hash  OBJECT-TYPE
    SYNTAX INTEGER {
      none(1),
      source(2),
	  detination(3),
	  both(4)
    }
    ACCESS  read-write
    STATUS  mandatory
    DESCRIPTION
      "Layer 4 ports usage in the hash function"
    DEFVAL { 1 }
    ::=  {rsLinkAggregationHash 3}



rsScheduleTable OBJECT-TYPE
   SYNTAX SEQUENCE OF RsScheduleEntry
   ACCESS not-accessible
   STATUS mandatory
   DESCRIPTION
       "The table of event schedules. All schedules are kept in it."
   ::= {rsServerDispatcher 106}

rsScheduleEntry OBJECT-TYPE
   SYNTAX RsScheduleEntry
   ACCESS not-accessible
   STATUS  mandatory
   DESCRIPTION
       " The row definition for this table."
   INDEX  { rsScheduleName }
   ::= {rsScheduleTable 1}

RsScheduleEntry ::= SEQUENCE {
     rsScheduleName           DisplayString,
     rsScheduleFrequency      INTEGER,
     rsScheduleTime           DisplayString,
     rsScheduleDays           DisplayString,
     rsScheduleDate           DisplayString,
     rsScheduleStatus         RowStatus
}

rsScheduleName OBJECT-TYPE
   SYNTAX DisplayString (SIZE(1..30))
   ACCESS  read-write
   STATUS  mandatory
   DESCRIPTION
       "The name of the schedule. It is the primary key"
   ::= {rsScheduleEntry 1}

rsScheduleFrequency OBJECT-TYPE
   SYNTAX INTEGER {
      once(1),
      daily(2),
      weekly(3)
   }
   ACCESS  read-write
   STATUS  mandatory
   DESCRIPTION
       "The frequency of the event."
 DEFVAL {1}
   ::= {rsScheduleEntry 2}

rsScheduleTime OBJECT-TYPE
   SYNTAX DisplayString (SIZE(4))
   ACCESS read-write
   STATUS mandatory
   DESCRIPTION
    "The time will be sent in the format hhmm- 0 means field not relevant "
   ::= {rsScheduleEntry 3}

rsScheduleDays OBJECT-TYPE
   SYNTAX DisplayString(SIZE(7))
   ACCESS  read-write
   STATUS  mandatory
   DESCRIPTION
       "Each octet represents status of day. 0 -not selected, 1-selected.
        The order is:
        Sunday    1000000
        Monday    0100000
        Tuesday   0010000
        wednesday 0001000
        Thursday  0000100
        Friday    0000010
        Saturday  0000001"
   ::= {rsScheduleEntry 4}

rsScheduleDate OBJECT-TYPE
   SYNTAX DisplayString (SIZE(8))
   ACCESS read-write
   STATUS mandatory
   DESCRIPTION
    "The date will be sent in the format ddmmyyyy - 0 means field not relevant"
   ::= {rsScheduleEntry 5}

rsScheduleStatus OBJECT-TYPE
   SYNTAX  RowStatus
   ACCESS  read-write
   STATUS  mandatory
   DESCRIPTION
         "delete/update an entry"
   ::= { rsScheduleEntry 6 }



rdwrFtpParameters OBJECT IDENTIFIER ::= { rsServerDispatcher 107}

rdwrFtpPort OBJECT-TYPE
    SYNTAX  INTEGER (1..65535)
    ACCESS  read-write
    STATUS  mandatory
    DESCRIPTION
      "The FTP Server Port."
--  DEFVAL  { 21 }
    ::=  {rdwrFtpParameters 1}


rdwrFtpStatus OBJECT-TYPE
   SYNTAX  INTEGER {
        enable(1),
      	disable(2)
   }
   ACCESS  read-write
   STATUS  mandatory
   DESCRIPTION
        "Ftp Status. Enable/Disable Ftp Server."
--  DEFVAL  { disable }
   ::= { rdwrFtpParameters 2 }

rsFullMacCompareStatus  OBJECT-TYPE
   SYNTAX  INTEGER {
            enforce(1),
            share(2)
   }
   ACCESS  read-write
   STATUS  mandatory
   DESCRIPTION
      "Select whether all 48 bits of the destination MAC address are used to determine if 
	   a packet is destined to the device, or just 42 (the default)"
   DEFVAL  { 2 }
    ::=  { rsServerDispatcher 108}

rsREStateMonitoring OBJECT IDENTIFIER ::= { rsServerDispatcher 109}

rsREACCReasonCounters OBJECT IDENTIFIER ::= { rsREStateMonitoring 1}

rsACCReasonUnknownCounter  OBJECT-TYPE
   SYNTAX  Counter 
   ACCESS  read-only
   STATUS  mandatory
   DESCRIPTION
      "ACC send packet to master with reason unknown"
    ::=  { rsREACCReasonCounters 1}

rsACCReasonETHBroadcastCounter  OBJECT-TYPE
   SYNTAX  Counter 
   ACCESS  read-only
   STATUS  mandatory
   DESCRIPTION
      "ACC send packet to master with reason ETH broadcast"
    ::=  { rsREACCReasonCounters 2}
    
rsACCReasonProtolcolTypeCounter  OBJECT-TYPE
   SYNTAX  Counter 
   ACCESS  read-only
   STATUS  mandatory
   DESCRIPTION
      "ACC send packet to master with reason protolcol type "
    ::=  { rsREACCReasonCounters 3}
    
rsACCReasonIPVERCounter  OBJECT-TYPE
   SYNTAX  Counter 
   ACCESS  read-only
   STATUS  mandatory
   DESCRIPTION
      "ACC send packet to master with reason IP ver"
    ::=  { rsREACCReasonCounters 4}

rsACCReasonIPHeaderLenCounter  OBJECT-TYPE
   SYNTAX  Counter 
   ACCESS  read-only
   STATUS  mandatory
   DESCRIPTION
      "ACC send packet to master with reason IP header lenght"
    ::=  { rsREACCReasonCounters 5}

rsACCReasonIPFragmentedCounter  OBJECT-TYPE
   SYNTAX  Counter 
   ACCESS  read-only
   STATUS  mandatory
   DESCRIPTION
      "ACC send packet to master with reason IP fragmented"
    ::=  { rsREACCReasonCounters 6}

rsACCReasonTTLCounter  OBJECT-TYPE
   SYNTAX  Counter 
   ACCESS  read-only
   STATUS  mandatory
   DESCRIPTION
      "ACC send packet to master with reason TTL 1 or 0"
    ::=  { rsREACCReasonCounters 7}

rsACCReasonNoFlowCounter  OBJECT-TYPE
   SYNTAX  Counter 
   ACCESS  read-only
   STATUS  mandatory
   DESCRIPTION
      "ACC send packet to master with reason no flow"
    ::=  { rsREACCReasonCounters 8}

rsACCReasonMACCFGCounter  OBJECT-TYPE
   SYNTAX  Counter 
   ACCESS  read-only
   STATUS  mandatory
   DESCRIPTION
      "ACC send packet to master with reason MAC cfg"
    ::=  { rsREACCReasonCounters 9}   

rsACCReasonSYNcookieOKCounter  OBJECT-TYPE
   SYNTAX  Counter 
   ACCESS  read-only
   STATUS  mandatory
   DESCRIPTION
      "ACC send packet to master with reason SYN cookie OK"
    ::=  { rsREACCReasonCounters 10}   
    
rsACCReasonSYNcookieInvalidCounter  OBJECT-TYPE
   SYNTAX  Counter 
   ACCESS  read-only
   STATUS  mandatory
   DESCRIPTION
      "ACC send packet to master with reason SYN cookie invalid"
    ::=  { rsREACCReasonCounters 11}   

rsACCReasonInconsistentPktLenCounter  OBJECT-TYPE
   SYNTAX  Counter 
   ACCESS  read-only
   STATUS  mandatory
   DESCRIPTION
      "ACC send packet to master with reason inconsistent packet lenght"
    ::=  { rsREACCReasonCounters 12}  
    
rsACCReasonNoReasonCounter  OBJECT-TYPE
   SYNTAX  Counter 
   ACCESS  read-only
   STATUS  mandatory
   DESCRIPTION
      "ACC send packet to master with reason no reason"
    ::=  { rsREACCReasonCounters 13}  
    
rsACCReasonFTPportCounter  OBJECT-TYPE
   SYNTAX  Counter 
   ACCESS  read-only
   STATUS  mandatory
   DESCRIPTION
      "ACC send packet to master with reason FTP port in packet"
    ::=  { rsREACCReasonCounters 14}
    
rsACCReasonFTP227Counter  OBJECT-TYPE
   SYNTAX  Counter 
   ACCESS  read-only
   STATUS  mandatory
   DESCRIPTION
      "ACC send packet to master with reason FTP 227 in packet"
    ::=  { rsREACCReasonCounters 15}
    
rsACCReasonIPLenghtCounter  OBJECT-TYPE
   SYNTAX  Counter 
   ACCESS  read-only
   STATUS  mandatory
   DESCRIPTION
      "ACC send packet to master with reason IP lenght > 40, this means a packet with data"
    ::=  { rsREACCReasonCounters 16}
    
rsACCReasonFINorRSTCounter  OBJECT-TYPE
   SYNTAX  Counter 
   ACCESS  read-only
   STATUS  mandatory
   DESCRIPTION
      "ACC send packet to master with reason FIN or RST, the session has ended"
    ::=  { rsREACCReasonCounters 17}
    
rsACCReasonClassifyCounter  OBJECT-TYPE
   SYNTAX  Counter 
   ACCESS  read-only
   STATUS  mandatory
   DESCRIPTION
      "ACC send packet to master with reason classify"
    ::=  { rsREACCReasonCounters 18} 
    
rsACCReasonVlanReplyCounter  OBJECT-TYPE
   SYNTAX  Counter 
   ACCESS  read-only
   STATUS  mandatory
   DESCRIPTION
      "ACC send packet to master with reason VLAN Reply"
    ::=  { rsREACCReasonCounters 19} 

rsACCReasonDBindNewSYNCounter  OBJECT-TYPE
   SYNTAX  Counter 
   ACCESS  read-only
   STATUS  mandatory
   DESCRIPTION
      "ACC send packet to master with reason new SYN on delayed binding"
    ::=  { rsREACCReasonCounters 20} 

rsACCReasonAllToMasterCounter  OBJECT-TYPE
   SYNTAX  Counter 
   ACCESS  read-only
   STATUS  mandatory
   DESCRIPTION
      "ACC send packet to master with reason all traffic"
    ::=  { rsREACCReasonCounters 21} 

rsREStateCounters OBJECT IDENTIFIER ::= { rsREStateMonitoring 2}

rsREStateRXReplyCounter  OBJECT-TYPE
   SYNTAX  Counter 
   ACCESS  read-only
   STATUS  mandatory
   DESCRIPTION
      "RE is state rx reply"
    ::=  { rsREStateCounters 1}
    
rsREStateRXRequestCounter  OBJECT-TYPE
   SYNTAX  Counter 
   ACCESS  read-only
   STATUS  mandatory
   DESCRIPTION
      "RE is state rx request"
    ::=  { rsREStateCounters 2}

rsREStateIPDAinFFTCounter  OBJECT-TYPE
   SYNTAX  Counter 
   ACCESS  read-only
   STATUS  mandatory
   DESCRIPTION
      "Packet IPDA in FFT"
    ::=  { rsREStateCounters 3}

rsREStateIPDAnotFFTCounter  OBJECT-TYPE
   SYNTAX  Counter 
   ACCESS  read-only
   STATUS  mandatory
   DESCRIPTION
      "Packet IPDA not FFT"
    ::=  { rsREStateCounters 4}

rsREStateBridgeCounter  OBJECT-TYPE
   SYNTAX  Counter 
   ACCESS  read-only
   STATUS  mandatory
   DESCRIPTION
      "Performing bridging"
    ::=  { rsREStateCounters 5}


rsREStateResetCounter  OBJECT-TYPE
   SYNTAX  INTEGER {
       reset(1)
       }
   ACCESS  read-write
   STATUS  mandatory
   DESCRIPTION
      "Reset the ACC counters"
   DEFVAL  { 1 }
    ::=  { rsREStateMonitoring 3} 
    


rdwrTerminalParams OBJECT IDENTIFIER ::= {rsServerDispatcher 110 }


rdwrTerminalAliasTable OBJECT-TYPE
  SYNTAX  SEQUENCE OF RdwrTerminalAliasEntry
  ACCESS  not-accessible
  STATUS  mandatory
  DESCRIPTION
  "A table containing the alias strings of a specific user."
  ::= {rdwrTerminalParams 1}

rdwrTerminalAliasEntry OBJECT-TYPE
  SYNTAX  RdwrTerminalAliasEntry
  ACCESS  not-accessible
  STATUS  mandatory
  DESCRIPTION
  "Information about a particular Alias entry."
  INDEX   { rdwrTerminalAliasName, rdwrTerminalUserName }
  ::= { rdwrTerminalAliasTable 1 }

RdwrTerminalAliasEntry ::= SEQUENCE {
    rdwrTerminalAliasName     DisplayString,
    rdwrTerminalUserName      DisplayString,
    rdwrTerminalAliasCommand  DisplayString,
    rdwrTerminalAliasStatus   RowStatus
  }

rdwrTerminalAliasName OBJECT-TYPE
    SYNTAX DisplayString (SIZE(0..80))
    ACCESS  read-write
    STATUS  mandatory
    DESCRIPTION
    "Alias string."
    ::= {rdwrTerminalAliasEntry 1}

rdwrTerminalUserName OBJECT-TYPE
    SYNTAX DisplayString (SIZE(0..80))
    ACCESS  read-write
    STATUS  mandatory
    DESCRIPTION
    "User name string."
    ::= {rdwrTerminalAliasEntry 2}

rdwrTerminalAliasCommand OBJECT-TYPE
    SYNTAX DisplayString (SIZE(0..80))
    ACCESS  read-write
    STATUS  mandatory
    DESCRIPTION
    "command string."
    ::= {rdwrTerminalAliasEntry 3}


rdwrTerminalAliasStatus OBJECT-TYPE
   SYNTAX RowStatus
   ACCESS read-write
   STATUS mandatory
   DESCRIPTION
   "Entry status"
   ::=  { rdwrTerminalAliasEntry 4}

rdwrTerminalPrompt OBJECT-TYPE
  SYNTAX  DisplayString (SIZE(0..32))
  ACCESS  read-write
  STATUS  mandatory
  DESCRIPTION
  "The system prompt of the device."
  ::= {rdwrTerminalParams 2}

rdwrMasterInterfaceGroupingPortsTable OBJECT-TYPE
    SYNTAX SEQUENCE OF RdwrMasterInterfaceGroupingPortsEntry
    ACCESS not-accessible
    STATUS mandatory
    DESCRIPTION
      "The table contains all the physical ports. Each port can be set to
       included/excluded from the master interface grouping."
    ::= { rsServerDispatcher 111}

rdwrMasterInterfaceGroupingPortsEntry OBJECT-TYPE
  SYNTAX RdwrMasterInterfaceGroupingPortsEntry
  ACCESS not-accessible
  STATUS mandatory
  DESCRIPTION
    "Row definition for the table."
  INDEX { rdwrMasterInterfaceGroupingPortNumber }
  ::= { rdwrMasterInterfaceGroupingPortsTable 1 }

RdwrMasterInterfaceGroupingPortsEntry ::= SEQUENCE {
  rdwrMasterInterfaceGroupingPortNumber INTEGER,
  rdwrMasterInterfaceGroupingPortState INTEGER
}

rdwrMasterInterfaceGroupingPortNumber OBJECT-TYPE
  SYNTAX INTEGER
  ACCESS read-only
  STATUS mandatory
  DESCRIPTION
    "Physical port number."
  ::= { rdwrMasterInterfaceGroupingPortsEntry 1 }

rdwrMasterInterfaceGroupingPortState OBJECT-TYPE
  SYNTAX INTEGER {
    included(1),
    excluded(2)
  }
  ACCESS read-write
  STATUS mandatory
  DESCRIPTION
    "included- the port effects the master interface grouping. 
    excluded- the port does not effects the master interface grouping."
  DEFVAL { 1 }
  ::= { rdwrMasterInterfaceGroupingPortsEntry 2 }


rdwr5SecAvgResourceUtilization OBJECT-TYPE
    SYNTAX  INTEGER  (0..100)
    ACCESS  read-only
    STATUS  mandatory
    DESCRIPTION
      "Last 5 sec. Engine Average Utilization"
    ::=  { rsServerDispatcher 112 }

rdwr60SecAvgResourceUtilization OBJECT-TYPE
    SYNTAX  INTEGER  (0..100)
    ACCESS  read-only
    STATUS  mandatory
    DESCRIPTION
      "Last 60 sec. Engine Average Utilization"
    ::=  { rsServerDispatcher 113 }


rdwrArpWithInterfaceGroup OBJECT-TYPE
    SYNTAX INTEGER {
        send(1),
        avoid(2)
    }
    ACCESS  read-write
    STATUS  mandatory
    DESCRIPTION
        "indicates if the device should send arp request (broadcast) when redundancy enable (interface grouping enable) and the (main) device is down (interface/s go down)"
    DEFVAL { send }
    ::=  { rsServerDispatcher 114}

rdwrDBind OBJECT IDENTIFIER ::= { rsServerDispatcher 115 }

rdwrDP    OBJECT IDENTIFIER ::= { rsServerDispatcher 116 }

rsDOS     OBJECT IDENTIFIER ::= { rsServerDispatcher 117 }

rsSTATEFUL OBJECT IDENTIFIER ::= { rsServerDispatcher 118 }

rsAPM OBJECT IDENTIFIER ::= { rsServerDispatcher 119 }


rdwrIpsec OBJECT IDENTIFIER ::= { rsServerDispatcher 120 }

rdwrIpsecIke OBJECT IDENTIFIER ::= { rdwrIpsec 1 }

rdwrIkeTable  OBJECT-TYPE
   SYNTAX  SEQUENCE OF RdwrIkeEntry
   ACCESS  not-accessible
   STATUS  mandatory
   DESCRIPTION
         "A table holding information about ike connections"
   ::= { rdwrIpsecIke 1 }


rdwrIkeEntry OBJECT-TYPE
   SYNTAX  RdwrIkeEntry
   ACCESS  not-accessible
   STATUS  mandatory
   DESCRIPTION
         "An entry in the ike table"
   INDEX  {rdwrIkeName}
   ::= { rdwrIkeTable 1 }

RdwrIkeEntry   ::= SEQUENCE {
     rdwrIkeName                           DisplayString,
     rdwrIkePhase1EncryptionAlg            INTEGER,
     rdwrIkePhase1HashAlg                  INTEGER,
     rdwrIkePhase1DhKeyGroup               INTEGER,
     rdwrIkePhase1LifeTime                 INTEGER,
     rdwrIkePhase1Psk                      DisplayString,
     rdwrIkePhase2Protocol                 INTEGER,
     rdwrIkePhase2EncryptionAlg            INTEGER,
     rdwrIkePhase2HashAlg                  INTEGER,
     rdwrIkePfsKeyGroup                    INTEGER,
     rdwrIkeSaLifeTime                     INTEGER,
     rdwrIkeIpCompression                  INTEGER,
	 rdwrIkeManualKeyMode				   INTEGER,
	 rdwrIkeEncrypKey	                   DisplayString,
	 rdwrIkeAuthntKey	                   DisplayString,
	 rdwrIkeInSpi		                   INTEGER,
	 rdwrIkeOutSpi		                   INTEGER,
     rdwrIkeDPDCheckInterval    	   INTEGER,
     rdwrIkeStatus                         RowStatus
   }

rdwrIkeName OBJECT-TYPE
   SYNTAX  DisplayString (SIZE(1..128))
   ACCESS  read-only
   STATUS  mandatory
   DESCRIPTION
         "The name of this entry in the ike table."
   ::= { rdwrIkeEntry 1 }

rdwrIkePhase1EncryptionAlg  OBJECT-TYPE
    SYNTAX INTEGER {
           des(1),
           idea(2),
           blowfish(3),
           rc5(4),
           des3(5),
           cast(6),
           aes(7)           
    }
    ACCESS  read-write
    STATUS  mandatory
    DESCRIPTION
        "The encryption algorithm used in phase1 negotiation"
    DEFVAL { 5 }
    ::=  {rdwrIkeEntry 2}

rdwrIkePhase1HashAlg  OBJECT-TYPE
    SYNTAX INTEGER {
           md5(1),
           sha(2)
    }
    ACCESS  read-write
    STATUS  mandatory
    DESCRIPTION
        "The hash algorithm used in phase1 negotiation"
    DEFVAL { 1 }
    ::=  {rdwrIkeEntry 3}

rdwrIkePhase1DhKeyGroup  OBJECT-TYPE
    SYNTAX INTEGER {
           modp768(1),
           modp1024(2),
           ec2n155(3),
           ec2n185(4),
           modp1536(5)
    }
    ACCESS  read-write
    STATUS  mandatory
    DESCRIPTION
        "The Diffie Hellman Group used in phase1 negotiations"
    DEFVAL { 1 }
    ::=  {rdwrIkeEntry 4}

rdwrIkePhase1LifeTime  OBJECT-TYPE
    SYNTAX INTEGER 
    ACCESS  read-write
    STATUS  mandatory
    DESCRIPTION
        "The lifetime in seconds"
    DEFVAL { 28800 }
    ::=  {rdwrIkeEntry 5}

rdwrIkePhase1Psk OBJECT-TYPE
   SYNTAX  DisplayString (SIZE(0..128))
   ACCESS  read-write
   STATUS  mandatory
   DESCRIPTION
         "The Pre Shared Key"
   ::= { rdwrIkeEntry 6 }


rdwrIkePhase2Protocol  OBJECT-TYPE
    SYNTAX INTEGER {
           ah(2),
           esp(3)
    }
    ACCESS  read-write
    STATUS  mandatory
    DESCRIPTION
        "The Encapsulation protocol"
    DEFVAL { 3 }
    ::=  {rdwrIkeEntry 7}


rdwrIkePhase2EncryptionAlg  OBJECT-TYPE
    SYNTAX INTEGER {
           des(1),
           idea(2),
           blowfish(3),
           rc5(4),
           des3(5),
           cast(6),
           aes(7)           
    }
    ACCESS  read-write
    STATUS  mandatory
    DESCRIPTION
        "The encryption algorithm to be used in phase2 negotiation"
    DEFVAL { 5 }
    ::=  {rdwrIkeEntry 8}

rdwrIkePhase2HashAlg  OBJECT-TYPE
    SYNTAX INTEGER {
           md5(1),
           sha(2),
	   null(3)
    }
    ACCESS  read-write
    STATUS  mandatory
    DESCRIPTION
        "The hash algorithm to be used in phase2 negotiation"
    DEFVAL { 1 }
    ::=  {rdwrIkeEntry 9}


rdwrIkePfsKeyGroup  OBJECT-TYPE
    SYNTAX INTEGER {
           modp768(1),
           modp1024(2),
           ec2n155(3),
           ec2n185(4),
           modp1536(5),
           off(65535)
    }
    ACCESS  read-write
    STATUS  mandatory
    DESCRIPTION
        "The Diffie Hellman Group to be used in phase2 negotiations"
    DEFVAL { 1 }
    ::=  {rdwrIkeEntry 10}

rdwrIkeSaLifeTime  OBJECT-TYPE
    SYNTAX INTEGER 
    ACCESS  read-write
    STATUS  mandatory
    DESCRIPTION
        "The lifetime in seconds"
    DEFVAL { 28800 }
    ::=  {rdwrIkeEntry 11}


rdwrIkeIpCompression  OBJECT-TYPE
   SYNTAX  INTEGER {
	   enabled(1),
	   disabled(2)
   }
   ACCESS  read-write
   STATUS  mandatory
   DESCRIPTION
         "Indicate whether to use ip compression."
   DEFVAL { 2 }
   ::= { rdwrIkeEntry 12}

rdwrIkeManualKeyMode  OBJECT-TYPE
    SYNTAX INTEGER {
           ike(1),
           manual(2)
    }
    ACCESS  read-write
    STATUS  mandatory
    DESCRIPTION
        "indicate the ipSec key mode: IKE (automatic) or manual"
    DEFVAL { 1 }
    ::=  {rdwrIkeEntry 13}


rdwrIkeEncrypKey OBJECT-TYPE
   SYNTAX  DisplayString (SIZE(0..48))
   ACCESS  read-write
   STATUS  mandatory
   DESCRIPTION
         "the encryption key in case of manual mode"
   ::= { rdwrIkeEntry 14 }

rdwrIkeAuthntKey OBJECT-TYPE
   SYNTAX  DisplayString (SIZE(0..40))
   ACCESS  read-write
   STATUS  mandatory
   DESCRIPTION
         "the authentication key in case of manual mode"
   ::= { rdwrIkeEntry 15 }
	 
rdwrIkeInSpi OBJECT-TYPE
    SYNTAX  INTEGER  
    ACCESS  read-write
    STATUS  mandatory
    DESCRIPTION
      "the inbound SPI value for manual key mode"
    ::=  { rdwrIkeEntry 16 }

rdwrIkeOutSpi OBJECT-TYPE
    SYNTAX  INTEGER  
    ACCESS  read-write
    STATUS  mandatory
    DESCRIPTION
      "the outbound SPI value for manual key mode"
    ::=  { rdwrIkeEntry 17 }

rdwrIkeDPDCheckInterval OBJECT-TYPE
    SYNTAX  INTEGER  
    ACCESS  read-write
    STATUS  mandatory
    DESCRIPTION
      "interval for the keep alive checks"
    ::=  { rdwrIkeEntry 18 }

rdwrIkeStatus OBJECT-TYPE
   SYNTAX  RowStatus
   ACCESS  read-write
   STATUS  mandatory
   DESCRIPTION
         "Operation to be performed on a specific ike table entry."
   ::= { rdwrIkeEntry 19 }


rdwrDedicatedManagementPort OBJECT-TYPE
   SYNTAX  INTEGER
   ACCESS  read-write
   STATUS  mandatory
   DESCRIPTION
        "A dedicated port for management - 0 is Not Assigned"
   DEFVAL { 0 }
   ::= { rsServerDispatcher 121 }

rsGeneric OBJECT IDENTIFIER ::= { rsServerDispatcher 122 }

rdwrClientsTableStatistics OBJECT IDENTIFIER ::= { rsServerDispatcher 123 }

rdwrClientsTableNumEntries OBJECT-TYPE
  SYNTAX INTEGER
  ACCESS  read-only
  STATUS  mandatory
  DESCRIPTION
  "Number of entries in the clients table."
  ::= {rdwrClientsTableStatistics 1}

rdwrClientsTableNumEntries5SecAvg OBJECT-TYPE
  SYNTAX INTEGER
  ACCESS  read-only
  STATUS  mandatory
  DESCRIPTION
  "Average number of entries in the clients table in the last 5 seconds."
  ::= {rdwrClientsTableStatistics 2}

rdwrClientsTableNumEntries60SecAvg OBJECT-TYPE
  SYNTAX INTEGER
  ACCESS  read-only
  STATUS  mandatory
  DESCRIPTION
  "Average number of entries in the clients table in the last 60 seconds."
  ::= {rdwrClientsTableStatistics 3}

rdwrPortsTagTable OBJECT-TYPE
    SYNTAX SEQUENCE OF RdwrPortsTagEntry
    ACCESS not-accessible
    STATUS mandatory
    DESCRIPTION
      "The table contains all the physical ports. Each entry can force port
       tag for incoming and outgoing traffic."
    ::= { rsServerDispatcher 125 }

rdwrPortsTagEntry OBJECT-TYPE
  SYNTAX RdwrPortsTagEntry
  ACCESS not-accessible
  STATUS mandatory
  DESCRIPTION
    "Row definition for the table."
  INDEX { rdwrPortsTagPortNumber }
  ::= { rdwrPortsTagTable 1 }

RdwrPortsTagEntry ::= SEQUENCE {
  rdwrPortsTagPortNumber INTEGER,
  rdwrPortsTagPortInTag  INTEGER,
  rdwrPortsTagPortOutTag INTEGER
}

rdwrPortsTagPortNumber OBJECT-TYPE
  SYNTAX INTEGER
  ACCESS read-only
  STATUS mandatory
  DESCRIPTION
    "Physical port number."
  ::= { rdwrPortsTagEntry 1 }
  
rdwrPortsTagPortInTag OBJECT-TYPE
  SYNTAX INTEGER
  ACCESS read-write
  STATUS mandatory
  DESCRIPTION
    "The incoming physical port vlan Tag value that represent this port."     
  ::= { rdwrPortsTagEntry 2 }
  
rdwrPortsTagPortOutTag OBJECT-TYPE
  SYNTAX INTEGER
  ACCESS read-write
  STATUS mandatory
  DESCRIPTION
    "The outgoing physical port vlan Tag value that represent this port."     
  ::= { rdwrPortsTagEntry 3 }

rdwrDayLightSaving OBJECT IDENTIFIER ::= { rsServerDispatcher 129 }

rdwrDayLightSavingBegins  OBJECT-TYPE
    SYNTAX  DisplayString (SIZE(0..255))
    ACCESS  read-write
    STATUS  mandatory
    DESCRIPTION
      "The day light saving beginning, this can be either a specific 
      date - format D|DD/Mon/HH, or a recurring date - format R|x/Day/Mon/HH"
	::=  { rdwrDayLightSaving 1 }

rdwrDayLightSavingEnds  OBJECT-TYPE
    SYNTAX  DisplayString (SIZE(0..255))
    ACCESS  read-write
    STATUS  mandatory
    DESCRIPTION
      "The day light saving ending, this can be either a specific 
      date - format D|DD/Mon/HH, or a recurring date - format R|x/Day/Mon/HH"
	::=  { rdwrDayLightSaving 2 }

rdwrDayLightSavingTimeDesignations  OBJECT-TYPE
    SYNTAX INTEGER {
      standardTime(1),
      summerTime(2)
    }
    ACCESS  read-only
    STATUS  mandatory
    DESCRIPTION
      "The day light saving actual designation."
 	::=  { rdwrDayLightSaving 3 }

rdwrDayLightSavingAdminStatus  OBJECT-TYPE
    SYNTAX INTEGER {
      enabled(1),
      disabled(2)
    }
    ACCESS  read-write
    STATUS  mandatory
    DESCRIPTION
      "The day light saving administrator status."
    DEFVAL { 2 }
 	::=  { rdwrDayLightSaving 4 }

rdwrDayLightSavingBeginDate  OBJECT-TYPE
    SYNTAX  DisplayString (SIZE(0..255))
    ACCESS  read-only
    STATUS  mandatory
    DESCRIPTION
      "Returns the date of the beginning of the daylight saving"
        ::=  { rdwrDayLightSaving 5 }

rdwrDayLightSavingEndDate  OBJECT-TYPE
    SYNTAX  DisplayString (SIZE(0..255))
    ACCESS  read-only
    STATUS  mandatory
    DESCRIPTION
      "Returns the date of the end of the daylight saving"
        ::=  { rdwrDayLightSaving 6 }

rdwrDayLightSavingDelta  OBJECT-TYPE
    SYNTAX  INTEGER
    ACCESS  read-write
    STATUS  mandatory
    DESCRIPTION
      "Indicates the daylight savings delta. When the daylight savings starts 
      the hour will be moved back delta hours. When it is started it will be 
      moved forward delta hours. The default is one hour."
--  DEFVAL {1}
        ::=  { rdwrDayLightSaving 7 }


rdwrCommonClientTable OBJECT IDENTIFIER ::= { rsServerDispatcher 130 }

rdwrClientsViewTable  OBJECT-TYPE
   SYNTAX  SEQUENCE OF RdwrClientsViewEntry
   ACCESS  not-accessible
   STATUS  mandatory
   DESCRIPTION
         "A table holding information for defining client table views (filtering)"
   ::= { rdwrCommonClientTable 1 }


rdwrClientsViewEntry OBJECT-TYPE
   SYNTAX  RdwrClientsViewEntry
   ACCESS  not-accessible
   STATUS  mandatory
   DESCRIPTION
         "An entry in the client views table"
   INDEX  {rdwrClientsViewIndex}
   ::= { rdwrClientsViewTable 1 }

RdwrClientsViewEntry   ::= SEQUENCE {
     rdwrClientsViewIndex             INTEGER,
     rdwrClientsViewSrcAddrFrom       IpAddress,
     rdwrClientsViewSrcAddrTo         IpAddress,
     rdwrClientsViewDstAddrFrom       IpAddress,
     rdwrClientsViewDstAddrTo         IpAddress,
     rdwrClientsViewSrcPortFrom       INTEGER,
     rdwrClientsViewSrcPortTo         INTEGER,
     rdwrClientsViewDstPortFrom       INTEGER,
     rdwrClientsViewDstPortTo         INTEGER,
     rdwrClientsViewFarmAddr          IpAddress,
     rdwrClientsViewServerAddr        IpAddress,
     rdwrClientsViewClientType        DisplayString,
     rdwrClientsViewAdminStatus       INTEGER,
     rdwrClientsViewStatus            RowStatus,
     rdwrClientsViewAction            INTEGER,
     rdwrClientsViewActionFeedback    DisplayString,
     rdwrClientsViewVlanTag           INTEGER,
     rdwrClientsViewFarmName          DisplayString
   }

rdwrClientsViewIndex OBJECT-TYPE
   SYNTAX  INTEGER
   ACCESS  read-only
   STATUS  mandatory
   DESCRIPTION
         "The index of this entry in the views table."
   ::= { rdwrClientsViewEntry 1 }

rdwrClientsViewSrcAddrFrom  OBJECT-TYPE
    SYNTAX IpAddress 
    ACCESS  read-write
    STATUS  mandatory
    DESCRIPTION
        "The IP Address of the low boundary of the source interval."
    ::=  { rdwrClientsViewEntry 2 }

rdwrClientsViewSrcAddrTo  OBJECT-TYPE
    SYNTAX IpAddress 
    ACCESS  read-write
    STATUS  mandatory
    DESCRIPTION
        "The IP Address of the high boundary of the source interval."
    ::=  { rdwrClientsViewEntry 3 }
    
    
rdwrClientsViewDstAddrFrom  OBJECT-TYPE
    SYNTAX IpAddress 
    ACCESS  read-write
    STATUS  mandatory
    DESCRIPTION
        "The IP Address of the low boundary of the requested interval."
    ::=  { rdwrClientsViewEntry 4 }

rdwrClientsViewDstAddrTo  OBJECT-TYPE
    SYNTAX IpAddress 
    ACCESS  read-write
    STATUS  mandatory
    DESCRIPTION
        "The IP Address of the high boundary of the requested interval."
    ::=  { rdwrClientsViewEntry 5 }

rdwrClientsViewSrcPortFrom  OBJECT-TYPE
    SYNTAX INTEGER (0..65535)
    ACCESS  read-write
    STATUS  mandatory
    DESCRIPTION
        "The TCP/UDP port of the low boundary of the source interval."
    ::=  { rdwrClientsViewEntry 6 }

rdwrClientsViewSrcPortTo  OBJECT-TYPE
    SYNTAX INTEGER (0..65535)
    ACCESS  read-write
    STATUS  mandatory
    DESCRIPTION
        "The TCP/UDP port of the high boundary of the source interval."
    ::=  { rdwrClientsViewEntry 7 }

rdwrClientsViewDstPortFrom  OBJECT-TYPE
    SYNTAX INTEGER (0..65535)
    ACCESS  read-write
    STATUS  mandatory
    DESCRIPTION
        "The TCP/UDP port of the low boundary of the requested interval."
    ::=  { rdwrClientsViewEntry 8 }

rdwrClientsViewDstPortTo  OBJECT-TYPE
    SYNTAX INTEGER (0..65535)
    ACCESS  read-write
    STATUS  mandatory
    DESCRIPTION
        "The TCP/UDP port of the high boundary of the requested interval."
    ::=  { rdwrClientsViewEntry 9 }

rdwrClientsViewFarmAddr  OBJECT-TYPE
    SYNTAX IpAddress 
    ACCESS  read-write
    STATUS  mandatory
    DESCRIPTION
        "The client IP Address of the farm."
    ::=  { rdwrClientsViewEntry 10 }

rdwrClientsViewServerAddr  OBJECT-TYPE
    SYNTAX IpAddress 
    ACCESS  read-write
    STATUS  mandatory
    DESCRIPTION
        "The client IP Address of the server."
    ::=  { rdwrClientsViewEntry 11 }

rdwrClientsViewClientType OBJECT-TYPE
   SYNTAX  DisplayString (SIZE(0..20))
   ACCESS  read-write
   STATUS  mandatory
   DESCRIPTION
         "The client type"
   ::= { rdwrClientsViewEntry 12 }

rdwrClientsViewAdminStatus  OBJECT-TYPE
    SYNTAX INTEGER {
           enabled(1),
           disabled(2)
    }
    ACCESS  read-write
    STATUS  mandatory
    DESCRIPTION
        "Administrative status of the view entry
	 enabled - activates the view.
         disabled - inactive the view."
    DEFVAL { 1 }
    ::=  { rdwrClientsViewEntry 13 }

rdwrClientsViewStatus  OBJECT-TYPE
   SYNTAX  RowStatus
   ACCESS  read-write
   STATUS  mandatory
   DESCRIPTION
         "It is used to create and delete a filter"
   ::= { rdwrClientsViewEntry 14 }

rdwrClientsViewAction OBJECT-TYPE
   SYNTAX INTEGER {
        noAction(1),
        deleteMatching(2),
        countMatching(3)
   }
   ACCESS  read-write
   STATUS  mandatory
   DESCRIPTION
         "The type of action to be performed on entries matching this filter."
   DEFVAL { 1 }
   ::= { rdwrClientsViewEntry 15 }

rdwrClientsViewActionFeedback OBJECT-TYPE
   SYNTAX  DisplayString (SIZE(0..240))
   ACCESS  read-only
   STATUS  mandatory
   DESCRIPTION
         "Message containing feedback for the action taken."
   ::= { rdwrClientsViewEntry 16 }

rdwrClientsViewVlanTag OBJECT-TYPE
   SYNTAX INTEGER (0..4095)
   ACCESS  read-write
   STATUS  mandatory
   DESCRIPTION
         "802.1q VLAN tag associated with the client entry. 0 - no tag."
   DEFVAL { 0 }
   ::= { rdwrClientsViewEntry 17 }

rdwrClientsViewFarmName  OBJECT-TYPE
    SYNTAX  DisplayString (SIZE (0..50))
    ACCESS  read-write
    STATUS  mandatory
    DESCRIPTION
        "The client's farm name."
    ::=  { rdwrClientsViewEntry 18 }


   
rdwrClientsTable  OBJECT-TYPE
   SYNTAX  SEQUENCE OF RdwrClientsEntry
   ACCESS  not-accessible
   STATUS  mandatory
   DESCRIPTION
         "A table holding the device filtered client table"
   ::= { rdwrCommonClientTable 2 }

rdwrClientsEntry OBJECT-TYPE
   SYNTAX  RdwrClientsEntry
   ACCESS  not-accessible
   STATUS  mandatory
   DESCRIPTION
         "An entry in the client table"
   INDEX  {rdwrClientsIndex}
   ::= { rdwrClientsTable 1 }

RdwrClientsEntry   ::= SEQUENCE {
     rdwrClientsIndex                 INTEGER,
     rdwrClientsSourceAddr            IpAddress,
     rdwrClientsSourcePort            INTEGER,
     rdwrClientsRequestedAddr         IpAddress,
     rdwrClientsRequestedPort         INTEGER,     
     rdwrClientsFarmAddr              IpAddress,
     rdwrClientsServerAddr            IpAddress,
     rdwrClientsServerPort            INTEGER,
     rdwrClientsAttachedTime          INTEGER,
     rdwrClientsNATaddr               IpAddress,
     rdwrClientsNATPort               INTEGER,
     rdwrClientsTimeToLive            INTEGER,
     rdwrClientsClientType            DisplayString,
     rdwrClientsClientMode            DisplayString,
     rdwrClientsUserData1             DisplayString,
     rdwrClientsUserData2             DisplayString,
     rdwrClientsStatus                RowStatus
   }

rdwrClientsIndex OBJECT-TYPE
   SYNTAX  INTEGER
   ACCESS  read-only
   STATUS  mandatory
   DESCRIPTION
         "The index of this entry in the table."
   ::= { rdwrClientsEntry 1 }

rdwrClientsSourceAddr  OBJECT-TYPE
    SYNTAX IpAddress 
    ACCESS  read-write
    STATUS  mandatory
    DESCRIPTION
        "The client source address."
    ::=  { rdwrClientsEntry 2 }


rdwrClientsSourcePort OBJECT-TYPE
   SYNTAX  INTEGER
   ACCESS  read-write
   STATUS  mandatory
   DESCRIPTION
         "The clinet source port."
   ::= { rdwrClientsEntry 3 }

rdwrClientsRequestedAddr  OBJECT-TYPE
    SYNTAX IpAddress 
    ACCESS  read-write
    STATUS  mandatory
    DESCRIPTION
        "The client requested address."
    ::=  {rdwrClientsEntry 4 }

rdwrClientsRequestedPort  OBJECT-TYPE
    SYNTAX INTEGER 
    ACCESS  read-write
    STATUS  mandatory
    DESCRIPTION
        "The client requested TCP/UDP Port."
    ::=  {rdwrClientsEntry 5 }

rdwrClientsFarmAddr  OBJECT-TYPE
    SYNTAX IpAddress 
    ACCESS  read-only
    STATUS  mandatory
    DESCRIPTION
        "IP Address of the farm the client trough which the client connected."
    ::=  {rdwrClientsEntry 6 }

rdwrClientsServerAddr  OBJECT-TYPE
    SYNTAX IpAddress 
    ACCESS  read-only
    STATUS  mandatory
    DESCRIPTION
        "IP Address of server currently serving this client."
    ::=  {rdwrClientsEntry 7 }

rdwrClientsServerPort  OBJECT-TYPE
    SYNTAX INTEGER 
    ACCESS  read-only
    STATUS  mandatory
    DESCRIPTION
        "TCP/UDP Port of server currently serving this client."
    ::=  {rdwrClientsEntry 8 }

rdwrClientsAttachedTime  OBJECT-TYPE
    SYNTAX INTEGER 
    ACCESS  read-only
    STATUS  mandatory
    DESCRIPTION
        "Indicates when the client was attached.
         Measured in seconds since device re-initialization."
    ::=  {rdwrClientsEntry 9 }

rdwrClientsNATaddr  OBJECT-TYPE
    SYNTAX IpAddress 
    ACCESS  read-only
    STATUS  mandatory
    DESCRIPTION
        "NAT IP Address of the client."
    ::=  {rdwrClientsEntry 10 }

rdwrClientsNATPort  OBJECT-TYPE
    SYNTAX INTEGER 
    ACCESS  read-only
    STATUS  mandatory
    DESCRIPTION
        "NAT TCP/UDP port of the client."
    ::=  {rdwrClientsEntry 11 }

rdwrClientsTimeToLive  OBJECT-TYPE
    SYNTAX INTEGER 
    ACCESS  read-only
    STATUS  mandatory
    DESCRIPTION
        "This variable measures the client time to live in seconds."
    ::=  {rdwrClientsEntry 12 }
    
rdwrClientsClientType OBJECT-TYPE
   SYNTAX  DisplayString (SIZE(1..20))
   ACCESS  read-only
   STATUS  mandatory
   DESCRIPTION
         "This variable indicates the administrative type of this entry."
   ::= { rdwrClientsEntry 13 }
    
rdwrClientsClientMode OBJECT-TYPE
   SYNTAX  DisplayString (SIZE(1..20))
   ACCESS  read-only
   STATUS  mandatory
   DESCRIPTION
         "This variable indicates how a single client's sessions are  
         handled in the client table."
   ::= { rdwrClientsEntry 14 }

rdwrClientsUserData1 OBJECT-TYPE
   SYNTAX  DisplayString (SIZE(0..240))
   ACCESS  read-only
   STATUS  mandatory
   DESCRIPTION
         "This variable holds miscellaneous client information."
   ::= { rdwrClientsEntry 15 }

rdwrClientsUserData2 OBJECT-TYPE
   SYNTAX  DisplayString (SIZE(0..240))
   ACCESS  read-only
   STATUS  mandatory
   DESCRIPTION
         "This variable holds miscellaneous client information."
   ::= { rdwrClientsEntry 16 }

rdwrClientsStatus  OBJECT-TYPE
   SYNTAX  RowStatus
   ACCESS  read-write
   STATUS  mandatory
   DESCRIPTION
         "It is used to delete an entry"
   ::= { rdwrClientsEntry 17 }

rdwrClientsTypeTable  OBJECT-TYPE
   SYNTAX  SEQUENCE OF RdwrClientsTypeEntry
   ACCESS  not-accessible
   STATUS  mandatory
   DESCRIPTION
         "A table holding the client types"
   ::= { rdwrCommonClientTable 3 }

rdwrClientsTypeEntry OBJECT-TYPE
   SYNTAX  RdwrClientsTypeEntry
   ACCESS  not-accessible
   STATUS  mandatory
   DESCRIPTION
         "An entry in the client types table"
   INDEX  {rdwrClientsType}
   ::= { rdwrClientsTypeTable 1 }

RdwrClientsTypeEntry   ::= SEQUENCE {
     rdwrClientsType                  DisplayString
   }

rdwrClientsType OBJECT-TYPE
   SYNTAX  DisplayString (SIZE(1..20))
   ACCESS  read-only
   STATUS  mandatory
   DESCRIPTION
         "The clinet type of this entry."
   ::= { rdwrClientsTypeEntry 1 }


rdwrVersionIdentifierTable OBJECT-TYPE
    SYNTAX SEQUENCE OF RdwrVersionIdentifierEntry
    ACCESS not-accessible
    STATUS mandatory
    DESCRIPTION
      "Row holding version verification information."
    ::= { rsServerDispatcher 131 }

rdwrVersionIdentifierEntry OBJECT-TYPE
  SYNTAX RdwrVersionIdentifierEntry
  ACCESS not-accessible
  STATUS mandatory
  DESCRIPTION
    "Row definition for the table."
  INDEX { rdwrVersionIdentifierIdx }
  ::= { rdwrVersionIdentifierTable 1 }

RdwrVersionIdentifierEntry ::= SEQUENCE {
  rdwrVersionIdentifierIdx     INTEGER,
  rdwrVersionIdentifierBase    INTEGER,
  rdwrVersionIdentifierVal     DisplayString
}

rdwrVersionIdentifierIdx OBJECT-TYPE
  SYNTAX INTEGER
  ACCESS read-only
  STATUS mandatory
  DESCRIPTION
    "Installed version index. Calculated by version major * 100 + version minor"
  ::= { rdwrVersionIdentifierEntry 1 }

rdwrVersionIdentifierBase OBJECT-TYPE
  SYNTAX INTEGER
  ACCESS read-write
  STATUS mandatory
  DESCRIPTION
    "Installed version base number. "
  ::= { rdwrVersionIdentifierEntry 2 }

rdwrVersionIdentifierVal OBJECT-TYPE
  SYNTAX DisplayString (SIZE(0..40))
  ACCESS read-write
  STATUS mandatory
  DESCRIPTION
    "Installed version identifier string. "
  ::= { rdwrVersionIdentifierEntry 3 }
rdwrVrrp  OBJECT IDENTIFIER ::= { rsServerDispatcher 132 }

rdwrVrrpAdmin OBJECT-TYPE
   SYNTAX  INTEGER {
        allDown(1),
        allUp(2),
        noChange(3)
  }
   ACCESS read-write
   STATUS  mandatory
   DESCRIPTION
         "Control all VRIDs admin status."
   ::= { rdwrVrrp  1 }

rdwrVrrpOperAdvertisementInterval OBJECT-TYPE
    SYNTAX  INTEGER
    ACCESS   read-write
    STATUS   mandatory
    DESCRIPTION
        "The time interval, in milliseconds, between sending
        advertisement messages for all VRIDs. Only the master router sends
        VRRP advertisements."
    DEFVAL       { 0 }
    ::= { rdwrVrrp  2 }

  -- *******************************************************************
   --  VRRP Associated IPv6 Address Table
   -- *******************************************************************
    rdwrVrrpAssoIpV6AddrTable OBJECT-TYPE SYNTAX       SEQUENCE OF RdwrVrrpAssoIpV6AddrEntry
        ACCESS   not-accessible
        STATUS       mandatory
        	DESCRIPTION "This MIB describes proparitery radware support for managing Virtual Router Redundancy Protocol (VRRP). Most of the support is given via the VRRP mib " ::= { rdwrVrrp 3 }
        	
    rdwrVrrpAssoIpV6AddrEntry 
    OBJECT-TYPE 
	SYNTAX       RdwrVrrpAssoIpV6AddrEntry
        ACCESS   not-accessible
        STATUS       mandatory
        DESCRIPTION "An entry in the table contains an IPv6 address that is
            associated with a virtual router. The number of rows for
            a given ifIndex and VrId will equal the number of IP addresses associated (e.g., backed up) by the virtual
            router (equivalent to 'vrrpOperIpV6AddrCount').
            Rows in the table cannot be modified unless the value
            of `vrrpOperAdminState' is `disabled' and the
            `vrrpOperState' has transitioned to `initialize'."
        INDEX    { rdwrVrrpAssoIpV6IfIndex, rdwrVrrpAssoIpV6VrId, rdwrVrrpAssoIpV6Addr } ::= { rdwrVrrpAssoIpV6AddrTable 1 }
    RdwrVrrpAssoIpV6AddrEntry ::= SEQUENCE {
    	 	rdwrVrrpAssoIpV6IfIndex             INTEGER,
            rdwrVrrpAssoIpV6VrId            VrId,
            rdwrVrrpAssoIpV6Addr            Ipv6Address,
            rdwrVrrpAssoIpV6AddrRowStatus         RowStatus }
	rdwrVrrpAssoIpV6IfIndex 
	OBJECT-TYPE SYNTAX       INTEGER
        ACCESS   read-only
        STATUS       mandatory
        DESCRIPTION "" ::= { rdwrVrrpAssoIpV6AddrEntry 1 }
	rdwrVrrpAssoIpV6VrId
	 OBJECT-TYPE SYNTAX       VrId
        ACCESS   read-only
        STATUS       mandatory
        DESCRIPTION "This object contains the Virtual Router Identifier (VRID)." ::= { rdwrVrrpAssoIpV6AddrEntry 2 }
    rdwrVrrpAssoIpV6Addr 
    OBJECT-TYPE SYNTAX       Ipv6Address
        ACCESS   read-only
        STATUS       mandatory
        DESCRIPTION "The assigned IPv6 addresses that a virtual router is
            responsible for backing up." ::= { rdwrVrrpAssoIpV6AddrEntry 3 }
    rdwrVrrpAssoIpV6AddrRowStatus 
    OBJECT-TYPE SYNTAX       RowStatus
    ACCESS   read-write
    STATUS   mandatory
        DESCRIPTION "The row status variable, used according to installation
            and removal conventions for conceptual rows. Setting this object to active(1) or createAndGo(4) results in the
            addition of an associated address for a virtual router. Destroying the entry or setting it to notInService(2)
            removes the associated address from the virtual router.
            The use of other values is implementation-dependent." ::= { rdwrVrrpAssoIpV6AddrEntry 4 }


rdwrVrrpPriorityTracking OBJECT-TYPE
    SYNTAX  INTEGER
    ACCESS   read-write
    STATUS   mandatory
    DESCRIPTION
        "VRRP priority tracking weight for interface link status, zero is disabled"
    DEFVAL       { 0 }
    ::= { rdwrVrrp  4 }

rdwrWSDCommon  OBJECT IDENTIFIER ::= { rsServerDispatcher 134 }

rdwrCdbParameters  OBJECT IDENTIFIER ::= { rsServerDispatcher 139 }

rdwrCdbTimeStamp OBJECT-TYPE
    SYNTAX INTEGER
    ACCESS  read-write
    STATUS  mandatory
    DESCRIPTION
        "The time stamp taken when the the CDB was last changed. Defined as the number of seconds since 1/1/1970."
    ::=  { rdwrCdbParameters 1 }

rdwrMirroring OBJECT IDENTIFIER ::= {rsServerDispatcher 140}

rdwrMirroringActiveThreshold OBJECT-TYPE
    SYNTAX  INTEGER
    ACCESS  read-write
    STATUS  mandatory
    DESCRIPTION
      "The maximum amount of entries to be sent from the active device."
--  DEFVAL  {20000}
    ::=  {rdwrMirroring 1}

rdwrMirroringActiveSleep OBJECT-TYPE
    SYNTAX  INTEGER
    ACCESS  read-write
    STATUS  mandatory
    DESCRIPTION
      "After sending the maximum amount of entries the active device 
      will sleep for the predefined period (in milliseconds)."
--  DEFVAL  {1}
    ::=  {rdwrMirroring 2}

rdwrMirroringActiveBackupThreshold OBJECT-TYPE
    SYNTAX  INTEGER
    ACCESS  read-write
    STATUS  mandatory
    DESCRIPTION
      "The maximum amount of entries to be sent from the active device to the 
      backup (after the backup device is up)."
--  DEFVAL  {2000}
    ::=  {rdwrMirroring 3}

rdwrMirroringActiveBackupSleep OBJECT-TYPE
    SYNTAX  INTEGER
    ACCESS  read-write
    STATUS  mandatory
    DESCRIPTION
      "After sending the maximum amount of entries the active device 
      will sleep for the predefined period (in milliseconds)."
--  DEFVAL  {200}
    ::=  {rdwrMirroring 4}

rdwrMirroringActiveBackupHoldtime OBJECT-TYPE
    SYNTAX  INTEGER
    ACCESS  read-write
    STATUS  mandatory
    DESCRIPTION
      "The active device will start to notify the main of all existing 
      entries after the configured time (in milliseconds)."
--  DEFVAL  {0}
    ::=  {rdwrMirroring 5}

rdwrMirroringActiveBackupUpdate  OBJECT-TYPE
    SYNTAX INTEGER {
        enable(1),
        disable(2)
    }
    ACCESS  read-write
    STATUS  mandatory
    DESCRIPTION
        "Enable/Disable the update of the backup device from the active"
--  DEFVAL {1}
    ::=  {rdwrMirroring 6}

rdwrTemperatureCPU1Get OBJECT-TYPE
   SYNTAX INTEGER
   ACCESS read-only
   STATUS mandatory
   DESCRIPTION
	   "get the temperature of CPU1"
   ::= {rsServerDispatcher 150}
   
rdwrTemperatureCPU2Get OBJECT-TYPE
   SYNTAX INTEGER
   ACCESS read-only
   STATUS mandatory
   DESCRIPTION
	   "get the temperature of CPU2"
   ::= {rsServerDispatcher 151}
	   
rdwrTemperatureWarningThresholdGet OBJECT-TYPE
   SYNTAX INTEGER
   ACCESS read-only
   STATUS mandatory
   DESCRIPTION
	   "get the temperature warning threshold"
   ::= {rsServerDispatcher 152}
   
rdwrTemperatureShutdownThresholdGet OBJECT-TYPE
   SYNTAX INTEGER
   ACCESS read-only
   STATUS mandatory
   DESCRIPTION
	   "get the temperature shutdown threshold"
   ::= {rsServerDispatcher 153}
      
rdwrTemperatureThresholdStatusCPU1Get OBJECT-TYPE
   SYNTAX INTEGER {
        normal(1),
        warning(2),
        critical(3)
    }
   ACCESS read-only
   STATUS mandatory
   DESCRIPTION
	   "get the threshold status of CPU1
	    warning - if the warning threshold exceeded
	    critical - if the shutdown threshold exceeded"
   ::= {rsServerDispatcher 154}
   
rdwrTemperatureThresholdStatusCPU2Get OBJECT-TYPE
   SYNTAX INTEGER {
        normal(1),
        warning(2),
        critical(3)
    }
   ACCESS read-only
   STATUS mandatory
   DESCRIPTION
	   "get the threshold status of CPU2
	    warning - if the warning threshold exceeded
	    critical - if the shutdown threshold exceeded"
   ::= {rsServerDispatcher 155}
   	
rdwrPrintToLogAndCli OBJECT-TYPE
   SYNTAX  DisplayString (SIZE(1..100))
   ACCESS  read-write
   STATUS  mandatory
   DESCRIPTION
       "print to system log file and to the CLI"
   ::= {rndMng 6}

rdwrClearTheLogFile OBJECT-TYPE
   SYNTAX INTEGER {
      clearSysLog(1)
	  }
   ACCESS  read-write
   STATUS  mandatory
   DESCRIPTION
       "Clears the system log file"
   ::= {rndMng 7}

rdwrAutoRowGenerationStatus  OBJECT-TYPE
    SYNTAX INTEGER {
        enable(1),
        disable(2)
    }
    ACCESS  read-write
    STATUS  mandatory
    DESCRIPTION
        "Enable/Disable automatic generation of rows by device"
--  DEFVAL {1}
    ::=  {rndMng 8}


rsSSLCertificate OBJECT IDENTIFIER ::= { rsServerDispatcher 148 }

rsSSLCertificateDefaultValues OBJECT IDENTIFIER ::= { rsSSLCertificate 1 }

rsSSLCertificateDefaultCommon OBJECT-TYPE
    SYNTAX DisplayString (SIZE (1..64))
    ACCESS  read-write
    STATUS  mandatory
    DESCRIPTION
       "default value for common field for certificate requests."
    ::= { rsSSLCertificateDefaultValues 1  }

rsSSLCertificateDefaultLocality OBJECT-TYPE
    SYNTAX DisplayString (SIZE (0..128))
    ACCESS  read-write
    STATUS  mandatory
    DESCRIPTION
       "default value for locality field for certificate requests."
    ::= { rsSSLCertificateDefaultValues 2  }

rsSSLCertificateDefaultStateOrProvince OBJECT-TYPE
    SYNTAX DisplayString (SIZE (0..128))
    ACCESS  read-write
    STATUS  mandatory
    DESCRIPTION
       "default value for state or province field for certificate requests."
    ::= { rsSSLCertificateDefaultValues 3  }

rsSSLCertificateDefaultOrganization OBJECT-TYPE
    SYNTAX DisplayString (SIZE (0..64))
    ACCESS  read-write
    STATUS  mandatory
    DESCRIPTION
       "default value for organization field for certificate requests."
    ::= { rsSSLCertificateDefaultValues 4  }

rsSSLCertificateDefaultOrganizationUnit OBJECT-TYPE
    SYNTAX DisplayString (SIZE (0..64))
    ACCESS  read-write
    STATUS  mandatory
    DESCRIPTION
       "default value for organization unit field for certificate requests."
    ::= { rsSSLCertificateDefaultValues 5  }

rsSSLCertificateDefaultCountryName OBJECT-TYPE
    SYNTAX DisplayString (SIZE (0..2))
    ACCESS  read-write
    STATUS  mandatory
    DESCRIPTION
       "default value for country name field for certificate requests."
    ::= { rsSSLCertificateDefaultValues 6  }

rsSSLCertificateDefaultEMail OBJECT-TYPE
    SYNTAX DisplayString (SIZE (0..128))
    ACCESS  read-write
    STATUS  mandatory
    DESCRIPTION
       "default value for e-mail field for certificate requests."
    ::= { rsSSLCertificateDefaultValues 7  }
 
rsSSLCertificateTable OBJECT-TYPE
   SYNTAX SEQUENCE OF RsSSLCertificateEntry
   ACCESS not-accessible
   STATUS mandatory
   DESCRIPTION
    "The table for certificate handling"
     ::= { rsSSLCertificate 2 }

rsSSLCertificateEntry  OBJECT-TYPE
   SYNTAX RsSSLCertificateEntry
   ACCESS not-accessible
   STATUS mandatory
   DESCRIPTION
       " The row definition for this table."
   INDEX { rsSSLCertificateName }
   ::= { rsSSLCertificateTable 1 }

RsSSLCertificateEntry ::= SEQUENCE {
   rsSSLCertificateName DisplayString,
   rsSSLCertificateEntryType INTEGER,
   rsSSLCertificateKeySize INTEGER,
   rsSSLCertificateKeyPassphrase DisplayString,
   rsSSLCertificateCommon DisplayString,
   rsSSLCertificateLocality DisplayString,
   rsSSLCertificateStateOrProvince DisplayString,
   rsSSLCertificateOrganization DisplayString,
   rsSSLCertificateOrganizationUnit DisplayString,
   rsSSLCertificateCountryName DisplayString,
   rsSSLCertificateEMail DisplayString,
   rsSSLCertificateExpiry DisplayString,
   rsSSLCertificateOCSPUrl DisplayString,
   rsSSLCertificateStatus RowStatus,
   rsSSLCertificateRequestedValidityPeriod INTEGER,
   rsSSLCertificateValidFromDate DisplayString,
   rsSSLCertificateIssuer DisplayString,
   rsSSLCertificateSerialNumber DisplayString,
   rsSSLCertificateHasAlternativeNames INTEGER
  }

rsSSLCertificateName OBJECT-TYPE
   SYNTAX DisplayString (SIZE(1..50))
   ACCESS read-only
   STATUS mandatory
   DESCRIPTION
    "The name of the certificate entry"
     ::= { rsSSLCertificateEntry 1 }


rsSSLCertificateEntryType OBJECT-TYPE
   SYNTAX INTEGER {
     key(1),
--   certificateSigningRequest(2),
     certificate(3),
     certificateChain(4)
--   clientCAcertificate(5),
--   rootTSLcertificate(6)
--   sshPublicKey(7)
      }  
   ACCESS read-write
   STATUS mandatory
   DESCRIPTION
    "entry type"
    DEFVAL { key }
     ::= { rsSSLCertificateEntry 2 }	 

rsSSLCertificateKeySize OBJECT-TYPE
   SYNTAX INTEGER {
     na(0),
     size1024(1024),
     size2048(2048),
     size4096(4096)
      } 
   ACCESS read-write
   STATUS mandatory
   DESCRIPTION
    "key data size in bits"
   DEFVAL { size1024 }
     ::= { rsSSLCertificateEntry 3 }

rsSSLCertificateKeyPassphrase OBJECT-TYPE
   SYNTAX DisplayString (SIZE (0..64))
   ACCESS read-write
   STATUS mandatory
   DESCRIPTION
    "password phrase to scramble key"
     ::= { rsSSLCertificateEntry 4 }

rsSSLCertificateCommon OBJECT-TYPE
    SYNTAX DisplayString (SIZE (0..64))
    ACCESS  read-write
    STATUS  mandatory
    DESCRIPTION
       "value for common name field for certificate requests."
    ::= { rsSSLCertificateEntry 5  }

rsSSLCertificateLocality OBJECT-TYPE
    SYNTAX DisplayString (SIZE (0..128))
    ACCESS  read-write
    STATUS  mandatory
    DESCRIPTION
       "value for locality field for certificate requests."
    ::= { rsSSLCertificateEntry 6  }

rsSSLCertificateStateOrProvince OBJECT-TYPE
    SYNTAX DisplayString (SIZE (0..128))
    ACCESS  read-write
    STATUS  mandatory
    DESCRIPTION
       "value for state or province field for certificate requests."
    ::= { rsSSLCertificateEntry 7  }

rsSSLCertificateOrganization OBJECT-TYPE
    SYNTAX DisplayString (SIZE (0..64))
    ACCESS  read-write
    STATUS  mandatory
    DESCRIPTION
       "value for organization field for certificate requests."
    ::= { rsSSLCertificateEntry 8  }

rsSSLCertificateOrganizationUnit OBJECT-TYPE
    SYNTAX DisplayString (SIZE (0..64))
    ACCESS  read-write
    STATUS  mandatory
    DESCRIPTION
       " value for organization unit field for certificate requests."
    ::= { rsSSLCertificateEntry 9  }

rsSSLCertificateCountryName OBJECT-TYPE
    SYNTAX DisplayString (SIZE (0..2))
    ACCESS  read-write
    STATUS  mandatory
    DESCRIPTION
       "value for country name field for certificate requests."
    ::= { rsSSLCertificateEntry 10  }

rsSSLCertificateEMail OBJECT-TYPE
    SYNTAX DisplayString (SIZE (0..128))
    ACCESS  read-write
    STATUS  mandatory
    DESCRIPTION
       "value for e-mail field for certificate requests."
    ::= { rsSSLCertificateEntry 11  }

rsSSLCertificateExpiry OBJECT-TYPE
    SYNTAX DisplayString
    ACCESS  read-only
    STATUS  mandatory
    DESCRIPTION
       "expiry date according to certificate"
    ::= { rsSSLCertificateEntry 12  }

rsSSLCertificateOCSPUrl OBJECT-TYPE
    SYNTAX DisplayString
    ACCESS  read-write
    STATUS  mandatory
    DESCRIPTION
       "OCSP url for client CA status validation"
    ::= { rsSSLCertificateEntry 13  }

rsSSLCertificateStatus OBJECT-TYPE
    SYNTAX RowStatus
    ACCESS  read-write
    STATUS  mandatory
    DESCRIPTION
       "row status for certificate entry"
    ::= { rsSSLCertificateEntry 14  }
    
rsSSLCertificateRequestedValidityPeriod OBJECT-TYPE
    SYNTAX INTEGER
    ACCESS  read-write
    STATUS  mandatory
    DESCRIPTION
       "validity period in days requested for self signed certificate"
    ::= { rsSSLCertificateEntry 15  }    
    
rsSSLCertificateValidFromDate OBJECT-TYPE
    SYNTAX DisplayString
    ACCESS  read-only
    STATUS  mandatory
    DESCRIPTION
       "valid from date according to certificate"
    ::= { rsSSLCertificateEntry 16  } 

rsSSLCertificateIssuer OBJECT-TYPE
    SYNTAX DisplayString
    ACCESS  read-only
    STATUS  mandatory
    DESCRIPTION
       "certificate's issuer"
    ::= { rsSSLCertificateEntry 17  } 
    
rsSSLCertificateSerialNumber OBJECT-TYPE
    SYNTAX DisplayString
    ACCESS  read-only
    STATUS  mandatory
    DESCRIPTION
       "certificate's serial number"
    ::= { rsSSLCertificateEntry 18  } 

rsSSLCertificateHasAlternativeNames OBJECT-TYPE
    SYNTAX INTEGER {
      no(0),
      yes(1)
   }
    ACCESS  read-write
    STATUS  mandatory
    DESCRIPTION
       "does certificate has subject alternative names"
    DEFVAL  {no}
    ::=  { rsSSLCertificateEntry 19 }

rsSSLCertificateImportExport OBJECT IDENTIFIER ::= { rsSSLCertificate 3 }

rsSSLCertificateImportExportEntryName OBJECT-TYPE
    SYNTAX DisplayString (SIZE(0..50))
    ACCESS  read-write
    STATUS  mandatory
    DESCRIPTION
       "entry name to be addressed."
    ::= { rsSSLCertificateImportExport 1  }

rsSSLCertificateImportExportFileName OBJECT-TYPE
    SYNTAX DisplayString
    ACCESS  read-write
    STATUS  mandatory
    DESCRIPTION
       "file name path to export to or import from according to action."
    ::= { rsSSLCertificateImportExport 2  }
    
rsSSLCertificateImportExportPassphrase OBJECT-TYPE
    SYNTAX DisplayString (SIZE(0..64))
    ACCESS  read-write
    STATUS  mandatory
    DESCRIPTION
       "Passphrase to be used when importing a key."
    ::= { rsSSLCertificateImportExport 3 }    

rsSSLCertificateImportExportAction OBJECT-TYPE
    SYNTAX INTEGER {
     importKey(1),
     exportKey(2),
     importCertificate(3),
     exportCertificate(4),
     exportSigningRequest(5),
     importCertChain(6),
     exportCertChain(7),
     importCertClientCA(8),
     exportCertClientCA(9)
    }
    ACCESS  read-write
    STATUS  mandatory
    DESCRIPTION
       "Action to be performed on the entry name or file specified."
    ::= { rsSSLCertificateImportExport 4 }

rndNumberOfHD OBJECT-TYPE
   SYNTAX INTEGER
   ACCESS read-only
   STATUS mandatory
   DESCRIPTION
    "The number of hard drives."
    ::= { rsServerDispatcher 156 }

rndSSLCardName OBJECT-TYPE
   SYNTAX DisplayString (SIZE(0..255))
   ACCESS read-only
   STATUS mandatory
   DESCRIPTION
    "The name of the SSL card."
    ::= { rsServerDispatcher 157 }

rndCompCardName OBJECT-TYPE
   SYNTAX DisplayString (SIZE(0..255))
   ACCESS read-only
   STATUS mandatory
   DESCRIPTION
    "The name of the compression card."
    ::= { rsServerDispatcher 158 }


rdwrHardDisk OBJECT IDENTIFIER ::= { rsServerDispatcher 159 }

rdwrHardDiskLogging OBJECT IDENTIFIER ::= { rsServerDispatcher 160 }

rdwrConfigurationSync OBJECT IDENTIFIER ::= {rsServerDispatcher 161 }

rdwrDualPsuStatus OBJECT-TYPE
    SYNTAX  INTEGER {
       singlePwrSupplyOk(0),
       firstPwrSupplyFailed(1),
       secondPwrSupplyFailed(2),
       doublePwrSupplyOk(3),
       unknownPwrSupplyFailed(4)
     }
    ACCESS  read-only
    STATUS  mandatory
    DESCRIPTION
      "This variable represent the current status of the power supplies
       0 - Single PowerSupply OK
	   1 - First PowerSupply Failed
	   2 - Second PowerSupply Failed
	   3 - Double PowerSupply OK
	   4 - Unknown PowerSupply Failed"
   ::= { rsServerDispatcher 163  }

   
rdwrTotalIncomingTrafficPeak OBJECT-TYPE
    SYNTAX  INTEGER 
    ACCESS  read-only
    STATUS  mandatory
    DESCRIPTION
      "This variable represent the maximum incoming traffic in Mbps"
   ::= { rsServerDispatcher 166  }
   
rsManagePro OBJECT IDENTIFIER ::= { rsServerDispatcher 170 }

rsUserLockoutInterval  OBJECT-TYPE
   SYNTAX  INTEGER 
   ACCESS  read-write
   STATUS  mandatory
   DESCRIPTION
      "Lockout time interval for user account (min). Zero means no lockout."
   DEFVAL  { 10 }
    ::=  { rsServerDispatcher 171} 

rdwrManagmentPortsStatus OBJECT-TYPE
    SYNTAX  FeatureStatus
    ACCESS  read-write
    STATUS  mandatory
    DESCRIPTION
      "Is management port enabled on the device"
    DEFVAL {2}
   ::= { rsServerDispatcher 172 }

rdwrSyslogServerTable 	OBJECT-TYPE
	SYNTAX SEQUENCE OF RdwrSyslogServerEntry
	ACCESS  not-accessible
    STATUS  mandatory
    DESCRIPTION
        "A table of syslog servers."
    ::= {rsServerDispatcher 173}

rdwrSyslogServerEntry OBJECT-TYPE
	SYNTAX RdwrSyslogServerEntry
	ACCESS not-accessible
	STATUS mandatory
	DESCRIPTION
		"An entry of the syslog servers table"
	INDEX {rdwrSyslogServerAddress}
	::= {rdwrSyslogServerTable 1}

RdwrSyslogServerEntry ::= SEQUENCE {
	rdwrSyslogServerAddress			DisplayString,
	rdwrSyslogServerStatus			FeatureStatus,
	rdwrSyslogServerSrcPort			INTEGER,
	rdwrSyslogServerDstPort			INTEGER,
	rdwrSyslogServerFacility		INTEGER,
	rdwrSyslogServerProtocol		INTEGER,
	rdwrSyslogCACertificate				DisplayString,
	rdwrSyslogServerConnectionStatus	INTEGER,
	rdwrSyslogServerNumberOfLogsInBackLog	INTEGER,
	rdwrSyslogServerRowStatus			RowStatus,
	rdwrSyslogSecuritySending		FeatureStatus,
	rdwrSyslogHealthSending			FeatureStatus,
	rdwrSyslogUserAuditSending		FeatureStatus
}

rdwrSyslogServerAddress OBJECT-TYPE
   SYNTAX DisplayString
   ACCESS  read-write
   STATUS  mandatory
   DESCRIPTION
       "IP address of the syslog server."
   ::= {rdwrSyslogServerEntry 1}
   
rdwrSyslogServerStatus OBJECT-TYPE
   SYNTAX FeatureStatus
   ACCESS  read-write
   STATUS  mandatory
   DESCRIPTION
       "Server operational status."
   DEFVAL {enable}
   ::= {rdwrSyslogServerEntry 2}
   
rdwrSyslogServerSrcPort OBJECT-TYPE
   SYNTAX INTEGER
   ACCESS  read-write
   STATUS  mandatory
   DESCRIPTION
       "Server source port."
   DEFVAL { 514 }
   ::= {rdwrSyslogServerEntry 3}
   
rdwrSyslogServerDstPort OBJECT-TYPE
   SYNTAX INTEGER 
   ACCESS  read-write
   STATUS  mandatory
   DESCRIPTION
       "Server destination port."
   DEFVAL { 514 }
   ::= {rdwrSyslogServerEntry 4}
   
rdwrSyslogServerFacility OBJECT-TYPE
   SYNTAX INTEGER{
		kernelMsg(0),
        userLevelMsg(1),
        mailSystem(2),
        systemDaemons(3),
        authorization(4),
        syslogdMessages(5),
        linePrinter(6),
        networkNews(7),
        uucp(8),
        clockDaemon1(9),
        security(10),
        ftpDaemon(11),
        ntpSubsystem(12),
        logAudit(13),
        logAlert(14),
        clockDaemon2(15),
        local0(16),
        local1(17),
        local2(18),
        local3(19),
        local4(20),
        local5(21),
        local6(22),
        local7(23)
	}
   ACCESS  read-write
   STATUS  mandatory
    DESCRIPTION
      "The SYSLOG Priority value is calculated by multiplying the Facility
       number by 8 and then adding the numerical value of the Severity."
   DEFVAL { local6 }
  
   ::= {rdwrSyslogServerEntry 5}
 
 
rdwrSyslogServerProtocol OBJECT-TYPE
   SYNTAX INTEGER{
		udpProtocol(1),
        tcpProtocol(2),
        tlsProtocol(3)
	}
   ACCESS  read-write
   STATUS  mandatory
    DESCRIPTION
      "The SYSLOG Protocol."
   DEFVAL { udpProtocol }
  
   ::= {rdwrSyslogServerEntry 6}
   

 rdwrSyslogCACertificate OBJECT-TYPE
   SYNTAX DisplayString
   ACCESS  read-write
   STATUS  mandatory
   DESCRIPTION
       "CA Certificate of the syslog server."
   ::= {rdwrSyslogServerEntry 7}
   
 
rdwrSyslogServerRowStatus OBJECT-TYPE
   SYNTAX RowStatus
   ACCESS  read-write
   STATUS  mandatory
   DESCRIPTION
       "IP address of the syslog server."
   ::= {rdwrSyslogServerEntry 8}

rdwrSyslogServerConnectionStatus OBJECT-TYPE
   SYNTAX INTEGER{
		nr (1),
        reachable(2),
        unreachable (3)
	}
   ACCESS  read-write
   STATUS  mandatory
    DESCRIPTION
      "The SYSLOG Protocol."
   DEFVAL { unreachable }
  
   ::= {rdwrSyslogServerEntry 9}
   


rdwrSyslogServerNumberOfLogsInBackLog OBJECT-TYPE
   SYNTAX INTEGER
   ACCESS  read-write
   STATUS  mandatory
   DESCRIPTION
       "Number of logs in the backlog."
   DEFVAL { 0 }
   ::= {rdwrSyslogServerEntry 10}

rdwrSyslogSecuritySending OBJECT-TYPE
   SYNTAX FeatureStatus
   ACCESS  read-write
   STATUS  mandatory
   DESCRIPTION
       "Security events sending status."
   DEFVAL {enable}
   ::= {rdwrSyslogServerEntry 11}  
   
rdwrSyslogHealthSending OBJECT-TYPE
   SYNTAX FeatureStatus
   ACCESS  read-write
   STATUS  mandatory
   DESCRIPTION
       "Health events sending status."
   DEFVAL {enable}
   ::= {rdwrSyslogServerEntry 12} 
rdwrSyslogUserAuditSending OBJECT-TYPE
   SYNTAX FeatureStatus
   ACCESS  read-write
   STATUS  mandatory
   DESCRIPTION
       "Audit events sending status."
   DEFVAL {enable}
   ::= {rdwrSyslogServerEntry 13}  
   
rsWSDSyslogGlobalStatus  OBJECT-TYPE
    SYNTAX INTEGER {
                    enable(1),
                    disable(2)
                   }
    ACCESS  read-write
    STATUS  mandatory
    DESCRIPTION
        "Enable/Disable syslog message sending to remote station."
--  DEFVAL { 2 }
    ::=  {rsServerDispatcher 174}

-- Enterprise-specific traps for RADWARE
-- Each enterprise-specific trap has two bound variables describing the exact nature of
-- the trap. rndErrorDesc provides a detailed description of the problem, including the
-- related interface number, board number or any other applicable variable.
-- rndErrorSeverity describes the severity of this problem.

-- Trap template
-- -------------
--    TRAP-TYPE
--       ENTERPRISE  rsServerDispatcher
--       VARIABLES   { rndErrorDesc, rndErrorSeverity }
--       DESCRIPTION
--             ""
--       ::=
-- -------------

rsWSDConnectionLimitReached TRAP-TYPE
   ENTERPRISE rsServerDispatcher
   VARIABLES { rndErrorDesc, rndErrorSeverity }
   DESCRIPTION
      "This warning is generated when the users connection limit of an application or a physical server is reached."
   ::= 1

rsWSDReadyForShutDown  TRAP-TYPE
       ENTERPRISE  rsServerDispatcher
       VARIABLES   { rndErrorDesc, rndErrorSeverity }
       DESCRIPTION
             "This warning is generated when all the clients sessions of an application or a physical server are finished and so, the application or server are ready to be shut down."
       ::=  2

rsWSDIllegalReport TRAP-TYPE
       ENTERPRISE  rsServerDispatcher
       VARIABLES   { rndErrorDesc, rndErrorSeverity }
       DESCRIPTION
             "This warning is generated when an LRP message arrives with illegal information."
       ::= 3

rsWSDRemoteWSDUnavailable TRAP-TYPE
       ENTERPRISE  rsServerDispatcher
       VARIABLES   { rndErrorDesc, rndErrorSeverity }
       DESCRIPTION
             "This warning is generated when a remote WSD is in full capacity, not in service or disabled. This server is then unavailable"
       ::= 4

rsWSDCapacityLimitReached TRAP-TYPE
       ENTERPRISE  rsServerDispatcher
       VARIABLES   { rndErrorDesc, rndErrorSeverity }
       DESCRIPTION
             "This warning is generated when WSD capacity limit is reached."
       ::= 5

rsWSDStatusMonitoring TRAP-TYPE
       ENTERPRISE  rsServerDispatcher
       VARIABLES   { rndErrorDesc, rndErrorSeverity }
       DESCRIPTION
             " This warning is generated for unavailable SNMP parameter from a server."
       ::= 6

rsWSDWrongPassword TRAP-TYPE
       ENTERPRISE  rsServerDispatcher
       VARIABLES   { rndErrorDesc, rndErrorSeverity }
       DESCRIPTION
             " This warning is generated when authentication failed because of wrong user name or password."
       ::= 7

rsWSDInternalTableOverflow  TRAP-TYPE
         ENTERPRISE  rsServerDispatcher
         VARIABLES   { rndErrorDesc, rndErrorSeverity }
         DESCRIPTION
             "This warning is generated when there are no more free entries in the table."
     ::=  8

rsWSDServerUp  TRAP-TYPE
         ENTERPRISE  rsServerDispatcher
         VARIABLES   { rndErrorDesc, rndErrorSeverity }
         DESCRIPTION
             "This informational trap is sent when a server correctly responds to a connectivity check for the first time."
     ::=  9

rsWSDPoliciesUpdated TRAP-TYPE
         ENTERPRISE rsServerDispatcher
         VARIABLES { rndErrorDesc, rndErrorSeverity }
         DESCRIPTION
             "This informational trap is sent when the rule policies are
             updated."
     ::=  10

rsWSDIntrusionDetected TRAP-TYPE
         ENTERPRISE rsServerDispatcher
         VARIABLES { rndErrorDesc, rndErrorSeverity }
         DESCRIPTION
             "This informational trap is sent when an intrusion is detected."
     ::=  11

rsWSDUserLocked TRAP-TYPE
         ENTERPRISE rsServerDispatcher
         VARIABLES { rndErrorDesc, rndErrorSeverity }
         DESCRIPTION
             "This warning trap is sent when a user is locked from managing the device because of login failure."
     ::=  12

rsWSDAuthenticationSuccess TRAP-TYPE
         ENTERPRISE rsServerDispatcher
         VARIABLES { rndErrorDesc, rndErrorSeverity }
         DESCRIPTION
             "This informational trap is sent when a user authentication succeeded."
     ::=  13

rsRadwareNTPUpdateProblem TRAP-TYPE
         ENTERPRISE rsServerDispatcher
         VARIABLES { rndErrorDesc, rndErrorSeverity }
         DESCRIPTION
             "This warning trap is sent when the device NTP client encounters problem updating 
              the system clock."
     ::=  14

rsRadwareVrrpErrors TRAP-TYPE
         ENTERPRISE rsServerDispatcher
         VARIABLES { rndErrorDesc, rndErrorSeverity }
         DESCRIPTION
             "This warning trap is generated when VRRP error occurs."
     ::=  15

rdwrDualPowerSupplyProblem TRAP-TYPE
         ENTERPRISE rsServerDispatcher
         VARIABLES { rndErrorDesc, rndErrorSeverity }
         DESCRIPTION
             "This warning trap is sent when a power supply becomes inacive on a dual power supply device."
     ::=  16

rdwrDualPowerSupplyUp TRAP-TYPE
         ENTERPRISE rsServerDispatcher
         VARIABLES { rndErrorDesc, rndErrorSeverity }
         DESCRIPTION
             "This info trap is sent when a power supply changes state from inactive to active on a dual power supply device."
     ::=  17

rdwrMngmntPortDisabled TRAP-TYPE
         ENTERPRISE rsServerDispatcher
         VARIABLES { rndErrorDesc, rndErrorSeverity }
         DESCRIPTION
             "This info trap is sent when a user tries to access a management port via a protocol, which is disabled on this port."
     ::=  18

rdwrUnauthorizedSourceIP TRAP-TYPE
         ENTERPRISE rsServerDispatcher
         VARIABLES { rndErrorDesc, rndErrorSeverity }
         DESCRIPTION
             "This info trap is sent when a user tries to access a management port from an IP address, that is not authorized to perform access."
     ::=  19

rsSSLCertificateSyncProblem TRAP-TYPE
         ENTERPRISE rsServerDispatcher
         VARIABLES { rndErrorDesc, rndErrorSeverity }
         DESCRIPTION
             "This trap is issued when a file is removed from certificate directory causing a synchronization problem with certificate table."
     ::=  20

rsARPTableIpConflict TRAP-TYPE
         ENTERPRISE rnd
         VARIABLES { rndErrorDesc, rndErrorSeverity }
         DESCRIPTION
             "Indecate IP Conflicts on ARP table."
     ::=  21

--Next two scalars exists in 7.x
--rsWSDAuthenticationServerSuccess TRAP-TYPE
--         ENTERPRISE rsServerDispatcher
--         VARIABLES { rndErrorDesc, rndErrorSeverity }
--         DESCRIPTION
--             "This informational trap is sent after a successful connection to authentication server such as RADIUS/TACACS+."
--     ::=  22
--	    
--rsWSDAuthenticationServerFail TRAP-TYPE
--         ENTERPRISE rsServerDispatcher
--         VARIABLES { rndErrorDesc, rndErrorSeverity }
--         DESCRIPTION
--             "This informational trap is sent after a connection to authentication server such as RADIUS/TACACS+ has failed."
--     ::=  23

rsIpInterfaceWithTplErase TRAP-TYPE
         ENTERPRISE rsServerDispatcher
         VARIABLES { rndErrorDesc, rndErrorSeverity }
         DESCRIPTION
             "Indicate that IP Interface associated with throughput license was erased."
     ::=  24

stpSpec      OBJECT IDENTIFIER ::= { rnd 30 }

rsStpMode OBJECT-TYPE
    SYNTAX  INTEGER {
        disabled(1),
        per-vlan(2)
    }
    ACCESS   read-write
    STATUS   mandatory
    DESCRIPTION
        "Default STP Mode."
    DEFVAL       { disabled }
    ::= { stpSpec  1 }


rsStpDefaultBridgePriority OBJECT-TYPE
    SYNTAX  INTEGER (0..61440)
    ACCESS   read-write
    STATUS   mandatory
    DESCRIPTION
        "Default STP priority for this bridge."
    DEFVAL       { 32768 }
    ::= { stpSpec  2 }

rsStpDefaultHelloTime OBJECT-TYPE
    SYNTAX  INTEGER (1..10)
    ACCESS   read-write
    STATUS   mandatory
    DESCRIPTION
        "Default STP hello time (Sec)."
    DEFVAL       { 2 }
    ::= { stpSpec  3 }

rsStpDefaultMaxAgingTime OBJECT-TYPE
    SYNTAX  INTEGER (6..40)
    ACCESS   read-write
    STATUS   mandatory
    DESCRIPTION
        "Default STP hello time (Sec)."
    DEFVAL       { 20 }
    ::= { stpSpec  4 }

rsStpDefaultForwardDelayTime OBJECT-TYPE
    SYNTAX  INTEGER (4..30)
    ACCESS   read-write
    STATUS   mandatory
    DESCRIPTION
        "Default STP hello time (Sec)."
    DEFVAL       { 15 }
    ::= { stpSpec  5 }

rsStpDefaultPortPriority OBJECT-TYPE
    SYNTAX  INTEGER (0..240)
    ACCESS   read-write
    STATUS   mandatory
    DESCRIPTION
        "Default Port Priority."
    DEFVAL       { 128 }
    ::= { stpSpec  6 }


rsStpInstancesTable  OBJECT-TYPE
   SYNTAX  SEQUENCE OF RsStpInstanceEntry
   ACCESS  not-accessible
   STATUS  mandatory
   DESCRIPTION
         "A table holding STP instances running on device"
   ::= { stpSpec  7 }


rsStpInstanceEntry OBJECT-TYPE
   SYNTAX  RsStpInstanceEntry
   ACCESS  not-accessible
   STATUS  mandatory
   DESCRIPTION
         "An entry in the STP instances table"
   INDEX  {rsStpInstanceVlanId}
   ::= { rsStpInstancesTable  1 }

RsStpInstanceEntry 	::= SEQUENCE {
     rsStpInstanceVlanId              INTEGER,
     rsStpInstanceBridgePriority      INTEGER,
     rsStpInstanceHelloTime           INTEGER,
     rsStpInstanceMaxAgingTime        INTEGER,
     rsStpInstanceForwardDelayTime    INTEGER,
     rsStpInstanceEnabled	      FeatureStatus,
     rsStpInstanceRootId	      DisplayString,
     rsStpInstanceRootPathCost	      INTEGER,
     rsStpInstanceDesignatedBridgeId  DisplayString,
     rsStpInstanceDesignatedPortId    INTEGER
   }

rsStpInstanceVlanId OBJECT-TYPE
   SYNTAX  INTEGER
   ACCESS  read-only
   STATUS  mandatory
   DESCRIPTION
         "Vlan of STP instance."
   ::= { rsStpInstanceEntry 1 }

rsStpInstanceBridgePriority OBJECT-TYPE
    SYNTAX INTEGER (0..61440)
    ACCESS  read-write
    STATUS  mandatory
    DESCRIPTION
        "Current bridge priority."
    ::=  { rsStpInstanceEntry 2 }

rsStpInstanceHelloTime OBJECT-TYPE
    SYNTAX INTEGER (1..10)
    ACCESS  read-write
    STATUS  mandatory
    DESCRIPTION
        "Hello Time (in seconds)."
    ::=  { rsStpInstanceEntry 3 }

rsStpInstanceMaxAgingTime OBJECT-TYPE
    SYNTAX INTEGER (6..40)
    ACCESS  read-write
    STATUS  mandatory
    DESCRIPTION
        "Max Aging Time (in seconds)."
    ::=  { rsStpInstanceEntry 4 }

rsStpInstanceForwardDelayTime OBJECT-TYPE
    SYNTAX INTEGER (4..30)
    ACCESS  read-write
    STATUS  mandatory
    DESCRIPTION
        "Forward Delay Time (in seconds)."
    ::=  { rsStpInstanceEntry 5 }

rsStpInstanceEnabled OBJECT-TYPE
    SYNTAX FeatureStatus
    ACCESS  read-write
    STATUS  mandatory
    DESCRIPTION
        "Whether this STP instance is enabled"
    ::=  { rsStpInstanceEntry 6 }

rsStpInstanceRootId OBJECT-TYPE
    SYNTAX DisplayString
    ACCESS  read-only
    STATUS  mandatory
    DESCRIPTION
        "Spanning Tree Root Id."
    ::=  { rsStpInstanceEntry 7 }

rsStpInstanceRootPathCost OBJECT-TYPE
    SYNTAX INTEGER
    ACCESS  read-only
    STATUS  mandatory
    DESCRIPTION
        "Spanning Tree Root Path Cost."
    ::=  { rsStpInstanceEntry 8 }

rsStpInstanceDesignatedBridgeId OBJECT-TYPE
    SYNTAX DisplayString
    ACCESS  read-only
    STATUS  mandatory
    DESCRIPTION
        "Designated Bridge Id."
    ::=  { rsStpInstanceEntry 9 }

rsStpInstanceDesignatedPortId OBJECT-TYPE
    SYNTAX INTEGER
    ACCESS  read-only
    STATUS  mandatory
    DESCRIPTION
        "Designated Port Id."
    ::=  { rsStpInstanceEntry 10 }

rsStpPortTable  OBJECT-TYPE
   SYNTAX  SEQUENCE OF RsStpPortEntry
   ACCESS  not-accessible
   STATUS  mandatory
   DESCRIPTION
         "A table holding STP Information and instance mapping for each port "
   ::= { stpSpec  8 }


rsStpPortEntry OBJECT-TYPE
   SYNTAX  RsStpPortEntry
   ACCESS  not-accessible
   STATUS  mandatory
   DESCRIPTION
         "An entry in the STP ports table"
   INDEX  {rsStpPortId}
   ::= { rsStpPortTable 1 }

RsStpPortEntry	::= SEQUENCE {
     rsStpPortId          	INTEGER,
     rsStpPortVlanId      	INTEGER,
     rsStpPortPriority    	INTEGER,
     rsStpPortPathCost    	INTEGER,
     rsStpPortModeFast    	FeatureStatus,
     rsStpPortEnabled    	FeatureStatus,
     rsStpPortState	  	INTEGER,
     rsStpPortRole	  	INTEGER
}

rsStpPortId OBJECT-TYPE
   SYNTAX  INTEGER
   ACCESS  read-only
   STATUS  mandatory
   DESCRIPTION
         "Port Id."
   ::= { rsStpPortEntry 1 }

rsStpPortVlanId OBJECT-TYPE
   SYNTAX  INTEGER
   ACCESS  read-only
   STATUS  mandatory
   DESCRIPTION
         "Vlan this port belongs to."
   ::= { rsStpPortEntry 2 }

rsStpPortPriority OBJECT-TYPE
   SYNTAX  INTEGER (0..240)
   ACCESS  read-write
   STATUS  mandatory
   DESCRIPTION
         "STP Priority for this port."
   ::= { rsStpPortEntry 3 }

rsStpPortPathCost OBJECT-TYPE
   SYNTAX  INTEGER (1..65535)
   ACCESS  read-write
   STATUS  mandatory
   DESCRIPTION
         "Port Path Cost."
   ::= { rsStpPortEntry 4 }

rsStpPortModeFast OBJECT-TYPE
   SYNTAX  FeatureStatus
   ACCESS  read-write
   STATUS  mandatory
   DESCRIPTION
         "Whether this port is an Edge port, and should start forwarding immediately."
   ::= { rsStpPortEntry 5 }

rsStpPortEnabled OBJECT-TYPE
    SYNTAX FeatureStatus
    ACCESS  read-write
    STATUS  mandatory
    DESCRIPTION
        "Whether this port participates in spanning tree"
    ::=  { rsStpPortEntry 6 }

rsStpPortState OBJECT-TYPE
   SYNTAX  INTEGER {
      discarding (1),
      learning (2),
      forwarding (3)
   }
   ACCESS  read-only
   STATUS  mandatory
   DESCRIPTION
         "Port State according to STP Algorithm."
   ::= { rsStpPortEntry 7 }

rsStpPortRole OBJECT-TYPE
   SYNTAX  INTEGER {
      disabled (1),
      root (2),
      designated (3),
      alternate (4),
      backup (5)
   }
   ACCESS  read-only
   STATUS  mandatory
   DESCRIPTION
         "Port Role according to STP Algorithm."
   ::= { rsStpPortEntry 8 }


   
rsStpPortStateTrap   TRAP-TYPE
       ENTERPRISE  stpSpec
        VARIABLES  { rndErrorDesc, rndErrorSeverity }
        DESCRIPTION
             "This trap is sent to inform the user of silent link failure or physical port state change, initiated by STP."
       ::=  1

rsSystemFansTable OBJECT-TYPE
  SYNTAX  SEQUENCE OF RsSystemFansEntry
  ACCESS  not-accessible
  STATUS  mandatory
  DESCRIPTION
    "A table containing the fans status."
  ::= {rsServerDispatcher 162}

rsSystemFansEntry OBJECT-TYPE
  SYNTAX  RsSystemFansEntry
  ACCESS  not-accessible
  STATUS  mandatory
  DESCRIPTION
    "Information about a particular fan."
  INDEX   { rsSystemFanIndex }
  ::= { rsSystemFansTable 1 }

RsSystemFansEntry ::= SEQUENCE {
    rsSystemFanIndex     INTEGER,
    rsSystemFansStatus DisplayString
  }

rsSystemFanIndex OBJECT-TYPE
    SYNTAX INTEGER
    ACCESS  read-only
    STATUS  mandatory
    DESCRIPTION
    "Fan Index."
    ::= {rsSystemFansEntry 1}

rsSystemFansStatus OBJECT-TYPE
    SYNTAX DisplayString
    ACCESS  read-only
    STATUS  mandatory
    DESCRIPTION
    "Fan Status."
    ::= {rsSystemFansEntry 2}

rsNetPortUtilizationTable OBJECT-TYPE
	SYNTAX      SEQUENCE OF RsNetPortUtilizationEntry
	ACCESS  	   not-accessible
	STATUS      mandatory
	DESCRIPTION
	   "Display the port Utilization."
	::=  {rsServerDispatcher 164}

rsNetPortUtilizationEntry OBJECT-TYPE
	SYNTAX      RsNetPortUtilizationEntry
	ACCESS  	   not-accessible
	STATUS      mandatory
	DESCRIPTION
	   "An entry containing a single port utilization."
	INDEX   { rsNetPortUtilizationIndex }
	::= { rsNetPortUtilizationTable 1 }

RsNetPortUtilizationEntry ::=
	SEQUENCE {
	rsNetPortUtilizationIndex        	         INTEGER,
	rsNetPortUtilizationEntryInUtil               INTEGER,
	rsNetPortUtilizationEntryOutUtil              INTEGER
	}

rsNetPortUtilizationIndex OBJECT-TYPE
	SYNTAX      INTEGER
	ACCESS  	   read-only
	STATUS      mandatory
	DESCRIPTION
	   "The ports index."
	::= { rsNetPortUtilizationEntry 1 }

rsNetPortUtilizationEntryInUtil OBJECT-TYPE
	SYNTAX      INTEGER
	ACCESS  	   read-only
	STATUS      mandatory
	DESCRIPTION
	   "The inbound utilization in-packets/speed."
	::= { rsNetPortUtilizationEntry 2 }

rsNetPortUtilizationEntryOutUtil OBJECT-TYPE
	SYNTAX      INTEGER
	ACCESS  	   read-only
	STATUS      mandatory
	DESCRIPTION
	   "The outbound utilization out-packets/speed."
	::= { rsNetPortUtilizationEntry 3 }
   
rsHWCPUTemperatureTable OBJECT-TYPE
   SYNTAX      SEQUENCE OF RsHWCPUTemperatureEntry
   ACCESS  	   not-accessible
   STATUS      mandatory
   DESCRIPTION
		   "Display the CPU temperature."
	::=  {rsServerDispatcher 165}

rsHWCPUTemperatureEntry OBJECT-TYPE
   SYNTAX      RsHWCPUTemperatureEntry
   ACCESS  	   not-accessible
   STATUS      mandatory
   DESCRIPTION
		   "An entry containing a single CPU temperature."
   INDEX   { rsHWCPUTemperatureIndex }
   ::= { rsHWCPUTemperatureTable 1 }

RsHWCPUTemperatureEntry ::=
   SEQUENCE {
	   rsHWCPUTemperatureIndex 	         INTEGER,
	   rsHWCPUTemperatureValue           INTEGER
   }

rsHWCPUTemperatureIndex OBJECT-TYPE
   SYNTAX      INTEGER
   ACCESS  	   read-only
   STATUS      mandatory
   DESCRIPTION
		   "The CPU index."
   ::= { rsHWCPUTemperatureEntry 1 }
   
rsHWCPUTemperatureValue OBJECT-TYPE
   SYNTAX      INTEGER
   ACCESS  	   read-only
   STATUS      mandatory
   DESCRIPTION
		   "The CPU temperature."
   ::= { rsHWCPUTemperatureEntry 2 }
 
rsHWCoreUtilizationTable OBJECT-TYPE
   SYNTAX      SEQUENCE OF RsHWCoreUtilizationEntry
   ACCESS  	   not-accessible
   STATUS      mandatory
   DESCRIPTION
		   "Display the device core utilization."
	::=  {rsServerDispatcher 167}

rsHWCoreUtilizationEntry OBJECT-TYPE
   SYNTAX      RsHWCoreUtilizationEntry
   ACCESS  	   not-accessible
   STATUS      mandatory
   DESCRIPTION
		   "An entry containing a single core utilization."
   INDEX   { rsHWCoreUtilizationIndex }
   ::= { rsHWCoreUtilizationTable 1 }

RsHWCoreUtilizationEntry ::=
   SEQUENCE {
	   rsHWCoreUtilizationIndex	         INTEGER,
	   rsHWCoreUtilizationValue          INTEGER
   }

rsHWCoreUtilizationIndex OBJECT-TYPE
   SYNTAX      INTEGER
   ACCESS  	   read-only
   STATUS      mandatory
   DESCRIPTION
		   "The core index."
   ::= { rsHWCoreUtilizationEntry 1 }
   
rsHWCoreUtilizationValue OBJECT-TYPE
   SYNTAX      INTEGER
   ACCESS  	   read-only
   STATUS      mandatory
   DESCRIPTION
		   "The core utilization."
   ::= { rsHWCoreUtilizationEntry 2 }


rsWSDResourceUtilizationInstance1 OBJECT-TYPE
    SYNTAX  INTEGER  (0..100)
    ACCESS  read-only
    STATUS  mandatory
    DESCRIPTION
      "Resource Utilization of WSD on instance 1. Considers network utilization and internal CPU utilization"
    DEFVAL  { 0 }
    ::=  { rsServerDispatcher 181 }


rsWSDREResourceUtilizationInstance1 OBJECT-TYPE
    SYNTAX  INTEGER  (0..100)
    ACCESS  read-only
    STATUS  mandatory
    DESCRIPTION
      "Resource Utilization of network utilization on instance 1"
    DEFVAL  { 0 }
    ::=  { rsServerDispatcher 182 }

rsWSDRSResourceUtilizationInstance1 OBJECT-TYPE
    SYNTAX  INTEGER  (0..100)
    ACCESS  read-only
    STATUS  mandatory
    DESCRIPTION
      "Resource Utilization of internal CPU utilization on instance 1"
    DEFVAL  { 0 }
    ::=  { rsServerDispatcher 183 }

rdwr5SecAvgResourceUtilizationInstance1 OBJECT-TYPE
    SYNTAX  INTEGER  (0..100)
    ACCESS  read-only
    STATUS  mandatory
    DESCRIPTION
      "Average 5 seconds Resource Utilization of internal CPU utilization on instance 1"
    ::=  { rsServerDispatcher 184 }

rdwr60SecAvgResourceUtilizationInstance1 OBJECT-TYPE
    SYNTAX  INTEGER  (0..100)
    ACCESS  read-only
    STATUS  mandatory
    DESCRIPTION
      "Average 60 seconds Resource Utilization of internal CPU utilization on instance 1"
    ::=  { rsServerDispatcher 185 }

rsFormFactor OBJECT-TYPE
      SYNTAX  INTEGER {
      asr9k (1),
      ssp (2),
      kvm (3),
      simulator (4),
      p8420 (5),
      hq (6),
      none (7),
      vmware (8)
   }
    ACCESS  read-write
    STATUS  mandatory
    DESCRIPTION
      "Show current platform type"
    ::=  { rsServerDispatcher 186 }
   
rsAppAgPort OBJECT-TYPE
    SYNTAX  INTEGER (0..65535)
    ACCESS  read-write
    STATUS  mandatory
    DESCRIPTION
      "Show current AppAG port number"
    ::=  { rsServerDispatcher 187 }

rsAppAgIpAddress OBJECT-TYPE
    SYNTAX  IpAddress
    ACCESS  read-write
    STATUS  mandatory
    DESCRIPTION
      "Show current AppAG IP Address"
    ::=  { rsServerDispatcher 188 }

rsAppAgInstId OBJECT-TYPE
    SYNTAX  DisplayString (SIZE(0..128))
    ACCESS  read-write
    STATUS  mandatory
    DESCRIPTION
      "Show current AppAG Instance Id"
    ::=  { rsServerDispatcher 189 }  

rsAppAGChannelIp OBJECT-TYPE
    SYNTAX  IpAddress
    ACCESS  read-write
    STATUS  mandatory
    DESCRIPTION
            "The Management interface IP of the AppAG"
    ::=  { rsServerDispatcher 190 }

rsAppAGChannelMask OBJECT-TYPE
    SYNTAX  IpAddress
    ACCESS  read-write
    STATUS  mandatory
    DESCRIPTION
            "The Management interface netmask of the AppAG"
    ::=  { rsServerDispatcher 191 }


rsAppAGChannelGw OBJECT-TYPE
    SYNTAX  IpAddress
    ACCESS  read-write
    STATUS  mandatory
    DESCRIPTION
            "The Management interface GW IP of the AppAG"
    ::=  { rsServerDispatcher 192 }


rsSSLCertificateSANTable OBJECT-TYPE
    SYNTAX SEQUENCE OF RsSSLCertificateSANEntry
    ACCESS not-accessible
    STATUS  mandatory
    DESCRIPTION
      "Table containing groups of filters."
    ::= { rsServerDispatcher 197  }

rsSSLCertificateSANEntry OBJECT-TYPE
    SYNTAX RsSSLCertificateSANEntry
    ACCESS not-accessible
    STATUS mandatory
    DESCRIPTION
       "The row definition for this table."
    INDEX { rsSSLCertificateEntryName, rsSSLCertificateEntrySANName, rsSSLCertificateEntrySANNameIndex }
    ::=  { rsSSLCertificateSANTable 1 }

RsSSLCertificateSANEntry ::= SEQUENCE {
    rsSSLCertificateEntryName DisplayString,
    rsSSLCertificateEntrySANName DisplayString,
    rsSSLCertificateEntrySANNameIndex INTEGER,
    rsSSLCertificateEntrySANStatus RowStatus
}

rsSSLCertificateEntryName OBJECT-TYPE
    SYNTAX DisplayString(SIZE(1..50))
    ACCESS read-only
    STATUS mandatory
    DESCRIPTION
      "The name of the group entry ."
    ::=  { rsSSLCertificateSANEntry 1 }

rsSSLCertificateEntrySANName OBJECT-TYPE
    SYNTAX DisplayString(SIZE(0..64))
    ACCESS read-only
    STATUS mandatory
    DESCRIPTION
      "The name of the subject alternate name entry in the group."
    ::=  { rsSSLCertificateSANEntry 2 }

rsSSLCertificateEntrySANNameIndex OBJECT-TYPE
    SYNTAX INTEGER
    ACCESS read-only
    STATUS mandatory
    DESCRIPTION
      "The index of the subject alternate name in the array."
    ::=  { rsSSLCertificateSANEntry 3 }

rsSSLCertificateEntrySANStatus OBJECT-TYPE
    SYNTAX RowStatus 
    ACCESS read-write
    STATUS mandatory
    DESCRIPTION
      "The status of the object."
    ::=  { rsSSLCertificateSANEntry 4 }

rsLinkAggregationModeTable OBJECT-TYPE
   SYNTAX SEQUENCE OF RsLinkAggregationEntry
   ACCESS not-accessible
   STATUS  mandatory
   DESCRIPTION
      "Table containing groups of filters."
    ::= { rsServerDispatcher 198  }

rsLinkAggregationEntry OBJECT-TYPE
  SYNTAX  RsLinkAggregationEntry
  ACCESS  not-accessible
  STATUS  mandatory
  DESCRIPTION
    "Configure LAG port parameters. Where LAG is static or dynamic and thus controlled by LACP protocol."
  INDEX   { rsLinkAggregationTrunkIndex }
  ::= { rsLinkAggregationModeTable 1 }

RsLinkAggregationEntry ::= SEQUENCE {
    rsLinkAggregationTrunkIndex     INTEGER,
    rsLinkAggregationMode INTEGER,
    rsLinkAggregationTimeout INTEGER,  
    rsLinkAggregationStatus RowStatus
  }

rsLinkAggregationTrunkIndex OBJECT-TYPE
   SYNTAX  INTEGER (1..7)
   ACCESS  read-write
   STATUS  mandatory
   DESCRIPTION
      "Define the index of the LAG port. The device has a fixed number of 7 LAG ports."
    ::=  { rsLinkAggregationEntry 1 }
  
rsLinkAggregationMode OBJECT-TYPE
    SYNTAX  INTEGER {
      static (1),
      dynamic (2)
   }
    ACCESS  read-write
    STATUS  mandatory
    DESCRIPTION
      "Define the wheter the LAG is static or dyanmic and thus contorlled by LACP protcol."
    ::=  { rsLinkAggregationEntry 2 }
  
rsLinkAggregationTimeout OBJECT-TYPE
    SYNTAX  INTEGER {
      fast (1),
      slow (2)
   }
    ACCESS  read-write
    STATUS  mandatory
    DESCRIPTION
      "Define whether the partner should work with fast or slow timeout. Fast timeout means that LCAPDU is sent by the partner every 1 second
       whereas slow timeout means that LCAPDU is sent by the partner every 30 seconds.
       If no response comes from the partner after 3 LACPDUs should be received, a timeout event occurs, 
       and the LACP state machine moves to the appropriate state based on its current state."
    ::=  { rsLinkAggregationEntry 3 }
                  
   rsLinkAggregationStatus OBJECT-TYPE
   SYNTAX RowStatus 
   ACCESS read-write
   STATUS mandatory
   DESCRIPTION
      "The status of the object."
    ::=  { rsLinkAggregationEntry 4 }   

rsLinkAggregationDynamicTrunksSupport OBJECT-TYPE
    SYNTAX FeatureStatus
    ACCESS  read-write
    STATUS  mandatory
    DESCRIPTION
        "Whether dynamic trunks (LACP) support is enabled or not"
    ::=  { rsServerDispatcher 199 }
  
    END

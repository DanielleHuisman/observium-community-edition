--MibName=rcDhcpServer
DHCP-SERVER-MIB DEFINITIONS ::= BEGIN

    IMPORTS
        MODULE-IDENTITY, TimeTicks, OBJECT-TYPE
             FROM SNMPv2-SMI       
        RowStatus    FROM SNMPv2-TC 
        EnableVar,Vlanset	 FROM SWITCH-TC       
        iscomSwitch  FROM RAISECOM-BASE-MIB;

    rcDhcpServer MODULE-IDENTITY
          LAST-UPDATED "200412200000Z"  -- Dec 20, 2004
          ORGANIZATION "raisecom."
          CONTACT-INFO
              "raisecom
                  E-mail: "

          DESCRIPTION "dhcp module management."

          REVISION    "200412200000Z"  -- Dec 20, 2004
          DESCRIPTION "Initial Version"

          ::= { iscomSwitch 12 }
          
    rcDhcpServerMibObjects	OBJECT IDENTIFIER ::= { rcDhcpServer 1 }
    rcDhcpDot1dDhcp      	OBJECT IDENTIFIER ::= { rcDhcpServerMibObjects 1 }
    rcDhcpServerStatistics  OBJECT IDENTIFIER ::= { rcDhcpServerMibObjects 2 }
                  
                   
--rcDhcpDot1dDhcp--
          rcDhcpPropEnable OBJECT-TYPE
              SYNTAX  EnableVar
              MAX-ACCESS  read-write
              STATUS  current
              DESCRIPTION
                      "The enabled/disabled status of the dhcp."
              DEFVAL { disable }
              ::= { rcDhcpDot1dDhcp 1 }
              
          rcDhcpVlanActive OBJECT-TYPE
              SYNTAX  Vlanset 
              MAX-ACCESS  read-write
              STATUS  current
              DESCRIPTION
                      "The enabled/disabled  status of dhcp of vlan."
              REFERENCE
                      "DHCP SERVER SOUCE-CODE"
              ::= { rcDhcpDot1dDhcp 2 }

          rcDhcpIpNextIndex OBJECT-TYPE
              SYNTAX  INTEGER (1..20)
              MAX-ACCESS  read-only
              STATUS  current
              DESCRIPTION
                      "The next index of the dhcp server ip pool."
              REFERENCE
                      "DHCP SERVER SOUCE-CODE"
              ::= { rcDhcpDot1dDhcp 3 }

          rcDhcpMaxLease OBJECT-TYPE
              SYNTAX  INTEGER (30..10080) -- is caculated with minute.It is must be greater than 30.
              MAX-ACCESS  read-write
              STATUS  current
              DESCRIPTION
                      "The max Lease of Ip address(minute)."             
              REFERENCE
                      "DHCP SERVER SOUCE-CODE"    
              DEFVAL { 10080 }
              ::= { rcDhcpDot1dDhcp 4 }

          rcDhcpMinLease OBJECT-TYPE
              SYNTAX  INTEGER  (30..10080)-- is caculated with minute.It is must be greater than 30.
              MAX-ACCESS  read-write
              STATUS  current
              DESCRIPTION
                      "The min Lease of Ip address(minute)."             
              REFERENCE
                      "DHCP SERVER SOUCE-CODE"   
              DEFVAL { 30 }
              ::= { rcDhcpDot1dDhcp 5 }

          rcDhcpDefLease OBJECT-TYPE
              SYNTAX  INTEGER  (30..10080)-- is caculated with minute. It is must be greater than 30.
              MAX-ACCESS  read-write
              STATUS  current
              DESCRIPTION
                      "The default Lease of Ip address(minute)."              
              REFERENCE
                      "DHCP SERVER SOUCE-CODE"      
              DEFVAL { 30 }
              ::= { rcDhcpDot1dDhcp 6 }

          rcDhcpVlanAuth OBJECT-TYPE
              SYNTAX  Vlanset 
              MAX-ACCESS  read-write
              STATUS  current
              DESCRIPTION
                      "The enabled/disabled auth status of dhcp of vlan."
              REFERENCE
                      "DHCP SERVER SOUCE-CODE"
              ::= { rcDhcpDot1dDhcp 7 }            

          rcDhcpServerStartTime OBJECT-TYPE
              SYNTAX  TimeTicks 
              MAX-ACCESS  read-write
              STATUS  current
              DESCRIPTION
                      "This read-only object displays the DHCP server startup time."
              REFERENCE
                      "DHCP SERVER SOUCE-CODE"
              ::= { rcDhcpDot1dDhcp 8 }

          rcDhcpIpTable OBJECT-TYPE
              SYNTAX  SEQUENCE OF RcDhcpIpEntry
              MAX-ACCESS  not-accessible
              STATUS  current
              DESCRIPTION
                      "A table that contains ip-pool information
                      for the DHCP Server."
              ::= { rcDhcpDot1dDhcp 9 }
              
          rcDhcpIpEntry OBJECT-TYPE
              SYNTAX  RcDhcpIpEntry
              MAX-ACCESS  not-accessible
              STATUS  current
              DESCRIPTION
                      "A entry that contains ip-pool information
                      for the DHCP Server."
              INDEX   { rcDhcpIpIndex }
              ::= { rcDhcpIpTable 1 }
            
          RcDhcpIpEntry ::=
              SEQUENCE {
                  rcDhcpIpIndex		INTEGER,
                  rcDhcpIpEntryName OCTET STRING,
                  rcDhcpIpVlanset 	Vlanset,
                  rcDhcpIpStartIp 	IpAddress,
                  rcDhcpIpEndIp   	IpAddress,
                  rcDhcpIpNetmask   IpAddress,
                  rcDhcpIpGateway   IpAddress,
                  rcDhcpIpDnsServer IpAddress,
                  rcDhcpIpSecondaryDnsServer IpAddress,
                  rcDhcpIpRowStatus RowStatus
                  }
               
          rcDhcpIpIndex OBJECT-TYPE
              SYNTAX  INTEGER (1..20)
              MAX-ACCESS  not-accessible
              STATUS  current
              DESCRIPTION
                      "index of Ip-pool row."
              REFERENCE
                      "SOUCE-CODE OF DHCP SERVER"
              ::= { rcDhcpIpEntry 1 }
              
          rcDhcpIpEntryName OBJECT-TYPE
              SYNTAX  OCTET STRING (SIZE(1..16))
              MAX-ACCESS  read-create
              STATUS  current
              DESCRIPTION
                      "Name of Ip-pool row."
              REFERENCE
                      "SOUCE-CODE OF DHCP SERVER"
              ::= { rcDhcpIpEntry 2 }
              
          rcDhcpIpVlanset OBJECT-TYPE
              SYNTAX  Vlanset
              MAX-ACCESS  read-create
              STATUS  current
              DESCRIPTION
                      "DURABLE:
                      Name of Ip-pool row."
              REFERENCE
                      "SOUCE-CODE OF DHCP SERVER."
              ::= { rcDhcpIpEntry 3 }
              
          rcDhcpIpStartIp OBJECT-TYPE
              SYNTAX  IpAddress
              MAX-ACCESS  read-create
              STATUS  current
              DESCRIPTION
                      "DURABLE:
                      start ip address."
              REFERENCE
                      "SOUCE-CODE OF DHCP SERVER."
              ::= { rcDhcpIpEntry 4 }
              
          rcDhcpIpEndIp OBJECT-TYPE
              SYNTAX  IpAddress
              MAX-ACCESS  read-create
              STATUS  current
              DESCRIPTION
                      "DURABLE:
                      end ip address."
              REFERENCE
                      "SOUCE-CODE OF DHCP SERVER."
              ::= { rcDhcpIpEntry 5 }              
              
          rcDhcpIpNetmask OBJECT-TYPE
              SYNTAX  IpAddress
              MAX-ACCESS  read-create
              STATUS  current
              DESCRIPTION
                      "DURABLE:
                      netmask of ip address."
              REFERENCE
                      "SOUCE-CODE OF DHCP SERVER."
              ::= { rcDhcpIpEntry 6 }   
              
          rcDhcpIpGateway OBJECT-TYPE
              SYNTAX  IpAddress
              MAX-ACCESS  read-create
              STATUS  current
              DESCRIPTION
                      "DURABLE:
                      gateway of ip address."
              REFERENCE
                      "SOUCE-CODE OF DHCP SERVER."
              ::= { rcDhcpIpEntry 7 }  
              
          rcDhcpIpDnsServer OBJECT-TYPE
              SYNTAX  IpAddress
              MAX-ACCESS  read-create
              STATUS  current
              DESCRIPTION
                      "DURABLE:
                      dns of ip address."
              REFERENCE
                      "SOUCE-CODE OF DHCP SERVER."
              ::= { rcDhcpIpEntry 8 }   
                 
          rcDhcpIpSecondaryDnsServer OBJECT-TYPE
              SYNTAX  IpAddress
              MAX-ACCESS  read-create
              STATUS  current
              DESCRIPTION
                      "DURABLE:
                      dns of ip address."
              REFERENCE
                      "SOUCE-CODE OF DHCP SERVER."
              ::= { rcDhcpIpEntry 9 }  
              
          rcDhcpIpRowStatus OBJECT-TYPE
              SYNTAX  RowStatus               
              MAX-ACCESS  read-create
              STATUS  current
              DESCRIPTION
                      "DURABLE:
                      rowstatus of ip address."
              REFERENCE
                      "SOUCE-CODE OF DHCP SERVER."
              ::= { rcDhcpIpEntry 10 } 

        
              
---------------dhcp relay table--------------------------  
          rcDhcpRelayNextIndex OBJECT-TYPE
              SYNTAX  INTEGER (1..8)
              MAX-ACCESS  read-only
              STATUS  current
              DESCRIPTION
                      "The next index of Relay server."
              REFERENCE
                      "DHCP SERVER SOUCE-CODE"
              ::= { rcDhcpDot1dDhcp 10 }  
                      
          rcDhcpRelayTable OBJECT-TYPE
              SYNTAX  SEQUENCE OF RcDhcpRelayEntry
              MAX-ACCESS  not-accessible
              STATUS  current
              DESCRIPTION
                      "A table that contains relay server information
                      for the DHCP Server."
              ::= { rcDhcpDot1dDhcp 11 }
              
          rcDhcpRelayEntry OBJECT-TYPE
              SYNTAX  RcDhcpRelayEntry
              MAX-ACCESS  not-accessible
              STATUS  current
              DESCRIPTION
                      "A entry that contains relay server information
                      for the DHCP Server."
              INDEX   { rcDhcpRelayIndex }
              ::= { rcDhcpRelayTable 1 }
            
          RcDhcpRelayEntry ::=
              SEQUENCE {
                  rcDhcpRelayIndex INTEGER,
                  rcDhcpRelayAddress IpAddress,
                  rcDhcpRelayMask IpAddress,
                  rcDhcpRelayRowStatus RowStatus                 
                  }
                  
          rcDhcpRelayIndex OBJECT-TYPE
              SYNTAX  INTEGER
              MAX-ACCESS  not-accessible
              STATUS  current
              DESCRIPTION
                      "index of relay server."
              REFERENCE
                      "SOUCE-CODE OF DHCP SERVER"
              ::= { rcDhcpRelayEntry 1 }                  
              
          rcDhcpRelayAddress OBJECT-TYPE
              SYNTAX  IpAddress
              MAX-ACCESS  read-create
              STATUS  current
              DESCRIPTION
                      "ip address of relay server."
              REFERENCE
                      "SOUCE-CODE OF DHCP SERVER"
              ::= { rcDhcpRelayEntry 2 } 
              
          rcDhcpRelayMask OBJECT-TYPE
              SYNTAX  IpAddress
              MAX-ACCESS  read-create
              STATUS  current
              DESCRIPTION
                      "ip mask of relay server."
              REFERENCE
                      "SOUCE-CODE OF DHCP SERVER"
              ::= { rcDhcpRelayEntry 3 }
              
          rcDhcpRelayRowStatus OBJECT-TYPE
              SYNTAX    RowStatus            
              MAX-ACCESS  read-create
              STATUS  current
              DESCRIPTION
                      "DURABLE:
                      rowstatus of relay server address."
              REFERENCE
                      "SOUCE-CODE OF DHCP SERVER."
              ::= { rcDhcpRelayEntry 4 }    
                             
--dhcp server statistics--
    rcDhcpServerStatsBootps  OBJECT-TYPE
        SYNTAX Counter
        MAX-ACCESS read-only
        STATUS mandatory
        DESCRIPTION
            "This read-only object displays the DHCP Server receive the Bootps num."
        ::= {rcDhcpServerStatistics 1 }  
        
    rcDhcpServerStatsDiscovers  OBJECT-TYPE
        SYNTAX Counter
        MAX-ACCESS read-only
        STATUS mandatory
        DESCRIPTION
            "This read-only object displays the DHCP Server receive the Discovers num."
        ::= { rcDhcpServerStatistics 2 }        
        
    rcDhcpServerStatsRequests  OBJECT-TYPE
        SYNTAX Counter
        MAX-ACCESS read-only
        STATUS mandatory
        DESCRIPTION
            "This read-only object displays the DHCP Server receive the Requests num."
        ::= { rcDhcpServerStatistics 3 }        

    rcDhcpServerStatsReleases  OBJECT-TYPE
        SYNTAX Counter
        MAX-ACCESS read-only
        STATUS mandatory
        DESCRIPTION
            "This read-only object displays the DHCP Server receive the Releases num."
        ::= { rcDhcpServerStatistics 4 }                

    rcDhcpServerStatsOffers  OBJECT-TYPE
        SYNTAX Counter
        MAX-ACCESS read-only
        STATUS mandatory
        DESCRIPTION
            "This read-only object displays the DHCP Server receive the Offers num."
        ::= { rcDhcpServerStatistics 5 }        

    rcDhcpServerStatsAcks  OBJECT-TYPE
        SYNTAX Counter
        MAX-ACCESS read-only
        STATUS mandatory
        DESCRIPTION
            "This read-only object displays the DHCP Server receive the Acks num."
        ::= { rcDhcpServerStatistics 6 }        

    rcDhcpServerStatsNacks  OBJECT-TYPE
        SYNTAX Counter
        MAX-ACCESS read-only
        STATUS mandatory
        DESCRIPTION
            "This read-only object displays the DHCP Server receive the Nacks num."
        ::= { rcDhcpServerStatistics 7 }     
           
    rcDhcpServerStatsDeclines  OBJECT-TYPE
        SYNTAX Counter
        MAX-ACCESS read-only
        STATUS mandatory
        DESCRIPTION
            "This read-only object displays the DHCP Server receive the Declines num."
        ::= {rcDhcpServerStatistics 8 }  

    rcDhcpServerStatsInformations  OBJECT-TYPE
        SYNTAX Counter
        MAX-ACCESS read-only
        STATUS mandatory
        DESCRIPTION
            "This read-only object displays the DHCP Server receive the Informations num."
        ::= {rcDhcpServerStatistics 9 }  
                
    rcDhcpServerStatsUnknows  OBJECT-TYPE
        SYNTAX Counter
        MAX-ACCESS read-only
        STATUS mandatory
        DESCRIPTION
            "This read-only object displays the DHCP Server receive the unknowed packets num."
        ::= {rcDhcpServerStatistics 10 }  
                
    rcDhcpServerStatsPackets  OBJECT-TYPE
        SYNTAX Counter
        MAX-ACCESS read-only
        STATUS mandatory
        DESCRIPTION
            "This read-only object displays the DHCP Server receive the total packets num."
        ::= {rcDhcpServerStatistics 11 }  
                                                               
END

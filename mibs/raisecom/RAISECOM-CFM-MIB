--MibName=rcCfm
-- *****************************************************************
-- RAISECOM-CFM-MIB.mib
--
-- november 2007, chendonghua
--
-- Copyright(c) 2003-2005 by RAISECOM TECH, Ltd. 
-- All rights reserved.     
-- 08, 20130502, wubin, add dot1agCfmMaCompPrimaryVlanId declare
-- 07, 20121221, fanmanjie, add rcCfmMepExPduPriority,
-- rcCfmMepExPmAdmin, rcCfmMepExRdiAdmin, rcCfmMaNetMipAutocreateAdmin,
-- rcCfmMipExTable
-- 06，20111022，huochao,add scaler mibs default values.    
-- 05，20111021,huochao,modify rcCfmMdEntry 's index.
-- 04，20110915,huochao,add multicast lb result table.
-- 03,20110711,zxh, Ros00007590
-- 02,20101106,liangyunqing, line 63,add rcCfmMepExLckAdmin,	
--  rcCfmMaExAisSuppressStatus, rcCfmMaExAisTable,rcCfmMaExLckTable  
-- 01,20100714,liweixing,line 570,delete the comma
-- *****************************************************************


RAISECOM-CFM-MIB DEFINITIONS ::= BEGIN      
IMPORTS
    Integer32, Counter64,
    Unsigned32               			FROM SNMPv2-SMI    -- [RFC2578]  
    InterfaceIndexOrZero                FROM IF-MIB        -- [RFC2863]
    Dot1agCfmMDLevelOrNone,
    Dot1agCfmMepId,
    Dot1agCfmMDLevel,
    Dot1agCfmMepDefects,
    Dot1agCfmLowestAlarmPri,  
    Dot1agCfmMDLevel,
	dot1agCfmMdIndex, 
    dot1agCfmMaIndex,
    dot1agCfmMepIdentifier, 
    dot1agCfmMepDbRMepIdentifier        FROM IEEE8021-CFM-MIB
    Dot1agCfmMaintAssocNameType         FROM IEEE8021-CFM-MIB 
    Dot1agCfmMaintAssocName             FROM IEEE8021-CFM-MIB 
    Dot1agCfmCcmInterval                FROM IEEE8021-CFM-MIB
    dot1agCfmMaCompPrimaryVlanId		FROM IEEE8021-CFM-MIB 
	RowStatus,TruthValue,MacAddress     FROM SNMPv2-TC     -- [RFC2579]
    InterfaceIndex					    FROM IF-MIB        -- [RFC2863]
    EnableVar                           FROM SWITCH-TC
    iscomSwitch                         FROM RAISECOM-BASE-MIB
	VlanIdOrNone, VlanId     			FROM Q-BRIDGE-MIB
    ;
rcCfm  MODULE-IDENTITY
    LAST-UPDATED   "200711020000Z"
    ORGANIZATION   "Raisecom, Inc."
    CONTACT-INFO  
                "       Raise Systems
                        
                Postal: Beijing,
                        China

                   Tel: 86-010-82884499

                E-mail: chendonghua@raisecom.com"
    DESCRIPTION
        "This MIB module defines objects to CFM "
        REVISION   "200711020000Z"
        DESCRIPTION
            "The initial revision of this MIB."
        ::={ iscomSwitch 26 } 

rcCfmBridge                   OBJECT IDENTIFIER ::= { rcCfm 1 }

-- MIB Object Definitions 
                                                                                                 
rcCfmBridgeAdminCfm        OBJECT-TYPE
	SYNTAX      EnableVar
    MAX-ACCESS  read-write
    STATUS      current
    DESCRIPTION
            "The administrative value of the bridge. 
            A value of TRUE(1) indicates that bridge should enable CFM. 
            FALSE(2) indicates that bridge should disable CFM" 
    DEFVAL { disable }
    ::= { rcCfmBridge 1 }
  
rcCfmBridgeCcmDbArchiveHoldtime        OBJECT-TYPE 
	SYNTAX      Unsigned32 (1..65535)
    MAX-ACCESS  read-write
    STATUS      current
    DESCRIPTION
            "The holdtime of fault CCM in CC database.(1-65535)"    
    DEFVAL { 100 }
    ::= { rcCfmBridge 2 }
    
rcCfmBridgeTracerouteCacheEnable        OBJECT-TYPE
	SYNTAX      TruthValue
    MAX-ACCESS  read-write
    STATUS      current
    DESCRIPTION
            "Enable or disable to use traceroute database storing data."
    DEFVAL { false }
    ::= { rcCfmBridge 3 }

rcCfmBridgeTracerouteCacheHoldtime        OBJECT-TYPE 
	SYNTAX      Unsigned32 (1..65535)
    MAX-ACCESS  read-write
    STATUS      current
    DESCRIPTION
            "The holdtime of entries in traceroute database."  
    DEFVAL { 100 }
    ::= { rcCfmBridge 4 }

rcCfmBridgeTracerouteCacheSize        OBJECT-TYPE 
	SYNTAX      Unsigned32(1..512)
    MAX-ACCESS  read-write
    STATUS      current
    DESCRIPTION
            "The number of entries in traceroute database."
    DEFVAL { 100 }
    ::= { rcCfmBridge 5 }

rcCfmBridgeTracerouteCacheClear        OBJECT-TYPE
	SYNTAX      TruthValue
    MAX-ACCESS  read-write
    STATUS      current
    DESCRIPTION
            "Clear the entries in traceroute database"   
    DEFVAL{false}
    ::= { rcCfmBridge 6 }    
    
rcCfmBridgeTrapConfig                  OBJECT-TYPE
	SYNTAX      Dot1agCfmLowestAlarmPri
    MAX-ACCESS  read-write
    STATUS      deprecated
    DESCRIPTION
            "An integer value specifying the lowest priority
             defect that is allowed to generate fault alarm. 
             It is similar to dot1agCfmMepLowPrDef, but the 
             difference is that this mib is used for bridge 
             and the latter is used for a mep. When this mib 
             is set, all meps configured in the bridge are 
             configured."   
    DEFVAL {noXcon}
    ::= { rcCfmBridge 7 }     
    
rcCfmBridgeRmepAgeTime                  OBJECT-TYPE
	SYNTAX      Unsigned32 (1..65535)
    MAX-ACCESS  read-write         
    STATUS      current
    DESCRIPTION
            "An integer value specifying the age time of remote
             MEP that is dynamic."  
    DEFVAL {100}      
    ::= { rcCfmBridge 8 }  
       
rcCfmBridgeMode                  OBJECT-TYPE
	SYNTAX   INTEGER{
                           multicast(1),
                           unicast(2)                    
                    } 
    MAX-ACCESS  read-write         
    STATUS      current
    DESCRIPTION
            "An integer value specifying the mode of the sending of ccm
            multicast(1)-idendify the mode of sending CCM by multicast,
            unicast(2)-idendify the mode of sending CCM by multicast." 
    DEFVAL {unicast}
    ::= { rcCfmBridge 9 }    
    

rcCfmLinkVlanList OBJECT-TYPE
    SYNTAX      OCTET STRING (SIZE (512))  
    MAX-ACCESS  read-create
    STATUS      current
    DESCRIPTION
       "The mapping VLANs with which the Maintenance Association is
        associated, or 0 if the MA is not attached to any VID."
    ::= { rcCfmBridge 10 }

       
-- CFM Interface Table   

rcCfmIfTable OBJECT-TYPE
    SYNTAX      SEQUENCE OF RcCfmIfEntry
    MAX-ACCESS  not-accessible
    STATUS      current
    DESCRIPTION
        "CFM Interface table"
    ::= { rcCfm 2 }

rcCfmIfEntry   OBJECT-TYPE
    SYNTAX      RcCfmIfEntry
    MAX-ACCESS  not-accessible
    STATUS      current
    DESCRIPTION
        "An entry in the rcCfmIfTable. It contains
        CFM status in each interface port."
	INDEX        { rcCfmIfIndex }    
    ::={ rcCfmIfTable 1 }
    
    RcCfmIfEntry ::= SEQUENCE {
    rcCfmIfIndex					InterfaceIndex,
	rcCfmIfAdminCfm					EnableVar,
	rcCfmIfMipLevel					Dot1agCfmMDLevelOrNone		
}

rcCfmIfIndex        OBJECT-TYPE
	SYNTAX      InterfaceIndex
    MAX-ACCESS  not-accessible
    STATUS      current
    DESCRIPTION
            "This object represents the  Bridge Port or
             aggregated port on which MEPs or MHFs might
             be configured." 
	::= { rcCfmIfEntry 1 }
	
rcCfmIfAdminCfm        OBJECT-TYPE
	SYNTAX      EnableVar
    MAX-ACCESS  read-write
    STATUS      current
    DESCRIPTION
            "The administrative value of the interface.
            A value of enable(1) indicates that interface
            should enable CFM. disable(2) indicates that 
            interface should disable CFM."   
    DEFVAL{enable}  
    ::= { rcCfmIfEntry 2 }    
     
rcCfmIfMipLevel        OBJECT-TYPE
	SYNTAX      Dot1agCfmMDLevelOrNone
    MAX-ACCESS  read-write
    STATUS      deprecated
    DESCRIPTION
            "The level on which the mip is configured. 
            The value of -1 indicates that no mip is configured 
            on the port or you must delete the mip configured on the port.
            The other value (0-7) indicates that a mip need to 
            be configured at this level on the port."
    ::= { rcCfmIfEntry 3 }    
    
-- CFM MD TABLE      
rcCfmMdTable OBJECT-TYPE
    SYNTAX      SEQUENCE OF RcCfmMdEntry
    MAX-ACCESS  not-accessible
    STATUS      current
    DESCRIPTION
        "CFM Md Table"  
        
    ::= { rcCfm 3 }

rcCfmMdEntry        OBJECT-TYPE
	SYNTAX      RcCfmMdEntry
    MAX-ACCESS  not-accessible
    STATUS      current
    DESCRIPTION
        "An entry in the rcCfmMdTable. It contains
         clearing remote MEP database operation."
    INDEX	{ dot1agCfmMdIndex }
    ::= { rcCfmMdTable 1 } 
       
    RcCfmMdEntry ::= SEQUENCE {
	rcCfmMdCcmRMpClear					TruthValue		
}

rcCfmMdCcmRMpClear          OBJECT-TYPE
	SYNTAX      TruthValue
    MAX-ACCESS  read-write
    STATUS      current
    DESCRIPTION
            "Clear Remote MP in CC database" 
    DEFVAL{false}
    ::= { rcCfmMdEntry 1 }
    
--CFM Error CCM Table    
rcCfmErrorCcmTable OBJECT-TYPE
    SYNTAX      SEQUENCE OF RcCfmErrorCcmEntry
    MAX-ACCESS  not-accessible
    STATUS      current
    DESCRIPTION
        "CFM Error CCM Table "  
        
    ::= { rcCfm 4 }
    
rcCfmErrorCcmEntry          OBJECT-TYPE
	SYNTAX      RcCfmErrorCcmEntry
    MAX-ACCESS  not-accessible
    STATUS      current
    DESCRIPTION
        "An entry in the rcCfmIfTable. It contains
        error CCM data received. 
        "
    INDEX		{ dot1agCfmMdIndex,
                  dot1agCfmMaIndex,
                  rcCfmErrorCcmRMepId,
                  rcCfmErrorCcmIndex
          }
    ::= { rcCfmErrorCcmTable 1 }  

RcCfmErrorCcmEntry ::= SEQUENCE { 
    rcCfmErrorCcmRMepId                 Dot1agCfmMepId,
	rcCfmErrorCcmIndex					Unsigned32 (0..4294967295),
	rcCfmErrorCcmLevel					Dot1agCfmMDLevel,
	rcCfmErrorCcmVlan					VlanIdOrNone ,
	rcCfmErrorCcmRecvMdName				OCTET STRING (SIZE(1..16)),
	rcCfmErrorCcmMaid					OCTET STRING (SIZE(1..44)),
	rcCfmErrorCcmMacAddress				MacAddress,
	rcCfmErrorCcmErrorType				Dot1agCfmMepDefects,
	rcCfmErrorCcmHoldTime               Unsigned32 (0..4294967295),
	rcCfmErrorCcmClear					TruthValue
}                  

rcCfmErrorCcmRMepId          		OBJECT-TYPE
	SYNTAX      Dot1agCfmMepId
    MAX-ACCESS  not-accessible
    STATUS      current
    DESCRIPTION
            "The index to the Error CCM table. Maintenance association End Point Identifier field of the 
            received CCM PDU that has some defect."
	::= { rcCfmErrorCcmEntry 1 }

   
rcCfmErrorCcmIndex          		OBJECT-TYPE
	SYNTAX      Unsigned32 (0..4294967295)
    MAX-ACCESS  not-accessible
    STATUS      current
    DESCRIPTION
            "The index to the Error CCM table. The index value
             should keep increasing up to the time that they wrap
             around. This is to facilitate access control based on OID."
	::= { rcCfmErrorCcmEntry 2 }
	
rcCfmErrorCcmLevel          		OBJECT-TYPE
	SYNTAX      Dot1agCfmMDLevel
	MAX-ACCESS  read-only
    STATUS      current
    DESCRIPTION
            "Maintenance Domain Level field of the received CCM PDU
             that has some defect."
	::= { rcCfmErrorCcmEntry 3 }

rcCfmErrorCcmVlan           		OBJECT-TYPE
	SYNTAX      VlanIdOrNone
	MAX-ACCESS  read-only
    STATUS      current
    DESCRIPTION
            "The VLAN ID associated with the MA Name field of the 
            received CCM PDU that has some defect."
	::= { rcCfmErrorCcmEntry 4 }

rcCfmErrorCcmRecvMdName     		OBJECT-TYPE
	SYNTAX      OCTET STRING (SIZE(1..16))
	MAX-ACCESS  read-only
    STATUS      current
    DESCRIPTION
            "The name of the domain in which the error ccm is received"
	::= { rcCfmErrorCcmEntry 5 }

rcCfmErrorCcmMaid           		OBJECT-TYPE
	SYNTAX      OCTET STRING (SIZE(1..44))
	MAX-ACCESS  read-only
    STATUS      current
    DESCRIPTION
            "Maintenance Domain name and Maintenance Association name 
            conveyed in the received CCM PDU that has some defect constitute
             MAID and the domain name and association name using  
             conjunctive character '-', for example, the domain name 
             is 'customer' and the association name is 'vlan100', so the 
             maid which is displayed to users is 'customer-vlan100'."
	::= { rcCfmErrorCcmEntry 6 }

rcCfmErrorCcmMacAddress          	OBJECT-TYPE
	SYNTAX      MacAddress
	MAX-ACCESS  read-only
    STATUS      current
    DESCRIPTION
            "Source MAC address field of the received CCM PDU that has 
            some defect."
	::= { rcCfmErrorCcmEntry 7 }

rcCfmErrorCcmErrorType             	OBJECT-TYPE
	SYNTAX      Dot1agCfmMepDefects
	MAX-ACCESS  read-only
    STATUS      current
    DESCRIPTION
            "Error type of defects in the received CCM PDU."
	::= { rcCfmErrorCcmEntry 8 } 
	   
rcCfmErrorCcmHoldTime        	OBJECT-TYPE
	SYNTAX      Unsigned32 (0..4294967295)
	MAX-ACCESS  read-only
    STATUS      current
    DESCRIPTION
            "Storage time (s) of defects in the ERROR CCM DB."
	::= { rcCfmErrorCcmEntry 9 }  

rcCfmErrorCcmClear                 	OBJECT-TYPE 
	SYNTAX      TruthValue
	MAX-ACCESS  read-write
    STATUS      current
    DESCRIPTION
            "Clear fault CCM in CC database"
	::= { rcCfmErrorCcmEntry 10 }  

--CFM Ltm Db Table
rcCfmLtmDbTable 					OBJECT-TYPE
    SYNTAX      SEQUENCE OF RcCfmLtmDbEntry
    MAX-ACCESS  not-accessible
    STATUS      current
    DESCRIPTION
        "CFM Ltm Database Table "  
        
    ::= { rcCfm 5 }
    
rcCfmLtmDbEntry          			OBJECT-TYPE
	SYNTAX      RcCfmLtmDbEntry
    MAX-ACCESS  not-accessible
    STATUS      current
    DESCRIPTION
        "An entry in the rcCfmLtmDbTable.  
        "
    INDEX	{ dot1agCfmMdIndex, 
    		  dot1agCfmMaIndex,
    		  dot1agCfmMepIdentifier, 
    		  rcCfmLtmDbTransactionId 
    		}
    ::= { rcCfmLtmDbTable 1 }   
    
RcCfmLtmDbEntry ::= SEQUENCE {
	rcCfmLtmDbTransactionId				Unsigned32 (0..4294967295), 
	rcCfmLtmDbTargetMacAddress			MacAddress
}                    

rcCfmLtmDbTransactionId          	OBJECT-TYPE 
	SYNTAX      Unsigned32 (0..4294967295)
	MAX-ACCESS  not-accessible
    STATUS      current
    DESCRIPTION
            "The index to the Ltm Db table. This is to facilitate access control based on OID."
	::= { rcCfmLtmDbEntry 1 }  
   
rcCfmLtmDbTargetMacAddress          OBJECT-TYPE 
	SYNTAX      MacAddress 
	MAX-ACCESS  read-only
    STATUS      current
    DESCRIPTION
            "Target Mac Address conveyed in the LTM PDU which has been sent."
	::= { rcCfmLtmDbEntry 2 }  
           
--CFM Mep Db Extended Table
rcCfmMepDbExTable 					OBJECT-TYPE
    SYNTAX      SEQUENCE OF RcCfmMepDbExEntry
    MAX-ACCESS  not-accessible
    STATUS      current
    DESCRIPTION
        "CFM MEP Datebase Extended Table "  
        
    ::= { rcCfm 6 }
    
rcCfmMepDbExEntry          			OBJECT-TYPE
	SYNTAX      RcCfmMepDbExEntry
    MAX-ACCESS  not-accessible
    STATUS      current
    DESCRIPTION
        "An entry in the rcCfmMepDbExTable. "
    INDEX	{ dot1agCfmMdIndex, 
    		  dot1agCfmMaIndex,
    		  dot1agCfmMepIdentifier, 
    		  dot1agCfmMepDbRMepIdentifier 
    		}
    ::= { rcCfmMepDbExTable 1 } 
    
    RcCfmMepDbExEntry ::= SEQUENCE 
    {                                             
		rcCfmMepDbExEntryHoldTime				Unsigned32 (0..4294967295)
	} 
	                   
rcCfmMepDbExEntryHoldTime          OBJECT-TYPE 
	SYNTAX      Unsigned32 (0..4294967295) 
	MAX-ACCESS  read-only
    STATUS      current
    DESCRIPTION
            "The time of the remote MEP's information which has been storaged 
            in MEP CCM Database."
	::= { rcCfmMepDbExEntry 1 }      

-- CFM MA CC enabled Table	
rcCfmMaCciEnableTable 					OBJECT-TYPE
    SYNTAX      SEQUENCE OF RcCfmMaCciEnableEntry
    MAX-ACCESS  not-accessible
    STATUS      deprecated
    DESCRIPTION
        "CFM MEP Datebase Extended Table "  
        
    ::= { rcCfm 7 }
    
rcCfmMaCciEnableEntry          			OBJECT-TYPE
	SYNTAX      RcCfmMaCciEnableEntry
    MAX-ACCESS  not-accessible
    STATUS      deprecated
    DESCRIPTION
        "An entry in the rcCfmMepDbExTable. "
    INDEX	{ 
    		     rcCfmMaMdLevel,
    		     rcCfmMaMaVlanId
    		}
    ::= { rcCfmMaCciEnableTable 1 } 
    
    RcCfmMaCciEnableEntry ::= SEQUENCE 
    {                                             
		rcCfmMaMdLevel				Dot1agCfmMDLevel,
		rcCfmMaMaVlanId				VlanIdOrNone,
		rcCfmMaCciEnabled			TruthValue 	} 
	                   
rcCfmMaMdLevel          OBJECT-TYPE 
	SYNTAX      Dot1agCfmMDLevel 
	MAX-ACCESS  not-accessible
    STATUS      deprecated
    DESCRIPTION
            "Level of The Maintenance Domain that the MA belong to"
	::= { rcCfmMaCciEnableEntry 1 }   
	
rcCfmMaMaVlanId          OBJECT-TYPE 
	SYNTAX      VlanIdOrNone 
	MAX-ACCESS  not-accessible
    STATUS      deprecated
    DESCRIPTION
            "The Primary VLAN ID with which the Maintenance Association is associated"
	::= { rcCfmMaCciEnableEntry 2 }   
	
rcCfmMaCciEnabled          OBJECT-TYPE 
	SYNTAX      TruthValue 
	MAX-ACCESS  read-write
    STATUS      deprecated
    DESCRIPTION
            "If set to true, All MEP belong to the MA will generate CCM messages."
	::= { rcCfmMaCciEnableEntry 3 }   

--CFM Mep Extended Table
rcCfmMepExTable 					OBJECT-TYPE
    SYNTAX      SEQUENCE OF RcCfmMepExEntry
    MAX-ACCESS  not-accessible
    STATUS      current
    DESCRIPTION
        "CFM MEP Extended Table "  
        
    ::= { rcCfm 8 }
    
rcCfmMepExEntry          			OBJECT-TYPE
	SYNTAX      RcCfmMepExEntry
    MAX-ACCESS  not-accessible
    STATUS      current
    DESCRIPTION
        "An entry in the rcCfmMepTable. "
    INDEX	{ dot1agCfmMdIndex, 
    		  dot1agCfmMaIndex,
    		  dot1agCfmMepIdentifier 
    		}
    ::= { rcCfmMepExTable 1 } 
    
    RcCfmMepExEntry ::= SEQUENCE 
    {                                             
		rcCfmMepExLbrTimeoutNum				Unsigned32 (0..4294967295),
		rcCfmMepExTransmitLbmDataTlvLen     Unsigned32 (1..1484),
		rcCfmMepExLckAdmin EnableVar,
		rcCfmMaExAisSuppressStatus INTEGER,
		rcCfmMaExAisSuppressAdmin EnableVar,
		rcCfmMepExPduPriority INTEGER,
		rcCfmMepExPmAdmin EnableVar,
		rcCfmMepExRdiAdmin EnableVar
	} 
	                   
rcCfmMepExLbrTimeoutNum          OBJECT-TYPE 
	SYNTAX      Unsigned32 (0..4294967295) 
	MAX-ACCESS  read-only
    STATUS      current
    DESCRIPTION
            "The total number of Lbrs revieving timeout. "    
    DEFVAL{0}
	::= { rcCfmMepExEntry 1 }      

rcCfmMepExTransmitLbmDataTlvLen          OBJECT-TYPE 
	SYNTAX      Unsigned32 (1..1484) 
	MAX-ACCESS  read-write
    STATUS      current
    DESCRIPTION
            "The length of Lbm data tlv . "   
    DEFVAL{1}
	::= { rcCfmMepExEntry 2 }      

rcCfmMepExLckAdmin          OBJECT-TYPE 
	SYNTAX      EnableVar 
	MAX-ACCESS  read-write
    STATUS      current
    DESCRIPTION
            "If set rcCfmMepExLckAdmin_enabled(1),The mep 
             can transmit lck packet when starting the lck 
             functionIf set rcCfmMepExLckAdmin_diabled (2),
             The mep must not transmit lck packet whatever 
             starting or stopping the lck function.
            " 
    DEFVAL{disable}
	::= { rcCfmMepExEntry 3 } 
	
rcCfmMaExAisSuppressStatus          OBJECT-TYPE 
	SYNTAX      INTEGER 
	MAX-ACCESS  read-only
    STATUS      current
    DESCRIPTION
            "It is read-only. When receiving the ais or lck packet, 
             the value is rcCfmMaExAisSuppressStatus_WAITING (1). 
             And when the fault is detected, the value is 
             rcCfmMaExAisSuppressStatus_SUPPRESSED (2). 
             If not receiving the ais or lck pakcet within 
             3.5 multiple periods, the value is rcCfmMaExAisSuppressStatus_NONE (3).
             If the status is not rcCfmMaExAisSuppressStatus_NONE (1), 
             will not sending trap even if have any error.
            "
     DEFVAL{3}
	::= { rcCfmMepExEntry 4 } 
	
rcCfmMaExAisSuppressAdmin          OBJECT-TYPE 
	SYNTAX      EnableVar 
	MAX-ACCESS  read-write
    STATUS      current
    DESCRIPTION
            "If set rcCfmMaExAisSuppressAdmin_enabled (1), The mep can suppress alarm trap. 
             If set rcCfmMaExAisSuppressAdmin_diabled (2), The mep must not suppress alarm trap.
            "    
    DEFVAL {enable}
	::= { rcCfmMepExEntry 5 } 	

rcCfmMepExPduPriority          OBJECT-TYPE 
	SYNTAX      INTEGER (0..7)
	MAX-ACCESS  read-write
    STATUS      current
    DESCRIPTION
            "The priority of CFM pdu"    
    DEFVAL {7}
	::= { rcCfmMepExEntry 6 }
	
rcCfmMepExPmAdmin          OBJECT-TYPE 
	SYNTAX      EnableVar 
	MAX-ACCESS  read-write
    STATUS      current
    DESCRIPTION
            "If set rcCfmMepExPmAdmin _enabled (1), The mep can support DM/LM measurement.
             If set rcCfmMepExPmAdmin _disabled (2), The mep must not support DM/LM measurement.
            "    
    DEFVAL {disable}
	::= { rcCfmMepExEntry 7 }     
	
rcCfmMepExRdiAdmin          OBJECT-TYPE 
	SYNTAX      EnableVar 
	MAX-ACCESS  read-write
    STATUS      current
    DESCRIPTION
            "If set rcCfmMepExRdiAdmin _enabled (1), when the associated port of mep is down，it can support to add RDI flag in the CCM.
             If set rcCfmMepExRdiAdmin _disabled (2), The mep must not support the RDI flag.
            "    
    DEFVAL {disable}
	::= { rcCfmMepExEntry 8 }  
			 	
--CFM Mep List Extended Table
rcCfmMaMepListExTable 					OBJECT-TYPE
    SYNTAX      SEQUENCE OF RcCfmMaMepListExEntry
    MAX-ACCESS  not-accessible
    STATUS      current
    DESCRIPTION
        "CFM Ma MEP List Extended Table "  
        
    ::= { rcCfm 9 }
    
rcCfmMaMepListExEntry          			OBJECT-TYPE
	SYNTAX      RcCfmMaMepListExEntry
    MAX-ACCESS  not-accessible
    STATUS      current
    DESCRIPTION
        "An entry in the rcCfmMepTable. "
    INDEX	{ dot1agCfmMdIndex, 
    		  dot1agCfmMaIndex,
    		  dot1agCfmMepIdentifier 
    		}
    ::= { rcCfmMaMepListExTable 1 } 
    
    RcCfmMaMepListExEntry ::= SEQUENCE 
    {       
		rcCfmMaMepListType                  INTEGER,
		rcCfmMaMepListMacAddress		    MacAddress,      
		rcCfmMaMepListIfIndex		        InterfaceIndex
	} 
	                   
rcCfmMaMepListType          OBJECT-TYPE 
	SYNTAX      INTEGER{
                           local(1),
                           static-remote(2),
                           dynamic-remote(3)
                       } 
	MAX-ACCESS  read-write
    STATUS      deprecated
    DESCRIPTION
            "mep type in the mep list."
	::= { rcCfmMaMepListExEntry 1 }
	 
rcCfmMaMepListMacAddress          OBJECT-TYPE 
	SYNTAX      MacAddress
	MAX-ACCESS  read-only
    STATUS      current
    DESCRIPTION
            "mep mac address in mep list. "
	::= { rcCfmMaMepListExEntry 2 }      

rcCfmMaMepListIfIndex          OBJECT-TYPE 
	SYNTAX      InterfaceIndex
	MAX-ACCESS  read-write
    STATUS      current
    DESCRIPTION
            "interface index for static remote mep in port mode. "
	::= { rcCfmMaMepListExEntry 3 }      
	
--CFM MaNet Extended Table
rcCfmMaNetExTable 					OBJECT-TYPE
    SYNTAX      SEQUENCE OF RcCfmMaNetExEntry
    MAX-ACCESS  not-accessible
    STATUS      current
    DESCRIPTION
        "CFM Ma net Extended Table "  
        
    ::= { rcCfm 10 }
    
rcCfmMaNetExEntry          			OBJECT-TYPE
	SYNTAX      RcCfmMaNetExEntry
    MAX-ACCESS  not-accessible
    STATUS      current
    DESCRIPTION
        "An entry in the rcCfmMaNetExTable. "
    INDEX	{ dot1agCfmMdIndex, 
    		  dot1agCfmMaIndex
    		}
    ::= { rcCfmMaNetExTable 1 } 
    
    RcCfmMaNetExEntry ::= SEQUENCE 
    {       
		rcCfmMaNetRemoteMepLearnEnabled                  TruthValue,
		rcCfmMaNetCostumerVlan                           VlanIdOrNone,
		rcCfmMaNetPduPriority                            Unsigned32 (0..7), 
		rcCfmMaNetRemoteMepLearnActive                   TruthValue,
		rcCfmMaNetCcCheckEnabled                         TruthValue                               
	} 
	                   
rcCfmMaNetRemoteMepLearnEnabled          OBJECT-TYPE 
	SYNTAX      TruthValue
	MAX-ACCESS  read-write
    STATUS      deprecated
    DESCRIPTION
            "status of remote mep learning. the value of true indicates that 
            mep in this ma can recieve unknown remote mep ccm pdu; the value 
            of false indicates that mep in this ma can not recieve unknown 
            remote mep ccm pdu. "
	::= { rcCfmMaNetExEntry 1 }
	
rcCfmMaNetCostumerVlan          OBJECT-TYPE 
	SYNTAX      VlanIdOrNone
	MAX-ACCESS  read-write
    STATUS      current
    DESCRIPTION
            "costumer vlan in oam pdu. the value of 0 indicates oam Pdu transmited 
            without costumer vlan."    
    DEFVAL{0}            
	::= { rcCfmMaNetExEntry 2 }
	
rcCfmMaNetPduPriority          OBJECT-TYPE 
	SYNTAX      Unsigned32 (0..7)
	MAX-ACCESS  read-write
    STATUS      current
    DESCRIPTION
            "The pdu Priority. default priority is 6."    
    DEFVAL{6} 
   	::= { rcCfmMaNetExEntry 3 }
	
rcCfmMaNetRemoteMepLearnActive	 OBJECT-TYPE               
	SYNTAX      TruthValue
	MAX-ACCESS  read-write
    STATUS      current
    DESCRIPTION
            "Remote MEP Learn function is enabled."     
    DEFVAL{false} 
   	::= { rcCfmMaNetExEntry 4 }
	 
rcCfmMaNetCcCheckEnabled          OBJECT-TYPE 
	SYNTAX      TruthValue
	MAX-ACCESS  read-write
    STATUS      current
    DESCRIPTION
            "check remote mep mpid in CCM."  
    DEFVAL{false} 
	::= { rcCfmMaNetExEntry 5 } 
	
--CFM Pm Table
rcCfmPMTable 					OBJECT-TYPE
    SYNTAX      SEQUENCE OF RcCfmPMEntry
    MAX-ACCESS  not-accessible
    STATUS      deprecated
    DESCRIPTION
        "CFM Performance monitor Table "  
        
    ::= { rcCfm 11 }
    
rcCfmPMEntry          			OBJECT-TYPE
	SYNTAX      RcCfmPMEntry
    MAX-ACCESS  not-accessible
    STATUS      deprecated
    DESCRIPTION
        "An entry in the rcCfmPMTable. "
    INDEX	{ 
              dot1agCfmMdIndex, 
    		  dot1agCfmMaIndex,
    		  dot1agCfmMepIdentifier,
    		  dot1agCfmMepDbRMepIdentifier
    		}
    ::= { rcCfmPMTable 1 } 
    
    RcCfmPMEntry ::= SEQUENCE 
    {       
		rcCfmPMEnabled                  TruthValue,
		rcCfmPMDmmTxInterval            INTEGER,
		rcCfmPMDelayObjective           Unsigned32 (0..1000),
		rcCfmPMDVObjective              Unsigned32 (0..1000),
		rcCfmPMFLRRisingThreshold       INTEGER,
		rcCfmPMFLRFallingThreshold      INTEGER,
		rcCfmPMDelayRisingThreshold     INTEGER,
		rcCfmPMDelayFallingThreshold    INTEGER,
		rcCfmPMDVRisingThreshold        INTEGER,
		rcCfmPMDVFallingThreshold       INTEGER,
		rcCfmPMStatiticsClear           INTEGER,
		rcCfmPMTrapSendEnable           TruthValue,
		rcCfmPMThroughputTimeout        Unsigned32(2..30),
		rcCfmPMThroughputObject         Unsigned32 (125..1000000),
		rcCfmPMThroughputPduLength      INTEGER,
		rcCfmPMThroughputEnable         TruthValue,
		rcCfmPMRowStatus                RowStatus
	}
	
rcCfmPMEnabled          OBJECT-TYPE 
	SYNTAX      TruthValue
	MAX-ACCESS  read-write
    STATUS      deprecated
    DESCRIPTION
            "performace monitor function enable "
	::= { rcCfmPMEntry 1 } 
	
rcCfmPMDmmTxInterval          OBJECT-TYPE 
	SYNTAX      INTEGER{
                  intervalInvalid   (0),
                  interval300Hz     (1),
                  interval10ms      (2),
                  interval100ms     (3),
                  interval1s        (4),
                  interval10s       (5),
                  interval1min      (6),
                  interval10min     (7)
	            }
	MAX-ACCESS  read-only
    STATUS      deprecated
    DESCRIPTION
            "DMM pdu transmit period. "
	::= { rcCfmPMEntry 2 }   
	
rcCfmPMDelayObjective          OBJECT-TYPE 
	SYNTAX      Unsigned32 (0..1000)
	MAX-ACCESS  read-write
    STATUS      deprecated
    DESCRIPTION
            "PM delay object."
	::= { rcCfmPMEntry 3 }
	 
rcCfmPMDVObjective          OBJECT-TYPE 
	SYNTAX      Unsigned32 (0..1000)
	MAX-ACCESS  read-write
    STATUS      deprecated
    DESCRIPTION
            "PM delay variation object. "
	::= { rcCfmPMEntry 4 }
                             
rcCfmPMFLRRisingThreshold          OBJECT-TYPE 
	SYNTAX      INTEGER{
	            threshold0           (0),
	            threshold1PerSouthend(1),
	            threshold2PerSouthend(2),
	            threshold5PerSouthend(3),
	            threshold1PerHundrud(4),
	            threshold2PerHundrud(5),
	            threshold5PerHundrud(6),
	            threshold1(7)
	            }
	MAX-ACCESS  read-write
    STATUS      deprecated
    DESCRIPTION
            "frame loss ratio rising threshold, if 15 minutes 
             statistics above this value, a notification will be send. "
	::= { rcCfmPMEntry 5 }
	
rcCfmPMFLRFallingThreshold          OBJECT-TYPE 
	SYNTAX      INTEGER{
	            threshold0           (0),
	            threshold1PerSouthend(1),
	            threshold2PerSouthend(2),
	            threshold5PerSouthend(3),
	            threshold1PerHundrud(4),
	            threshold2PerHundrud(5),
	            threshold5PerHundrud(6),
	            threshold1(7)
	            }
	MAX-ACCESS  read-write
    STATUS      deprecated
    DESCRIPTION
            "frame loss ratio falling threshold, if 15 minutes 
             statistics below this value, a notification will be send."
	::= { rcCfmPMEntry 6 }
	
rcCfmPMDelayRisingThreshold          OBJECT-TYPE 
	SYNTAX      INTEGER{
	            threshold0           (0),
	            threshold1PerSouthend(1),
	            threshold2PerSouthend(2),
	            threshold5PerSouthend(3),
	            threshold1PerHundrud(4),
	            threshold2PerHundrud(5),
	            threshold5PerHundrud(6),
	            threshold1(7)
	            }
	MAX-ACCESS  read-write
    STATUS      deprecated
    DESCRIPTION
            "delay rising threshold, if 15 minutes 
             statistics above this value, a notification will be send."
	::= { rcCfmPMEntry 7 }

rcCfmPMDelayFallingThreshold          OBJECT-TYPE 
	SYNTAX      INTEGER{
	            threshold0           (0),
	            threshold1PerSouthend(1),
	            threshold2PerSouthend(2),
	            threshold5PerSouthend(3),
	            threshold1PerHundrud(4),
	            threshold2PerHundrud(5),
	            threshold5PerHundrud(6),
	            threshold1(7)
	            }
	MAX-ACCESS  read-write
    STATUS      deprecated
    DESCRIPTION
            "delay falling threshold, if 15 minutes 
             statistics below this value, a notification will be send."
	::= { rcCfmPMEntry 8 } 

rcCfmPMDVRisingThreshold          OBJECT-TYPE 
	SYNTAX      INTEGER{
	            threshold0           (0),
	            threshold1PerSouthend(1),
	            threshold2PerSouthend(2),
	            threshold5PerSouthend(3),
	            threshold1PerHundrud(4),
	            threshold2PerHundrud(5),
	            threshold5PerHundrud(6),
	            threshold1(7)
	            }
	MAX-ACCESS  read-write
    STATUS      deprecated
    DESCRIPTION
            "delay variation rising threshold, if 15 minutes 
             statistics above this value, a notification will be send."
	::= { rcCfmPMEntry 9 } 
	
rcCfmPMDVFallingThreshold          OBJECT-TYPE 
	SYNTAX      INTEGER{
	            threshold0           (0),
	            threshold1PerSouthend(1),
	            threshold2PerSouthend(2),
	            threshold5PerSouthend(3),
	            threshold1PerHundrud(4),
	            threshold2PerHundrud(5),
	            threshold5PerHundrud(6),
	            threshold1(7)
	            }
	MAX-ACCESS  read-write
    STATUS      deprecated
    DESCRIPTION
            "delay variation falling threshold, if 15 minutes 
             statistics below this value, a notification will be send. "
	::= { rcCfmPMEntry 10 }
	
rcCfmPMStatiticsClear          OBJECT-TYPE 
	SYNTAX      INTEGER{
	            all              (0),
	            frame-loss-ratio (1),
	            delay            (2),
	            delay-variation  (3)
	            }
	MAX-ACCESS  read-write
    STATUS      deprecated
    DESCRIPTION
            "clear performance monitor statistics in the service. "
	::= { rcCfmPMEntry 11 }

rcCfmPMTrapSendEnable          OBJECT-TYPE 
	SYNTAX      TruthValue
	MAX-ACCESS  read-write
    STATUS      deprecated
    DESCRIPTION
            "performance monitor notification enable status."
	::= { rcCfmPMEntry 12 }

rcCfmPMThroughputTimeout          OBJECT-TYPE 
	SYNTAX      Unsigned32 (2..30)
	MAX-ACCESS  read-write
    STATUS      deprecated
    DESCRIPTION
            "ITU-T Y.1731 throughput(rfc2544) test timeout period, unit second."
	::= { rcCfmPMEntry 13 } 

rcCfmPMThroughputObject          OBJECT-TYPE 
	SYNTAX      Unsigned32 (125..1000000)
	MAX-ACCESS  read-write
    STATUS      deprecated
    DESCRIPTION
            "ITU-T Y.1731 throughput(rfc2544) test expected 
            Object band-wide, unit kbps."
	::= { rcCfmPMEntry 14 } 

rcCfmPMThroughputPduLength          OBJECT-TYPE 
	SYNTAX      INTEGER{
	            length64      (0),
	            length128     (1),
	            length256     (2),
	            length512     (3),
	            length1024    (4),
	            length1280    (5),
	            length1518    (6)
	            }
	MAX-ACCESS  read-write
    STATUS      deprecated
    DESCRIPTION
            "ITU-T Y.1731 throughput(rfc2544) test pdu length."
	::= { rcCfmPMEntry 15 }

rcCfmPMThroughputEnable          OBJECT-TYPE 
	SYNTAX      TruthValue
	MAX-ACCESS  read-write
    STATUS      deprecated
    DESCRIPTION
            "ITU-T Y.1731 throughput(rfc2544) test enable."
	::= { rcCfmPMEntry 16 }

rcCfmPMRowStatus          OBJECT-TYPE 
	SYNTAX      RowStatus
	MAX-ACCESS  read-write
    STATUS      deprecated
    DESCRIPTION
            "the row status of rcCfmPMTable. "
	::= { rcCfmPMEntry 17 }

--CFM Pm frame-loss-ratio total statistic Table
rcCfmPMFLRTotalTable 					OBJECT-TYPE
    SYNTAX      SEQUENCE OF RcCfmPMFLRTotalEntry
    MAX-ACCESS  not-accessible
    STATUS      deprecated
    DESCRIPTION
        "CFM Performance monitor Table "  
        
    ::= { rcCfm 12 }
    
rcCfmPMFLRTotalEntry          		OBJECT-TYPE
	SYNTAX      RcCfmPMFLRTotalEntry
    MAX-ACCESS  not-accessible
    STATUS      deprecated
    DESCRIPTION
        "An entry in the rcCfmPMTable. "
    INDEX	{ 
              dot1agCfmMdIndex, 
    		  dot1agCfmMaIndex,
    		  dot1agCfmMepIdentifier
    		}
    ::= { rcCfmPMFLRTotalTable 1 } 
    
    RcCfmPMFLRTotalEntry ::= SEQUENCE 
    {
        rcCfmPMFLRTotalElapsedTime              Unsigned32,
        rcCfmPMFLRTotalFarEndTxCounter          Unsigned32,
        rcCfmPMFLRTotalFarEndLostCounter        Unsigned32,
        rcCfmPMFLRTotalFarEndLossRatio          Unsigned32(0..1000),
        rcCfmPMFLRTotalFarEndUnaviableSecond    Unsigned32,
        rcCfmPMFLRTotalNearEndTxCounter         Unsigned32,
        rcCfmPMFLRTotalNearEndLostCounter       Unsigned32,
        rcCfmPMFLRTotalNearEndLossRatio         Unsigned32(0..1000),
        rcCfmPMFLRTotalNearEndUnaviableSecond   Unsigned32
    } 
          
rcCfmPMFLRTotalElapsedTime          OBJECT-TYPE 
	SYNTAX      Unsigned32
	MAX-ACCESS  read-only
    STATUS      deprecated
    DESCRIPTION
            "total second passed since performance monitor enabled."
	::= { rcCfmPMFLRTotalEntry 1 } 
	
rcCfmPMFLRTotalFarEndTxCounter          OBJECT-TYPE 
	SYNTAX      Unsigned32
	MAX-ACCESS  read-only
    STATUS      deprecated
    DESCRIPTION
            "total far end frames transmited since performance monitor enabled."
	::= { rcCfmPMFLRTotalEntry 2 }
	
rcCfmPMFLRTotalFarEndLostCounter          OBJECT-TYPE 
	SYNTAX      Unsigned32
	MAX-ACCESS  read-only
    STATUS      deprecated
    DESCRIPTION
            "total far end frames lost since performance monitor enabled."
	::= { rcCfmPMFLRTotalEntry 3 } 
	
rcCfmPMFLRTotalFarEndLossRatio          OBJECT-TYPE 
	SYNTAX      Unsigned32(0..1000)
	MAX-ACCESS  read-only
    STATUS      deprecated
    DESCRIPTION
            "total far end frame lost ratio since performance monitor enabled."
	::= { rcCfmPMFLRTotalEntry 4 }
	 
rcCfmPMFLRTotalFarEndUnaviableSecond          OBJECT-TYPE 
	SYNTAX      Unsigned32
	MAX-ACCESS  read-only
    STATUS      deprecated
    DESCRIPTION
            "total far end unaviable second since performance monitor enabled."
	::= { rcCfmPMFLRTotalEntry 5 }
		
rcCfmPMFLRTotalNearEndTxCounter          OBJECT-TYPE 
	SYNTAX      Unsigned32
	MAX-ACCESS  read-only
    STATUS      deprecated
    DESCRIPTION
            "total near end frames transmited since performance monitor enabled. "
	::= { rcCfmPMFLRTotalEntry 6 }
	
rcCfmPMFLRTotalNearEndLostCounter          OBJECT-TYPE 
	SYNTAX      Unsigned32
	MAX-ACCESS  read-only
    STATUS      deprecated
    DESCRIPTION
            "total near end frames lost since performance monitor enabled."
	::= { rcCfmPMFLRTotalEntry 7 } 
	
rcCfmPMFLRTotalNearEndLossRatio          OBJECT-TYPE 
	SYNTAX      Unsigned32(0..1000)
	MAX-ACCESS  read-only
    STATUS      deprecated
    DESCRIPTION
            "total near end frames lost ratio since performance monitor enabled."
	::= { rcCfmPMFLRTotalEntry 8 }
	 
rcCfmPMFLRTotalNearEndUnaviableSecond          OBJECT-TYPE 
	SYNTAX      Unsigned32
	MAX-ACCESS  read-only
    STATUS      deprecated
    DESCRIPTION
            "total near end unaviable seconds since performance monitor enabled."
	::= { rcCfmPMFLRTotalEntry 9 }
	
-- PM frame-loss-ratio current statistic table    
rcCfmPMFLRCurrentTable 					OBJECT-TYPE
    SYNTAX      SEQUENCE OF RcCfmPMFLRCurrentEntry
    MAX-ACCESS  not-accessible
    STATUS      deprecated
    DESCRIPTION
        "CFM Performance monitor frame loss ratio current table "  
        
    ::= { rcCfm 13 }

rcCfmPMFLRCurrentEntry          		OBJECT-TYPE
	SYNTAX      RcCfmPMFLRCurrentEntry
    MAX-ACCESS  not-accessible
    STATUS      deprecated
    DESCRIPTION
        "An entry in the rcCfmPMFLRCurrentTable. "
    INDEX	{ 
              dot1agCfmMdIndex, 
    		  dot1agCfmMaIndex,
    		  dot1agCfmMepIdentifier,
    		  rcCfmPMFLRCurrentPeriod
    		}
    ::= { rcCfmPMFLRCurrentTable 1 }
 
    RcCfmPMFLRCurrentEntry ::= SEQUENCE 
    {
        rcCfmPMFLRCurrentPeriod                     INTEGER,
        rcCfmPMFLRCurrentElapsedTime                Unsigned32,
        rcCfmPMFLRCurrentFarEndTxFrameCounter       Unsigned32,
        rcCfmPMFLRCurrentFarEndLostFrameCounter     Unsigned32,
        rcCfmPMFLRCurrentFarEndLossRatio            Unsigned32(0..1000),
        rcCfmPMFLRCurrentNearEndTxFrameCounter      Unsigned32,
        rcCfmPMFLRCurrentNearEndLostFrameCounter    Unsigned32,
        rcCfmPMFLRCurrentNearEndLossRatio           Unsigned32(0..1000)
    }
    
rcCfmPMFLRCurrentPeriod          OBJECT-TYPE 
	SYNTAX      INTEGER{
	            rcCfmPMFLRCurrentPeriod15Minutes(1),
	            rcCfmPMFLRCurrentPeriod24Hours  (2)
	            }
	MAX-ACCESS  not-accessible
    STATUS      deprecated
    DESCRIPTION
            "current period type ,15 minutes table or 24 hours table"
	::= { rcCfmPMFLRCurrentEntry 1 }

rcCfmPMFLRCurrentElapsedTime          OBJECT-TYPE 
	SYNTAX      Unsigned32
	MAX-ACCESS  read-only
    STATUS      deprecated
    DESCRIPTION
            "seconds passed in current intervla period."
	::= { rcCfmPMFLRCurrentEntry 2 } 
	
rcCfmPMFLRCurrentFarEndTxFrameCounter          OBJECT-TYPE 
	SYNTAX      Unsigned32
	MAX-ACCESS  read-only
    STATUS      deprecated
    DESCRIPTION
            "far end frames transmited in current interval. "
	::= { rcCfmPMFLRCurrentEntry 3 }
	
rcCfmPMFLRCurrentFarEndLostFrameCounter          OBJECT-TYPE 
	SYNTAX      Unsigned32
	MAX-ACCESS  read-only
    STATUS      deprecated
    DESCRIPTION
            "far end frames lost in current interval."
	::= { rcCfmPMFLRCurrentEntry 4 }
     
rcCfmPMFLRCurrentFarEndLossRatio          OBJECT-TYPE 
	SYNTAX      Unsigned32(0..1000)                                                
	MAX-ACCESS  read-only
    STATUS      deprecated
    DESCRIPTION
            "Far end frame loss ratio in current interval."
	::= { rcCfmPMFLRCurrentEntry 5 }   
	
rcCfmPMFLRCurrentNearEndTxFrameCounter          OBJECT-TYPE 
	SYNTAX      Unsigned32                                                
	MAX-ACCESS  read-only
    STATUS      deprecated
    DESCRIPTION
            "Near end frames transmited in current interval. "
	::= { rcCfmPMFLRCurrentEntry 6 }
	
rcCfmPMFLRCurrentNearEndLostFrameCounter          OBJECT-TYPE 
	SYNTAX      Unsigned32                                                
	MAX-ACCESS  read-only
    STATUS      deprecated
    DESCRIPTION
            "Near end frames lost in current interval."
	::= { rcCfmPMFLRCurrentEntry 7 }     
	
rcCfmPMFLRCurrentNearEndLossRatio          OBJECT-TYPE 
	SYNTAX      Unsigned32(0..1000)                                                
	MAX-ACCESS  read-only
    STATUS      deprecated
    DESCRIPTION
            "PDUs lost ratio from peer mep to local mep in current interval"
	::= { rcCfmPMFLRCurrentEntry 8 }
	
-- PM frame-loss-ratio interval statistic table    
rcCfmPMFLRIntervalTable 					OBJECT-TYPE
    SYNTAX      SEQUENCE OF RcCfmPMFLRIntervalEntry
    MAX-ACCESS  not-accessible
    STATUS      deprecated
    DESCRIPTION
        "CFM Performance monitor frame loss ratio interval Table "  
        
    ::= { rcCfm 14 }

rcCfmPMFLRIntervalEntry          		OBJECT-TYPE
	SYNTAX      RcCfmPMFLRIntervalEntry
    MAX-ACCESS  not-accessible
    STATUS      deprecated
    DESCRIPTION
        "An entry in the rcCfmPMFLRIntervalTable. "
    INDEX	{ 
              dot1agCfmMdIndex, 
    		  dot1agCfmMaIndex,
    		  dot1agCfmMepIdentifier,
      		  rcCfmPMFLRIntervalPeriod,
    		  rcCfmPMFLRIntervalIndex
    		}
    ::= { rcCfmPMFLRIntervalTable 1 }
 
    RcCfmPMFLRIntervalEntry ::= SEQUENCE 
    {
        rcCfmPMFLRIntervalPeriod                     INTEGER,
        rcCfmPMFLRIntervalIndex                      Unsigned32,
        rcCfmPMFLRIntervalPeerMepId                  Dot1agCfmMepId,
        rcCfmPMFLRIntervalBeginTime                  Unsigned32,
        rcCfmPMFLRIntervalFarEndTxFrameCounter       Unsigned32,
        rcCfmPMFLRIntervalFarEndLostFrameCounter     Unsigned32,
        rcCfmPMFLRIntervalFarEndLossRatio            Unsigned32(0..1000),
        rcCfmPMFLRIntervalNearEndTxFrameCounter      Unsigned32,
        rcCfmPMFLRIntervalNearEndLostFrameCounter    Unsigned32,
        rcCfmPMFLRIntervalNearEndLossRatio           Unsigned32(0..1000)
    }
    
rcCfmPMFLRIntervalPeriod          OBJECT-TYPE 
	SYNTAX      INTEGER{
	            rcCfmPMFLRIntervalPeriod15Minutes(1),
	            rcCfmPMFLRIntervalPeriod24Hours  (2)
	            }
	MAX-ACCESS  not-accessible
    STATUS      deprecated
    DESCRIPTION
            "interval period type ,history 15 minutes table or 24 hours table"
	::= { rcCfmPMFLRIntervalEntry 1 } 
	
rcCfmPMFLRIntervalIndex          OBJECT-TYPE 
	SYNTAX      Unsigned32
	MAX-ACCESS  not-accessible
    STATUS      deprecated
    DESCRIPTION
            "interval period index "
	::= { rcCfmPMFLRIntervalEntry 2 }

rcCfmPMFLRIntervalPeerMepId          OBJECT-TYPE 
	SYNTAX      Dot1agCfmMepId
	MAX-ACCESS  read-only
    STATUS      deprecated
    DESCRIPTION
            "peer remote mepid. "
	::= { rcCfmPMFLRIntervalEntry 3 }

	
rcCfmPMFLRIntervalBeginTime          OBJECT-TYPE 
	SYNTAX      Unsigned32
	MAX-ACCESS  read-only
    STATUS      deprecated
    DESCRIPTION
            "begin time in this intervla period, unit second. "
	::= { rcCfmPMFLRIntervalEntry 4 } 
	
rcCfmPMFLRIntervalFarEndTxFrameCounter          OBJECT-TYPE 
	SYNTAX      Unsigned32
	MAX-ACCESS  read-only
    STATUS      deprecated
    DESCRIPTION
            "far end frames transmited in this interval."
	::= { rcCfmPMFLRIntervalEntry 5 }
	
rcCfmPMFLRIntervalFarEndLostFrameCounter          OBJECT-TYPE 
	SYNTAX      Unsigned32
	MAX-ACCESS  read-only
    STATUS      deprecated
    DESCRIPTION
            "far end frames lost in this interval."
	::= { rcCfmPMFLRIntervalEntry 6 }
     
rcCfmPMFLRIntervalFarEndLossRatio          OBJECT-TYPE 
	SYNTAX      Unsigned32(0..1000)                                                
	MAX-ACCESS  read-only
    STATUS      deprecated
    DESCRIPTION
            "far end frame loss ratio in this interval."
	::= { rcCfmPMFLRIntervalEntry 7 }   
	
rcCfmPMFLRIntervalNearEndTxFrameCounter          OBJECT-TYPE 
	SYNTAX      Unsigned32                                                
	MAX-ACCESS  read-only
    STATUS      deprecated
    DESCRIPTION
            "near end frames transmited in this interval."
	::= { rcCfmPMFLRIntervalEntry 8 }
	
rcCfmPMFLRIntervalNearEndLostFrameCounter          OBJECT-TYPE 
	SYNTAX      Unsigned32                                                
	MAX-ACCESS  read-only
    STATUS      deprecated
    DESCRIPTION
            "near end frames lost in this interval."
	::= { rcCfmPMFLRIntervalEntry 9 }     
	
rcCfmPMFLRIntervalNearEndLossRatio          OBJECT-TYPE 
	SYNTAX      Unsigned32(0..1000)                                                
	MAX-ACCESS  read-only
    STATUS      deprecated
    DESCRIPTION
            "near end frame loss ratio in this interval."
	::= { rcCfmPMFLRIntervalEntry 10 }

-- PM delay current statistic table    
rcCfmPMDelayCurrentTable 					OBJECT-TYPE
    SYNTAX      SEQUENCE OF RcCfmPMDelayCurrentEntry
    MAX-ACCESS  not-accessible
    STATUS      deprecated
    DESCRIPTION
        "CFM Performance monitor delay current table "  
        
    ::= { rcCfm 15 }

rcCfmPMDelayCurrentEntry          		OBJECT-TYPE
	SYNTAX      RcCfmPMDelayCurrentEntry
    MAX-ACCESS  not-accessible
    STATUS      deprecated
    DESCRIPTION
        "An entry in the rcCfmPMDelayCurrentTable. "
    INDEX	{ 
              dot1agCfmMdIndex, 
    		  dot1agCfmMaIndex,
    		  dot1agCfmMepIdentifier,
    		  rcCfmPMDelayCurrentPeriod
    		}
    ::= { rcCfmPMDelayCurrentTable 1 }
 
    RcCfmPMDelayCurrentEntry ::= SEQUENCE 
    {
        rcCfmPMDelayCurrentPeriod                               INTEGER,
        rcCfmPMDelayCurrentFarEndAboveObjCounter                Unsigned32,
        rcCfmPMDelayCurrentFarEndBelowObjCounter                Unsigned32,
        rcCfmPMDelayCurrentFarEndMaxDelay                       Unsigned32,
        rcCfmPMDelayCurrentFarEndAvgDelay                       Unsigned32,
        rcCfmPMDelayCurrentFarEndMinDelay                       Unsigned32,
        rcCfmPMDelayCurrentNearEndAboveObjCounter               Unsigned32,
        rcCfmPMDelayCurrentNearEndBelowObjCounter               Unsigned32,
        rcCfmPMDelayCurrentNearEndMaxDelay                      Unsigned32,
        rcCfmPMDelayCurrentNearEndAvgDelay                      Unsigned32,
        rcCfmPMDelayCurrentNearEndMinDelay                      Unsigned32,
        rcCfmPMDelayCurrentRoundTripAboveObjCounter             Unsigned32,
        rcCfmPMDelayCurrentRoundTripBelowObjCounter             Unsigned32,
        rcCfmPMDelayCurrentRoundTripMaxDelay                    Unsigned32,
        rcCfmPMDelayCurrentRoundTripAvgDelay                    Unsigned32,
        rcCfmPMDelayCurrentRoundTripMinDelay                    Unsigned32
    }
    
rcCfmPMDelayCurrentPeriod          OBJECT-TYPE 
	SYNTAX      INTEGER{
	            rcCfmPMDelayCurrentPeriod15Minutes(1),
	            rcCfmPMDelayCurrentPeriod24Hours  (2)
	            }
	MAX-ACCESS  not-accessible
    STATUS      deprecated
    DESCRIPTION
            "current period type ,15 minutes table or 24 hours table."
	::= { rcCfmPMDelayCurrentEntry 1 }

rcCfmPMDelayCurrentFarEndAboveObjCounter          OBJECT-TYPE 
	SYNTAX      Unsigned32
	MAX-ACCESS  read-only
    STATUS      deprecated
    DESCRIPTION
            "numbers of far end delay above object in current interval."
	::= { rcCfmPMDelayCurrentEntry 2 } 
	
rcCfmPMDelayCurrentFarEndBelowObjCounter          OBJECT-TYPE 
	SYNTAX      Unsigned32
	MAX-ACCESS  read-only
    STATUS      deprecated
    DESCRIPTION
            "numbers of far end delay below object in current interval."
	::= { rcCfmPMDelayCurrentEntry 3 }
	
rcCfmPMDelayCurrentFarEndMaxDelay          OBJECT-TYPE 
	SYNTAX      Unsigned32
	MAX-ACCESS  read-only
    STATUS      deprecated
    DESCRIPTION
            "max far end delay in current interval, unit ms"
	::= { rcCfmPMDelayCurrentEntry 4 }
     
rcCfmPMDelayCurrentFarEndAvgDelay          OBJECT-TYPE 
	SYNTAX      Unsigned32                                                
	MAX-ACCESS  read-only
    STATUS      deprecated
    DESCRIPTION
            "average far end delay in current interval, unit ms"
	::= { rcCfmPMDelayCurrentEntry 5 }   
	
rcCfmPMDelayCurrentFarEndMinDelay          OBJECT-TYPE 
	SYNTAX      Unsigned32                                                
	MAX-ACCESS  read-only
    STATUS      deprecated
    DESCRIPTION
            "min far end delay in current interval, unit ms"
	::= { rcCfmPMDelayCurrentEntry 6 }
	
rcCfmPMDelayCurrentNearEndAboveObjCounter          OBJECT-TYPE 
	SYNTAX      Unsigned32                                                
	MAX-ACCESS  read-only
    STATUS      deprecated
    DESCRIPTION
            "numbers of near end delay above object in current interval."
	::= { rcCfmPMDelayCurrentEntry 7 }     
	
rcCfmPMDelayCurrentNearEndBelowObjCounter          OBJECT-TYPE 
	SYNTAX      Unsigned32                                                
	MAX-ACCESS  read-only
    STATUS      deprecated
    DESCRIPTION
            "numbers of near end delay below object in current interval."
	::= { rcCfmPMDelayCurrentEntry 8 }
	
rcCfmPMDelayCurrentNearEndMaxDelay          OBJECT-TYPE 
	SYNTAX      Unsigned32                                                
	MAX-ACCESS  read-only
    STATUS      deprecated
    DESCRIPTION
            "max near end delay in current interval, unit ms"
	::= { rcCfmPMDelayCurrentEntry 9 }

rcCfmPMDelayCurrentNearEndAvgDelay          OBJECT-TYPE 
	SYNTAX      Unsigned32                                                
	MAX-ACCESS  read-only
    STATUS      deprecated
    DESCRIPTION
            "average near end delay in current interval, unit ms"
	::= { rcCfmPMDelayCurrentEntry 10 }
	
rcCfmPMDelayCurrentNearEndMinDelay          OBJECT-TYPE 
	SYNTAX      Unsigned32                                                
	MAX-ACCESS  read-only
    STATUS      deprecated
    DESCRIPTION
            "min near end delay in current interval, unit ms"
	::= { rcCfmPMDelayCurrentEntry 11 }

rcCfmPMDelayCurrentRoundTripAboveObjCounter          OBJECT-TYPE 
	SYNTAX      Unsigned32                                                
	MAX-ACCESS  read-only
    STATUS      deprecated
    DESCRIPTION
            "numbers of round trip delay above object in current interval."
	::= { rcCfmPMDelayCurrentEntry 12 } 
	
rcCfmPMDelayCurrentRoundTripBelowObjCounter          OBJECT-TYPE 
	SYNTAX      Unsigned32                                                
	MAX-ACCESS  read-only
    STATUS      deprecated
    DESCRIPTION
            "numbers of round trip delay below object in current interval."
	::= { rcCfmPMDelayCurrentEntry 13 }
	
rcCfmPMDelayCurrentRoundTripMaxDelay          OBJECT-TYPE 
	SYNTAX      Unsigned32                                                
	MAX-ACCESS  read-only
    STATUS      deprecated
    DESCRIPTION
            "max round trip delay in current interval, unit ms"
	::= { rcCfmPMDelayCurrentEntry 14 }
	
rcCfmPMDelayCurrentRoundTripAvgDelay          OBJECT-TYPE 
	SYNTAX      Unsigned32                                                
	MAX-ACCESS  read-only
    STATUS      deprecated
    DESCRIPTION
            "averge round trip delay in current interval, unit ms"
	::= { rcCfmPMDelayCurrentEntry 15 }
	
rcCfmPMDelayCurrentRoundTripMinDelay          OBJECT-TYPE 
	SYNTAX      Unsigned32                                                
	MAX-ACCESS  read-only
    STATUS      deprecated
    DESCRIPTION
            "min round trip delay in current interval, unit ms"
	::= { rcCfmPMDelayCurrentEntry 16 }
	
-- PM delay interval statistic table    
rcCfmPMDelayIntervalTable 					OBJECT-TYPE
    SYNTAX      SEQUENCE OF RcCfmPMDelayIntervalEntry
    MAX-ACCESS  not-accessible
    STATUS      deprecated
    DESCRIPTION
        "CFM Performance monitor frame loss ratio current table "  
        
    ::= { rcCfm 16 }

rcCfmPMDelayIntervalEntry          		OBJECT-TYPE
	SYNTAX      RcCfmPMDelayIntervalEntry
    MAX-ACCESS  not-accessible
    STATUS      deprecated
    DESCRIPTION
        "An entry in the rcCfmPMDelayIntervalTable. "
    INDEX	{ 
              dot1agCfmMdIndex, 
    		  dot1agCfmMaIndex,
    		  dot1agCfmMepIdentifier,
    		  rcCfmPMDelayIntervalPeriod,
    		  rcCfmPMDelayIntervalIndex
    		}
    ::= { rcCfmPMDelayIntervalTable 1 }
 
    RcCfmPMDelayIntervalEntry ::= SEQUENCE 
    {
        rcCfmPMDelayIntervalPeriod                               INTEGER,
        rcCfmPMDelayIntervalIndex                                Unsigned32, 
        rcCfmPMDelayIntervalBeginTime                            Unsigned32,
        rcCfmPMDelayIntervalPeerMepId                            Dot1agCfmMepId,
        rcCfmPMDelayIntervalFarEndAboveObjCounter                Unsigned32,
        rcCfmPMDelayIntervalFarEndBelowObjCounter                Unsigned32,
        rcCfmPMDelayIntervalFarEndMaxDelay                       Unsigned32,
        rcCfmPMDelayIntervalFarEndAvgDelay                       Unsigned32,
        rcCfmPMDelayIntervalFarEndMinDelay                       Unsigned32,
        rcCfmPMDelayIntervalNearEndAboveObjCounter               Unsigned32,
        rcCfmPMDelayIntervalNearEndBelowObjCounter               Unsigned32,
        rcCfmPMDelayIntervalNearEndMaxDelay                      Unsigned32,
        rcCfmPMDelayIntervalNearEndAvgDelay                      Unsigned32,
        rcCfmPMDelayIntervalNearEndMinDelay                      Unsigned32,
        rcCfmPMDelayIntervalRoundTripAboveObjCounter             Unsigned32,
        rcCfmPMDelayIntervalRoundTripBelowObjCounter             Unsigned32,
        rcCfmPMDelayIntervalRoundTripMaxDelay                    Unsigned32,
        rcCfmPMDelayIntervalRoundTripAvgDelay                    Unsigned32,
        rcCfmPMDelayIntervalRoundTripMinDelay                    Unsigned32
    }
    
rcCfmPMDelayIntervalPeriod          OBJECT-TYPE 
	SYNTAX      INTEGER{
	            rcCfmPMDelayIntervalPeriod15Minutes(1),
	            rcCfmPMDelayIntervalPeriod24Hours  (2)
	            }
	MAX-ACCESS  not-accessible
    STATUS      deprecated
    DESCRIPTION
            "interval period type ,15 minutes table or 24 hours table"
	::= { rcCfmPMDelayIntervalEntry 1 }

rcCfmPMDelayIntervalIndex          OBJECT-TYPE 
	SYNTAX      Unsigned32
	MAX-ACCESS  not-accessible
    STATUS      deprecated
    DESCRIPTION
            "interval index."
	::= { rcCfmPMDelayIntervalEntry 2 }

rcCfmPMDelayIntervalBeginTime          OBJECT-TYPE 
	SYNTAX      Unsigned32
	MAX-ACCESS  read-only
    STATUS      deprecated
    DESCRIPTION
            "begin time in this intervla period, unit second. "
	::= { rcCfmPMDelayIntervalEntry 3 } 

rcCfmPMDelayIntervalPeerMepId          OBJECT-TYPE 
	SYNTAX      Dot1agCfmMepId
	MAX-ACCESS  read-only
    STATUS      deprecated
    DESCRIPTION
            "peer remote mepid. "
	::= { rcCfmPMDelayIntervalEntry 4 }

rcCfmPMDelayIntervalFarEndAboveObjCounter          OBJECT-TYPE 
	SYNTAX      Unsigned32
	MAX-ACCESS  read-only
    STATUS      deprecated
    DESCRIPTION
            "numbers of far end delay above object in this interval."
	::= { rcCfmPMDelayIntervalEntry 5 } 
	
rcCfmPMDelayIntervalFarEndBelowObjCounter          OBJECT-TYPE 
	SYNTAX      Unsigned32
	MAX-ACCESS  read-only
    STATUS      deprecated
    DESCRIPTION
            "numbers of far end delay below object in this interval."
	::= { rcCfmPMDelayIntervalEntry 6 }
	
rcCfmPMDelayIntervalFarEndMaxDelay          OBJECT-TYPE 
	SYNTAX      Unsigned32
	MAX-ACCESS  read-only
    STATUS      deprecated
    DESCRIPTION
            "max far end delay in this interval, unit ms"
	::= { rcCfmPMDelayIntervalEntry 7 }
     
rcCfmPMDelayIntervalFarEndAvgDelay          OBJECT-TYPE 
	SYNTAX      Unsigned32                                                
	MAX-ACCESS  read-only
    STATUS      deprecated
    DESCRIPTION
            "average far end delay in this interval, unit ms"
	::= { rcCfmPMDelayIntervalEntry 8 }   
	
rcCfmPMDelayIntervalFarEndMinDelay          OBJECT-TYPE 
	SYNTAX      Unsigned32                                                
	MAX-ACCESS  read-only
    STATUS      deprecated
    DESCRIPTION
            "min far end delay in this interval, unit ms"
	::= { rcCfmPMDelayIntervalEntry 9 }
	
rcCfmPMDelayIntervalNearEndAboveObjCounter          OBJECT-TYPE 
	SYNTAX      Unsigned32                                                
	MAX-ACCESS  read-only
    STATUS      deprecated
    DESCRIPTION
            "numbers of near end delay above object in this interval."
	::= { rcCfmPMDelayIntervalEntry 10 }     
	
rcCfmPMDelayIntervalNearEndBelowObjCounter          OBJECT-TYPE 
	SYNTAX      Unsigned32                                                
	MAX-ACCESS  read-only
    STATUS      deprecated
    DESCRIPTION
            "numbers of near end delay above object in this interval."
	::= { rcCfmPMDelayIntervalEntry 11 }
	
rcCfmPMDelayIntervalNearEndMaxDelay          OBJECT-TYPE 
	SYNTAX      Unsigned32                                                
	MAX-ACCESS  read-only
    STATUS      current
    DESCRIPTION
            "max near end delay in this interval, unit ms"
	::= { rcCfmPMDelayIntervalEntry 12 }

rcCfmPMDelayIntervalNearEndAvgDelay          OBJECT-TYPE 
	SYNTAX      Unsigned32                                                
	MAX-ACCESS  read-only
    STATUS      deprecated
    DESCRIPTION
            "average near end delay in this interval, unit ms"
	::= { rcCfmPMDelayIntervalEntry 13 }
	
rcCfmPMDelayIntervalNearEndMinDelay          OBJECT-TYPE 
	SYNTAX      Unsigned32                                                
	MAX-ACCESS  read-only
    STATUS      deprecated
    DESCRIPTION
            "min near end delay in this interval, unit ms"
	::= { rcCfmPMDelayIntervalEntry 14 }

rcCfmPMDelayIntervalRoundTripAboveObjCounter          OBJECT-TYPE 
	SYNTAX      Unsigned32                                                
	MAX-ACCESS  read-only
    STATUS      deprecated
    DESCRIPTION
            "numbers of round trip delay above object in this interval."
	::= { rcCfmPMDelayIntervalEntry 15 } 
	
rcCfmPMDelayIntervalRoundTripBelowObjCounter          OBJECT-TYPE 
	SYNTAX      Unsigned32                                                
	MAX-ACCESS  read-only
    STATUS      deprecated
    DESCRIPTION
            "numbers of round trip delay below object in this interval."
	::= { rcCfmPMDelayIntervalEntry 16 }
	
rcCfmPMDelayIntervalRoundTripMaxDelay          OBJECT-TYPE 
	SYNTAX      Unsigned32                                                
	MAX-ACCESS  read-only
    STATUS      deprecated
    DESCRIPTION
            "max round trip delay in this interval, unit ms"
	::= { rcCfmPMDelayIntervalEntry 17 }
	
rcCfmPMDelayIntervalRoundTripAvgDelay          OBJECT-TYPE 
	SYNTAX      Unsigned32                                                
	MAX-ACCESS  read-only
    STATUS      deprecated
    DESCRIPTION
            "average round trip delay in this interval, unit ms"
	::= { rcCfmPMDelayIntervalEntry 18 }
	
rcCfmPMDelayIntervalRoundTripMinDelay          OBJECT-TYPE 
	SYNTAX      Unsigned32                                                
	MAX-ACCESS  read-only
    STATUS      deprecated
    DESCRIPTION
            "min round trip delay in this interval, unit ms"
	::= { rcCfmPMDelayIntervalEntry 19 }
	
-- PM delay variation current statistic table    
rcCfmPMDVCurrentTable 					OBJECT-TYPE
    SYNTAX      SEQUENCE OF RcCfmPMDVCurrentEntry
    MAX-ACCESS  not-accessible
    STATUS      deprecated
    DESCRIPTION
        "CFM Performance monitor delay variation current table "  
        
    ::= { rcCfm 17 }

rcCfmPMDVCurrentEntry          		OBJECT-TYPE
	SYNTAX      RcCfmPMDVCurrentEntry
    MAX-ACCESS  not-accessible
    STATUS      deprecated
    DESCRIPTION
        "An entry in the rcCfmPMFLRCurrentTable. "
    INDEX	{ 
              dot1agCfmMdIndex, 
    		  dot1agCfmMaIndex,
    		  dot1agCfmMepIdentifier,
    		  rcCfmPMDVCurrentPeriod
    		}
    ::= { rcCfmPMDVCurrentTable 1 }
 
    RcCfmPMDVCurrentEntry ::= SEQUENCE 
    {
        rcCfmPMDVCurrentPeriod                               INTEGER,
        rcCfmPMDVCurrentFarEndAboveObjCounter                Unsigned32,
        rcCfmPMDVCurrentFarEndBelowObjCounter                Unsigned32,
        rcCfmPMDVCurrentFarEndMaxDv                          Unsigned32,
        rcCfmPMDVCurrentFarEndAvgDv                          Unsigned32,
        rcCfmPMDVCurrentNearEndAboveObjCounter               Unsigned32,
        rcCfmPMDVCurrentNearEndBelowObjCounter               Unsigned32,
        rcCfmPMDVCurrentNearEndMaxDv                         Unsigned32,
        rcCfmPMDVCurrentNearEndAvgDv                         Unsigned32,
        rcCfmPMDVCurrentRoundTripAboveObjCounter             Unsigned32,
        rcCfmPMDVCurrentRoundTripBelowObjCounter             Unsigned32,
        rcCfmPMDVCurrentRoundTripMaxDv                       Unsigned32,
        rcCfmPMDVCurrentRoundTripAvgDv                       Unsigned32
    }
    
rcCfmPMDVCurrentPeriod          OBJECT-TYPE 
	SYNTAX      INTEGER{
	            rcCfmPMDVCurrentPeriod15Minutes(1),
	            rcCfmPMDVCurrentPeriod24Hours  (2)
	            }
	MAX-ACCESS  not-accessible
    STATUS      deprecated
    DESCRIPTION
            "current period type ,15 minutes table or 24 hours table"
	::= { rcCfmPMDVCurrentEntry 1 }

rcCfmPMDVCurrentFarEndAboveObjCounter          OBJECT-TYPE 
	SYNTAX      Unsigned32
	MAX-ACCESS  read-only
    STATUS      deprecated
    DESCRIPTION
            "numbers of far end delay aviation above object in current interval."
	::= { rcCfmPMDVCurrentEntry 2 } 
	
rcCfmPMDVCurrentFarEndBelowObjCounter          OBJECT-TYPE 
	SYNTAX      Unsigned32
	MAX-ACCESS  read-only
    STATUS      deprecated
    DESCRIPTION
            "numbers of far end delay aviation below object in current interval."
	::= { rcCfmPMDVCurrentEntry 3 }
	
rcCfmPMDVCurrentFarEndMaxDv          OBJECT-TYPE 
	SYNTAX      Unsigned32
	MAX-ACCESS  read-only
    STATUS      deprecated
    DESCRIPTION
            "max far end delay variation in current interval, unit ms"
	::= { rcCfmPMDVCurrentEntry 4 }
     
rcCfmPMDVCurrentFarEndAvgDv          OBJECT-TYPE 
	SYNTAX      Unsigned32                                                
	MAX-ACCESS  read-only
    STATUS      deprecated
    DESCRIPTION
            "average far end delay variation in current interval, unit ms"
	::= { rcCfmPMDVCurrentEntry 5 }   
	
rcCfmPMDVCurrentNearEndAboveObjCounter          OBJECT-TYPE 
	SYNTAX      Unsigned32                                                
	MAX-ACCESS  read-only
    STATUS      deprecated
    DESCRIPTION
            "numbers of near end delay aviation above object in current interval."
	::= { rcCfmPMDVCurrentEntry 6 }     
	
rcCfmPMDVCurrentNearEndBelowObjCounter          OBJECT-TYPE 
	SYNTAX      Unsigned32                                                
	MAX-ACCESS  read-only
    STATUS      deprecated
    DESCRIPTION
            "numbers of near end delay aviation below object in current interval."
	::= { rcCfmPMDVCurrentEntry 7 }
	
rcCfmPMDVCurrentNearEndMaxDv          OBJECT-TYPE 
	SYNTAX      Unsigned32                                                
	MAX-ACCESS  read-only
    STATUS      deprecated
    DESCRIPTION
            "max far end delay variation in current interval, unit ms"
	::= { rcCfmPMDVCurrentEntry 8 }

rcCfmPMDVCurrentNearEndAvgDv          OBJECT-TYPE 
	SYNTAX      Unsigned32                                                
	MAX-ACCESS  read-only
    STATUS      deprecated
    DESCRIPTION
            "average far end delay variation in current interval, unit ms"
	::= { rcCfmPMDVCurrentEntry 9 }

rcCfmPMDVCurrentRoundTripAboveObjCounter          OBJECT-TYPE 
	SYNTAX      Unsigned32                                                
	MAX-ACCESS  read-only
    STATUS      deprecated
    DESCRIPTION
            "numbers of round trip delay aviation above object in current interval."
	::= { rcCfmPMDVCurrentEntry 10 } 
	
rcCfmPMDVCurrentRoundTripBelowObjCounter          OBJECT-TYPE 
	SYNTAX      Unsigned32                                                
	MAX-ACCESS  read-only
    STATUS      deprecated
    DESCRIPTION
            "numbers of round trip delay aviation below object in current interval."
	::= { rcCfmPMDVCurrentEntry 11 }
	
rcCfmPMDVCurrentRoundTripMaxDv          OBJECT-TYPE 
	SYNTAX      Unsigned32                                                
	MAX-ACCESS  read-only
    STATUS      deprecated
    DESCRIPTION
            "max far end delay variation in current interval, unit ms"
	::= { rcCfmPMDVCurrentEntry 12 }
	
rcCfmPMDVCurrentRoundTripAvgDv          OBJECT-TYPE 
	SYNTAX      Unsigned32                                                
	MAX-ACCESS  read-only
    STATUS      deprecated
    DESCRIPTION
            "average far end delay variation in current interval, unit ms"
	::= { rcCfmPMDVCurrentEntry 13 }
	
-- PM delay variation interval statistic table    
rcCfmPMDVIntervalTable 					OBJECT-TYPE
    SYNTAX      SEQUENCE OF RcCfmPMDVIntervalEntry
    MAX-ACCESS  not-accessible
    STATUS      deprecated
    DESCRIPTION
        "CFM Performance monitor delay variation interval table "  
        
    ::= { rcCfm 18 }

rcCfmPMDVIntervalEntry          		OBJECT-TYPE
	SYNTAX      RcCfmPMDVIntervalEntry
    MAX-ACCESS  not-accessible
    STATUS      deprecated
    DESCRIPTION
        "An entry in the rcCfmPMDelayIntervalTable. "
    INDEX	{ 
              dot1agCfmMdIndex, 
    		  dot1agCfmMaIndex,
    		  dot1agCfmMepIdentifier,
    		  rcCfmPMDVIntervalPeriod,
    		  rcCfmPMDVIntervalIndex
    		}
    ::= { rcCfmPMDVIntervalTable 1 }
 
    RcCfmPMDVIntervalEntry ::= SEQUENCE 
    {
        rcCfmPMDVIntervalPeriod                               INTEGER,
        rcCfmPMDVIntervalIndex                                Unsigned32,
        rcCfmPMDVIntervalBeginTime                            Unsigned32,  
        rcCfmPMDVIntervalPeerMepId                           Dot1agCfmMepId,
        rcCfmPMDVIntervalFarEndAboveObjCounter                Unsigned32,
        rcCfmPMDVIntervalFarEndBelowObjCounter                Unsigned32,
        rcCfmPMDVIntervalFarEndMaxDv                          Unsigned32,
        rcCfmPMDVIntervalFarEndAvgDv                          Unsigned32,
        rcCfmPMDVIntervalNearEndAboveObjCounter               Unsigned32,
        rcCfmPMDVIntervalNearEndBelowObjCounter               Unsigned32,
        rcCfmPMDVIntervalNearEndMaxDv                         Unsigned32,
        rcCfmPMDVIntervalNearEndAvgDv                         Unsigned32,
        rcCfmPMDVIntervalRoundTripAboveObjCounter             Unsigned32,
        rcCfmPMDVIntervalRoundTripBelowObjCounter             Unsigned32,
        rcCfmPMDVIntervalRoundTripMaxDv                       Unsigned32,
        rcCfmPMDVIntervalRoundTripAvgDv                       Unsigned32
    }
    
rcCfmPMDVIntervalPeriod          OBJECT-TYPE 
	SYNTAX      INTEGER{
	            rcCfmPMDVIntervalPeriod15Minutes(1),
	            rcCfmPMDVIntervalPeriod24Hours  (2)
	            }
	MAX-ACCESS  not-accessible
    STATUS      deprecated
    DESCRIPTION
            "interval period type ,15 minutes table or 24 hours table"
	::= { rcCfmPMDVIntervalEntry 1 }

rcCfmPMDVIntervalIndex          OBJECT-TYPE 
	SYNTAX      Unsigned32
	MAX-ACCESS  not-accessible
    STATUS      deprecated
    DESCRIPTION
            "interval period index."
	::= { rcCfmPMDVIntervalEntry 2 }

rcCfmPMDVIntervalBeginTime      OBJECT-TYPE 
	SYNTAX      Unsigned32
	MAX-ACCESS  read-only
    STATUS      deprecated
    DESCRIPTION
            "begin time in this intervla period, unit second. "
	::= { rcCfmPMDVIntervalEntry 3 } 


rcCfmPMDVIntervalPeerMepId     OBJECT-TYPE 
	SYNTAX      Dot1agCfmMepId
	MAX-ACCESS  read-only
    STATUS      deprecated
    DESCRIPTION
            "peer remote mepid."
	::= { rcCfmPMDVIntervalEntry 4 }

rcCfmPMDVIntervalFarEndAboveObjCounter          OBJECT-TYPE 
	SYNTAX      Unsigned32
	MAX-ACCESS  read-only
    STATUS      deprecated
    DESCRIPTION
            "numbers of far end delay variation above object in this interval."
	::= { rcCfmPMDVIntervalEntry 5 } 
	
rcCfmPMDVIntervalFarEndBelowObjCounter          OBJECT-TYPE 
	SYNTAX      Unsigned32
	MAX-ACCESS  read-only
    STATUS      deprecated
    DESCRIPTION
            "numbers of far end delay variation above object in this interval."
	::= { rcCfmPMDVIntervalEntry 6 }
	
rcCfmPMDVIntervalFarEndMaxDv          OBJECT-TYPE 
	SYNTAX      Unsigned32
	MAX-ACCESS  read-only
    STATUS      deprecated
    DESCRIPTION
            "max far end delay variation in this interval, unit ms"
	::= { rcCfmPMDVIntervalEntry 7 }
     
rcCfmPMDVIntervalFarEndAvgDv          OBJECT-TYPE 
	SYNTAX      Unsigned32                                                
	MAX-ACCESS  read-only
    STATUS      deprecated
    DESCRIPTION
            "average far end delay variation in this interval, unit ms"
	::= { rcCfmPMDVIntervalEntry 8 }   
	
rcCfmPMDVIntervalNearEndAboveObjCounter          OBJECT-TYPE 
	SYNTAX      Unsigned32                                                
	MAX-ACCESS  read-only
    STATUS      deprecated
    DESCRIPTION
            "numbers of near end delay variation above object in this interval."
	::= { rcCfmPMDVIntervalEntry 9 }     
	
rcCfmPMDVIntervalNearEndBelowObjCounter          OBJECT-TYPE 
	SYNTAX      Unsigned32                                                
	MAX-ACCESS  read-only
    STATUS      deprecated
    DESCRIPTION
            "numbers of near end delay variation below object in this interval."
	::= { rcCfmPMDVIntervalEntry 10 }
	
rcCfmPMDVIntervalNearEndMaxDv          OBJECT-TYPE 
	SYNTAX      Unsigned32                                                
	MAX-ACCESS  read-only
    STATUS      deprecated
    DESCRIPTION
            "max near end delay variation in this interval, unit ms"
	::= { rcCfmPMDVIntervalEntry 11 }

rcCfmPMDVIntervalNearEndAvgDv          OBJECT-TYPE 
	SYNTAX      Unsigned32                                                
	MAX-ACCESS  read-only
    STATUS      deprecated
    DESCRIPTION
            "average near end delay variation in this interval, unit ms"
	::= { rcCfmPMDVIntervalEntry 12 }

rcCfmPMDVIntervalRoundTripAboveObjCounter          OBJECT-TYPE 
	SYNTAX      Unsigned32                                                
	MAX-ACCESS  read-only
    STATUS      deprecated
    DESCRIPTION
            "numbers of round trip delay variation above object in this interval."
	::= { rcCfmPMDVIntervalEntry 13 } 
	
rcCfmPMDVIntervalRoundTripBelowObjCounter          OBJECT-TYPE 
	SYNTAX      Unsigned32                                                
	MAX-ACCESS  read-only
    STATUS      deprecated
    DESCRIPTION
            "numbers of round trip delay variation below object in this interval."
	::= { rcCfmPMDVIntervalEntry 14 }
	
rcCfmPMDVIntervalRoundTripMaxDv          OBJECT-TYPE 
	SYNTAX      Unsigned32                                                
	MAX-ACCESS  read-only
    STATUS      deprecated
    DESCRIPTION
            "max near end delay variation in this interval, unit ms"
	::= { rcCfmPMDVIntervalEntry 15 }
	
rcCfmPMDVIntervalRoundTripAvgDv          OBJECT-TYPE 
	SYNTAX      Unsigned32                                                
	MAX-ACCESS  read-only
    STATUS      deprecated
    DESCRIPTION
            "average near end delay variation in this interval, unit ms"
	::= { rcCfmPMDVIntervalEntry 16 }

-- rfc2544 throughput statistic table
rcCfmPMThroughputTable 					OBJECT-TYPE
    SYNTAX      SEQUENCE OF RcCfmPMThroughputEntry
    MAX-ACCESS  not-accessible
    STATUS      deprecated
    DESCRIPTION
        "ITU-T Y.1731 throughput(according to rfc2544) test statistics table."  
        
    ::= { rcCfm 19 }
    
rcCfmPMThroughputEntry          		OBJECT-TYPE
	SYNTAX      RcCfmPMThroughputEntry
    MAX-ACCESS  not-accessible
    STATUS      deprecated
    DESCRIPTION
        "An entry in the rcCfmPMTable. "
    INDEX	{ 
              dot1agCfmMdIndex, 
    		  dot1agCfmMaIndex,
    		  dot1agCfmMepIdentifier,
    		  dot1agCfmMepDbRMepIdentifier
    		}
    ::= { rcCfmPMThroughputTable 1 } 
    
    RcCfmPMThroughputEntry ::= SEQUENCE 
    {   
        rcCfmPMThroughputTestResult                 INTEGER,
        rcCfmPMThroughputTestState                  INTEGER,
        rcCfmPMThroughputFarEndSendbps              Counter64,
        rcCfmPMThroughputFarEndRecievebps           Counter64,
        rcCfmPMThroughputFarEndSendpps              Counter64,
        rcCfmPMThroughputFarEndRecievepps           Counter64,
        rcCfmPMThroughputNearEndSendbps             Counter64,
        rcCfmPMThroughputNearEndRecievebps          Counter64,
        rcCfmPMThroughputNearEndSendpps             Counter64,
        rcCfmPMThroughputNearEndRecievepps          Counter64
    }

rcCfmPMThroughputTestResult             OBJECT-TYPE 
	SYNTAX      INTEGER{         
	            successed                (0),
	            unknownReasonFailed      (1),
	            localReourceConflict     (2), 
	            remoteResourceConflict   (3),
	            vsxTimeOut               (4)
	            }                                               
	MAX-ACCESS  read-only
    STATUS      deprecated
    DESCRIPTION
            "result of rfc2544 throughput test."
	::= { rcCfmPMThroughputEntry 1 }

rcCfmPMThroughputTestState              OBJECT-TYPE 
	SYNTAX      INTEGER{
	            idle             (0),
	            farEndStart      (1),
	            farEndSend       (2),
	            farEndTest       (3),
	            nearEndStart     (4),
	            nearEndTest      (5),
	            nearEndClose     (6)
	            }                                               
	MAX-ACCESS  read-only
    STATUS      deprecated
    DESCRIPTION
            "state of rfc2544 throughput test."
	::= { rcCfmPMThroughputEntry 2 }

rcCfmPMThroughputFarEndSendbps          OBJECT-TYPE 
	SYNTAX      Counter64                                               
	MAX-ACCESS  read-only
    STATUS      deprecated
    DESCRIPTION
            "far end rfc2544 throughput flow sended statistics, unit bps."
	::= { rcCfmPMThroughputEntry 3 } 
	
rcCfmPMThroughputFarEndRecievebps       OBJECT-TYPE 
	SYNTAX      Counter64                                               
	MAX-ACCESS  read-only
    STATUS      deprecated
    DESCRIPTION
            "far end rfc2544 throughput flow received statistics, unit bps."
	::= { rcCfmPMThroughputEntry 4 }  
	
rcCfmPMThroughputFarEndSendpps          OBJECT-TYPE 
	SYNTAX      Counter64                                               
	MAX-ACCESS  read-only
    STATUS      deprecated
    DESCRIPTION
            "far end rfc2544 throughput flow sended statistics, unit pps."
	::= { rcCfmPMThroughputEntry 5 }
	 
rcCfmPMThroughputFarEndRecievepps       OBJECT-TYPE 
	SYNTAX      Counter64                                               
	MAX-ACCESS  read-only
    STATUS      deprecated
    DESCRIPTION
            "far end rfc2544 throughput flow received statistics, unit pps."
	::= { rcCfmPMThroughputEntry 6 } 
	
rcCfmPMThroughputNearEndSendbps          OBJECT-TYPE 
	SYNTAX      Counter64                                               
	MAX-ACCESS  read-only
    STATUS      deprecated
    DESCRIPTION
            "near end rfc2544 throughput flow sended statistics, unit bps."
	::= { rcCfmPMThroughputEntry 7 }
	 
rcCfmPMThroughputNearEndRecievebps       OBJECT-TYPE 
	SYNTAX      Counter64                                               
	MAX-ACCESS  read-only
    STATUS      deprecated
    DESCRIPTION
            "near end rfc2544 throughput flow received statistics, unit bps."
	::= { rcCfmPMThroughputEntry 8 }   
	
rcCfmPMThroughputNearEndSendpps          OBJECT-TYPE 
	SYNTAX      Counter64                                               
	MAX-ACCESS  read-only
    STATUS      deprecated
    DESCRIPTION
            "near end rfc2544 throughput flow sended statistics, unit pps."
	::= { rcCfmPMThroughputEntry 9 }
	 
rcCfmPMThroughputNearEndRecievepps       OBJECT-TYPE 
	SYNTAX      Counter64                                               
	MAX-ACCESS  read-only
    STATUS      deprecated
    DESCRIPTION
            "near end rfc2544 throughput flow received statistics, unit pps."
	::= { rcCfmPMThroughputEntry 10 }

--CFM Ma Extended Table
rcCfmMaExTable 					OBJECT-TYPE
    SYNTAX      SEQUENCE OF RcCfmMaExEntry
    MAX-ACCESS  not-accessible
    STATUS      current
    DESCRIPTION
        "CFM MA Extended Table "  
        
    ::= { rcCfm 20 }
    
rcCfmMaExEntry          			OBJECT-TYPE
	SYNTAX      RcCfmMaExEntry
    MAX-ACCESS  not-accessible
    STATUS      current
    DESCRIPTION
        "An entry in the rcCfmMaExTable. "
    INDEX	{ dot1agCfmMdIndex, 
    		  dot1agCfmMaIndex
    		}
    ::= { rcCfmMaExTable 1 } 
    
    RcCfmMaExEntry ::= SEQUENCE 
    {
		rcCfmMaExFormat             Dot1agCfmMaintAssocNameType,  
		rcCfmMaExName				Dot1agCfmMaintAssocName,
		rcCfmMaExVlanList           OCTET STRING (SIZE (512))  ,
		rcCfmMaExCcmInterval        Dot1agCfmCcmInterval,
		rcCfmMaExCostumerVlan       VlanIdOrNone,
		rcCfmMaExPduPriority        Unsigned32 (0..7),
        rcCfmMaExRowStatus          RowStatus,
		rcCfmMaExPrimaryVlanId      VlanIdOrNone,
		rcCfmMaExMipAutocreateAdmin   EnableVar
	}
 
rcCfmMaExFormat OBJECT-TYPE
    SYNTAX      Dot1agCfmMaintAssocNameType
    MAX-ACCESS  read-create
    STATUS      current
    DESCRIPTION
       "The type (and thereby format) of the Maintenance Association
        Name.
       "
    REFERENCE
       "802.1ag clauses 21.6.5.4"
    ::= { rcCfmMaExEntry 1 }

rcCfmMaExName OBJECT-TYPE
    SYNTAX      Dot1agCfmMaintAssocName
    MAX-ACCESS  read-create
    STATUS      current
    DESCRIPTION
       "The Short Maintenance Association name. The type/format of
        this object is determined by the value of the
        dot1agCfmMaNetNameType object.  This name must be unique within
        a maintenance domain.
       "
    REFERENCE
       "802.1ag clauses 21.6.5.6, and Table 21-20"
    ::= { rcCfmMaExEntry 2 }  
    
rcCfmMaExVlanList OBJECT-TYPE
    SYNTAX      OCTET STRING (SIZE (512))  
    MAX-ACCESS  read-create
    STATUS      current
    DESCRIPTION
       "The mapping VLANs with which the Maintenance Association is
        associated, or 0 if the MA is not attached to any VID."
    ::= { rcCfmMaExEntry 3 }

rcCfmMaExCcmInterval OBJECT-TYPE
    SYNTAX      Dot1agCfmCcmInterval
    MAX-ACCESS  read-create
    STATUS      current
    DESCRIPTION
       "Interval between CCM transmissions to be used by all MEPs
        in the MA.
       "
    REFERENCE
       "802.1ag clause 12.14.6.1.3:e"
    DEFVAL { interval1s }
    ::= { rcCfmMaExEntry 4 }    
    
rcCfmMaExCostumerVlan OBJECT-TYPE
    SYNTAX      VlanIdOrNone
    MAX-ACCESS  read-create
    STATUS      current
    DESCRIPTION
        "costumer vlan in oam pdu. the value of 0 indicates oam Pdu transmited 
            without costumer vlan."     
   DEFVAL{0}
   	::= { rcCfmMaExEntry 5 }
	
rcCfmMaExPduPriority          OBJECT-TYPE 
	SYNTAX      Unsigned32 (0..7)
	MAX-ACCESS  read-create
    STATUS      current
    DESCRIPTION
            "The pdu Priority. default priority is 6."    
    DEFVAL {6}
	::= { rcCfmMaExEntry 6 }    

rcCfmMaExRowStatus OBJECT-TYPE
    SYNTAX      RowStatus
    MAX-ACCESS  read-create
    STATUS      current
    DESCRIPTION
       "The status of the row.

        The writable columns in a row can not be changed if the row
        is active. All columns must have a valid value before a row
        can be activated.
       "
    ::= {rcCfmMaExEntry 7 }
    	
rcCfmMaExPrimaryVlanId          OBJECT-TYPE 
	SYNTAX      VlanIdOrNone
	MAX-ACCESS  read-create
    STATUS      current
    DESCRIPTION
            "The PrimaryVlanId. default the minimum vlan in the vlanlist."    
	::= { rcCfmMaExEntry 8 } 

rcCfmMaExMipAutocreateAdmin          OBJECT-TYPE 
	SYNTAX      EnableVar
	MAX-ACCESS  read-write
    STATUS      current
    DESCRIPTION
            "If set rcCfmMaExMipAutocreateAdmin _enabled (1), The MIP can be auto-created.
             If set rcCfmMaExMipAutocreateAdmin _diabled (2), The MIP can be only manual-created.
            "  
    DEFVAL{disable} 
	::= { rcCfmMaExEntry 9 } 
	                


--Y.1731 Ma Extern AIS table
rcCfmMaExAisTable OBJECT-TYPE
    SYNTAX      SEQUENCE OF RcCfmMaExAisEntry
    MAX-ACCESS  not-accessible
    STATUS      current
    DESCRIPTION
        "Y.1731 MA Extended Ais Table "  
    ::= { rcCfm 21 }
    
rcCfmMaExAisEntry OBJECT-TYPE
	SYNTAX      RcCfmMaExAisEntry
    MAX-ACCESS  not-accessible
    STATUS      current
    DESCRIPTION
        "An entry in the rcCfmMaExAisTable. "
    INDEX	{ dot1agCfmMdIndex, 
    		  dot1agCfmMaIndex
    		}
    ::= { rcCfmMaExAisTable 1 } 
    
RcCfmMaExAisEntry ::= SEQUENCE
    {
		rcCfmMaExAisEnable EnableVar,  
		rcCfmMaExAisLevelAdmin Dot1agCfmMDLevelOrNone,
		rcCfmMaExAisLevelOper Dot1agCfmMDLevelOrNone,
		rcCfmMaExAisPeriod INTEGER,
		rcCfmMaExAisStatus INTEGER, 
        rcCfmMaExAisAge Unsigned32,
        rcCfmMaExAisStatisticsTx Unsigned32,
		rcCfmMaExAisStatisticsRx Unsigned32
	}
 
rcCfmMaExAisEnable OBJECT-TYPE
    SYNTAX      EnableVar
    MAX-ACCESS  read-create
    STATUS      current
    DESCRIPTION
       "Set the enable or disable status of AIS in this MA,then send ais 
        packet when some errors occur."  
     DEFVAL{disable}   
    ::= { rcCfmMaExAisEntry 1 }

rcCfmMaExAisLevelAdmin OBJECT-TYPE
    SYNTAX      Dot1agCfmMDLevelOrNone
    MAX-ACCESS  read-create
    STATUS      current
    DESCRIPTION
       "Set the level of AIS in this MA,then send ais packet when 
        some errors occur." 
    DEFVAL {-1}
    ::= { rcCfmMaExAisEntry 2 }  
    
rcCfmMaExAisLevelOper OBJECT-TYPE
    SYNTAX      Dot1agCfmMDLevelOrNone  
    MAX-ACCESS  read-only
    STATUS      current
    DESCRIPTION
       "The actually level of sending ais."
    ::= { rcCfmMaExAisEntry 3 }

rcCfmMaExAisPeriod OBJECT-TYPE
    SYNTAX      INTEGER{
                 aisPeriod1s(1),
                 aisPeriod60s(60)
                 }
                   
    MAX-ACCESS  read-create
    STATUS      current
    DESCRIPTION
       "IWhen setting the period of sending AIS in this MA,it’s 
        periodically send ais when the timer arrived because of 
        some errors occur.
       "
    DEFVAL {aisPeriod1s}
    ::= { rcCfmMaExAisEntry 4 }
	
rcCfmMaExAisStatus          OBJECT-TYPE 
	SYNTAX      INTEGER
                {  Active(1),
                   noActive(2)
                } 
	MAX-ACCESS  read-only
    STATUS      current
    DESCRIPTION
            "When receiving ais, it is in active status(rcCfmMaExAisStatus_Active(1));
             When not receiving ais with in 3.5 multiple period,it is in not active 
             status(rcCfmMaExAisStatus_noActive (2)).
            "    
    DEFVAL { noActive }
	::= { rcCfmMaExAisEntry 5 } 
	                
rcCfmMaExAisAge OBJECT-TYPE
    SYNTAX      Unsigned32
    MAX-ACCESS  read-only
    STATUS      current
    DESCRIPTION
       "The storage time (s) when last receiving ais packet."
    DEFVAL{0}   
    ::= {rcCfmMaExAisEntry 6 }

rcCfmMaExAisStatisticsTx OBJECT-TYPE
    SYNTAX      Unsigned32
    MAX-ACCESS  read-only
    STATUS      current
    DESCRIPTION
       "The counters of sended ais packets." 
    DEFVAL{0}
    ::= {rcCfmMaExAisEntry 7 }    
    
rcCfmMaExAisStatisticsRx OBJECT-TYPE
    SYNTAX      Unsigned32
    MAX-ACCESS  read-only
    STATUS      current
    DESCRIPTION
       "The counters of received ais packets."
    DEFVAL{0}
    ::= {rcCfmMaExAisEntry 8 } 
         
--Y.1731 Ma Extern LCK table
rcCfmMaExLckTable OBJECT-TYPE
    SYNTAX      SEQUENCE OF RcCfmMaExLckEntry
    MAX-ACCESS  not-accessible
    STATUS      current
    DESCRIPTION
        "Y.1731 MA Extended LCK table"
    ::= { rcCfm 22 }
    
rcCfmMaExLckEntry OBJECT-TYPE
	  SYNTAX      RcCfmMaExLckEntry
    MAX-ACCESS  not-accessible
    STATUS      current
    DESCRIPTION
        "An entry in the rcCfmMaExLckTable. "
    INDEX	{ dot1agCfmMdIndex, 
    		  dot1agCfmMaIndex
    		}
    ::= { rcCfmMaExLckTable 1 } 
    
    RcCfmMaExLckEntry ::= SEQUENCE 
    {
		rcCfmMaExLckLevelAdmin Dot1agCfmMDLevelOrNone,  
		rcCfmMaExLckLevelOper Dot1agCfmMDLevelOrNone,
		rcCfmMaExLckPeriod INTEGER,
		rcCfmMaExLckStatus INTEGER,
		rcCfmMaExLckAge Unsigned32,
		rcCfmMaExLckStatisticsTx Unsigned32,
		rcCfmMaExLckStatisticsRx Unsigned32
	}
 
rcCfmMaExLckLevelAdmin OBJECT-TYPE
    SYNTAX      Dot1agCfmMDLevelOrNone
    MAX-ACCESS  read-create
    STATUS      current
    DESCRIPTION
       "Set the level of AIS in this MA,then send ais 
       packet when some errors occur."  
    DEFVAL{-1}
    ::= { rcCfmMaExLckEntry 1 }

rcCfmMaExLckLevelOper OBJECT-TYPE
    SYNTAX      Dot1agCfmMDLevelOrNone
    MAX-ACCESS  read-only
    STATUS      current
    DESCRIPTION
       "The actually level of sending ais."
    ::= { rcCfmMaExLckEntry 2 }  
    
rcCfmMaExLckPeriod OBJECT-TYPE
    SYNTAX      INTEGER{
                 lckPeriod1s(1),
                 lckPeriod60s(60)
                 }  
    MAX-ACCESS  read-create
    STATUS      current
    DESCRIPTION
       "When setting the period of sending LCK in this MA,
        it’s periodically send lck when the timer arrived 
        because of some errors occur."  
    DEFVAL{lckPeriod1s}
    ::= { rcCfmMaExLckEntry 3 }

rcCfmMaExLckStatus OBJECT-TYPE
    SYNTAX      INTEGER
                {  Active(1),
                   noActive(2)
                }       
    MAX-ACCESS  read-only
    STATUS      current
    DESCRIPTION
       "When receiving lck, it is in active status(rcCfmMaExLckStatus _Active(1));
        When not receiving lck with in 3.5 multiple period,
        it is in not active status(rcCfmMaExLckStatus _noActive (2)).
       "
    DEFVAL{noActive}
    ::= { rcCfmMaExLckEntry 4 }    
    
rcCfmMaExLckAge OBJECT-TYPE
    SYNTAX      Unsigned32
    MAX-ACCESS  read-only
    STATUS      current
    DESCRIPTION
        "The storage time (s) when last receiving lck packet." 
    DEFVAL{0}    
	::= { rcCfmMaExLckEntry 5 }
	
rcCfmMaExLckStatisticsTx OBJECT-TYPE
    SYNTAX      Unsigned32
    MAX-ACCESS  read-only
    STATUS      current
    DESCRIPTION
        "The counters of sended lck packets."  
    DEFVAL{0} 
   	::= { rcCfmMaExLckEntry 6 }	
	
rcCfmMaExLckStatisticsRx OBJECT-TYPE
    SYNTAX      Unsigned32
    MAX-ACCESS  read-only
    STATUS      current
    DESCRIPTION
        "The counters of received lck packets."  
    DEFVAL{0} 
    ::= { rcCfmMaExLckEntry 7 }
    		
-- trap notification 
rcCfmNotifications           OBJECT IDENTIFIER ::= { rcCfm 23 }
rcCfmPmFLRRaisingThreshFaultAlarm
NOTIFICATION-TYPE
    OBJECTS     { rcCfmPMFLRRisingThreshold
                }
    STATUS      deprecated
    DESCRIPTION
       "A MEP has a persistent defect condition. A notification
        dot1agCfmMdIndex - Also the index of the MEP's
                              Maintenance Domain table entry
                              (dot1agCfmMdTable).
        dot1agCfmMaIndex - Also an index (with the MD table index)
                              of the MEP's Maintenance Association
                              network table entry
                              (dot1agCfmMaNetTable), and (with the MD
                              table index and component ID) of the
                              MEP's MA component table entry
                              (dot1agCfmMaCompTable).
        dot1agCfmMepIdentifier - MEP Identifier and final index
                              into the MEP table (dot1agCfmMepTable).
        dot1agCfmMepDbRMepIdentifier
       "
    REFERENCE
       "802.1ag clause 12.14.7.7"
    ::= { rcCfmNotifications 1 }

rcCfmPmFLRFallingThreshFaultAlarm
NOTIFICATION-TYPE
    OBJECTS     { rcCfmPMFLRFallingThreshold
                }
    STATUS      deprecated
    DESCRIPTION
       "A MEP has a persistent defect condition. A notification
        dot1agCfmMdIndex - Also the index of the MEP's
                              Maintenance Domain table entry
                              (dot1agCfmMdTable).
        dot1agCfmMaIndex - Also an index (with the MD table index)
                              of the MEP's Maintenance Association
                              network table entry
                              (dot1agCfmMaNetTable), and (with the MD
                              table index and component ID) of the
                              MEP's MA component table entry
                              (dot1agCfmMaCompTable).
        dot1agCfmMepIdentifier - MEP Identifier and final index
                              into the MEP table (dot1agCfmMepTable).
        dot1agCfmMepDbRMepIdentifier
       "
    REFERENCE
       "802.1ag clause 12.14.7.7"
    ::= { rcCfmNotifications 2 }

rcCfmPmDelayRisingThreshFaultAlarm
NOTIFICATION-TYPE
    OBJECTS     { rcCfmPMDelayRisingThreshold
                }
    STATUS      deprecated
    DESCRIPTION
       "A MEP has a persistent defect condition. A notification
        dot1agCfmMdIndex - Also the index of the MEP's
                              Maintenance Domain table entry
                              (dot1agCfmMdTable).
        dot1agCfmMaIndex - Also an index (with the MD table index)
                              of the MEP's Maintenance Association
                              network table entry
                              (dot1agCfmMaNetTable), and (with the MD
                              table index and component ID) of the
                              MEP's MA component table entry
                              (dot1agCfmMaCompTable).
        dot1agCfmMepIdentifier - MEP Identifier and final index
                              into the MEP table (dot1agCfmMepTable).
        dot1agCfmMepDbRMepIdentifier
       "
    REFERENCE
       "802.1ag clause 12.14.7.7"
    ::= { rcCfmNotifications 3 }  
    
rcCfmPmDelayFallingThreshFaultAlarm
NOTIFICATION-TYPE
    OBJECTS     { rcCfmPMDelayFallingThreshold
                }
    STATUS      deprecated
    DESCRIPTION
       "A MEP has a persistent defect condition. A notification
        dot1agCfmMdIndex - Also the index of the MEP's
                              Maintenance Domain table entry
                              (dot1agCfmMdTable).
        dot1agCfmMaIndex - Also an index (with the MD table index)
                              of the MEP's Maintenance Association
                              network table entry
                              (dot1agCfmMaNetTable), and (with the MD
                              table index and component ID) of the
                              MEP's MA component table entry
                              (dot1agCfmMaCompTable).
        dot1agCfmMepIdentifier - MEP Identifier and final index
                              into the MEP table (dot1agCfmMepTable).
        dot1agCfmMepDbRMepIdentifier
       "
    REFERENCE
       "802.1ag clause 12.14.7.7"
    ::= { rcCfmNotifications 4 }

rcCfmPmDVRisingThreshFaultAlarm
NOTIFICATION-TYPE
    OBJECTS     { rcCfmPMDVRisingThreshold
                }
    STATUS      deprecated
    DESCRIPTION
       "A MEP has a persistent defect condition. A notification
        dot1agCfmMdIndex - Also the index of the MEP's
                              Maintenance Domain table entry
                              (dot1agCfmMdTable).
        dot1agCfmMaIndex - Also an index (with the MD table index)
                              of the MEP's Maintenance Association
                              network table entry
                              (dot1agCfmMaNetTable), and (with the MD
                              table index and component ID) of the
                              MEP's MA component table entry
                              (dot1agCfmMaCompTable).
        dot1agCfmMepIdentifier - MEP Identifier and final index
                              into the MEP table (dot1agCfmMepTable).
        dot1agCfmMepDbRMepIdentifier
       "
    REFERENCE
       "802.1ag clause 12.14.7.7"
    ::= { rcCfmNotifications 5 }

rcCfmPmDVFallingThreshFaultAlarm
NOTIFICATION-TYPE
    OBJECTS     { 
                  rcCfmPMDVFallingThreshold
                }
    STATUS      deprecated
    DESCRIPTION
       "A MEP has a persistent defect condition. A notification
        dot1agCfmMdIndex - Also the index of the MEP's
                              Maintenance Domain table entry
                              (dot1agCfmMdTable).
        dot1agCfmMaIndex - Also an index (with the MD table index)
                              of the MEP's Maintenance Association
                              network table entry
                              (dot1agCfmMaNetTable), and (with the MD
                              table index and component ID) of the
                              MEP's MA component table entry
                              (dot1agCfmMaCompTable).
        dot1agCfmMepIdentifier - MEP Identifier and final index
                              into the MEP table (dot1agCfmMepTable).
        dot1agCfmMepDbRMepIdentifier
       "
    REFERENCE
       "802.1ag clause 12.14.7.7"
    ::= { rcCfmNotifications 6 }

--------------------------------------------------------------------------------
--CFM multicast  loopback result Table 
--------------------------------------------------------------------------------
rcCfmMulticastLbResultTable 	OBJECT-TYPE
    SYNTAX      SEQUENCE OF RcCfmMulticastLbResultEntry
    MAX-ACCESS  not-accessible
    STATUS      current
    DESCRIPTION
        "CFM Multicast Loopback Result Table "  
    ::= { rcCfm 24 }
    
rcCfmMulticastLbResultEntry          			OBJECT-TYPE
	SYNTAX      RcCfmMulticastLbResultEntry
    MAX-ACCESS  not-accessible
    STATUS      current
    DESCRIPTION
        "An entry in the rcCfmMulticastLbResultTable.  "
    INDEX	{ dot1agCfmMdIndex, 
    		  dot1agCfmMaIndex,
    		  dot1agCfmMepIdentifier,
    		  rcCfmMcastLbResultIndex
    		}
    ::= { rcCfmMulticastLbResultTable 1 }   
    
RcCfmMulticastLbResultEntry ::= SEQUENCE {
    rcCfmMcastLbResultIndex         Unsigned32 (1..256),
	rcCfmMcastLbResultRemoteMepId   Unsigned32 (0..8191),
	rcCfmMcastLbResultRecvPort      Unsigned32 (0..65535),
	rcCfmMcastLbResultMacAddress	MacAddress,
	rcCfmMcastLbResultRtt           Unsigned32(0..5000)	
}                    

rcCfmMcastLbResultIndex    OBJECT-TYPE 
	SYNTAX      Unsigned32 (1..256)
	MAX-ACCESS  read-only
	STATUS      current
    DESCRIPTION
            "The fourth index to the multicast loopback table."
	::= { rcCfmMulticastLbResultEntry 1 }   
	
rcCfmMcastLbResultRemoteMepId    OBJECT-TYPE 
	SYNTAX      Unsigned32 (0..8191)
	MAX-ACCESS  read-only
	STATUS      current
    DESCRIPTION
            "The remote mep id."
	::= { rcCfmMulticastLbResultEntry 2 }  

rcCfmMcastLbResultRecvPort    OBJECT-TYPE 
	SYNTAX      Unsigned32 (0..65535)
	MAX-ACCESS  read-only
	STATUS      current
    DESCRIPTION
            "The lbr reveived port,0 means no lbr received."
	::= { rcCfmMulticastLbResultEntry 3 } 
	  
rcCfmMcastLbResultMacAddress    OBJECT-TYPE 
	SYNTAX      MacAddress
	MAX-ACCESS  read-only
	STATUS      current
    DESCRIPTION
            "The remote mep mac address,0000.0000.0000 means no remote mep mac."
	::= { rcCfmMulticastLbResultEntry 4 }  

rcCfmMcastLbResultRtt    OBJECT-TYPE 
	SYNTAX      Unsigned32
	MAX-ACCESS  read-only
	STATUS      current
    DESCRIPTION
            "lb rtt time,0 means rtt <1ms,5000 means timeout."
	::= { rcCfmMulticastLbResultEntry 5 }  

--------------------------------------------------------------------------------
--CFM mip extend Table 
--------------------------------------------------------------------------------
rcCfmMipExTable 	OBJECT-TYPE
    SYNTAX  SEQUENCE OF RcCfmMipExEntry
    ACCESS  not-accessible
    STATUS      current
    DESCRIPTION
        "CFM mip extend Table "  
    ::= { rcCfm 25 }
    
rcCfmMipExEntry     OBJECT-TYPE
	SYNTAX      RcCfmMipExEntry
    ACCESS  not-accessible
    STATUS      current
    DESCRIPTION
        "An entry in the rcCfmMipExTable."
    INDEX	{ dot1agCfmMaCompPrimaryVlanId, 
    		  rcCfmMipExIfIndex
    		  
    		}
    ::= { rcCfmMipExTable 1 }   
    
RcCfmMipExEntry ::= SEQUENCE {
    rcCfmMipExIfIndex         INTEGER,
	rcCfmMipRowStatus         RowStatus 
}                    

rcCfmMipExIfIndex    OBJECT-TYPE 
	SYNTAX      INTEGER
	MAX-ACCESS  read-create
	STATUS      current
    DESCRIPTION
            "The ifIndex of the manual-created MIP"
	::= { rcCfmMipExEntry 1 }   
	
rcCfmMipRowStatus OBJECT-TYPE
          SYNTAX    RowStatus
          ACCESS    read-create
          STATUS    current
          DESCRIPTION
                 "The status of this entry."
          ::= { rcCfmMipExEntry 2 } 

	
END

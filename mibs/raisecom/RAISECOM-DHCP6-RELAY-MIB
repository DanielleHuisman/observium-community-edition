--MibName=raisecomDhcp6Relay
RAISECOM-DHCP6-RELAY-MIB DEFINITIONS ::= BEGIN

    IMPORTS
        MODULE-IDENTITY, TimeTicks, OBJECT-TYPE
             FROM SNMPv2-SMI       
        RowStatus,MacAddress FROM SNMPv2-TC 
        EnableVar,Vlanset	 FROM SWITCH-TC    
        InetAddressIPv6      FROM INET-ADDRESS-MIB   
        raisecomAgent        FROM RAISECOM-BASE-MIB;  

    raisecomDhcp MODULE-IDENTITY
        LAST-UPDATED "201102180000Z"
        ORGANIZATION "raisecom Group"
        CONTACT-INFO
                "       Raise Systems
                        
                Postal: Beijing,
                        China

                   Tel: 86-010-82884499

                E-mail: aiyingjie@raisecom.com"
        DESCRIPTION
            "The MIB module for DHCPv6 Server Module."
    ::= { raisecomAgent 44}       
          
    raisecomDhcpRelay             OBJECT IDENTIFIER ::= { raisecomDhcp 3 }  
    raisecomDhcp6Relay            OBJECT IDENTIFIER ::= { raisecomDhcpRelay 1 }    
    
    raisecomDhcp6RNotifications    OBJECT IDENTIFIER ::= { raisecomDhcp6Relay 1 }        
    raisecomDhcp6RObjects          OBJECT IDENTIFIER ::= { raisecomDhcp6Relay 2 }   
    raisecomDhcp6RConformance      OBJECT IDENTIFIER ::= { raisecomDhcp6Relay 3 }  
         
    raisecomDhcp6RScalar              OBJECT IDENTIFIER ::= { raisecomDhcp6RObjects 1 }            
                                                                                    
-----------------raisecomDhcp6RelayConfig-------------------
                  
          raisecomDhcp6REnable OBJECT-TYPE
              SYNTAX  EnableVar 
              MAX-ACCESS  read-write
              STATUS  current
              DESCRIPTION
                      "The global switch of Dhcp6 server."
              DEFVAL { 2 }
              ::= { raisecomDhcp6RScalar 1 }
         
                            
---------------If Table--------------------------            
          raisecomDhcp6RIfTable OBJECT-TYPE
              SYNTAX  SEQUENCE OF raisecomDhcp6RIfEntry
              MAX-ACCESS  not-accessible
              STATUS  current
              DESCRIPTION
                      "A table that contains ip interface information
                      for the DHCP Server."
              ::= { raisecomDhcp6RObjects 2 }
              
          raisecomDhcp6RIfEntry OBJECT-TYPE
              SYNTAX  raisecomDhcp6RIfEntry
              MAX-ACCESS  not-accessible
              STATUS  current
              DESCRIPTION
                      "An entry that contains ip interface information
                      for the DHCP Server."
              INDEX   { raisecomDhcp6RIfIndex }
              ::= { raisecomDhcp6RIfTable 1 }
            
          raisecomDhcp6RIfEntry ::=
              SEQUENCE {
                  raisecomDhcp6RIfIndex	   INTEGER,
                  raisecomDhcp6RIfEnable   EnableVar
                  }
               
          raisecomDhcp6RIfIndex OBJECT-TYPE
              SYNTAX  INTEGER 
              MAX-ACCESS  not-accessible
              STATUS  current
              DESCRIPTION
                      "The index of ip interface number."
              ::= { raisecomDhcp6RIfEntry 1 }
              
          raisecomDhcp6RIfEnable OBJECT-TYPE
              SYNTAX  EnableVar
              MAX-ACCESS  read-write
              STATUS  current
              DESCRIPTION
                      "Enable Dhcp6 Server on interface."
              ::= { raisecomDhcp6RIfEntry 2 }
                   
---------------target table--------------------------                        
          raisecomDhcp6RIfTargetTable OBJECT-TYPE
              SYNTAX  SEQUENCE OF raisecomDhcp6RIfTargetEntry
              MAX-ACCESS  not-accessible
              STATUS  current
              DESCRIPTION
                      "A table that contains clients binding information."
              ::= { raisecomDhcp6RObjects 3 }
              
          raisecomDhcp6RIfTargetEntry OBJECT-TYPE
              SYNTAX  raisecomDhcp6RIfTargetEntry
              MAX-ACCESS  not-accessible
              STATUS  current
              DESCRIPTION
                      "A entry that contains clients binding information."
              INDEX   { raisecomDhcp6RIfTargetIndex,
                        raisecomDhcp6RIfTargetAddress }
              ::= { raisecomDhcp6RIfTargetTable 1 }
            
          raisecomDhcp6RIfTargetEntry ::=
              SEQUENCE {  
                  
                  raisecomDhcp6RIfTargetIndex INTEGER,
                  raisecomDhcp6RIfTargetAddress InetAddressIPv6,    
                  raisecomDhcp6RIfTargetOutLinkPort INTEGER,
                  raisecomDhcp6RIfTargetRowStatus  RowStatus                
                  }
           
          raisecomDhcp6RIfTargetIndex OBJECT-TYPE
              SYNTAX    INTEGER          
              MAX-ACCESS  not-accessible
              STATUS  current
              DESCRIPTION
                      "Indicates witch ip interface the client attached to."
              ::= { raisecomDhcp6RIfTargetEntry 1 } 
                  
          raisecomDhcp6RIfTargetAddress OBJECT-TYPE
              SYNTAX  InetAddressIPv6
              MAX-ACCESS  not-accessible
              STATUS  current
              DESCRIPTION
                      "The link-local address of client."
              ::= { raisecomDhcp6RIfTargetEntry 2 }                  
              
           raisecomDhcp6RIfTargetOutLinkPort OBJECT-TYPE
              SYNTAX    INTEGER          
              MAX-ACCESS  read-create
              STATUS  current
              DESCRIPTION
                      "Indicates witch ip interface the client attached to."
              ::= { raisecomDhcp6RIfTargetEntry 3 }     
              
           raisecomDhcp6RIfTargetRowStatus OBJECT-TYPE
              SYNTAX  RowStatus
              MAX-ACCESS  read-create
              STATUS  current
              DESCRIPTION
                      "The row status of this entry.."
              ::= { raisecomDhcp6RIfTargetEntry 4 }                 
              
 END

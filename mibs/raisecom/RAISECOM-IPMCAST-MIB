-- *****************************************************************
-- RAISECOM-IPMCAST-MIB.mib:  IPMCAST MIB
--
-- January 2012, xuguiping
--
-- Copyright (c) 1996-2009 by Raisecom Technology Co., Ltd.
-- All rights reserved.
--
-- *****************************************************************
--

RAISECOM-IPMCAST-MIB DEFINITIONS ::= BEGIN

IMPORTS
        MODULE-IDENTITY, OBJECT-TYPE, Integer32 	FROM SNMPv2-SMI
        TEXTUAL-CONVENTION, MacAddress, RowStatus	FROM SNMPv2-TC
        EnableVar	  								FROM SWITCH-TC
        rcPortIndex							        FROM SWITCH-SYSTEM-MIB
        raisecomAgent                           	FROM RAISECOM-BASE-MIB
        InetAddress, InetAddressType, 
        InetAddressIPv6                             FROM INET-ADDRESS-MIB    -- [RFC4001]       
        InterfaceIndexOrZero,
        InterfaceIndex                              FROM IF-MIB;             -- [RFC2863]

raisecomIpmcast   MODULE-IDENTITY
        LAST-UPDATED    "201201050000Z"
        ORGANIZATION    "Raisecom Technology Co., Ltd."
        CONTACT-INFO
		                "Raisecom Science & Technology Co., ltd.
		                 E-mail: support@raisecom.com"
        DESCRIPTION
		        		"This MIB module defines a MIB which provides
		                mechanisms to the IPMCAST."

        REVISION     	"201201050000Z"
        DESCRIPTION
            		 	"version 1.0"

        ::= { raisecomAgent 71 }

raisecomIpmcastNotifications	OBJECT IDENTIFIER ::= {	raisecomIpmcast 1 }
raisecomIpmcastObjects			OBJECT IDENTIFIER ::= {	raisecomIpmcast 2 }   
raisecomIpmcastConformance		OBJECT IDENTIFIER ::= {	raisecomIpmcast 3 }  
                                                                                                   
raisecomIpMcastScalar		    OBJECT IDENTIFIER ::= {	raisecomIpmcastObjects 1 }  
        
raisecomIpMcastRouteLimit OBJECT-TYPE           
        SYNTAX      INTEGER
		MAX-ACCESS  read-write
        STATUS      current
        DESCRIPTION
               "The limit of multicast route table. 
                The upper limit is depended on device." 
        ::= { raisecomIpMcastScalar 1 }   
        
raisecomIpMcastOifLimitPerRoute OBJECT-TYPE           
        SYNTAX      INTEGER 
        MAX-ACCESS  read-write
        STATUS      current
        DESCRIPTION
               "The limit of downstream interface per multicast route entry.
                The upper limit is depended on device."     
        ::= { raisecomIpMcastScalar 2 }
        
raisecomIpMcastStaticTable 	OBJECT-TYPE
        SYNTAX      SEQUENCE OF RaisecomIpMcastStaticEntry
        MAX-ACCESS  not-accessible
        STATUS      current
        DESCRIPTION
	        		"This table provides the static mroute information."
        ::= { raisecomIpmcastObjects 2 }
 
raisecomIpMcastStaticEntry 	OBJECT-TYPE
        SYNTAX      RaisecomIpMcastStaticEntry
        MAX-ACCESS  not-accessible
        STATUS      current
        DESCRIPTION
	        		"Each entry provides the static mroute information."
        INDEX   	{ raisecomIpMcastStaticSAddressType,
        			  raisecomIpMcastStaticSAddress,
        			  raisecomIpMcastStaticSAddressPrefix}
        ::= { raisecomIpMcastStaticTable 1 }

RaisecomIpMcastStaticEntry ::= SEQUENCE { 
		raisecomIpMcastStaticSAddressType		InetAddressType,
		raisecomIpMcastStaticSAddress    		InetAddress,
		raisecomIpMcastStaticSAddressPrefix 	INTEGER,
		raisecomIpMcastStaticNAddressType		InetAddressType,
		raisecomIpMcastStaticNAddress       	InetAddress,
		raisecomIpMcastStaticIfIndex       	    InterfaceIndexOrZero,
		raisecomIpMcastStaticPreference        	INTEGER,
		raisecomIpMcastStaticRowStatus       	RowStatus
        }
  
raisecomIpMcastStaticSAddressType 	OBJECT-TYPE
        SYNTAX      InetAddressType
        MAX-ACCESS  not-accessible
        STATUS      current
        DESCRIPTION
	        		"The address type of the multicast source."
        ::= { raisecomIpMcastStaticEntry 1 }
        
raisecomIpMcastStaticSAddress  OBJECT-TYPE    
        SYNTAX      InetAddress
        MAX-ACCESS  not-accessible
        STATUS      current
        DESCRIPTION
	        		"The address of the multicast source."  
        ::= { raisecomIpMcastStaticEntry 2 }  
        
raisecomIpMcastStaticSAddressPrefix  OBJECT-TYPE
        SYNTAX      INTEGER
        MAX-ACCESS  not-accessible
        STATUS      current
        DESCRIPTION
	        		"The prefix length of the multicast source address."
        ::= { raisecomIpMcastStaticEntry 3 }     
        
raisecomIpMcastStaticNAddressType OBJECT-TYPE
        SYNTAX      InetAddressType
        MAX-ACCESS  read-write
        STATUS      current
        DESCRIPTION
	        		"The address type of the next hop."
        ::= { raisecomIpMcastStaticEntry 4 }           
   
raisecomIpMcastStaticNAddress OBJECT-TYPE
        SYNTAX      InetAddress
        MAX-ACCESS  read-write
        STATUS      current
        DESCRIPTION
	        		"The address of the next hop."
        ::= { raisecomIpMcastStaticEntry 5 }    
        
raisecomIpMcastStaticIfIndex OBJECT-TYPE
        SYNTAX      InterfaceIndexOrZero
        MAX-ACCESS  read-write
        STATUS      current
        DESCRIPTION
	        		"The interface index of the next hop. A value of 0 
	        		indicates that the next hop interface is unknown."
        ::= { raisecomIpMcastStaticEntry 6 }   
        
raisecomIpMcastStaticPreference OBJECT-TYPE
        SYNTAX      INTEGER 
        MAX-ACCESS  read-write
        STATUS      current
        DESCRIPTION
	        		"The preference of the static route protocol."   
	   	DEFVAL {0}

        ::= { raisecomIpMcastStaticEntry 7 } 
        
raisecomIpMcastStaticRowStatus OBJECT-TYPE
        SYNTAX      RowStatus
        MAX-ACCESS  read-create
        STATUS      current
        DESCRIPTION
	        		"The row status of this entry."
        ::= { raisecomIpMcastStaticEntry 8 }
        
--
-- END of RAISECOM-IPMCAST-MIB
--

END

-- =======================================================================
-- Version info 
-- 
--Modify Record 
--01, 20100401, huochao ,  having compile errors ,chang at :
--      1. add ：DisplayString      FROM SNMPv2-TC
--      2. RaisecomModuleEntry    OBJECT-TYPE   
--             SYNTAX          RaisecomModuleEntry  changed to: raisecomModuleEntry         	    
--      3.  ::= { raisecomModuleManageGroup 1 }     changed to::= { raisecomModuleManagementGroup  }
--        
--
-- Version 0.1 Created 2008.11.24 by YINGJIANGANG
-- This version of MIB is created just for management of module information. 
-- Copyright(c) 2003-2008 by RAISECOM TECH, Ltd. 
-- =======================================================================

-- ===========================================================================
--
--
-- RAISECOM module management objects
--            

RAISECOM-MODULE-MANAGEMENT-MIB DEFINITIONS ::= BEGIN

    IMPORTS
		MODULE-IDENTITY,
		OBJECT-TYPE,
		Integer32
			FROM SNMPv2-SMI
        DisplayString
            FROM SNMPv2-TC			
		raisecomAgent
			FROM RAISECOM-BASE-MIB;

	raisecomModuleManagementGroup    MODULE-IDENTITY
		LAST-UPDATED 	"200811240000Z"
		ORGANIZATION 	"RAISECOM TECH, Ltd."
		CONTACT-INFO 	"www.raisecom.com"
		DESCRIPTION  	
		    "The MIB module defining objects for module information management functions"
		::= { raisecomAgent  17}  
	                
	--groups                 

--	raisecomModuleManageGroup 	OBJECT IDENTIFIER ::= {raisecomAgent 17}
  
  

  -- raisecomModuleManageGroup

     --user module table
    raisecomModuleTable    OBJECT-TYPE
        SYNTAX          SEQUENCE OF RaisecomModuleEntry
        MAX-ACCESS      not-accessible
        STATUS          current
        DESCRIPTION     "Module manage table"
    ::= { raisecomModuleManagementGroup 1 }

    raisecomModuleEntry    OBJECT-TYPE
				SYNTAX          RaisecomModuleEntry
				MAX-ACCESS      not-accessible
        STATUS          current
				DESCRIPTION     "An entry of the module information table."
				INDEX { raisecomModuleName }
    ::= { raisecomModuleTable 1 }

    RaisecomModuleEntry ::=
        SEQUENCE {
		raisecomModuleName 					OCTET STRING (SIZE (1..16)),
		raisecomModuleClass					Integer32,   
		raisecomModuleCreateDate  	OCTET STRING (SIZE (10)),
		raisecomModuleReleaseDate		OCTET STRING (SIZE (10)),
		raisecomModuleVersion    		OCTET STRING (SIZE (10)),
		raisecomModuleDescription 	DisplayString,        
		raisecomModuleSubModule   	DisplayString,
		raisecomModuleRelayonModule DisplayString,
		raisecomModuleRelatedTask 	DisplayString	        
        }

	raisecomModuleName         OBJECT-TYPE
        SYNTAX          OCTET STRING (SIZE (1..16))        
        MAX-ACCESS      not-accessible
        STATUS          current
        DESCRIPTION     
            "The name of the module."
    ::= { raisecomModuleEntry 1 }   
    
    raisecomModuleClass     OBJECT-TYPE
        SYNTAX          Integer32{
        			 	kernel(1),
        			 	library(2),
        			 	driver(3),
        			 	protocol(4),
        			 	management(5),
        			 	registry(6),
        			 	systeminit(7)
        			 	}
        MAX-ACCESS      read-only
        STATUS          current
        DESCRIPTION     
            "The class of the module."
    ::= { raisecomModuleEntry 2 }    


    raisecomModuleCreateDate  OBJECT-TYPE
        SYNTAX 		OCTET STRING (SIZE (10))
        MAX-ACCESS 	read-only
        STATUS current
        DESCRIPTION
            "The create local date of the module. Date format is as YYYY-MM-DD, for example 2008-07-25"
        ::= { raisecomModuleEntry 3 }
    
    raisecomModuleReleaseDate  OBJECT-TYPE
        SYNTAX 		OCTET STRING (SIZE (10))
        MAX-ACCESS 	read-only
        STATUS current
        DESCRIPTION
            "The release date of the module. Date format is as YYYY-MM-DD, for example 2008-07-25"
        ::= { raisecomModuleEntry 4 }
    
    raisecomModuleVersion  OBJECT-TYPE
        SYNTAX 		OCTET STRING (SIZE (10))
        MAX-ACCESS 	read-only
        STATUS current
        DESCRIPTION
            "The version of the module.Version format is as xx.yy.zzzz, for example 01.02.0012."
        ::= { raisecomModuleEntry 5 }
    
    raisecomModuleDescription  OBJECT-TYPE
        SYNTAX 		DisplayString
        MAX-ACCESS 	read-only
        STATUS current
        DESCRIPTION
            "The description of the module."
        ::= { raisecomModuleEntry 6 }

    raisecomModuleSubModule  OBJECT-TYPE
        SYNTAX 		DisplayString
        MAX-ACCESS 	read-only
        STATUS current
        DESCRIPTION
            "The sub-module name list of the module."
        ::= { raisecomModuleEntry 7 }

    raisecomModuleRelayonModule  OBJECT-TYPE
        SYNTAX 		DisplayString
        MAX-ACCESS 	read-only
        STATUS current
        DESCRIPTION
            "The relay on module name list of the module."
        ::= { raisecomModuleEntry 8 }

    raisecomModuleRelatedTask  OBJECT-TYPE
        SYNTAX 		DisplayString
        MAX-ACCESS 	read-only
        STATUS current
        DESCRIPTION
            "The related task name list of the module."
        ::= { raisecomModuleEntry 9 }
                        
END

-- MibName=rcPerformance
-- *****************************************************************
-- RAISECOM-PERF-MIB DEFINITIONS:	 Raisecom PERF MIB file
--
-- Dec 2012, liconge
--
-- Copyright (c) 1994-2012,	2012 by	Raisecom, Inc.
-- All rights reserved.
--    
-- 
-- *****************************************************************

RAISECOM-PERF-MIB DEFINITIONS ::= BEGIN

IMPORTS
		    iscomSwitch
				    FROM RAISECOM-BASE-MIB
		    MacAddress
				    FROM SNMPv2-TC
        RowStatus
        		FROM SNMPv2-TC  
        Ipv6Address 
            FROM IPV6-TC
        PortList 
            FROM SWITCH-TC
        Vlanset 
            FROM SWITCH-TC
       TimeTicks
            FROM RFC1155-SMI
       DateAndTime
       			FROM SWITCH-TC
		    Gauge32
				    FROM SNMPv2-SMI;

rcPerformance MODULE-IDENTITY
		LAST-UPDATED	"201212270000Z"
		ORGANIZATION	"Raisecom, Inc."
		CONTACT-INFO
				"		Raise Systems

				    Postal:	Beijing, China

				       Tel:	86-010-82884499

				    E-mail:	support@raisecom.com"
		DESCRIPTION
				"The MIB module for performance management."
				::=	{ iscomSwitch	76 }

-- START rcPerformanceControlGroup 
	
	rcPerformanceControlGroup	  OBJECT IDENTIFIER ::= {	rcPerformance 1 }  
		
	rcPerformanceShortBucketsNum   OBJECT-TYPE
		    SYNTAX  INTEGER (10..100)
		    ACCESS read-write
		    STATUS current
		    DESCRIPTION
		        "The buckets number of short interval."
		    ::= {  rcPerformanceControlGroup 1 }
	
	rcPerformanceLongBucketsNum   OBJECT-TYPE
		    SYNTAX  INTEGER (3..100)
		    ACCESS read-write
		    STATUS current
		    DESCRIPTION
		        "The buckets number of long interval."
		    ::= {  rcPerformanceControlGroup 2 }
		    	
  rcPerformanceShortVlanPeriod         OBJECT-TYPE
		    SYNTAX INTEGER (1..24)
		    ACCESS  read-write
		    STATUS  current
		    DESCRIPTION
		        "The short peroid number of writing vlan performance data."
		    ::= {  rcPerformanceControlGroup 3 }
		
  rcPerformanceShortInterfacePeriod         OBJECT-TYPE
		    SYNTAX INTEGER (1..24)
		    ACCESS  read-write
		    STATUS  current
		    DESCRIPTION
		        "The short peroid number of writing interface performance data."
		    ::= {  rcPerformanceControlGroup 4 }	   
		    
  rcPerformanceLongVlanPeriod         OBJECT-TYPE
		    SYNTAX INTEGER (1..30)
		    ACCESS  read-write
		    STATUS  current
		    DESCRIPTION
		        "The long peroid number of writing vlan performance data."
		    ::= {  rcPerformanceControlGroup 5 }
		    
  rcPerformanceLongInterfacePeriod         OBJECT-TYPE
		    SYNTAX INTEGER (1..30)
		    ACCESS  read-write
		    STATUS  current
		    DESCRIPTION
		        "The long peroid number of writing interface performance data."
		    ::= {  rcPerformanceControlGroup 6 }
		    
  rcPerformanceNvramEnable             OBJECT-TYPE
		    SYNTAX  INTEGER
		    {
		    	Enable(1),
		 			Disable(2)
				}
		    ACCESS  read-write
		    STATUS  current
		    DESCRIPTION
		        "Indicates whether the Remote Device must be able to periodically create performance data files.
 						Enable(1) means that the Remote Device should be periodically create performance data files.
 						Disable(2) means that the Remote Device should not be periodically create performance data files."
		    ::= {  rcPerformanceControlGroup 7 }
		    	  		     
	rcPerformanceClearHistory             OBJECT-TYPE
		    SYNTAX  INTEGER
		    {
		    	clear(1)
				}
		    ACCESS  read-write
		    STATUS  current
		    DESCRIPTION
		        "Clear all the history data."
		    ::= {  rcPerformanceControlGroup 8 }	   
		    
--  END rcPerformanceControlGroup 
		        
--  START rcPerformancePortControlTable 
  	
  rcPerformancePortControlTable             OBJECT-TYPE
		SYNTAX		SEQUENCE OF	rcPerformancePortControlEntry       
		MAX-ACCESS	not-accessible
		STATUS		current
		DESCRIPTION
			"A table of	Port control."
		::=	{ rcPerformance 2}
		
	rcPerformancePortControlEntry              OBJECT-TYPE
		SYNTAX		rcPerformancePortControlEntry
		MAX-ACCESS	not-accessible
		STATUS		current
		DESCRIPTION
			"Table entry for Port. control"
		INDEX {	rcPerformancePortIndex  }
		::=	{ rcPerformancePortControlTable 1 }

	rcPerformancePortControlEntry ::= SEQUENCE {
		rcPerformancePortIndex					          INTEGER	(0..14),
		rcPerformancePortEnable   				        INTEGER,
		rcPerformancePortFileEnable        			  INTEGER,
		}

	rcPerformancePortIndex     OBJECT-TYPE
		SYNTAX	INTEGER
		ACCESS	read-only
		STATUS	current
		DESCRIPTION
			"An index that uniquely identifies an entry in
             the performance port control table."
		::=	{ rcPerformancePortControlEntry 1 }
		
	rcPerformancePortEnable     OBJECT-TYPE
		SYNTAX  INTEGER
		{
		   Enable(1),
		 	 Disable(2)
		}
		ACCESS	read-write
		STATUS	current
		DESCRIPTION
			"Enable/Disable port performance."
		::=	{ rcPerformancePortControlEntry 2 }
		
	rcPerformancePortFileEnable     OBJECT-TYPE
		SYNTAX  INTEGER
		{
		   Enable(1),
		 	 Disable(2)
		}
		ACCESS	read-write
		STATUS	current
		DESCRIPTION
			"Enable/Disable port performance data create files."
		::=	{ rcPerformancePortControlEntry 3 }
		
-- END rcPerformancePortControlTable
		
-- START rcPerformanceVlanControlTable
  	
  rcPerformanceVlanControlTable             OBJECT-TYPE
		SYNTAX		SEQUENCE OF	rcPerformanceVlanControlEntry       
		MAX-ACCESS	not-accessible
		STATUS		current
		DESCRIPTION
			"A table of	Vlan control."
		::=	{ rcPerformance 3 }
		
  rcPerformanceVlanControlEntry              OBJECT-TYPE
		SYNTAX		rcPerformanceVlanControlEntry
		MAX-ACCESS	not-accessible
		STATUS		current
		DESCRIPTION
			"Table entry for Vlan."
		INDEX {	rcPerformanceVlanIndex }
		::=	{ rcPerformanceVlanControlTable 1 }

	rcPerformanceVlanControlEntry ::= SEQUENCE {
		rcPerformanceVlanIndex					            INTEGER,
		rcPerformanceVlanCosEnale        					  INTEGER,
		rcPerformanceVlanFileEnable                 INTEGER,
		rcPerformanceVlanCosRowStatus               RowStatus
		}

	rcPerformanceVlanIndex     OBJECT-TYPE
		SYNTAX	INTEGER
		ACCESS	read-only
		STATUS	current
		DESCRIPTION
			"An index that uniquely identifies an entry in
             the performance vlan control table."
		::=	{ rcPerformanceVlanControlEntry 1 }
				
	rcPerformanceVlanCosEnale     OBJECT-TYPE
		SYNTAX  INTEGER
		{
		   Enable(1),
		 	 Disable(2)
		}
		ACCESS	read-create
		STATUS	current
		DESCRIPTION
			"Performance object vlan support cos."
		::=	{ rcPerformanceVlanControlEntry 2 }		
			
	rcPerformanceVlanFileEnable     OBJECT-TYPE
		SYNTAX  INTEGER
		{
		   Enable(1),
		 	 Disable(2)
		}
		ACCESS	read-create
		STATUS	current
		DESCRIPTION
			"Enable/Disable vlan  performance data creat files."
		::=	{ rcPerformanceVlanControlEntry 3 }
	
	rcPerformanceVlanCosRowStatus OBJECT-TYPE
        SYNTAX        RowStatus
        MAX-ACCESS    read-create
        STATUS        current
	DESCRIPTION  
		"The vlan control status."
        ::= { rcPerformanceVlanControlEntry 4 }    
       	
-- END rcPerformanceVlanControlTable

-- START rcPerformanceShortPortHistoryTable 
   
  rcPerformanceShortPortHistoryTable             OBJECT-TYPE
		SYNTAX		SEQUENCE OF	rcPerformanceShortPortHistoryEntry       
		MAX-ACCESS	not-accessible
		STATUS		current
		DESCRIPTION
			"A table of	short interval port counters value."
		::=	{ rcPerformance 4}
		
	rcPerformanceShortPortHistoryEntry              OBJECT-TYPE
		SYNTAX		rcPerformanceShortPortHistoryEntry
		MAX-ACCESS	not-accessible
		STATUS		current
		DESCRIPTION
			"Table entry for Port counter value."
		INDEX {	rcPerformanceShortPortHistoryPortIndex, rcPerformanceShortPortHistorySampleIndex}
		::=	{ rcPerformanceShortPortHistoryTable 1 }

	rcPerformanceShortPortHistoryEntry ::= SEQUENCE {
		rcPerformanceShortPortHistoryPortIndex        			INTEGER,
		rcPerformanceShortPortHistorySampleIndex      			INTEGER,
		rcPerformanceShortPortHistoryIntervalStart    			DateAndTime,
		rcPerformanceShortPortHistoryStatus           			INTEGER,
    rcPerformanceShortPortHistoryInOctets		      			Counter64,
    rcPerformanceShortPortHistoryOutOctets        			Counter64,
    rcPerformanceShortPortHistoryInUcastPkts	        	Counter64,
    rcPerformanceShortPortHistoryOutUcastPkts	          Counter64,
    rcPerformanceShortPortHistoryInMulticastPkts				Counter64,
    rcPerformanceShortPortHistoryOutMulticastPkts				Counter64,
    rcPerformanceShortPortHistoryInBroadcastPkts				Counter64,
    rcPerformanceShortPortHistoryOutBroadcastPkts				Counter64,
    rcPerformanceShortPortHistoryInErrors								Counter64,
    rcPerformanceShortPortHistoryOutErrors							Counter64,
    rcPerformanceShortPortHistoryInDiscards							Counter64,
    rcPerformanceShortPortHistoryOutDiscards						Counter64,
    rcPerformanceShortPortHistoryInUnknowProtos      		Counter64		      					  
		}
    
	rcPerformanceShortPortHistoryPortIndex     OBJECT-TYPE
		SYNTAX	INTEGER
		ACCESS	read-only
		STATUS	current
		DESCRIPTION
			"An index that uniquely identifies an entry in
             the performance port counter table."
		::=	{ rcPerformanceShortPortHistoryEntry 1 }
		
	rcPerformanceShortPortHistorySampleIndex     OBJECT-TYPE
		SYNTAX	INTEGER
		ACCESS	read-only
		STATUS	current
		DESCRIPTION
			"An index that uniquely identifies the particular
 	sample this entry represents performance all samples
 	associated with the same historyControlEntry.
 	This index starts at 1 and increases by one
 	as each new sample is taken."
		::=	{ rcPerformanceShortPortHistoryEntry 2 }
			
	rcPerformanceShortPortHistoryIntervalStart       OBJECT-TYPE
		SYNTAX	DateAndTime
		ACCESS	read-only
		STATUS	current
		DESCRIPTION
			"Peroid start time."
		::=	{ rcPerformanceShortPortHistoryEntry 3 }		
		
	rcPerformanceShortPortHistoryStatus     OBJECT-TYPE
		SYNTAX	INTEGER
		{
		    Valid(1),
		 		Invalid(2)
		}
		ACCESS	read-only
		STATUS	current
		DESCRIPTION
			"Mark the invalid performance data."
		::=	{ rcPerformanceShortPortHistoryEntry 4 }	
		
	rcPerformanceShortPortHistoryInOctets     OBJECT-TYPE
		SYNTAX	Counter64
		ACCESS	read-only
		STATUS	current
		DESCRIPTION
			"Income octets number."
		::=	{ rcPerformanceShortPortHistoryEntry 5 }
		
	rcPerformanceShortPortHistoryOutOctets     OBJECT-TYPE
		SYNTAX	Counter64
		ACCESS	read-only
		STATUS	current
		DESCRIPTION
			"Out octets number."
		::=	{ rcPerformanceShortPortHistoryEntry 6 }
		
	rcPerformanceShortPortHistoryInUcastPkts     OBJECT-TYPE
		SYNTAX	Counter64
		ACCESS	read-only
		STATUS	current
		DESCRIPTION
			"Income uncast packets number."
		::=	{ rcPerformanceShortPortHistoryEntry 7 }
		
	rcPerformanceShortPortHistoryOutUcastPkts     OBJECT-TYPE
		SYNTAX	Counter64
		ACCESS	read-only
		STATUS	current
		DESCRIPTION
			"Out uncast packets number."
		::=	{ rcPerformanceShortPortHistoryEntry 8 }
		
	rcPerformanceShortPortHistoryInMulticastPkts     OBJECT-TYPE
		SYNTAX	Counter64
		ACCESS	read-only
		STATUS	current
		DESCRIPTION
			"Income multicast packets number."
		::=	{ rcPerformanceShortPortHistoryEntry 9 }
		
	rcPerformanceShortPortHistoryOutMulticastPkts     OBJECT-TYPE
		SYNTAX	Counter64
		ACCESS	read-only
		STATUS	current
		DESCRIPTION
			"Out multicast packets number."
		::=	{ rcPerformanceShortPortHistoryEntry 10 }
		
	rcPerformanceShortPortHistoryInBroadcastPkts     OBJECT-TYPE
		SYNTAX	Counter64
		ACCESS	read-only
		STATUS	current
		DESCRIPTION
			"Income Broadcast packets number."
		::=	{ rcPerformanceShortPortHistoryEntry 11 }
		
	rcPerformanceShortPortHistoryOutBroadcastPkts     OBJECT-TYPE
		SYNTAX	Counter64
		ACCESS	read-only
		STATUS	current
		DESCRIPTION
			"Out Broadcast packets number."
		::=	{ rcPerformanceShortPortHistoryEntry 12 }
		
	rcPerformanceShortPortHistoryInErrors     OBJECT-TYPE
		SYNTAX	Counter64
		ACCESS	read-only
		STATUS	current
		DESCRIPTION
			"Income error packets number."
		::=	{ rcPerformanceShortPortHistoryEntry 13 }
		
	rcPerformanceShortPortHistoryOutErrors     OBJECT-TYPE
		SYNTAX	Counter64
		ACCESS	read-only
		STATUS	current
		DESCRIPTION
			"Out error packets number."
		::=	{ rcPerformanceShortPortHistoryEntry 14 }
		
	rcPerformanceShortPortHistoryInDiscards     OBJECT-TYPE
		SYNTAX	Counter64
		ACCESS	read-only
		STATUS	current
		DESCRIPTION
			"Income discard packets number."
		::=	{ rcPerformanceShortPortHistoryEntry 15 }
		
	rcPerformanceShortPortHistoryOutDiscards     OBJECT-TYPE
		SYNTAX	Counter64
		ACCESS	read-only
		STATUS	current
		DESCRIPTION
			"Out discard packets number."
		::=	{ rcPerformanceShortPortHistoryEntry 16 }
		
	rcPerformanceShortPortHistoryInUnknowProtos   OBJECT-TYPE
		SYNTAX	Counter64
		ACCESS	read-only
		STATUS	current
		DESCRIPTION
			"Income Unknow Protos number."
		::=	{ rcPerformanceShortPortHistoryEntry 17 }
		
-- END rcPerformanceShortPortHistoryTable 

-- START rcPerformanceLongPortHistoryTable 
   
  rcPerformanceLongPortHistoryTable             OBJECT-TYPE
		SYNTAX		SEQUENCE OF	rcPerformanceLongPortHistoryEntry       
		MAX-ACCESS	not-accessible
		STATUS		current
		DESCRIPTION
			"A table of	Long interval port counters value."
		::=	{ rcPerformance 5}
		
	rcPerformanceLongPortHistoryEntry              OBJECT-TYPE
		SYNTAX		rcPerformanceLongPortHistoryEntry
		MAX-ACCESS	not-accessible
		STATUS		current
		DESCRIPTION
			"Table entry for Port counter value."
		INDEX {	rcPerformanceLongPortHistoryPortIndex, rcPerformanceLongPortHistorySampleIndex}
		::=	{ rcPerformanceLongPortHistoryTable 1 }

	rcPerformanceLongPortHistoryEntry ::= SEQUENCE {
		rcPerformanceLongPortHistoryPortIndex        			INTEGER,
		rcPerformanceLongPortHistorySampleIndex      			INTEGER,
		rcPerformanceLongPortHistoryIntervalStart    			DateAndTime,
		rcPerformanceLongPortHistoryStatus           			INTEGER,
    rcPerformanceLongPortHistoryInOctets		      			Counter64,
    rcPerformanceLongPortHistoryOutOctets        			Counter64,
    rcPerformanceLongPortHistoryInUcastPkts	        	Counter64,
    rcPerformanceLongPortHistoryOutUcastPkts	          Counter64,
    rcPerformanceLongPortHistoryInMulticastPkts				Counter64,
    rcPerformanceLongPortHistoryOutMulticastPkts				Counter64,
    rcPerformanceLongPortHistoryInBroadcastPkts				Counter64,
    rcPerformanceLongPortHistoryOutBroadcastPkts				Counter64,
    rcPerformanceLongPortHistoryInErrors								Counter64,
    rcPerformanceLongPortHistoryOutErrors							Counter64,
    rcPerformanceLongPortHistoryInDiscards							Counter64,
    rcPerformanceLongPortHistoryOutDiscards						Counter64,
    rcPerformanceLongPortHistoryInUnknowProtos      		Counter64		      					  
		}
    
	rcPerformanceLongPortHistoryPortIndex     OBJECT-TYPE
		SYNTAX	INTEGER
		ACCESS	read-only
		STATUS	current
		DESCRIPTION
			"An index that uniquely identifies an entry in
             the performance port counter table."
		::=	{ rcPerformanceLongPortHistoryEntry 1 }
		
	rcPerformanceLongPortHistorySampleIndex     OBJECT-TYPE
		SYNTAX	INTEGER
		ACCESS	read-only
		STATUS	current
		DESCRIPTION
			"An index that uniquely identifies the particular
 	sample this entry represents performance all samples
 	associated with the same historyControlEntry.
 	This index starts at 1 and increases by one
 	as each new sample is taken."
		::=	{ rcPerformanceLongPortHistoryEntry 2 }
			
	rcPerformanceLongPortHistoryIntervalStart       OBJECT-TYPE
		SYNTAX	DateAndTime
		ACCESS	read-only
		STATUS	current
		DESCRIPTION
			"Peroid start time."
		::=	{ rcPerformanceLongPortHistoryEntry 3 }		
		
	rcPerformanceLongPortHistoryStatus     OBJECT-TYPE
		SYNTAX	INTEGER
		{
		    Valid(1),
		 		Invalid(2)
		}
		ACCESS	read-only
		STATUS	current
		DESCRIPTION
			"Mark the invalid performance data."
		::=	{ rcPerformanceLongPortHistoryEntry 4 }	
		
	rcPerformanceLongPortHistoryInOctets     OBJECT-TYPE
		SYNTAX	Counter64
		ACCESS	read-only
		STATUS	current
		DESCRIPTION
			"Income octets number."
		::=	{ rcPerformanceLongPortHistoryEntry 5 }
		
	rcPerformanceLongPortHistoryOutOctets     OBJECT-TYPE
		SYNTAX	Counter64
		ACCESS	read-only
		STATUS	current
		DESCRIPTION
			"Out octets number."
		::=	{ rcPerformanceLongPortHistoryEntry 6 }
		
	rcPerformanceLongPortHistoryInUcastPkts     OBJECT-TYPE
		SYNTAX	Counter64
		ACCESS	read-only
		STATUS	current
		DESCRIPTION
			"Income uncast packets number."
		::=	{ rcPerformanceLongPortHistoryEntry 7 }
		
	rcPerformanceLongPortHistoryOutUcastPkts     OBJECT-TYPE
		SYNTAX	Counter64
		ACCESS	read-only
		STATUS	current
		DESCRIPTION
			"Out uncast packets number."
		::=	{ rcPerformanceLongPortHistoryEntry 8 }
		
	rcPerformanceLongPortHistoryInMulticastPkts     OBJECT-TYPE
		SYNTAX	Counter64
		ACCESS	read-only
		STATUS	current
		DESCRIPTION
			"Income multicast packets number."
		::=	{ rcPerformanceLongPortHistoryEntry 9 }
		
	rcPerformanceLongPortHistoryOutMulticastPkts     OBJECT-TYPE
		SYNTAX	Counter64
		ACCESS	read-only
		STATUS	current
		DESCRIPTION
			"Out multicast packets number."
		::=	{ rcPerformanceLongPortHistoryEntry 10 }
		
	rcPerformanceLongPortHistoryInBroadcastPkts     OBJECT-TYPE
		SYNTAX	Counter64
		ACCESS	read-only
		STATUS	current
		DESCRIPTION
			"Income Broadcast packets number."
		::=	{ rcPerformanceLongPortHistoryEntry 11 }
		
	rcPerformanceLongPortHistoryOutBroadcastPkts     OBJECT-TYPE
		SYNTAX	Counter64
		ACCESS	read-only
		STATUS	current
		DESCRIPTION
			"Out Broadcast packets number."
		::=	{ rcPerformanceLongPortHistoryEntry 12 }
		
	rcPerformanceLongPortHistoryInErrors     OBJECT-TYPE
		SYNTAX	Counter64
		ACCESS	read-only
		STATUS	current
		DESCRIPTION
			"Income error packets number."
		::=	{ rcPerformanceLongPortHistoryEntry 13 }
		
	rcPerformanceLongPortHistoryOutErrors     OBJECT-TYPE
		SYNTAX	Counter64
		ACCESS	read-only
		STATUS	current
		DESCRIPTION
			"Out error packets number."
		::=	{ rcPerformanceLongPortHistoryEntry 14 }
		
	rcPerformanceLongPortHistoryInDiscards     OBJECT-TYPE
		SYNTAX	Counter64
		ACCESS	read-only
		STATUS	current
		DESCRIPTION
			"Income discard packets number."
		::=	{ rcPerformanceLongPortHistoryEntry 15 }
		
	rcPerformanceLongPortHistoryOutDiscards     OBJECT-TYPE
		SYNTAX	Counter64
		ACCESS	read-only
		STATUS	current
		DESCRIPTION
			"Out discard packets number."
		::=	{ rcPerformanceLongPortHistoryEntry 16 }
		
	rcPerformanceLongPortHistoryInUnknowProtos   OBJECT-TYPE
		SYNTAX	Counter64
		ACCESS	read-only
		STATUS	current
		DESCRIPTION
			"Income Unknow Protos number."
		::=	{ rcPerformanceLongPortHistoryEntry 17 }
		
-- END rcPerformanceLongPortHistoryTable

-- START rcPerformanceShortVlanHistoryTable

  rcPerformanceShortVlanHistoryTable             OBJECT-TYPE
		SYNTAX		SEQUENCE OF	rcPerformanceShortVlanHistoryEntry        
		MAX-ACCESS	not-accessible
		STATUS		current
		DESCRIPTION
			"A table of	short interval vlan counter."
		::=	{ rcPerformance 6}
		
	rcPerformanceShortVlanHistoryEntry               OBJECT-TYPE
		SYNTAX		rcPerformanceShortVlanHistoryEntry 
		MAX-ACCESS	not-accessible
		STATUS		current
		DESCRIPTION
			"Table entry for short interval Vlan counter."
		INDEX {	rcPerformanceShortVlanHistoryVlanIndex, rcPerformanceShortVlanHistoryCosIndex, rcPerformanceShortVlanHistorySampleIndex }
		::=	{ rcPerformanceShortVlanHistoryTable 1 }

	rcPerformanceShortVlanHistoryEntry ::= SEQUENCE {
		rcPerformanceShortVlanHistoryVlanIndex 		            INTEGER,
		rcPerformanceShortVlanHistoryCosIndex     						INTEGER,
		rcPerformanceShortVlanHistorySampleIndex  						INTEGER,
		rcPerformanceShortVlanHistoryIntervalStart    				DateAndTime,
		rcPerformanceShortVlanHistoryStatus        						INTEGER,
		rcPerformanceShortVlanHistoryUpOctets		              Counter64,
    rcPerformanceShortVlanHistoryUpFrames		              Counter64,
    rcPerformanceShortVlanHistoryUpDiscards	              Counter64,
    rcPerformanceShortVlanHistoryDownOctets	              Counter64,
    rcPerformanceShortVlanHistoryDownFrames								Counter64,
    rcPerformanceShortVlanHistoryDownDiscards   					Counter64    					  
		}
    
	rcPerformanceShortVlanHistoryVlanIndex     OBJECT-TYPE
		SYNTAX	INTEGER
		ACCESS	read-only
		STATUS	current
		DESCRIPTION
			"An index that uniquely identifies an entry in
             the short interval vlan counter table."
		::=	{ rcPerformanceShortVlanHistoryEntry 1 }
		
	rcPerformanceShortVlanHistoryCosIndex     OBJECT-TYPE
		SYNTAX	INTEGER
		ACCESS	read-only
		STATUS	current
		DESCRIPTION
			"An index that uniquely identifies an entry in
             the short interval vlan counter table."
		::=	{ rcPerformanceShortVlanHistoryEntry 2 }	
		
	rcPerformanceShortVlanHistorySampleIndex     OBJECT-TYPE
		SYNTAX	INTEGER
		ACCESS	read-only
		STATUS	current
		DESCRIPTION
			"An index that uniquely identifies the particular
 	sample this entry represents performance all samples
 	associated with the same historyControlEntry.
 	This index starts at 1 and increases by one
 	as each new sample is taken."
		::=	{ rcPerformanceShortVlanHistoryEntry 3 }	
	
	rcPerformanceShortVlanHistoryIntervalStart             OBJECT-TYPE
		SYNTAX	DateAndTime
		ACCESS	read-only
		STATUS	current
		DESCRIPTION
			"Peroid start time." 
		::=	{ rcPerformanceShortVlanHistoryEntry 4 }		
	
	rcPerformanceShortVlanHistoryStatus                   OBJECT-TYPE
		SYNTAX	INTEGER
		{
		    Valid(1),
		 		Invalid(2)
		}
		ACCESS	read-only
		STATUS	current
		DESCRIPTION
			"Mark the invalid performance data."
		::=	{ rcPerformanceShortVlanHistoryEntry 5 }	
		
	rcPerformanceShortVlanHistoryUpOctets     OBJECT-TYPE
		SYNTAX	Counter64
		ACCESS	read-only
		STATUS	current
		DESCRIPTION
			"Upload Octets number."
		::=	{ rcPerformanceShortVlanHistoryEntry 6 }
		
	rcPerformanceShortVlanHistoryUpFrames     OBJECT-TYPE
		SYNTAX	Counter64
		ACCESS	read-only
		STATUS	current
		DESCRIPTION
			"Upload frame number."
		::=	{ rcPerformanceShortVlanHistoryEntry 7 }
		
	rcPerformanceShortVlanHistoryUpDiscards     OBJECT-TYPE
		SYNTAX	Counter64
		ACCESS	read-only
		STATUS	current
		DESCRIPTION
			"Upload discards packets number."
		::=	{ rcPerformanceShortVlanHistoryEntry 8 }
		
	rcPerformanceShortVlanHistoryDownOctets     OBJECT-TYPE
		SYNTAX	Counter64
		ACCESS	read-only
		STATUS	current
		DESCRIPTION
			"Download Octets number."
		::=	{ rcPerformanceShortVlanHistoryEntry 9 }
		
	rcPerformanceShortVlanHistoryDownFrames     OBJECT-TYPE
		SYNTAX	Counter64
		ACCESS	read-only
		STATUS	current
		DESCRIPTION
			"Download frame number."
		::=	{ rcPerformanceShortVlanHistoryEntry 10 }
		
	rcPerformanceShortVlanHistoryDownDiscards        OBJECT-TYPE
		SYNTAX	Counter64
		ACCESS	read-only
		STATUS	current
		DESCRIPTION
			"Download discards packets number ."
		::=	{ rcPerformanceShortVlanHistoryEntry 11 }
		
-- END rcPerformanceShortVlanHistoryTable

-- START rcPerformanceLongVlanHistoryTable

 rcPerformanceLongVlanHistoryTable             OBJECT-TYPE
		SYNTAX		SEQUENCE OF	rcPerformanceLongVlanHistoryEntry        
		MAX-ACCESS	not-accessible
		STATUS		current
		DESCRIPTION
			"A table of	Long interval vlan counter."
		::=	{ rcPerformance 7}
		
	rcPerformanceLongVlanHistoryEntry               OBJECT-TYPE
		SYNTAX		rcPerformanceLongVlanHistoryEntry 
		MAX-ACCESS	not-accessible
		STATUS		current
		DESCRIPTION
			"Table entry for Long interval Vlan counter."
		INDEX {	rcPerformanceLongVlanHistoryVlanIndex, rcPerformanceLongVlanHistorySampleIndex, rcPerformanceLongVlanHistoryCosIndex }
		::=	{ rcPerformanceLongVlanHistoryTable 1 }

	rcPerformanceLongVlanHistoryEntry ::= SEQUENCE {
		rcPerformanceLongVlanHistoryVlanIndex 		            INTEGER,
		rcPerformanceLongVlanHistoryCosIndex     							INTEGER,
		rcPerformanceLongVlanHistorySampleIndex  							INTEGER,
		rcPerformanceLongVlanHistoryIntervalStart    					DateAndTime,
		rcPerformanceLongVlanHistoryStatus        						INTEGER,
		rcPerformanceLongVlanHistoryUpOctets		              Counter64,
    rcPerformanceLongVlanHistoryUpFrames		              Counter64,
    rcPerformanceLongVlanHistoryUpDiscards	              Counter64,
    rcPerformanceLongVlanHistoryDownOctets	              Counter64,
    rcPerformanceLongVlanHistoryDownFrames								Counter64,
    rcPerformanceLongVlanHistoryDownDiscards   						Counter64    					  
		}
    
	rcPerformanceLongVlanHistoryVlanIndex     OBJECT-TYPE
		SYNTAX	INTEGER
		ACCESS	read-only
		STATUS	current
		DESCRIPTION
			"An index that uniquely identifies an entry in
             the Long interval vlan counter table."
		::=	{ rcPerformanceLongVlanHistoryEntry 1 }
		
	rcPerformanceLongVlanHistoryCosIndex     OBJECT-TYPE
		SYNTAX	INTEGER
		ACCESS	read-only
		STATUS	current
		DESCRIPTION
			"An index that uniquely identifies an entry in
             the Long interval vlan counter table."
		::=	{ rcPerformanceLongVlanHistoryEntry 2 }
		
	rcPerformanceLongVlanHistorySampleIndex     OBJECT-TYPE
		SYNTAX	INTEGER
		ACCESS	read-only
		STATUS	current
		DESCRIPTION
			"An index that uniquely identifies the particular
 	sample this entry represents performance all samples
 	associated with the same historyControlEntry.
 	This index starts at 1 and increases by one
 	as each new sample is taken."
		::=	{ rcPerformanceLongVlanHistoryEntry 3 }	
	
	rcPerformanceLongVlanHistoryIntervalStart             OBJECT-TYPE
		SYNTAX	DateAndTime
		ACCESS	read-only
		STATUS	current
		DESCRIPTION
			"Peroid start time." 
		::=	{ rcPerformanceLongVlanHistoryEntry 4 }		
	
	rcPerformanceLongVlanHistoryStatus                   OBJECT-TYPE
		SYNTAX	INTEGER
		{
		    Valid(1),
		 		Invalid(2)
		}
		ACCESS	read-only
		STATUS	current
		DESCRIPTION
			"Mark the invalid performance data."
		::=	{ rcPerformanceLongVlanHistoryEntry 5 }	
		
	rcPerformanceLongVlanHistoryUpOctets     OBJECT-TYPE
		SYNTAX	Counter64
		ACCESS	read-only
		STATUS	current
		DESCRIPTION
			"Upload Octets number."
		::=	{ rcPerformanceLongVlanHistoryEntry 6 }
		
	rcPerformanceLongVlanHistoryUpFrames     OBJECT-TYPE
		SYNTAX	Counter64
		ACCESS	read-only
		STATUS	current
		DESCRIPTION
			"Upload frame number."
		::=	{ rcPerformanceLongVlanHistoryEntry 7 }
		
	rcPerformanceLongVlanHistoryUpDiscards     OBJECT-TYPE
		SYNTAX	Counter64
		ACCESS	read-only
		STATUS	current
		DESCRIPTION
			"Upload discards packets number."
		::=	{ rcPerformanceLongVlanHistoryEntry 8 }
		
	rcPerformanceLongVlanHistoryDownOctets     OBJECT-TYPE
		SYNTAX	Counter64
		ACCESS	read-only
		STATUS	current
		DESCRIPTION
			"Download Octets number."
		::=	{ rcPerformanceLongVlanHistoryEntry 9 }
		
	rcPerformanceLongVlanHistoryDownFrames     OBJECT-TYPE
		SYNTAX	Counter64
		ACCESS	read-only
		STATUS	current
		DESCRIPTION
			"Download frame number."
		::=	{ rcPerformanceLongVlanHistoryEntry 10 }
		
	rcPerformanceLongVlanHistoryDownDiscards        OBJECT-TYPE
		SYNTAX	Counter64
		ACCESS	read-only
		STATUS	current
		DESCRIPTION
			"Download discards packets number ."
		::=	{ rcPerformanceLongVlanHistoryEntry 11 }
		
-- END rcPerformanceLongVlanHistoryTable

-- START rcPerformanceShortPortCurrentTable
   
  rcPerformanceShortPortCurrentTable             OBJECT-TYPE
		SYNTAX		SEQUENCE OF	rcPerformanceShortPortCurrentEntry       
		MAX-ACCESS	not-accessible
		STATUS		current
		DESCRIPTION
			"A table of	current short interval port counters value."
		::=	{ rcPerformance 8}
		
	rcPerformanceShortPortCurrentEntry              OBJECT-TYPE
		SYNTAX		rcPerformanceShortPortCurrentEntry
		MAX-ACCESS	not-accessible
		STATUS		current
		DESCRIPTION
			"Table entry for Port counter value."
		INDEX {	rcPerformanceShortPortCurrentPortIndex}
		::=	{ rcPerformanceShortPortCurrentTable 1 }

	rcPerformanceShortPortCurrentEntry ::= SEQUENCE {
		rcPerformanceShortPortCurrentPortIndex        			INTEGER,
		rcPerformanceShortPortCurrentIntervalStart    			DateAndTime,
		rcPerformanceShortPortCurrentPassedTime             INTEGER,
		rcPerformanceShortPortCurrentStatus           			INTEGER,
    rcPerformanceShortPortCurrentInOctets		      			Counter64,
    rcPerformanceShortPortCurrentOutOctets        			Counter64,
    rcPerformanceShortPortCurrentInUcastPkts	        	Counter64,
    rcPerformanceShortPortCurrentOutUcastPkts	          Counter64,
    rcPerformanceShortPortCurrentInMulticastPkts				Counter64,
    rcPerformanceShortPortCurrentOutMulticastPkts				Counter64,
    rcPerformanceShortPortCurrentInBroadcastPkts				Counter64,
    rcPerformanceShortPortCurrentOutBroadcastPkts				Counter64,
    rcPerformanceShortPortCurrentInErrors								Counter64,
    rcPerformanceShortPortCurrentOutErrors							Counter64,
    rcPerformanceShortPortCurrentInDiscards							Counter64,
    rcPerformanceShortPortCurrentOutDiscards						Counter64,
    rcPerformanceShortPortCurrentInUnknowProtos      		Counter64		      					  
		}
    
	rcPerformanceShortPortCurrentPortIndex     OBJECT-TYPE
		SYNTAX	INTEGER
		ACCESS	read-only
		STATUS	current
		DESCRIPTION
			"An index that uniquely identifies an entry in
             the performance port counter table."
		::=	{ rcPerformanceShortPortCurrentEntry 1 }
					
	rcPerformanceShortPortCurrentIntervalStart       OBJECT-TYPE
		SYNTAX	DateAndTime
		ACCESS	read-only
		STATUS	current
		DESCRIPTION
			"Peroid start time."
		::=	{ rcPerformanceShortPortCurrentEntry 2 }		
		
  rcPerformanceShortPortCurrentPassedTime       OBJECT-TYPE
		SYNTAX	INTEGER
		ACCESS	read-only
		STATUS	current
		DESCRIPTION
			"Peroid passed time, unit is second."
		::=	{ rcPerformanceShortPortCurrentEntry 3 }
						
	rcPerformanceShortPortCurrentStatus     OBJECT-TYPE
		SYNTAX	INTEGER
		{
		    Valid(1),
		 		Invalid(2)
		}
		ACCESS	read-only
		STATUS	current
		DESCRIPTION
			"Mark the invalid performance data."
		::=	{ rcPerformanceShortPortCurrentEntry 4 }	
		
	rcPerformanceShortPortCurrentInOctets     OBJECT-TYPE
		SYNTAX	Counter64
		ACCESS	read-only
		STATUS	current
		DESCRIPTION
			"Income octets number."
		::=	{ rcPerformanceShortPortCurrentEntry 5 }
		
	rcPerformanceShortPortCurrentOutOctets     OBJECT-TYPE
		SYNTAX	Counter64
		ACCESS	read-only
		STATUS	current
		DESCRIPTION
			"Out octets number."
		::=	{ rcPerformanceShortPortCurrentEntry 6 }
		
	rcPerformanceShortPortCurrentInUcastPkts     OBJECT-TYPE
		SYNTAX	Counter64
		ACCESS	read-only
		STATUS	current
		DESCRIPTION
			"Income uncast packets number."
		::=	{ rcPerformanceShortPortCurrentEntry 7 }
		
	rcPerformanceShortPortCurrentOutUcastPkts     OBJECT-TYPE
		SYNTAX	Counter64
		ACCESS	read-only
		STATUS	current
		DESCRIPTION
			"Out uncast packets number."
		::=	{ rcPerformanceShortPortCurrentEntry 8 }
		
	rcPerformanceShortPortCurrentInMulticastPkts     OBJECT-TYPE
		SYNTAX	Counter64
		ACCESS	read-only
		STATUS	current
		DESCRIPTION
			"Income multicast packets number."
		::=	{ rcPerformanceShortPortCurrentEntry 9 }
		
	rcPerformanceShortPortCurrentOutMulticastPkts     OBJECT-TYPE
		SYNTAX	Counter64
		ACCESS	read-only
		STATUS	current
		DESCRIPTION
			"Out multicast packets number."
		::=	{ rcPerformanceShortPortCurrentEntry 10 }
		
	rcPerformanceShortPortCurrentInBroadcastPkts     OBJECT-TYPE
		SYNTAX	Counter64
		ACCESS	read-only
		STATUS	current
		DESCRIPTION
			"Income Broadcast packets number."
		::=	{ rcPerformanceShortPortCurrentEntry 11 }
		
	rcPerformanceShortPortCurrentOutBroadcastPkts     OBJECT-TYPE
		SYNTAX	Counter64
		ACCESS	read-only
		STATUS	current
		DESCRIPTION
			"Out Broadcast packets number."
		::=	{ rcPerformanceShortPortCurrentEntry 12 }
		
	rcPerformanceShortPortCurrentInErrors     OBJECT-TYPE
		SYNTAX	Counter64
		ACCESS	read-only
		STATUS	current
		DESCRIPTION
			"Income error packets number."
		::=	{ rcPerformanceShortPortCurrentEntry 13 }
		
	rcPerformanceShortPortCurrentOutErrors     OBJECT-TYPE
		SYNTAX	Counter64
		ACCESS	read-only
		STATUS	current
		DESCRIPTION
			"Out error packets number."
		::=	{ rcPerformanceShortPortCurrentEntry 14 }
		
	rcPerformanceShortPortCurrentInDiscards     OBJECT-TYPE
		SYNTAX	Counter64
		ACCESS	read-only
		STATUS	current
		DESCRIPTION
			"Income discard packets number."
		::=	{ rcPerformanceShortPortCurrentEntry 15 }
		
	rcPerformanceShortPortCurrentOutDiscards     OBJECT-TYPE
		SYNTAX	Counter64
		ACCESS	read-only
		STATUS	current
		DESCRIPTION
			"Out discard packets number."
		::=	{ rcPerformanceShortPortCurrentEntry 16 }
		
	rcPerformanceShortPortCurrentInUnknowProtos   OBJECT-TYPE
		SYNTAX	Counter64
		ACCESS	read-only
		STATUS	current
		DESCRIPTION
			"Income Unknow Protos number."
		::=	{ rcPerformanceShortPortCurrentEntry 17 }
		
-- END rcPerformanceShortPortCurrentTable

-- START rcPerformanceLongPortCurrentTable
   
  rcPerformanceLongPortCurrentTable             OBJECT-TYPE
		SYNTAX		SEQUENCE OF	rcPerformanceLongPortCurrentEntry       
		MAX-ACCESS	not-accessible
		STATUS		current
		DESCRIPTION
			"A table of	current Long interval port counters value."
		::=	{ rcPerformance 9}
		
	rcPerformanceLongPortCurrentEntry              OBJECT-TYPE
		SYNTAX		rcPerformanceLongPortCurrentEntry
		MAX-ACCESS	not-accessible
		STATUS		current
		DESCRIPTION
			"Table entry for Port counter value."
		INDEX {	rcPerformanceLongPortCurrentPortIndex}
		::=	{ rcPerformanceLongPortCurrentTable 1 }

	rcPerformanceLongPortCurrentEntry ::= SEQUENCE {
		rcPerformanceLongPortCurrentPortIndex        			INTEGER,
		rcPerformanceLongPortCurrentIntervalStart    			DateAndTime,
		rcPerformanceLongPortCurrentPassedTime             INTEGER,
		rcPerformanceLongPortCurrentStatus           			INTEGER,
    rcPerformanceLongPortCurrentInOctets		      			Counter64,
    rcPerformanceLongPortCurrentOutOctets        			Counter64,
    rcPerformanceLongPortCurrentInUcastPkts	        	Counter64,
    rcPerformanceLongPortCurrentOutUcastPkts	          Counter64,
    rcPerformanceLongPortCurrentInMulticastPkts				Counter64,
    rcPerformanceLongPortCurrentOutMulticastPkts				Counter64,
    rcPerformanceLongPortCurrentInBroadcastPkts				Counter64,
    rcPerformanceLongPortCurrentOutBroadcastPkts				Counter64,
    rcPerformanceLongPortCurrentInErrors								Counter64,
    rcPerformanceLongPortCurrentOutErrors							Counter64,
    rcPerformanceLongPortCurrentInDiscards							Counter64,
    rcPerformanceLongPortCurrentOutDiscards						Counter64,
    rcPerformanceLongPortCurrentInUnknowProtos      		Counter64		      					  
		}
    
	rcPerformanceLongPortCurrentPortIndex     OBJECT-TYPE
		SYNTAX	INTEGER
		ACCESS	read-only
		STATUS	current
		DESCRIPTION
			"An index that uniquely identifies an entry in
             the performance port counter table."
		::=	{ rcPerformanceLongPortCurrentEntry 1 }
					
	rcPerformanceLongPortCurrentIntervalStart       OBJECT-TYPE
		SYNTAX	DateAndTime
		ACCESS	read-only
		STATUS	current
		DESCRIPTION
			"Peroid start time."
		::=	{ rcPerformanceLongPortCurrentEntry 2 }		
		
  rcPerformanceLongPortCurrentPassedTime       OBJECT-TYPE
		SYNTAX	INTEGER
		ACCESS	read-only
		STATUS	current
		DESCRIPTION
			"Peroid passed time."
		::=	{ rcPerformanceLongPortCurrentEntry 3 }
						
	rcPerformanceLongPortCurrentStatus     OBJECT-TYPE
		SYNTAX	INTEGER
		{
		    Valid(1),
		 		Invalid(2)
		}
		ACCESS	read-only
		STATUS	current
		DESCRIPTION
			"Mark the invalid performance data."
		::=	{ rcPerformanceLongPortCurrentEntry 4 }	
		
	rcPerformanceLongPortCurrentInOctets     OBJECT-TYPE
		SYNTAX	Counter64
		ACCESS	read-only
		STATUS	current
		DESCRIPTION
			"Income octets number."
		::=	{ rcPerformanceLongPortCurrentEntry 5 }
		
	rcPerformanceLongPortCurrentOutOctets     OBJECT-TYPE
		SYNTAX	Counter64
		ACCESS	read-only
		STATUS	current
		DESCRIPTION
			"Out octets number."
		::=	{ rcPerformanceLongPortCurrentEntry 6 }
		
	rcPerformanceLongPortCurrentInUcastPkts     OBJECT-TYPE
		SYNTAX	Counter64
		ACCESS	read-only
		STATUS	current
		DESCRIPTION
			"Income uncast packets number."
		::=	{ rcPerformanceLongPortCurrentEntry 7 }
		
	rcPerformanceLongPortCurrentOutUcastPkts     OBJECT-TYPE
		SYNTAX	Counter64
		ACCESS	read-only
		STATUS	current
		DESCRIPTION
			"Out uncast packets number."
		::=	{ rcPerformanceLongPortCurrentEntry 8 }
		
	rcPerformanceLongPortCurrentInMulticastPkts     OBJECT-TYPE
		SYNTAX	Counter64
		ACCESS	read-only
		STATUS	current
		DESCRIPTION
			"Income multicast packets number."
		::=	{ rcPerformanceLongPortCurrentEntry 9 }
		
	rcPerformanceLongPortCurrentOutMulticastPkts     OBJECT-TYPE
		SYNTAX	Counter64
		ACCESS	read-only
		STATUS	current
		DESCRIPTION
			"Out multicast packets number."
		::=	{ rcPerformanceLongPortCurrentEntry 10 }
		
	rcPerformanceLongPortCurrentInBroadcastPkts     OBJECT-TYPE
		SYNTAX	Counter64
		ACCESS	read-only
		STATUS	current
		DESCRIPTION
			"Income Broadcast packets number."
		::=	{ rcPerformanceLongPortCurrentEntry 11 }
		
	rcPerformanceLongPortCurrentOutBroadcastPkts     OBJECT-TYPE
		SYNTAX	Counter64
		ACCESS	read-only
		STATUS	current
		DESCRIPTION
			"Out Broadcast packets number."
		::=	{ rcPerformanceLongPortCurrentEntry 12 }
		
	rcPerformanceLongPortCurrentInErrors     OBJECT-TYPE
		SYNTAX	Counter64
		ACCESS	read-only
		STATUS	current
		DESCRIPTION
			"Income error packets number."
		::=	{ rcPerformanceLongPortCurrentEntry 13 }
		
	rcPerformanceLongPortCurrentOutErrors     OBJECT-TYPE
		SYNTAX	Counter64
		ACCESS	read-only
		STATUS	current
		DESCRIPTION
			"Out error packets number."
		::=	{ rcPerformanceLongPortCurrentEntry 14 }
		
	rcPerformanceLongPortCurrentInDiscards     OBJECT-TYPE
		SYNTAX	Counter64
		ACCESS	read-only
		STATUS	current
		DESCRIPTION
			"Income discard packets number."
		::=	{ rcPerformanceLongPortCurrentEntry 15 }
		
	rcPerformanceLongPortCurrentOutDiscards     OBJECT-TYPE
		SYNTAX	Counter64
		ACCESS	read-only
		STATUS	current
		DESCRIPTION
			"Out discard packets number."
		::=	{ rcPerformanceLongPortCurrentEntry 16 }
		
	rcPerformanceLongPortCurrentInUnknowProtos   OBJECT-TYPE
		SYNTAX	Counter64
		ACCESS	read-only
		STATUS	current
		DESCRIPTION
			"Income Unknow Protos number."
		::=	{ rcPerformanceLongPortCurrentEntry 17 }
		
-- END rcPerformanceLongPortCurrentTable

-- START rcPerformanceShortVlanCurrentTable

 rcPerformanceShortVlanCurrentTable             OBJECT-TYPE
		SYNTAX		SEQUENCE OF	rcPerformanceShortVlanCurrentEntry        
		MAX-ACCESS	not-accessible
		STATUS		current
		DESCRIPTION
			"A table of	current Short interval vlan counter."
		::=	{ rcPerformance 10}
		
	rcPerformanceShortVlanCurrentEntry               OBJECT-TYPE
		SYNTAX		rcPerformanceShortVlanCurrentEntry 
		MAX-ACCESS	not-accessible
		STATUS		current
		DESCRIPTION
			"Table entry for Short interval Vlan counter."
		INDEX {	rcPerformanceShortVlanCurrentVlanIndex, rcPerformanceShortVlanCurrentCosIndex}
		::=	{ rcPerformanceShortVlanCurrentTable 1 }

	rcPerformanceShortVlanCurrentEntry ::= SEQUENCE {
		rcPerformanceShortVlanCurrentVlanIndex 		            INTEGER,
		rcPerformanceShortVlanCurrentCosIndex     						INTEGER,
		rcPerformanceShortVlanCurrentIntervalStart    				DateAndTime,
		rcPerformanceShortVlanCurrentPassedTime               INTEGER,
		rcPerformanceShortVlanCurrentStatus        						INTEGER,
		rcPerformanceShortVlanCurrentUpOctets		              Counter64,
    rcPerformanceShortVlanCurrentUpFrames		              Counter64,
    rcPerformanceShortVlanCurrentUpDiscards	              Counter64,
    rcPerformanceShortVlanCurrentDownOctets	              Counter64,
    rcPerformanceShortVlanCurrentDownFrames								Counter64,
    rcPerformanceShortVlanCurrentDownDiscards   					Counter64    					  
		}
    
	rcPerformanceShortVlanCurrentVlanIndex     OBJECT-TYPE
		SYNTAX	INTEGER
		ACCESS	read-only
		STATUS	current
		DESCRIPTION
			"An index that uniquely identifies an entry in
             the Short interval vlan counter table."
		::=	{ rcPerformanceShortVlanCurrentEntry 1 }
		
	rcPerformanceShortVlanCurrentCosIndex     OBJECT-TYPE
		SYNTAX	INTEGER
		ACCESS	read-only
		STATUS	current
		DESCRIPTION
			"An index that uniquely identifies an entry in
             the Short interval vlan counter table."
		::=	{ rcPerformanceShortVlanCurrentEntry 2 }
	
	rcPerformanceShortVlanCurrentIntervalStart             OBJECT-TYPE
		SYNTAX	DateAndTime
		ACCESS	read-only
		STATUS	current
		DESCRIPTION
			"Peroid start time." 
		::=	{ rcPerformanceShortVlanCurrentEntry 3 }		
	
	rcPerformanceShortVlanCurrentPassedTime             OBJECT-TYPE
		SYNTAX	INTEGER
		ACCESS	read-only
		STATUS	current
		DESCRIPTION
			"Peroid start time, unit is second." 
		::=	{ rcPerformanceShortVlanCurrentEntry 4 }		
		
	rcPerformanceShortVlanCurrentStatus                   OBJECT-TYPE
		SYNTAX	INTEGER
		{
		    Valid(1),
		 		Invalid(2)
		}
		ACCESS	read-only
		STATUS	current
		DESCRIPTION
			"Mark the invalid performance data."
		::=	{ rcPerformanceShortVlanCurrentEntry 5 }	
		
	rcPerformanceShortVlanCurrentUpOctets     OBJECT-TYPE
		SYNTAX	Counter64
		ACCESS	read-only
		STATUS	current
		DESCRIPTION
			"Upload Octets number."
		::=	{ rcPerformanceShortVlanCurrentEntry 6 }
		
	rcPerformanceShortVlanCurrentUpFrames     OBJECT-TYPE
		SYNTAX	Counter64
		ACCESS	read-only
		STATUS	current
		DESCRIPTION
			"Upload frame number."
		::=	{ rcPerformanceShortVlanCurrentEntry 7 }
		
	rcPerformanceShortVlanCurrentUpDiscards     OBJECT-TYPE
		SYNTAX	Counter64
		ACCESS	read-only
		STATUS	current
		DESCRIPTION
			"Upload discards packets number."
		::=	{ rcPerformanceShortVlanCurrentEntry 8 }
		
	rcPerformanceShortVlanCurrentDownOctets     OBJECT-TYPE
		SYNTAX	Counter64
		ACCESS	read-only
		STATUS	current
		DESCRIPTION
			"Download Octets number."
		::=	{ rcPerformanceShortVlanCurrentEntry 9 }
		
	rcPerformanceShortVlanCurrentDownFrames     OBJECT-TYPE
		SYNTAX	Counter64
		ACCESS	read-only
		STATUS	current
		DESCRIPTION
			"Download frame number."
		::=	{ rcPerformanceShortVlanCurrentEntry 10 }
		
	rcPerformanceShortVlanCurrentDownDiscards        OBJECT-TYPE
		SYNTAX	Counter64
		ACCESS	read-only
		STATUS	current
		DESCRIPTION
			"Download discards packets number."
		::=	{ rcPerformanceShortVlanCurrentEntry 11 }
		
-- END rcPerformanceShortVlanCurrentTable

-- START rcPerformanceLongVlanCurrentTable

 rcPerformanceLongVlanCurrentTable             OBJECT-TYPE
		SYNTAX		SEQUENCE OF	rcPerformanceLongVlanCurrentEntry        
		MAX-ACCESS	not-accessible
		STATUS		current
		DESCRIPTION
			"A table of	current Long interval vlan counter."
		::=	{ rcPerformance 11}
		
	rcPerformanceLongVlanCurrentEntry               OBJECT-TYPE
		SYNTAX		rcPerformanceLongVlanCurrentEntry 
		MAX-ACCESS	not-accessible
		STATUS		current
		DESCRIPTION
			"Table entry for Long interval Vlan counter."
		INDEX {	rcPerformanceLongVlanCurrentVlanIndex, rcPerformanceLongVlanCurrentCosIndex}
		::=	{ rcPerformanceLongVlanCurrentTable 1 }

	rcPerformanceLongVlanCurrentEntry ::= SEQUENCE {
		rcPerformanceLongVlanCurrentVlanIndex 		            INTEGER,
		rcPerformanceLongVlanCurrentCosIndex     						INTEGER,
		rcPerformanceLongVlanCurrentIntervalStart    				DateAndTime,
		rcPerformanceLongVlanCurrentPassedTime             INTEGER,
		rcPerformanceLongVlanCurrentStatus        						INTEGER,
		rcPerformanceLongVlanCurrentUpOctets		              Counter64,
    rcPerformanceLongVlanCurrentUpFrames		              Counter64,
    rcPerformanceLongVlanCurrentUpDiscards	              Counter64,
    rcPerformanceLongVlanCurrentDownOctets	              Counter64,
    rcPerformanceLongVlanCurrentDownFrames								Counter64,
    rcPerformanceLongVlanCurrentDownDiscards   					Counter64     					  
		}
    
	rcPerformanceLongVlanCurrentVlanIndex     OBJECT-TYPE
		SYNTAX	INTEGER
		ACCESS	read-only
		STATUS	current
		DESCRIPTION
			"An index that uniquely identifies an entry in
             the Long interval vlan counter table."
		::=	{ rcPerformanceLongVlanCurrentEntry 1 }
		
	rcPerformanceLongVlanCurrentCosIndex     OBJECT-TYPE
		SYNTAX	INTEGER
		ACCESS	read-only
		STATUS	current
		DESCRIPTION
			"An index that uniquely identifies an entry in
             the Long interval vlan counter table."
		::=	{ rcPerformanceLongVlanCurrentEntry 2 }
	
	rcPerformanceLongVlanCurrentIntervalStart             OBJECT-TYPE
		SYNTAX	DateAndTime
		ACCESS	read-only
		STATUS	current
		DESCRIPTION
			"Peroid start time." 
		::=	{ rcPerformanceLongVlanCurrentEntry 3 }		
	
	rcPerformanceLongVlanCurrentPassedTime             OBJECT-TYPE
		SYNTAX	INTEGER
		ACCESS	read-only
		STATUS	current
		DESCRIPTION
			"Peroid start time, unit is second." 
		::=	{ rcPerformanceLongVlanCurrentEntry 4 }		
		
	rcPerformanceLongVlanCurrentStatus                   OBJECT-TYPE
		SYNTAX	INTEGER
		{
		    Valid(1),
		 		Invalid(2)
		}
		ACCESS	read-only
		STATUS	current
		DESCRIPTION
			"Mark the invalid performance data."
		::=	{ rcPerformanceLongVlanCurrentEntry 5 }	
		
	rcPerformanceLongVlanCurrentUpOctets     OBJECT-TYPE
		SYNTAX	Counter64
		ACCESS	read-only
		STATUS	current
		DESCRIPTION
			"Upload Octets number."
		::=	{ rcPerformanceLongVlanCurrentEntry 6 }
		
	rcPerformanceLongVlanCurrentUpFrames     OBJECT-TYPE
		SYNTAX	Counter64
		ACCESS	read-only
		STATUS	current
		DESCRIPTION
			"Upload frame number."
		::=	{ rcPerformanceLongVlanCurrentEntry 7 }
		
	rcPerformanceLongVlanCurrentUpDiscards     OBJECT-TYPE
		SYNTAX	Counter64
		ACCESS	read-only
		STATUS	current
		DESCRIPTION
			"Upload discards packets number."
		::=	{ rcPerformanceLongVlanCurrentEntry 8 }
		
	rcPerformanceLongVlanCurrentDownOctets     OBJECT-TYPE
		SYNTAX	Counter64
		ACCESS	read-only
		STATUS	current
		DESCRIPTION
			"Download Octets number."
		::=	{ rcPerformanceLongVlanCurrentEntry 9 }
		
	rcPerformanceLongVlanCurrentDownFrames     OBJECT-TYPE
		SYNTAX	Counter64
		ACCESS	read-only
		STATUS	current
		DESCRIPTION
			"Download frame number."
		::=	{ rcPerformanceLongVlanCurrentEntry 10 }
		
	rcPerformanceLongVlanCurrentDownDiscards        OBJECT-TYPE
		SYNTAX	Counter64
		ACCESS	read-only
		STATUS	current
		DESCRIPTION
			"Download discards packets number ."
		::=	{ rcPerformanceLongVlanCurrentEntry 11 }
		
-- END rcPerformanceLongVlanCurrentTable

-- START rcPerformancePortVlanCurrentTable

 rcPerformancePortVlanCurrentTable             OBJECT-TYPE
		SYNTAX		SEQUENCE OF	rcPerformancePortVlanCurrentEntry        
		MAX-ACCESS	not-accessible
		STATUS		current
		DESCRIPTION
			"A table of	current port/vlan counter."
		::=	{ rcPerformance 12}
		
	rcPerformancePortVlanCurrentEntry               OBJECT-TYPE
		SYNTAX		rcPerformancePortVlanCurrentEntry 
		MAX-ACCESS	not-accessible
		STATUS		current
		DESCRIPTION
			"Table entry for port/vlan counter."
		INDEX {	rcPerformancePortIndex, rcPerformanceVlanIndex, rcPerformanceCosIndex}
		::=	{ rcPerformancePortVlanCurrentTable 1 }

		rcPerformancePortVlanCurrentEntry ::= SEQUENCE {
	  	rcPerformanceCosIndex    				      		INTEGER,
		rcPerformancePortVlanInOctets             Counter64,
		rcPerformancePortVlanInPkts        				Counter64,
		rcPerformancePortVlanInDiscards		        Counter64,
    	rcPerformancePortVlanOutOctets		        Counter64,
    	rcPerformancePortVlanOutPkts	            Counter64,	
    	rcPerformancePortVlanCIR	                INTEGER,
    	rcPerformancePortVlanEIR	                INTEGER,
		}
    	
	rcPerformanceCosIndex             OBJECT-TYPE
		SYNTAX	INTEGER
		ACCESS	read-only
		STATUS	current
		DESCRIPTION
			"An index that uniquely identifies an entry in
             the port/vlan counter table." 
		::=	{ rcPerformancePortVlanCurrentEntry 1 }		
	
	rcPerformancePortVlanInOctets             OBJECT-TYPE
		SYNTAX	Counter64
		ACCESS	read-only
		STATUS	current
		DESCRIPTION
			"Income octets number." 
		::=	{ rcPerformancePortVlanCurrentEntry 2 }		
		
	rcPerformancePortVlanInPkts                   OBJECT-TYPE
		SYNTAX	Counter64
		ACCESS	read-only
		STATUS	current
		DESCRIPTION
			"Income packets number."
		::=	{ rcPerformancePortVlanCurrentEntry 3 }	
		
	rcPerformancePortVlanInDiscards     OBJECT-TYPE
		SYNTAX	Counter64
		ACCESS	read-only
		STATUS	current
		DESCRIPTION
			"Income discard number."
		::=	{ rcPerformancePortVlanCurrentEntry 4 }
		
	rcPerformancePortVlanOutOctets     OBJECT-TYPE
		SYNTAX	Counter64
		ACCESS	read-only
		STATUS	current
		DESCRIPTION
			"Out octets number."
		::=	{ rcPerformancePortVlanCurrentEntry 5 }
		
	rcPerformancePortVlanOutPkts     OBJECT-TYPE
		SYNTAX	Counter64
		ACCESS	read-only
		STATUS	current
		DESCRIPTION
			"Out packets number."
		::=	{ rcPerformancePortVlanCurrentEntry 6 }
	
  rcPerformancePortVlanCIR     OBJECT-TYPE
		SYNTAX	INTEGER
		ACCESS	read-only
		STATUS	current
		DESCRIPTION
			"It indicates the base buckets rate. Its unit is kbps."
		::=	{ rcPerformancePortVlanCurrentEntry 7 }	
		
	rcPerformancePortVlanEIR     OBJECT-TYPE
		SYNTAX	INTEGER
		ACCESS	read-only
		STATUS	current
		DESCRIPTION
			"It indicates the extended buckets rate. Its unit is kbps."
		::=	{ rcPerformancePortVlanCurrentEntry 8 }		
        			
-- END rcPerformancePortVlanCurrentTable

-- START rcPerformanceVlanCosCurrentTable

 rcPerformanceVlanCosCurrentTable             OBJECT-TYPE
		SYNTAX		SEQUENCE OF	rcPerformanceVlanCosCurrentEntry        
		MAX-ACCESS	not-accessible
		STATUS		current
		DESCRIPTION
			"A table of	current vlan + cos counter."
		::=	{ rcPerformance 13}
		
	rcPerformanceVlanCosCurrentEntry               OBJECT-TYPE
		SYNTAX		rcPerformanceVlanCosCurrentEntry 
		MAX-ACCESS	not-accessible
		STATUS		current
		DESCRIPTION
			"Table entry for vlan + cos counter."
		INDEX {rcPerformanceVlanIndex, rcPerformanceVlanCosIndex}
		::=	{ rcPerformanceVlanCosCurrentTable 1 }
		
  rcPerformanceVlanCosCurrentEntry ::= SEQUENCE {
	  rcPerformanceVlanCosIndex    				      		INTEGER,
		rcPerformanceVlanCosUpOctets        				  Counter64,
		rcPerformanceVlanCosUpFrames		              Counter64,
    rcPerformanceVlanCosUpDiscards		            Counter64,
    rcPerformanceVlanCosDownOctets	              Counter64,	
    rcPerformanceVlanCosDownFrames	              Counter64,
    rcPerformanceVlanCosDownDiscards	            Counter64,		
    rcPerformanceVlanCosCIR	                      INTEGER,
    rcPerformanceVlanCosEIR	                      INTEGER				 			  
		}
		
	rcPerformanceVlanCosIndex             OBJECT-TYPE
		SYNTAX	INTEGER
		ACCESS	read-only
		STATUS	current
		DESCRIPTION
			"An index that uniquely identifies an entry in
             the vlan + cos counter table." 
		::=	{ rcPerformanceVlanCosCurrentEntry 1 }		
	
	rcPerformanceVlanCosUpOctets             OBJECT-TYPE
		SYNTAX	Counter64
		ACCESS	read-only
		STATUS	current
		DESCRIPTION
			"Upload Octets number." 
		::=	{ rcPerformanceVlanCosCurrentEntry 2 }		
		
	rcPerformanceVlanCosUpFrames             OBJECT-TYPE
		SYNTAX	Counter64
		ACCESS	read-only
		STATUS	current
		DESCRIPTION
			"Upload frame number." 
		::=	{ rcPerformanceVlanCosCurrentEntry 3 }	
		
	rcPerformanceVlanCosUpDiscards             OBJECT-TYPE
		SYNTAX	Counter64
		ACCESS	read-only
		STATUS	current
		DESCRIPTION
			"Upload discards packets number." 
		::=	{ rcPerformanceVlanCosCurrentEntry 4 }	
		
	rcPerformanceVlanCosDownOctets             OBJECT-TYPE
		SYNTAX	Counter64
		ACCESS	read-only
		STATUS	current
		DESCRIPTION
			"Download Octets number." 
		::=	{ rcPerformanceVlanCosCurrentEntry 5 }	
		
	rcPerformanceVlanCosDownFrames             OBJECT-TYPE
		SYNTAX	Counter64
		ACCESS	read-only
		STATUS	current
		DESCRIPTION
			"Download frame number." 
		::=	{ rcPerformanceVlanCosCurrentEntry 6 }
		
	rcPerformanceVlanCosDownDiscards             OBJECT-TYPE
		SYNTAX	Counter64
		ACCESS	read-only
		STATUS	current
		DESCRIPTION
			"Download discards packets number." 
		::=	{ rcPerformanceVlanCosCurrentEntry 7 }
		
	rcPerformanceVlanCosCIR             OBJECT-TYPE
		SYNTAX	INTEGER
		ACCESS	read-only
		STATUS	current
		DESCRIPTION
			"It indicates the base buckets rate. Its unit is kbps." 
		::=	{ rcPerformanceVlanCosCurrentEntry 8 }
		
	rcPerformanceVlanCosEIR             OBJECT-TYPE
		SYNTAX	INTEGER
		ACCESS	read-only
		STATUS	current
		DESCRIPTION
			"It indicates the extended buckets rate. Its unit is kbps." 
		::=	{ rcPerformanceVlanCosCurrentEntry 9 }
		                                             
-- END rcPerformanceVlanCosCurrentTable
                                                     
                                                     
-- START rcPerformancePortVlanCosControlTable

 rcPerformancePortVlanCosControlTable             OBJECT-TYPE
		SYNTAX		SEQUENCE OF	rcPerformancePortVlanCosControlEntry        
		MAX-ACCESS	not-accessible
		STATUS		current
		DESCRIPTION
			"A table of	port + vlan + cos counter."
		::=	{ rcPerformance 14}
		
	rcPerformancePortVlanCosControlEntry               OBJECT-TYPE
		SYNTAX		rcPerformancePortVlanCosControlEntry 
		MAX-ACCESS	not-accessible
		STATUS		current
		DESCRIPTION
			"Table entry for port + vlan + cos counter."
		INDEX {rcPerformancePortVlanCosPortIndex, 
				rcPerformancePortVlanCosVlanIndex,
				rcPerformancePortVlanCosCosIndex}
		::=	{ rcPerformancePortVlanCosControlTable 1 }
		
  	rcPerformancePortVlanCosControlEntry ::= SEQUENCE {
	  	rcPerformancePortVlanCosPortIndex    			INTEGER,
		rcPerformancePortVlanCosVlanIndex        		INTEGER,
		rcPerformancePortVlanCosCosIndex		        INTEGER,
    	rcPerformancePortVlanCosRowStatus		        RowStatus				 			  
		}
		
	rcPerformancePortVlanCosPortIndex             OBJECT-TYPE
		SYNTAX	INTEGER
		ACCESS	not-accessible
		STATUS	current
		DESCRIPTION
			"An port index that identifies an entry in
             the vlan + cos counter table." 
		::=	{ rcPerformancePortVlanCosControlEntry 1 }		
	
	rcPerformancePortVlanCosVlanIndex             OBJECT-TYPE
		SYNTAX INTEGER (1..4094)
		ACCESS	not-accessible
		STATUS	current
		DESCRIPTION
			"An vlan index that identifies an entry in
             the vlan + cos counter table." 
		::=	{ rcPerformancePortVlanCosControlEntry 2 }		
		
	rcPerformancePortVlanCosCosIndex             OBJECT-TYPE
		SYNTAX INTEGER (0..8)
		ACCESS	not-accessible
		STATUS	current
		DESCRIPTION
			"An cos index that identifies an entry in
             the vlan + cos counter table." 
		::=	{ rcPerformancePortVlanCosControlEntry 3 }	
		
	rcPerformancePortVlanCosRowStatus             OBJECT-TYPE
		SYNTAX	RowStatus
		ACCESS	read-create
		STATUS	current
		DESCRIPTION
			"Upload discards packets number." 
		::=	{ rcPerformancePortVlanCosControlEntry 4 }	
					
-- END rcPerformanceVlanCosCurrentTable
                                                   
END

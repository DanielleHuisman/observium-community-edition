--MibName=raisecomPim
-- *****************************************************************
-- RAISECOM-PIM-MIB.mib:  PIM MIB
--
-- Jan 2012, linxiaofang
--
-- Copyright (c) 1996-2012 by Raisecom Technology Co., Ltd. 
-- All rights reserved.
-- 
-- *****************************************************************
--

  RAISECOM-PIM-MIB DEFINITIONS ::= BEGIN

  IMPORTS
     TEXTUAL-CONVENTION,TruthValue,Unsigned32     
        FROM SNMPv2-TC                -- [RFC2579]
     EnableVar
        FROM SWITCH-TC    
     pimInterfaceEntry
        FROM PIM-STD-MIB              -- [RFC5060]
     raisecomAgent
		FROM RAISECOM-BASE-MIB;

  raisecomPim MODULE-IDENTITY
     LAST-UPDATED "201201050000Z"  -- 5 Jan 2012 00:00:00 GMT
     ORGANIZATION "Raisecom Technology Co., Ltd."
     CONTACT-INFO
        "Raisecom Science & Technology Co., ltd.
        E-mail: support@raisecom.com ."
     DESCRIPTION
        "This MIB module contains managed object definitions for
         PIM. "
        ::= { raisecomAgent 72 } 
   
raisecomPimNotifications	OBJECT IDENTIFIER ::= {	raisecomPim 1 }
raisecomPimObjects			OBJECT IDENTIFIER ::= {	raisecomPim 2 }   
raisecomPimConformance		OBJECT IDENTIFIER ::= {	raisecomPim 3 }  
     
--start of Pim interface Table
          
  raisecomPimIfTable   OBJECT-TYPE
     SYNTAX        SEQUENCE OF RaisecomPimIfEntry
     MAX-ACCESS    not-accessible
     STATUS        current
     DESCRIPTION
         "The (conceptual) table listing the router's PIM interfaces.
         This table is augmented to pimInterfaceTable."
     ::= { raisecomPimObjects 1 }

  raisecomPimIfEntry   OBJECT-TYPE
     SYNTAX        RaisecomPimIfEntry
     MAX-ACCESS    not-accessible
     STATUS        current
     DESCRIPTION
          "An entry (conceptual row) in the raisecomPimIfTable.
            Each entry represents multicast related interface 
            configuration and operational states. An interface
            can have more than one type of Inet address family
            enabled and there will be one entry per interface
            and address family version"
     AUGMENTS           { pimInterfaceEntry  }
            ::= { raisecomPimIfTable 1 }
  
  RaisecomPimIfEntry ::= SEQUENCE {
        raisecomPimIfDmEnable       EnableVar,
        raisecomPimIfPimVersion     Unsigned32,
        raisecomPimIfNumNbrs        Unsigned32
}

raisecomPimIfDmEnable   OBJECT-TYPE
     SYNTAX        EnableVar
     MAX-ACCESS    read-write
     STATUS        current
     DESCRIPTION
          "If this object is set to enabled(1), then it enables
 	Pim dense-mode function on this interface; otherwise Pim 
 	dense-mode funciton is not enabled on this interface."
     DEFVAL { disable }
     ::= { raisecomPimIfEntry 1 }
            
   
raisecomPimIfPimVersion  OBJECT-TYPE
    SYNTAX      Unsigned32
    MAX-ACCESS  read-only
    STATUS      current
    DESCRIPTION
        "The version of PIM running on this interface."   
    DEFVAL { 2 }
    ::= { raisecomPimIfEntry 2 }

raisecomPimIfNumNbrs  OBJECT-TYPE
    SYNTAX      Unsigned32
    MAX-ACCESS  read-only
    STATUS      current
    DESCRIPTION
        "Number of PIM neighbors detected on this interface."
    ::= { raisecomPimIfEntry 3 }
     
 --end of Pim interface Table    
 
 
 --start of Pim scalars
    raisecomPimScalars OBJECT IDENTIFIER ::= { raisecomPimObjects 2 }
    
    raisecomPimSREnable   OBJECT-TYPE
       SYNTAX        EnableVar
       MAX-ACCESS    read-write
       STATUS        current
       DESCRIPTION
            "If this object is set to disable(2), then it disable Pim State Refresh function on this system;
            otherwise Pim State Refresh function is enabled on this system."
       DEFVAL { enable }
         ::= { raisecomPimScalars 1 }
    
    raisecomPimMRouteClear   OBJECT-TYPE
       SYNTAX        TruthValue
       MAX-ACCESS    read-write
       STATUS        current
       DESCRIPTION
            "If this object is set to false(1), then it Clear all Pim Multicast Routing entries on this system."
       DEFVAL { false }
         ::= { raisecomPimScalars 2 } 
               
--end of Pim scalars        
   
  END

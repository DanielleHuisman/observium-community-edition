-- MibName=raisecomRemoteManagementRemote
-- =======================================================================
-- Version info 
--
-- Version 0.1 Created 2006.9.11 by CHENJUNYONG
-- This version of MIB is created just for extoam remote management on remote devices. 
-- 
-- Copyright(c) 2003-2005 by RAISECOM TECH, Ltd. 
-- =======================================================================

-- ===========================================================================

--
-- RAISECOM remote management objects on remote devices
--            

RAISECOM-REMOTE-MANAGEMENT-REMOTE-MIB DEFINITIONS ::= BEGIN

    IMPORTS
		MODULE-IDENTITY,
		OBJECT-TYPE,
		NOTIFICATION-TYPE ,
		Integer32,
		IpAddress,
		Unsigned32
			FROM SNMPv2-SMI
		DisplayString,		
		RowStatus,
		TruthValue
			FROM SNMPv2-TC    
		EnableVar,
		PortList
			FROM SWITCH-TC     
		EntryStatus
			FROM RMON-MIB  
		raisecomAgent		
			FROM RAISECOM-BASE-MIB;
--	
	raisecomRemoteManagementRemote    MODULE-IDENTITY
		LAST-UPDATED 	"200609110000Z"
		ORGANIZATION 	"RAISECOM TECH, Ltd."
		CONTACT-INFO 	"www.raisecom.com"
		DESCRIPTION  	
		    "The MIB module defining objects for remote management on remote devices."
		::= { raisecomAgent 13}  
                
-- groups                 
	 	  		
   	raisecomRemoteManagementRemoteHideMibObjects OBJECT IDENTIFIER ::= { raisecomRemoteManagementRemote 1 }
  	
-- raisecomRemoteManagementRemoteHideMibObjects  
   
	
-- MIB according to local raisecomRemoteEnvironmentTable
	
	raisecomRemoteTemperature OBJECT-TYPE
		    SYNTAX INTEGER 
		    ACCESS read-only
		    STATUS current
		    DESCRIPTION
		        "The current environment temperature of remote device."		       		       
		    DEFVAL {65535}
		    ::= { raisecomRemoteManagementRemoteHideMibObjects 1 }	
		    
	raisecomRemoteVolt3300  OBJECT-TYPE
		    SYNTAX INTEGER 
		    ACCESS read-only
		    STATUS current
		    DESCRIPTION
		        "Current voltage value of 3.3v of remote device."		     		       
		    DEFVAL {65535}
		    ::= { raisecomRemoteManagementRemoteHideMibObjects 2 }
		    
	raisecomRemoteVolt2500  OBJECT-TYPE
		    SYNTAX INTEGER 
		    ACCESS read-only
		    STATUS current
		    DESCRIPTION
		        "Current voltage value of 2.5v of remote device."
		    DEFVAL {65535}		     		       
		    ::= { raisecomRemoteManagementRemoteHideMibObjects 3 }
		    
	raisecomRemoteVolt1800  OBJECT-TYPE
		    SYNTAX INTEGER 
		    ACCESS read-only
		    STATUS current
		    DESCRIPTION
		        "Current voltage value of 1.8v of remote device."
		    DEFVAL {65535}		     		       
		    ::= { raisecomRemoteManagementRemoteHideMibObjects 4 }	
		    	    		   		    	    
	raisecomRemoteVolt1200  OBJECT-TYPE
		    SYNTAX INTEGER 
		    ACCESS read-only
		    STATUS current
		    DESCRIPTION
		        "Current voltage value of 1.2v of remote device."		     		       
		    DEFVAL {65535}
		    ::= { raisecomRemoteManagementRemoteHideMibObjects 5 } 
    	
-- MIB according to local raisecomRemoteSysCfgTable 
   	
	raisecomRemoteSysOperation OBJECT-TYPE
		    SYNTAX INTEGER{
        			ready(1),
        			write(2),
        			erase(3),
        			reboot(4)}
		    ACCESS read-write
		    STATUS current
		    DESCRIPTION
		        "Specifies system command in remote device.Currently,support three
		         types command:reboot,write and erase.Reboot command is used to reset
		         remote device,write is used to save startup-config file in remote device,
		         and erase is used to erase startup-config file of remote device."
		    DEFVAL {ready}		    
		    ::= { raisecomRemoteManagementRemoteHideMibObjects 6 }

	raisecomRemoteSysOperationState OBJECT-TYPE
		    SYNTAX INTEGER {
		        	ready(1),
		        	running(2),
		        	successful(3),
		       		failed(4)}
		    ACCESS read-only
		    STATUS current
		    DESCRIPTION
		        "Specifies the state of this system operation to remote device."
		     DEFVAL {ready}   		       
		    ::= { raisecomRemoteManagementRemoteHideMibObjects 7 }

	raisecomRemoteHostName OBJECT-TYPE
		    SYNTAX  OCTET STRING (SIZE(1..32))
		    ACCESS read-write
		    STATUS current
		    DESCRIPTION
		        "Host name of Remote device."		    
		    ::= { raisecomRemoteManagementRemoteHideMibObjects 8 }

	 raisecomRemoteOamNotificationEnable OBJECT-TYPE
		    SYNTAX EnableVar
		    ACCESS read-write
		    STATUS current
		    DESCRIPTION
		        "Specifies whether or not remote device send OAM notificaton frames."		       
		    ::= { raisecomRemoteManagementRemoteHideMibObjects 9 }		

-- MIB according to local raisecomRemoteCommunityTable
	
	raisecomRemoteCommunityName OBJECT-TYPE
		    SYNTAX OCTET STRING (SIZE (1..20))
		    ACCESS read-write
		    STATUS current
		    DESCRIPTION
		        "The SNMPv1/v2c community name string in remote device.
		        In remote device's community table,the index of this community
		        is 3,and the view for this community is 'internet'."		    		    
		    ::= { raisecomRemoteManagementRemoteHideMibObjects 10 }

	raisecomRemoteCommunityPermission OBJECT-TYPE
		    SYNTAX INTEGER {
		        		readOnly(1),
               			readWrite(2),
               			invalid(3)
               			}
		    ACCESS read-write
		    STATUS current
		    DESCRIPTION
		        "This object specifies the type of access allowed. 
		        'readOnly(1)' allows GET operations (i.e., GET, 
		        GET-NEXT, GET-BULK) and 'readWrite(2)' allows both 
		        GET and SET operations."
		     DEFVAL {readOnly}   		       
		    ::= { raisecomRemoteManagementRemoteHideMibObjects 11 }
-- MIB according to local raisecomRemoteL3Table
	
	raisecomRemoteL3IpAddr OBJECT-TYPE
		    SYNTAX IpAddress
		    ACCESS read-write
		    STATUS current
		    DESCRIPTION
		        "The IP Address of remote device.  This IP address 
		        logically AND'ed with 'raisecomRemoteL3Mask' yields 
		        the actual subnet value for this subnet.Set the object
		        as '0.0.0.0' means delete IP address of remote devices "		    		    
		    ::= { raisecomRemoteManagementRemoteHideMibObjects 12 }

	raisecomRemoteL3Mask OBJECT-TYPE
		    SYNTAX IpAddress
		    ACCESS read-write
		    STATUS current
		    DESCRIPTION
		        "The subnet mask for this remote subnet.  It contains 1's 
		        in the bit positions for the net and subnet IDs and 0's in 
		        the bit positions for host ID.  The 1's must be contiguous, 
		        starting with the left most bit."		        		       
		    ::= { raisecomRemoteManagementRemoteHideMibObjects 13 }

	raisecomRemoteL3VidIface OBJECT-TYPE
		    SYNTAX INTEGER (1..4094)
		    ACCESS read-write
		    STATUS current
		    DESCRIPTION
		        "This object contains the actual VLAN ID (VID) from 1 to 4094.
		         It is actually the management vlan of remote device."		        		       
		    ::= { raisecomRemoteManagementRemoteHideMibObjects 14 }

	 raisecomRemoteL3VidMemberPorts OBJECT-TYPE
		    SYNTAX PortList
		    ACCESS read-only
		    STATUS current
		    DESCRIPTION
		        "The set of ports which are permanently assigned to the egress
		         list for this VLAN by management.Changes to a bit in this object
		          affect the per-port per-VLAN Registrar control for Registration
		          Fixed for the relevant GVRP state machine on each port.  A port
		          may not be added in this set if it is already a member of the set 
		          of ports in dot1qVlanForbiddenEgressPorts.  The default value of 
		          this object is a string of zeros of appropriate length, indicating 
		          not fixed."		        		       
		    ::= { raisecomRemoteManagementRemoteHideMibObjects 15}
		    
	raisecomRemoteL3VidUntaggedPorts OBJECT-TYPE
		    SYNTAX PortList
		    ACCESS read-only
		    STATUS current
		    DESCRIPTION
		        "The set of ports which should transmit egress packets for this VLAN 
		        as untagged.  The default value of this object for the default VLAN 
		        (dot1qVlanIndex = 1) is a string of appropriate length including all 
		        ports.  There is no specified default for other VLANs. If a device agent 
		        cannot support the set of ports being set then it will reject the set 
		        operation with an error. An example might be if a manager attempts to set 
		        more than one VLAN to be untagged on egress where the device does not support 
		        this IEEE 802.1Q option."		        		       
		    ::= { raisecomRemoteManagementRemoteHideMibObjects 16 }   
		    
    raisecomRemoteL3DefaultGateway  OBJECT-TYPE
		    SYNTAX IpAddress
		    ACCESS read-write
		    STATUS current
		    DESCRIPTION
		        "With this object to Set or get default gateway of remote devices."		        		       
		    ::= { raisecomRemoteManagementRemoteHideMibObjects 17 }		    		    		    		    
 		    
-- MIB according to local raisecomRemotePortTable
	 
   	raisecomRemotePortTable OBJECT-TYPE
		    SYNTAX SEQUENCE OF RaisecomRemotePortEntry
		    ACCESS not-accessible
		    STATUS current
		    DESCRIPTION
		        "A table of remote devices port properties. "
		    ::= { raisecomRemoteManagementRemoteHideMibObjects 18 }

	raisecomRemotePortEntry OBJECT-TYPE
		    SYNTAX RaisecomRemotePortEntry
		    ACCESS not-accessible
		    STATUS current
		    DESCRIPTION
		        "Table entry for port control and status information in remote devices."
		    INDEX { raisecomRemotePortIfindex}
		    ::= { raisecomRemotePortTable 1 }

	RaisecomRemotePortEntry ::= SEQUENCE {
		    raisecomRemotePortIfindex		INTEGER,		    
		    raisecomRemotePortType              INTEGER,
		    raisecomRemotePortName 		OCTET STRING,
		    raisecomRemotePortAdminStatus 	TruthValue,
		    raisecomRemotePortOperStatus 	INTEGER,
		    raisecomRemotePortDuplexSpeedSet 	INTEGER,
		    raisecomRemotePortDuplexSpeedGet 	INTEGER,
		    raisecomRemotePortFlowControlEnable 	EnableVar,
		    raisecomRemotePortFlowControlStatus 	EnableVar,    
		    raisecomRemotePortIngressRate	INTEGER (0..1048576),
		    raisecomRemotePortEgressRate  	INTEGER (0..1048576),		
		    raisecomRemotePortFaultPassEnable	EnableVar,
		    raisecomRemotePortFaultPassPorts    PortList,
		    raisecomRemotePortFaultPassStatus   INTEGER,
		    raisecomRemotePortFaultReturnEnable INTEGER ,
		    raisecomRemotePortFaultReturnStatus   INTEGER,
		    raisecomRemotePortSD   INTEGER,
		    raisecomRemoteOptModuleType  	INTEGER,
		    raisecomRemotePortDescr   OCTET STRING (SIZE (1..255))		        
		    }		   
	
	raisecomRemotePortIfindex OBJECT-TYPE
		    SYNTAX INTEGER
		    ACCESS not-accessible
		    STATUS current
		    DESCRIPTION
		        "The ifIndex value based 1 which identifies the unique interface of remote device."
		    ::= { raisecomRemotePortEntry 2 }

	raisecomRemotePortType OBJECT-TYPE
		    SYNTAX INTEGER{
        			inexistence(0),
        			fx-DulMode-1000M(1), 
        			tx-1000M(2), 
        			fx-SigMode-1000M(3), 
        			fx-DulMode-100M(4), 
        			fx-SigMode-100M(5), 
        			tx-100M(6)
        			}
		    ACCESS read-only
		    STATUS current
		    DESCRIPTION
		        "Port type in remote devices,same as slot type."		         		       
		    ::= { raisecomRemotePortEntry 3 }

	raisecomRemotePortName OBJECT-TYPE
		    SYNTAX OCTET STRING (SIZE (1..32))
		    ACCESS read-only
		    STATUS current
		    DESCRIPTION
		        "The  port  name of  remote devices."		    
		    ::= { raisecomRemotePortEntry 4 }

	 raisecomRemotePortAdminStatus OBJECT-TYPE
		    SYNTAX INTEGER {
             				up(1), 
            				down(2)
       	 			   }
		    ACCESS read-write
		    STATUS current
		    DESCRIPTION
		        "The administrative state of the port on remote devices."		        
		    ::= { raisecomRemotePortEntry 5 }

	 raisecomRemotePortOperStatus OBJECT-TYPE
		    SYNTAX INTEGER {
             				up(1), 
             				down(2)
       				   }
		    ACCESS read-only
		    STATUS current
		    DESCRIPTION
		        "The current operational state of the interface in remote devices."		      
		    ::= {  raisecomRemotePortEntry 6 }

	raisecomRemotePortDuplexSpeedSet OBJECT-TYPE
		    SYNTAX  INTEGER {
             				autonegotiate(1),
             				half-10(2),
             				full-10(3),
             				half-100(4),
            				full-100(5), 
             				half-1000(6),
             				full-1000(7)
        			   }
		    ACCESS read-write
		    STATUS current
		    DESCRIPTION
		        "The desired speed and duplex of the interface in remote devices."		          
		    ::= {  raisecomRemotePortEntry 7 }

	raisecomRemotePortDuplexSpeedGet OBJECT-TYPE
		    SYNTAX  INTEGER {
             				 unknown(1),
            				 half-10(2),
            				 full-10(3),
            				 half-100(4),
            				 full-100(5), 
            				 half-1000(6),
            				 full-1000(7),
           				 illegal(99)
       				   }
		    ACCESS read-only
		    STATUS current
		    DESCRIPTION
		        "The actual speed and duplex for this interface.   If the interface 
		        is not configured for an acceptable value, a value of illegal(99) is 
		        returned. A value of unknown(1) is returned when the interface is down."
		    ::= {  raisecomRemotePortEntry 8 }

	 raisecomRemotePortFlowControlEnable OBJECT-TYPE
		    SYNTAX EnableVar
		    ACCESS read-write
		    STATUS current
		    DESCRIPTION
		        "Set the flow control on the interface to enable(1) or disable(2)."		    
		    ::= {  raisecomRemotePortEntry 9 }

	 raisecomRemotePortFlowControlStatus OBJECT-TYPE
		    SYNTAX  EnableVar
		    ACCESS read-only
		    STATUS current
		    DESCRIPTION
		        "The actual port flow control status of remote device."
		    ::= {  raisecomRemotePortEntry 10 }

	 raisecomRemotePortIngressRate OBJECT-TYPE
		    SYNTAX INTEGER  (0..1048576)
		    ACCESS read-write
		    STATUS current
		    DESCRIPTION
		        "The value is the ingress rate( kbps) of the port."
		    ::= {  raisecomRemotePortEntry 11 }

	 raisecomRemotePortEgressRate OBJECT-TYPE
		    SYNTAX INTEGER  (0..1048576)
		    ACCESS read-write
		    STATUS current
		    DESCRIPTION
		        "The value is the egress rate( kbps) of the port."
		    ::= {  raisecomRemotePortEntry 12 }

	 raisecomRemotePortFaultPassEnable OBJECT-TYPE
		    SYNTAX  EnableVar
		    ACCESS read-write
		    STATUS current
		    DESCRIPTION
		        "Set fault pass to enable(1) or disable(2) on the port in remote device."
		    ::= {  raisecomRemotePortEntry 13 }
		    
	raisecomRemotePortFaultPassPorts OBJECT-TYPE
		    SYNTAX  PortList
		    ACCESS read-write
		    STATUS current
		    DESCRIPTION
		        "The ports set which should be down when fault pass occurs.If 
		        the value is 0,stands for fault pass function is disable on 
		        this port,otherwise fault pass function  is enable and the ports 
		        set specifies which ports should be down when fault pass occurs."
		    ::= {  raisecomRemotePortEntry 14 }
		    
	raisecomRemotePortFaultPassStatus OBJECT-TYPE
		    SYNTAX  INTEGER  {  
	           			normal (1),
	           			down (2)
	       			     }
		    ACCESS read-only
		    STATUS current
		    DESCRIPTION
		        "Port state changging result of fault pass. If normal(1), there is no 
		        fault pass occurring. If down(2), the port is down because of fault 
		        pass occurring."
		    ::= {  raisecomRemotePortEntry 15 }
		    
	raisecomRemotePortFaultReturnEnable OBJECT-TYPE
		    SYNTAX  INTEGER	{
	          			 enable (1),
	          			 disable (2),
	          			 unavailable(3)
        				} 
		    ACCESS read-write
		    STATUS current
		    DESCRIPTION
		        "Set fault return on the port in remote device to enable(1) or disable(2). 
		        This value of TP is unavailable."
		    ::= {  raisecomRemotePortEntry 16 }
		    
	raisecomRemotePortFaultReturnStatus OBJECT-TYPE
		    SYNTAX INTEGER {
	           			normal (1),
	           			down (2),
	           			unavailable(3)
        			   } 
		    ACCESS read-only
		    STATUS current
		    DESCRIPTION
		        "Port state changging result of fault return.If normal(1), there 
		        is no fault return occurring.If down(2), the port is down result 
		        of fault return occurring.This value of TP is unavailable."
		    ::= {  raisecomRemotePortEntry 17 }
		    
	raisecomRemotePortSD OBJECT-TYPE
		    SYNTAX  INTEGER    {
	         			 normal (1),
	         			 sd (2),
	          			 unavailable(3)
        				} 
		    ACCESS read-only
		    STATUS current
		    DESCRIPTION
		        "SD status. This value of TP is unavailable."
		    ::= {  raisecomRemotePortEntry 18 }
		    
	raisecomRemoteOptModuleType OBJECT-TYPE
		    SYNTAX  INTEGER   {      
      	     				optical-M(1),
      	     				optical-S1(2),
      	     				optical-S2(3),
      	     				optical-S3(4),
      	     				optical-SS13(5), 
      	     				optical-SS15(6),
      	     				optical-SS23(7),
      	     				optical-SS25(8),
      	     				optical-SS35(9),
       	  				unknown(10)   	     	   	
       	  				} 
		    ACCESS read-only
		    STATUS current
		    DESCRIPTION
		        "Optical module type of remote device port."
		    ::= {  raisecomRemotePortEntry 19 }
		    
	raisecomRemotePortDescr OBJECT-TYPE
		    SYNTAX  OCTET STRING (SIZE (1..255))
		    ACCESS read-write
		    STATUS current
		    DESCRIPTION
		        "The description of a port in remote device."
		    ::= {  raisecomRemotePortEntry 20 }
   
   
-- MIB according to local raisecomRemotePortStatsTable

	raisecomRemotePortStatsTable OBJECT-TYPE
		    SYNTAX SEQUENCE OF RaisecomRemotePortStatsEntry
		    ACCESS not-accessible
		    STATUS current
		    DESCRIPTION
		        "A table of remote devices port statistics."
		    ::= { raisecomRemoteManagementRemoteHideMibObjects 19 }

	raisecomRemotePortStatsEntry OBJECT-TYPE
		    SYNTAX RaisecomRemotePortStatsEntry
		    ACCESS not-accessible
		    STATUS current
		    DESCRIPTION
		        "Table entry of remote devices port statistics."
		    INDEX {raisecomRemoteStatsPortIfindex}
		    ::= { raisecomRemotePortStatsTable 1 }

	RaisecomRemotePortStatsEntry ::= SEQUENCE {
		    raisecomRemoteStatsPortIfindex	INTEGER,		    
		    raisecomRemotePortInOctets          Counter64,
		    raisecomRemotePortInPkts 		Counter64,
		    raisecomRemotePortInUcastPkts 	Counter64,
		    raisecomRemotePortInMulticastPkts 	Counter64,
		    raisecomRemotePortInBroadcastPkts 	Counter64,
		    raisecomRemotePortOutOctets 	Counter64,
		    raisecomRemotePortOutPkts 		Counter64,
		    raisecomRemotePortOutUcastPkts 	Counter64,    
		    raisecomRemotePortOutMulticastPkts	Counter64,
		    raisecomRemotePortOutBroadcastPkts  Counter64,		
		    raisecomRemotePortErrorPkts 	Counter32,
		    raisecomRemotePortDropEvents    	Counter32,
		    raisecomRemotePortCRCAlignErrors    Counter32,
		    raisecomRemotePortUndersizePkts 	Counter32 ,
		    raisecomRemotePortOversizePkts   	Counter32,
		    raisecomRemotePortFragments   	Counter32,
		    raisecomRemotePortJabbers  		Counter32,
		    raisecomRemotePortCollisions   	Counter32		        
		    }		   

	
	raisecomRemoteStatsPortIfindex OBJECT-TYPE
		    SYNTAX INTEGER
		    ACCESS not-accessible
		    STATUS current
		    DESCRIPTION
		        "The ifIndex value based 1 which identifies the unique interface of remote device."
		    ::= { raisecomRemotePortStatsEntry 1 }

	raisecomRemotePortInOctets OBJECT-TYPE
		    SYNTAX Counter64
		    ACCESS read-only
		    STATUS current
		    DESCRIPTION
		        "The total number of octets received on the port."		         		       
		    ::= { raisecomRemotePortStatsEntry 2 }
		    
	raisecomRemotePortInPkts OBJECT-TYPE
		    SYNTAX Counter64
		    ACCESS read-only
		    STATUS current
		    DESCRIPTION
		        "The total number of packets received on the port.."		         		       
		    ::= { raisecomRemotePortStatsEntry 3 }
		    
	raisecomRemotePortInUcastPkts OBJECT-TYPE
		    SYNTAX Counter64
		    ACCESS read-only
		    STATUS current
		    DESCRIPTION
		        "The number of packets, delivered by this sub-layer to  a 
		        higher (sub-)layer, which were not addressed to a  multicast 
		        or broadcast address at this sub-layer."		         		       
		    ::= { raisecomRemotePortStatsEntry 4 }
		    
	raisecomRemotePortInMulticastPkts OBJECT-TYPE
		    SYNTAX Counter64
		    ACCESS read-only
		    STATUS current
		    DESCRIPTION
		        "The number of packets, delivered by this sub-layer to a 
		        higher (sub-)layer, which were addressed to a multicast 
		        address at this sub-layer. For a MAC layer  protocol, this
		         includes both Group and Functional addresses"		         		       
		    ::= { raisecomRemotePortStatsEntry 5 }
		    
	raisecomRemotePortInBroadcastPkts OBJECT-TYPE
		    SYNTAX Counter64
		    ACCESS read-only
		    STATUS current
		    DESCRIPTION
		        "The number of packets, delivered by this sub-layer to a higher (sub-)layer,
		         which were addressed to a broadcast address at this sub-layer."		         		       
		    ::= { raisecomRemotePortStatsEntry 6 }
	
	raisecomRemotePortOutOctets OBJECT-TYPE
		    SYNTAX Counter64
		    ACCESS read-only
		    STATUS current
		    DESCRIPTION
		        "The total number of octets transmitted out of the port, 
		        including framing characters."		         		       
		    ::= { raisecomRemotePortStatsEntry 7 }
		    
	raisecomRemotePortOutPkts OBJECT-TYPE
		    SYNTAX Counter64
		    ACCESS read-only
		    STATUS current
		    DESCRIPTION
		        "The total number of packets transmitted out of the port."		         		       
		    ::= { raisecomRemotePortStatsEntry 8 }
		    
	raisecomRemotePortOutUcastPkts OBJECT-TYPE
		    SYNTAX Counter64
		    ACCESS read-only
		    STATUS current
		    DESCRIPTION
		        "The total number of packets that higher-level protocols requested be 
		        transmitted, and which were not addressed to a multicast or broadcast
		        address at this sub-layer, including those that were discarded or not sent."		         		       
		    ::= { raisecomRemotePortStatsEntry 9 }
		    
	raisecomRemotePortOutMulticastPkts OBJECT-TYPE
		    SYNTAX Counter64
		    ACCESS read-only
		    STATUS current
		    DESCRIPTION
		        "The total number of packets that higher-level protocols requested be transmitted,
		         and which were  addressed to a multicast address at this sub-layer, including those
		         that were discarded or not sent.  For a MAC layer protocol, this includes both 
		         Group and  Functional addresses."		         		       
		    ::= { raisecomRemotePortStatsEntry 10 }
		    
	raisecomRemotePortOutBroadcastPkts OBJECT-TYPE
		    SYNTAX Counter64
		    ACCESS read-only
		    STATUS current
		    DESCRIPTION
		        "The total number of packets that higher-level protocols requested be transmitted,
		         and which were  addressed to a broadcast address at this sub-layer, including 
		         those that were discarded or not sent. "		         		       
		    ::= { raisecomRemotePortStatsEntry 11 }
		    
	raisecomRemotePortErrorPkts OBJECT-TYPE
		    SYNTAX Counter32
		    ACCESS read-only
		    STATUS current
		    DESCRIPTION
		        "The total number of bad packets received by a specific port of remote device."		         		       
		    ::= { raisecomRemotePortStatsEntry 12 }
		    
	raisecomRemotePortDropEvents OBJECT-TYPE
		    SYNTAX Counter32
		    ACCESS read-only
		    STATUS current
		    DESCRIPTION
		        "The total number of events in which packets were dropped by 
		        the probe due to lack of resources. Note that this number is 
		        not necessarily the number of packets dropped; it is just the
		         number of times this  condition has been detected."		         		       
		    ::= { raisecomRemotePortStatsEntry 13 }
		    
	raisecomRemotePortCRCAlignErrors OBJECT-TYPE
		    SYNTAX Counter32
		    ACCESS read-only
		    STATUS current
		    DESCRIPTION
		        "The total number of packets received that had a length (excluding
		         framing bits, but including FCS octets) of between 64 and 1518 octets,
		         inclusive, but but had either a bad  Frame Check Sequence (FCS) with
		         an integral number of octets (FCS Error) or a bad FCS with a 
		         non-integral number of octets (Alignment Error)."		         		       
		    ::= { raisecomRemotePortStatsEntry 14 }
		    
	raisecomRemotePortUndersizePkts OBJECT-TYPE
		    SYNTAX Counter32
		    ACCESS read-only
		    STATUS current
		    DESCRIPTION
		        "The total number of packets received that were less than 64 octets
		         long (excluding framing bits, but including FCS octets) and were 
		         otherwise well formed."		         		       
		    ::= { raisecomRemotePortStatsEntry 15 }
		    
	raisecomRemotePortOversizePkts OBJECT-TYPE
		    SYNTAX Counter32
		    ACCESS read-only
		    STATUS current
		    DESCRIPTION
		        "The total number of packets received that were longer than 1518
		         octets (excluding framing bits,  but including FCS octets) and
		         were otherwise  well formed."		         		       
		    ::= { raisecomRemotePortStatsEntry 16 }
		    
	raisecomRemotePortFragments OBJECT-TYPE
		    SYNTAX Counter32                      
		    ACCESS read-only
		    STATUS current
		    DESCRIPTION
		        "The total number of packets received that were less than 64 octets 
		        in length (excluding framing bits but   including FCS octets) and had
		        either a bad Frame Check Sequence (FCS) with an integral number of
		        octets (FCS Error) or a bad FCS with a non-integral number of octets 
		        (Alignment Error)."		         		       
		    ::= { raisecomRemotePortStatsEntry 17 }	    	    	    	    		    
		    		    		    	    		    		   	    		    		    		    
	raisecomRemotePortJabbers OBJECT-TYPE
		    SYNTAX Counter32
		    ACCESS read-only
		    STATUS current
		    DESCRIPTION
		        "The total number of packets received that were longer than 1518
		         octets (excluding framing bits, but including FCS octets), and
		         had either a bad Frame Check Sequence (FCS) with an integral
		         number of octets (FCS Error) or a bad FCS with a on-integral 
		         number of octets (Alignment Error)."		         		       
		    ::= { raisecomRemotePortStatsEntry 18 }
		    
	raisecomRemotePortCollisions OBJECT-TYPE
		    SYNTAX Counter32
		    ACCESS read-only
		    STATUS current
		    DESCRIPTION
		        "The best estimate of the total number of collisions on
		         this Ethernet segment."		         		       
		    ::= { raisecomRemotePortStatsEntry 19 }
		    
    raisecomRemoteVoltNormal  OBJECT-TYPE
		    SYNTAX INTEGER{
		                    normal(1),
		                    high(2),
		                    low(3)		        
	                      }  
		    ACCESS read-only
		    STATUS current
		    DESCRIPTION
		        "This object specifies whether remote votage is in normal range or not."    		       
		    ::= { raisecomRemoteManagementRemoteHideMibObjects 20 }	  
		    
	raisecomRemoteMaxAllowedFrameLength OBJECT-TYPE
		    SYNTAX INTEGER
		    ACCESS read-write
		    STATUS current
		    DESCRIPTION
		        "This object specifies max ethernet frame length of remote device." 		    		    
		    ::= { raisecomRemoteManagementRemoteHideMibObjects 21 }	
	 raisecomRemoteL3ObPortIpAddr	OBJECT-TYPE
		    SYNTAX IpAddress
		    ACCESS read-write
		    STATUS current
		    DESCRIPTION
			"The out IP Address of remote device."
		    ::= { raisecomRemoteManagementRemoteHideMibObjects 22 }		    		    		    		    
 	raisecomRemoteL3ObPortMask OBJECT-TYPE
		    SYNTAX IpAddress
		    ACCESS read-write
		    STATUS current
		    DESCRIPTION
		        "The subnet mask for this remote subnet."		        		       
		    ::= { raisecomRemoteManagementRemoteHideMibObjects 23 }

END

--MibName=rcRip
RAISECOM-RIP-MIB DEFINITIONS ::= BEGIN

    IMPORTS
        MODULE-IDENTITY, OBJECT-TYPE,
        Integer32, IpAddress                     FROM SNMPv2-SMI
        
        RowStatus, TruthValue                   FROM SNMPv2-TC 
        EnableVar		FROM SWITCH-TC
        
        OBJECT-GROUP         FROM SNMPv2-CONF
        
        iscomSwitch	            	FROM RAISECOM-BASE-MIB ;
        

    rcRip MODULE-IDENTITY
        LAST-UPDATED    "0412200000Z"  -- Dec 20, 2004
        ORGANIZATION    "Raisecom, Inc."
        CONTACT-INFO    
                "       Raise Systems
                        
                Postal: Beijing,
                        China

                   Tel: 86-010-82884499

                E-mail: zhaohongce@raisecom.com"

        DESCRIPTION     "RIP Enterprise MIB definition."

        REVISION        "0412200000Z"  -- Dec 20, 2004  
        DESCRIPTION     "Initial MIB creation."

        ::= { iscomSwitch 17}

------------------------------------------------------------------------------
--  define groups in TMS-COMMON-MIB
------------------------------------------------------------------------------

    rcRipConfig        OBJECT IDENTIFIER ::= { rcRip 1 }
    rcRipIfConfig      OBJECT IDENTIFIER ::= { rcRip 2 }
    rcRipNetConfig     OBJECT IDENTIFIER ::= { rcRip 3 }
     --

------------------------------------------------------------------------------
--
--   rcRipConfig- rip Parameters
--
--  This group is used to instrument the Layer 3 rip support.
--
------------------------------------------------------------------------------
--
    rcRip2GlobalEnable  OBJECT-TYPE
        SYNTAX EnableVar        
        MAX-ACCESS read-write
        STATUS current
        DESCRIPTION
            "DURABLE: { disable }
             Setting this object to enable(1) enables RIP.  Setting
             it to disable(2) disables RIP." 
        DEFVAL {disable}
        ::= { rcRipConfig 1 }
        
    rcRip2GlobalPassive  OBJECT-TYPE
        SYNTAX TruthValue
        MAX-ACCESS read-write
        STATUS current
        DESCRIPTION
            "DURABLE: { true }
             Setting this object to true(1) enables RIP passive.  Setting
             it to false(2) disables RIP passive."
        ::= { rcRipConfig 2 }

    rcRip2UpdateTime  OBJECT-TYPE
        SYNTAX Integer32 (30..500)
        MAX-ACCESS read-write
        STATUS current
        DESCRIPTION
            "DURABLE: { 30 }
             The timeout period in seconds for send update packets."
        ::= { rcRipConfig 3 }
        
    rcRip2ExpireTime  OBJECT-TYPE
        SYNTAX Integer32 (120..180)
        MAX-ACCESS read-write
        STATUS current
        DESCRIPTION
            "DURABLE: { 180 }
             The timeout period in seconds for the route expire."
        ::= { rcRipConfig 4 }    
        
    rcRip2FlushTime  OBJECT-TYPE
        SYNTAX Integer32 (180..500)
        MAX-ACCESS read-write
        STATUS current
        DESCRIPTION
            "DURABLE: { 300 }
             The timeout period in seconds for the route flush when expired."
        ::= { rcRipConfig 5 }    
                
    rcRip2Distance  OBJECT-TYPE
        SYNTAX Integer32 (1..255)
        MAX-ACCESS read-write
        STATUS current
        DESCRIPTION
            "DURABLE: { 120 }
             The distance of RIP."
        ::= { rcRipConfig 6 }                    
------------------------------------------------------------------------------
--
--  tmsCommonrip - rip Parameters
--
--  This group is used to instrument the Layer 3 rip if support.
--
------------------------------------------------------------------------------
--
    rcRip2IfConfigTable OBJECT-TYPE
        SYNTAX   SEQUENCE OF RcRip2IfConfigEntry
        MAX-ACCESS   not-accessible
        STATUS   current
        DESCRIPTION
           "A list of subnets which require separate
           status monitoring in RIP."
       ::= { rcRipIfConfig 1 }

   rcRip2IfConfigEntry OBJECT-TYPE
       SYNTAX   RcRip2IfConfigEntry
       MAX-ACCESS   not-accessible
       STATUS   current
       DESCRIPTION
          "A list of subnets which require separate
           status monitoring in RIP."
      INDEX { rcRip2IfConfigAddress }
      ::= { rcRip2IfConfigTable 1 }

    RcRip2IfConfigEntry ::=
        SEQUENCE {
            rcRip2IfConfigAddress IpAddress,
            rcRip2IfConfigSplit TruthValue,
            rcRip2IfConfigRowStatus  RowStatus
    }

    rcRip2IfConfigAddress OBJECT-TYPE
        SYNTAX   IpAddress
        MAX-ACCESS   read-only
        STATUS   current
        DESCRIPTION
           "The IP Address of this system on the indicated
           subnet. For unnumbered interfaces, the value 0.0.0.N,
           where the least significant 24 bits (N) is the ifIndex
           for the IP Interface in network byte order."
       ::= { rcRip2IfConfigEntry 1 }

    rcRip2IfConfigSplit OBJECT-TYPE
        SYNTAX   TruthValue
        MAX-ACCESS   read-create
        STATUS   current
        DESCRIPTION
           "DURABLE: { true }
             Setting this object to true(1) enables split horazon.  Setting
             it to false(2) disables split horizon."
       ::= { rcRip2IfConfigEntry 2 }

    rcRip2IfConfigRowStatus OBJECT-TYPE
        SYNTAX   RowStatus
        MAX-ACCESS   read-create
        STATUS   current
        DESCRIPTION
           "Writing invalid has  the  effect  of  deleting
           this interface."
       ::= { rcRip2IfConfigEntry 3 }

-----------------------------------------------------------------------
rcRip2NetConfigTable OBJECT-TYPE
    SYNTAX SEQUENCE OF RcRip2NetConfigEntry
    MAX-ACCESS not-accessible
    STATUS current
    DESCRIPTION
        "the network address table for startup the rip on a interface."
    ::=  { rcRipNetConfig 1 }                                                             

rcRip2NetConfigEntry OBJECT-TYPE
    SYNTAX RcRip2NetConfigEntry
    MAX-ACCESS not-accessible
    STATUS current
    DESCRIPTION
        " the network address table for startup the rip on a interface."
    INDEX { rcRip2NetConfigSubnet, rcRip2NetConfigMask }
    ::=  { rcRip2NetConfigTable 1 }

RcRip2NetConfigEntry ::= SEQUENCE {
    rcRip2NetConfigSubnet		 IpAddress, 
    rcRip2NetConfigMask		IpAddress,
    rcRip2NetConfigRowStatus		RowStatus
    }

rcRip2NetConfigSubnet  OBJECT-TYPE
    SYNTAX IpAddress
    MAX-ACCESS read-create
    STATUS current
    DESCRIPTION
        "the network address for startup the rip on a interface."
    ::=  { rcRip2NetConfigEntry 1 }
                                     
rcRip2NetConfigMask OBJECT-TYPE
    SYNTAX IpAddress
    MAX-ACCESS read-create
    STATUS current
    DESCRIPTION
        " the network mask for startup the rip on a interface."
    ::=  { rcRip2NetConfigEntry 2 }

rcRip2NetConfigRowStatus OBJECT-TYPE
    SYNTAX RowStatus
    MAX-ACCESS read-create
    STATUS current
    DESCRIPTION
        " This variable displays the status of the entry. "
    ::=  { rcRip2NetConfigEntry 3 }



END

-- MibName=raisecomTopoDiscovery
-- *****************************************************************
-- RAISECOM-TOPODISCOVERY-MIB.MIB:  Raisecom Topology Discovery MIB file
--
-- Sep. 2004, xieyong
--
-- Copyright (c) 1994-2004, 2004 by Raisecom, Inc.
-- All rights reserved.
--
-- *****************************************************************
RAISECOM-RTDP-MIB  DEFINITIONS ::= BEGIN

IMPORTS
       raisecomCluster
                FROM RAISECOM-BASE-MIB  
       EnableVar,PortList FROM SWITCH-TC
       MacAddress
				FROM SNMPv2-TC
	   raisecomRndpDiscoveryDeviceId
	   			FROM RAISECOM-RNDP-MIB;
	   			
raisecomTopoDiscovery MODULE-IDENTITY
        LAST-UPDATED    "200412210000Z"
        ORGANIZATION    "Raisecom, Inc."
        CONTACT-INFO
                        "Raisecom Systems

                        Postal: Beijing, China

                        Tel: 86-010-82884499

                        E-mail: xieyong@raisecom.com"
        DESCRIPTION
                        "description of topology discovery."
                ::= {raisecomCluster 2}
                
-- RTDP Scalar 
    raisecomRtdpCollectEnable OBJECT-TYPE
        SYNTAX  EnableVar
        ACCESS read-write
        STATUS mandatory
        DESCRIPTION
                "DURABLE: { disable }
                  enable(1) or disable(2) raisecomRtdp collecting on the switch."
        DEFVAL {disable}
        ::= { raisecomTopoDiscovery 4 }

    raisecomRtdpReportEnable OBJECT-TYPE
        SYNTAX  EnableVar
        ACCESS read-write
        STATUS mandatory
        DESCRIPTION
                "DURABLE: { enable }
                  enable(1) or disable(2) raisecomRtdp collecting on the switch."
        DEFVAL {enable}
        ::= { raisecomTopoDiscovery 5 }

    raisecomRtdpMaxHops OBJECT-TYPE
        SYNTAX INTEGER (1..16)
        ACCESS read-write
        STATUS mandatory
        DESCRIPTION
                "RTDP collecting max hops."
        ::= { raisecomTopoDiscovery 6 }

-- RTDP Device Discovery Table 
    raisecomRtdpDeviceDiscoveryTable OBJECT-TYPE
        SYNTAX SEQUENCE OF RaisecomRtdpDeviceDiscoveryEntry
        MAX-ACCESS not-accessible
        STATUS current
        DESCRIPTION
            "raisecomRtdp discovery table."
        ::= { raisecomTopoDiscovery 7 }

    raisecomRtdpDeviceDiscoveryEntry OBJECT-TYPE
        SYNTAX RaisecomRtdpDeviceDiscoveryEntry
        MAX-ACCESS not-accessible
        STATUS current
        DESCRIPTION
            "raisecomRtdp discovery table entry."
        INDEX { raisecomRndpDiscoveryDeviceId }
        ::= { raisecomRtdpDeviceDiscoveryTable 1 }

    RaisecomRtdpDeviceDiscoveryEntry ::= SEQUENCE {
        raisecomRtdpDeviceDiscoveryDeviceId        MacAddress,
        raisecomRtdpDeviceDiscoveryHops            INTEGER,
        raisecomRtdpDeviceDiscoveryHostName        OCTET STRING,
        raisecomRtdpDeviceDiscoveryPlatformOid     OBJECT IDENTIFIER,
        raisecomRtdpDeviceDiscoveryVersion         OCTET STRING,
        raisecomRtdpDeviceDiscoveryCapabilities    INTEGER,
        raisecomRtdpDeviceDiscoveryRole            INTEGER,
        raisecomRtdpDeviceDiscoveryCommanderMac    MacAddress,
        raisecomRtdpDeviceDiscoveryAutoActive      EnableVar,
        raisecomRtdpDeviceDiscoveryAutoActiveMac   MacAddress
     }

    raisecomRtdpDeviceDiscoveryDeviceId OBJECT-TYPE
        SYNTAX  MacAddress
        MAX-ACCESS read-only
        STATUS current
        DESCRIPTION
            "System mac address, uniquely identifies a remote device."
        ::= { raisecomRtdpDeviceDiscoveryEntry 1 }

    raisecomRtdpDeviceDiscoveryHops OBJECT-TYPE
        SYNTAX  INTEGER (1..16)
        MAX-ACCESS read-only
        STATUS current
        DESCRIPTION
            "The hops away from this Rtdp collector, at which the remote device has been found."
        ::= { raisecomRtdpDeviceDiscoveryEntry 2 }

    raisecomRtdpDeviceDiscoveryHostName OBJECT-TYPE
        SYNTAX  OCTET STRING
        MAX-ACCESS read-only
        STATUS current
        DESCRIPTION
            "Remote device host name."
        ::= { raisecomRtdpDeviceDiscoveryEntry 3 }

    raisecomRtdpDeviceDiscoveryPlatformOid OBJECT-TYPE
        SYNTAX  OBJECT IDENTIFIER
        MAX-ACCESS read-only
        STATUS current
        DESCRIPTION
            "Remote device playform OID."
        ::= { raisecomRtdpDeviceDiscoveryEntry 4 }

    raisecomRtdpDeviceDiscoveryVersion OBJECT-TYPE
        SYNTAX  OCTET STRING
        MAX-ACCESS read-only
        STATUS current
        DESCRIPTION
            "Remote device software version."
        ::= { raisecomRtdpDeviceDiscoveryEntry 5 }

    raisecomRtdpDeviceDiscoveryCapabilities OBJECT-TYPE
        SYNTAX  INTEGER  {
                 switch(1),
                 router(2),
                 eoa(3),
                 eos(4),
                 others(5)
                }
        MAX-ACCESS read-only
        STATUS current
        DESCRIPTION
            "Remote device capabilities."
        ::= { raisecomRtdpDeviceDiscoveryEntry 6 }

    raisecomRtdpDeviceDiscoveryRole OBJECT-TYPE
        SYNTAX  INTEGER  {
                 member(1),
                 candidate(2),
                 commander(3)
                }
        MAX-ACCESS read-only
        STATUS current
        DESCRIPTION
            "Remote device cluster role, candidate(1), member(2) or commander(3)."
        ::= { raisecomRtdpDeviceDiscoveryEntry 7 }

    raisecomRtdpDeviceDiscoveryCommanderMac OBJECT-TYPE
        SYNTAX  MacAddress
        MAX-ACCESS read-only
        STATUS current
        DESCRIPTION
            "The mac address of the commander, which the remote device belongs to.
            If the remote device is not a member of any commander, this object has no value."
        ::= { raisecomRtdpDeviceDiscoveryEntry 8 }

    raisecomRtdpDeviceDiscoveryAutoActive OBJECT-TYPE
        SYNTAX  EnableVar
        MAX-ACCESS read-only
        STATUS current
        DESCRIPTION
            "Indicates whether the remote device can be active automatically, true(1) or false(2)."
        ::= { raisecomRtdpDeviceDiscoveryEntry 9 }

    raisecomRtdpDeviceDiscoveryAutoActiveMac OBJECT-TYPE
        SYNTAX  MacAddress
        MAX-ACCESS read-only
        STATUS current
        DESCRIPTION
            "The mac address of the commander which can active this remote member automatically."
        ::= { raisecomRtdpDeviceDiscoveryEntry 10 }

-- RTDP Device Relationship Table 
    raisecomRtdpRelationshipTable OBJECT-TYPE
        SYNTAX SEQUENCE OF RaisecomRtdpRelationshipEntry
        MAX-ACCESS not-accessible
        STATUS current
        DESCRIPTION
            "Rtdp devices relationship table."
        ::= { raisecomTopoDiscovery 8 }

    raisecomRtdpRelationshipEntry OBJECT-TYPE
        SYNTAX RaisecomRtdpRelationshipEntry
        MAX-ACCESS not-accessible
        STATUS current
        DESCRIPTION
            "Rtdp devices relationship table entry."
        INDEX { raisecomRtdpRelationshipDeviceId, raisecomRtdpRelationshipPeerDeviceId }
        ::= { raisecomRtdpRelationshipTable 1 }

    RaisecomRtdpRelationshipEntry ::= SEQUENCE {
        raisecomRtdpRelationshipDeviceId            MacAddress,
        raisecomRtdpRelationshipPeerDeviceId        MacAddress,
        raisecomRtdpRelationshipNativePort          INTEGER,
        raisecomRtdpRelationshipPeerPort            INTEGER
     }

    raisecomRtdpRelationshipDeviceId OBJECT-TYPE
        SYNTAX MacAddress
        MAX-ACCESS read-only
        STATUS current
        DESCRIPTION
            "Device mac address."
        ::= { raisecomRtdpRelationshipEntry 1 }

    raisecomRtdpRelationshipPeerDeviceId OBJECT-TYPE
        SYNTAX MacAddress
        MAX-ACCESS read-only
        STATUS current
        DESCRIPTION
            "Peer device mac address."
        ::= { raisecomRtdpRelationshipEntry 2 }

    raisecomRtdpRelationshipNativePort OBJECT-TYPE
        SYNTAX INTEGER
        MAX-ACCESS read-only
        STATUS current
        DESCRIPTION
            "Native port id base 1."
        ::= { raisecomRtdpRelationshipEntry 3 }

    raisecomRtdpRelationshipPeerPort OBJECT-TYPE
        SYNTAX INTEGER
        MAX-ACCESS read-only
        STATUS current
        DESCRIPTION
            "Peer port id base 1."
        ::= { raisecomRtdpRelationshipEntry 4 }

	raisecomRtdpTrap NOTIFICATION-TYPE
           STATUS  current
           DESCRIPTION
               "rtdp topology change trap."
       ::= { raisecomTopoDiscovery 9 }    
        
	raisecomRtdpControlVlan OBJECT-TYPE
        SYNTAX INTEGER  (2..4094)
        MAX-ACCESS read-write
        STATUS current
        DESCRIPTION
               "rtdp and cluster vlan."
       ::= { raisecomTopoDiscovery 10 }  
         
	raisecomRtdpControlVlanPorts OBJECT-TYPE
        SYNTAX PortList
        MAX-ACCESS read-write
        STATUS current
        DESCRIPTION
               "rtdp and cluster vlan ports."
       ::= { raisecomTopoDiscovery 11 }


END

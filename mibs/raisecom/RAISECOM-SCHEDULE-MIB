-- MibName=raisecomSchedule
-- *****************************************************************
--RAISECOM-SCHEDULE-MIB.mi2 : Raisecom schedule task MIB file
--
-- Jan 2005, liujunfu
--
-- Copyright (c) 1994-2004,	2001 by	Raisecom, Inc.
-- All rights reserved.
-- modify raisecomScheduleListFlag and raisecomScheduleCommandMode type guokai 20130315
-- *****************************************************************

RAISECOM-SCHEDULE-MIB DEFINITIONS ::= BEGIN


IMPORTS
    
    Integer32             FROM SNMPv2-SMI
    TEXTUAL-CONVENTION, RowStatus	     FROM SNMPv2-TC
    MODULE-COMPLIANCE, OBJECT-GROUP,
    NOTIFICATION-GROUP                       FROM SNMPv2-CONF
    raisecomAgent			FROM RAISECOM-BASE-MIB;
    
     raisecomSchedule MODULE-IDENTITY
		LAST-UPDATED	"200501260000Z"
		ORGANIZATION	"Raisecom, Inc."
		CONTACT-INFO
				"Raise Systems
				Postal:	Beijing, China
				   Tel:	86-010-82884499
				E-mail:	support@raisecom.com"
		DESCRIPTION
				"Modified description of access	list object."
				::=	{ raisecomAgent 8 }

--
--	define groups in RAISECOM-ACCESSLIST-MIB
-- 
	raisecomScheduleconfig	OBJECT IDENTIFIER ::= {	raisecomSchedule 1 } 
	raisecomScheduleList			OBJECT IDENTIFIER ::= {	raisecomSchedule 2 }
--

-- 
--   schedule list tables 
-- 
--   command string table 
-- 

	raisecomScheduleListTable OBJECT-TYPE
		SYNTAX		SEQUENCE OF	RaisecomScheduleListEntry
		MAX-ACCESS	not-accessible
		STATUS		current
		DESCRIPTION
			"schedule-list table object, consist a list of schedule time "
		::={ raisecomScheduleList 1}

	raisecomScheduleListEntry OBJECT-TYPE
		SYNTAX		RaisecomScheduleListEntry
		MAX-ACCESS	not-accessible
		STATUS		current
		DESCRIPTION
			"an schedule list entry consist objects for schedule"
		INDEX {	raisecomScheduleListIndex }
		::=	{ raisecomScheduleListTable 1 }

	RaisecomScheduleListEntry ::= SEQUENCE {
		raisecomScheduleListIndex			Integer32(0..99),
		raisecomScheduleListFlag			INTEGER,      
		
		raisecomScheduleListStartTime			Integer32,			
		raisecomScheduleListPeriod			Integer32,   
		raisecomScheduleListStopTime			Integer32,	
		
		raisecomScheduleListLastExeTime		Integer32,
		raisecomScheduleListNextExeTime		Integer32,
		raisecomScheduleRef					Integer32,
		raisecomScheduleListStatus			RowStatus
	}

				
	raisecomScheduleListIndex OBJECT-TYPE
		SYNTAX	Integer32(0..99)
		ACCESS	not-accessible
		STATUS	current
		DESCRIPTION
			"The index of schedule-list"
		::=	{ raisecomScheduleListEntry 1 }
		
	raisecomScheduleListFlag OBJECT-TYPE
		SYNTAX	INTEGER{
			startup(1),
			realdate(2)
		}		
		ACCESS	read-write
		STATUS	current
		DESCRIPTION
			"flag is used to define the start time attribute, startup stands for time from system start-up 
			 realdate stands for time is system date time"
		::=	{ raisecomScheduleListEntry 2 }
		
	raisecomScheduleListStartTime OBJECT-TYPE
		SYNTAX	Integer32	
		ACCESS	read-write
		STATUS	current
		DESCRIPTION
			"the command attached to the schedule list begin to execute time,
			this is an interger (unit:second )"
		::=	{ raisecomScheduleListEntry 3 }
		
		
	raisecomScheduleListPeriod OBJECT-TYPE
		SYNTAX	Integer32(0..31622400)	
		ACCESS	read-write
		STATUS	current
		DESCRIPTION
			"0 stand for no schedule period time 
			other vale stand for vlaue for period time to execute."
		::=	{ raisecomScheduleListEntry 4 }
		
		
		

	raisecomScheduleListStopTime OBJECT-TYPE
		SYNTAX	Integer32
		ACCESS	read-write
		STATUS	current
		DESCRIPTION
			"time for sechedule to stop execute command
			:Requid larger than start time"
		::=	{ raisecomScheduleListEntry 5 }
	
	raisecomScheduleListLastExeTime OBJECT-TYPE
		SYNTAX	Integer32
		ACCESS	read-only
		STATUS	current
		DESCRIPTION
			"0, for never execute command, 
			 other value stands for last time execute command"
		::=	{ raisecomScheduleListEntry 6 }
		
	raisecomScheduleListNextExeTime  OBJECT-TYPE
		SYNTAX	Integer32
		ACCESS	read-only
		STATUS	current
		DESCRIPTION
			"0, for no time for next execute command, 
			 other value stands for next  time execute command"
		::=	{ raisecomScheduleListEntry 7 }
	
	raisecomScheduleRef OBJECT-TYPE
		SYNTAX	Integer32
		ACCESS	read-only
		STATUS	current
		DESCRIPTION
			"commands number attached for schedule-list"
		::=	{ raisecomScheduleListEntry 8 }
		
	raisecomScheduleListStatus OBJECT-TYPE
		SYNTAX	RowStatus
		ACCESS	read-write
		STATUS	current
		DESCRIPTION
			"Row status for schedule-list"
		::=	{ raisecomScheduleListEntry 9 }

 -- -------------------------------------------------------------------------- --
 --
 --   command string table 
 --
 -- ------------------------------------------------------------------------- --  
 
	raisecomScheduleCommandTable OBJECT-TYPE
		SYNTAX		SEQUENCE OF	RaisecomScheduleCommandEntry
		MAX-ACCESS	not-accessible
		STATUS		current
		DESCRIPTION
			"table for command attached on schedule-list"
		::=	{ raisecomScheduleList 2}

	raisecomScheduleCommandEntry OBJECT-TYPE
		SYNTAX		RaisecomScheduleCommandEntry
		MAX-ACCESS	not-accessible
		STATUS		current
		DESCRIPTION
			"Table entry for commands attached on schedule -list"
		INDEX {	raisecomScheduleIndex, raisecomScheduleCommandNo }
		::=	{ raisecomScheduleCommandTable 1 }

	RaisecomScheduleCommandEntry ::= SEQUENCE {
		raisecomScheduleIndex					Integer32(0..99),
		raisecomScheduleCommandNo				Integer32(0..99),
		raisecomScheduleCommandString			OCTET STRING,
		raisecomScheduleCommandMode			INTEGER,
		raisecomScheduleCommandNodeInfo   	OCTET STRING,
		raisecomScheduleCommandExeCount		Integer32,		
		raisecomScheduleCommandLastExeTime	Integer32
	}
     raisecomScheduleIndex OBJECT-TYPE
		SYNTAX	Integer32(0..99)
		ACCESS	not-accessible
		STATUS	current
		DESCRIPTION
			"index of schedule-list  "
		::=	{ raisecomScheduleCommandEntry 1 }

    raisecomScheduleCommandNo OBJECT-TYPE
		SYNTAX	Integer32(0..99)
		ACCESS	not-accessible
		STATUS	current
		DESCRIPTION
			"index of command attached on schedule-list "
		::=	{ raisecomScheduleCommandEntry 2 }

     raisecomScheduleCommandString OBJECT-TYPE
		SYNTAX	OCTET STRING (SIZE(0..255))
		ACCESS	read-only
		STATUS	current
		DESCRIPTION
			"comnmand string attached on schedule-list "
		::=	{ raisecomScheduleCommandEntry 3 }
		
     raisecomScheduleCommandMode  OBJECT-TYPE
		SYNTAX	INTEGER {
			user-mode(0),
			auth-mode(1),
			view-mode(2),
			auth-enable-mode(3),
			enable-mode(4),
			vlan-mode(5),
			interface-mode(6),	
			interface-range-mode(7),	
			aggregator-mode(8),
			ip-mode(9),
			config-mode(10),
			rip-mode(11),
			bgp-mode(12),
			ospf-mode(13),
			factory-mode(14),
			game-mode(15),
			hide-mode(16),
			cluster-mode(17)
		}
		ACCESS	read-only
		STATUS	current
		DESCRIPTION
			"command run on specific mode"
		::=	{ raisecomScheduleCommandEntry 4 }   
		
	raisecomScheduleCommandNodeInfo   OBJECT-TYPE
		SYNTAX	OCTET STRING (SIZE(0..255))
		ACCESS	read-only
		STATUS	current
		DESCRIPTION
			"command mode info "
		::=	{ raisecomScheduleCommandEntry 5}

		
     raisecomScheduleCommandExeCount  OBJECT-TYPE
		SYNTAX	Integer32 
		ACCESS	read-only
		STATUS	current
		DESCRIPTION
			"The schedule command  execute times"
		::=	{ raisecomScheduleCommandEntry 6 }
				
     raisecomScheduleCommandLastExeTime  OBJECT-TYPE
		SYNTAX	Integer32 
		ACCESS	read-only
		STATUS	current
		DESCRIPTION
			"last time for this command executed"
		::=	{ raisecomScheduleCommandEntry 7 }

	END

--MibName=rcSla
-- *****************************************************************
-- RAISECOM-SLA-MIB.mib
--
-- july 2008, wangyuhang
--
-- Copyright(c) 2003-2005 by RAISECOM TECH, Ltd. 
-- All rights reserved.    
-- 02,20121023, guohm, 增加rcmefSoamLastStatsGroup
-- 01,20111221,yangkewei, ROS00008189,修改节点 rcSlaConfigParam说明，使之与代码一致
-- *****************************************************************


RAISECOM-SLA-MIB DEFINITIONS ::= BEGIN      
IMPORTS
    Integer32,                     
    Counter32, 
    Counter64,                                            
    Unsigned32,
    Gauge32,          
    IpAddress                   		FROM SNMPv2-SMI    -- [RFC2578]  
    TimeStamp,
    RowStatus,
    TruthValue,
    MacAddress                          FROM SNMPv2-TC     -- [RFC2579]
    InterfaceIndex					    FROM IF-MIB        -- [RFC2863]
    EnableVar                           FROM SWITCH-TC
    VlanId     		                	FROM Q-BRIDGE-MIB  
    iscomSwitch                         FROM RAISECOM-BASE-MIB     
    dot1agCfmMdIndex,
    dot1agCfmMaIndex, 
    dot1agCfmMepIdentifier,
    Dot1agCfmMepId,
    Dot1agCfmMDLevel                    FROM IEEE8021-CFM-MIB   
    rcServiceCosLabel                   FROM SWTICH-SERVICE-MIB  
    ;
rcSla  MODULE-IDENTITY
    LAST-UPDATED   "200711020000Z"
    ORGANIZATION   "Raisecom, Inc."
    CONTACT-INFO  
                "       Raise Systems
                        
                Postal: Beijing,
                        China

                   Tel: 86-010-82884499

                E-mail: wangyuhang@raisecom.com"
    DESCRIPTION
        "This MIB module defines objects to SLA "
        REVISION   "200711020000Z"
        DESCRIPTION
            "The initial revision of this MIB."
        ::={ iscomSwitch  36 } 
--
--
RcSlaCfgOperType ::= TEXTUAL-CONVENTION
    STATUS      current
    DESCRIPTION
       "  Specifies the type of operation to be performed. 
        The value 'y1731-echo' will cause the  application to perform a timed echo y1731
    operation directed at the 'rcSlaConfigDestMacAddr' or 'rcSlaConfigRMepId'.
        The value 'y1731-jitter' will cause the  application to perform delay variance analysis.  
        The value 'icmp-echo' will cause the  application to perform a timed echo icmp
    operation directed at the 'rcSlaConfigDestIpAddr'.
        The value 'icmp-jitter' will cause the  application to perform delay variance analysis.   
      " 
    REFERENCE
       "rcSla"
    SYNTAX      INTEGER {
                  y1731-echo         (1),
                  y1731-jitter       (2),
                  icmp-echo          (3),
                  icmp-jitter        (4),
                  y1731-pkt-loss     (5)

                }
--   
-- 
RcSlaCfgScheduleStatus ::= TEXTUAL-CONVENTION
    STATUS      current
    DESCRIPTION
       " The RcSlaCfgScheduleStatus textual convention is used to manage the
 	creation and deletion of Schedule.
     	The status column has five defined values: 
     	 - `scheduleInitial', which indicates that the operation dose not be 
     scheduled ;    
     	 - `scheduleCreate', which is supplied by a management station wishing to 
      create a new schedule and to have its status automatically set to active;
     	 - `scheduleBreak', which is supplied by a management station wishing to 
      break a scheduling operationand to have its status automatically set to complete;   
         - `scheduleActive', which indicates that the operation is being scheduled ; 
         - `scheduleComplete', which indicates that the scheduled operation has been over; 
         "
    REFERENCE
       "rcSla"
    SYNTAX      INTEGER {
                  scheduleInitial   (1),
                  scheduleCreate    (2),
                  scheduleBreak     (3),
                  scheduleActive    (4),
                  scheduleComplete  (5)
                }  
                
--                                   

                        
--
RcSlaOWSupport ::= TEXTUAL-CONVENTION
    STATUS      current
    DESCRIPTION
       "  The type  use to  decide whether to support one way Test. " 
    REFERENCE
       "rcSla"
    SYNTAX      INTEGER {
                  sla-unknown        (1),
                  sla-support        (2),
                  sla-no-support     (3)
                  }
  
             

--groupsType
    rcSlaObjectsGroup	OBJECT IDENTIFIER ::= {rcSla 1}  
    rcSlaConfigGroup	OBJECT IDENTIFIER ::= {rcSla 2}  
    rcSlaScheduleGroup	OBJECT IDENTIFIER ::= {rcSla 3}        
    rcSlaThroughputGroup  OBJECT IDENTIFIER ::= {rcSla 4}
    rcSlaThresholdGroup  OBJECT IDENTIFIER ::= {rcSla 5}  
    rcmefSoamLastStatsGroup  OBJECT IDENTIFIER ::= {rcSla 6}  
    rcSlaMaintenanceGroup  OBJECT IDENTIFIER ::= {rcSla 7}
    rcSlaThresholdProfileGroup  OBJECT IDENTIFIER ::= {rcSla 8}
    
--rcSlaObjectsGroup
	-- rcSlaConfigOperSum
	-- rcSlaActiveOperSum  
                     
-- rcSlaConfigOperSum
                                                                         
	rcSlaConfigOperSum        OBJECT-TYPE
		SYNTAX      Gauge32
   		MAX-ACCESS  read-only
    	STATUS      current
    	DESCRIPTION
            "The total number of operation configured " 
       	::= { rcSlaObjectsGroup 1 }     
    	
-- rcSlaActiveOperSum 
                                                                                              
	rcSlaActiveOperSum        OBJECT-TYPE
		SYNTAX      Gauge32
   		MAX-ACCESS  read-only
    	STATUS      current
    	DESCRIPTION
            "The total number of active configured " 
    	::= { rcSlaObjectsGroup 2 }                
    	
 -- rcSlaY1731OperType 
                                                                                              
	rcSlaY1731OperType        OBJECT-TYPE
		SYNTAX      RcSlaCfgOperType
   		MAX-ACCESS  read-write
    	STATUS      current
    	DESCRIPTION
            "Y.1731 Operation Type : y1731-echo / y1731-jitter" 
    	::= { rcSlaObjectsGroup 3 }

 -- rcSlaY1731MDLevel
                                                                                              
	rcSlaY1731MDLevel        OBJECT-TYPE
		SYNTAX      Dot1agCfmMDLevel
   		MAX-ACCESS  read-write
    	STATUS      current
    	DESCRIPTION
            "This object specifies the maintenance domain level to be used by Y.1731 operation." 
    	::= { rcSlaObjectsGroup 4 }

 -- rcSlaY1731SVlanId
                                                                                              
    rcSlaY1731SVlanId       OBJECT-TYPE
		SYNTAX      VlanId
   		MAX-ACCESS  read-write
    	STATUS      current
    	DESCRIPTION
            "This object specifies the identifier of VLAN for MA to be used by  Y.1731 operation.
				It is an unique identifier for a service instance 
				within a Maintenance Domain specified by rcSlaConfigMDLevel."
    	::= { rcSlaObjectsGroup 5 }

  -- rcSlaY1731OperQuickInput
                                                                                              
    rcSlaY1731OperQuickInput       OBJECT-TYPE
		SYNTAX      TruthValue
   		MAX-ACCESS  read-write
    	STATUS      current
    	DESCRIPTION
            "Quick creat operation when  learning Rmep by Y.1731"
    	::= { rcSlaObjectsGroup 6 } 
    	      	
   -- rcSlaY1731TestPduType                                                                         
    rcSlaY1731TestPduType       OBJECT-TYPE
		SYNTAX      INTEGER {loopBack(1),delayMeasurement(2)}
   		MAX-ACCESS  read-write
    	STATUS      current
    	DESCRIPTION
            "Quick input test pdu type"
    	::= { rcSlaObjectsGroup 7 } 

--OperConfigGroup --  
--rcSlaConfigGroup                                                                                              
		--rcSlaConfigTable    
			--rcSlaConfigEntry 
				--rcSlaConfigOperId
				--rcSlaConfigOwner   
				--rcSlaOneWaySupport
				--rcSlaConfigOperType
				--rcSlaConfigCos   				
				--rcSlaConfigCVlanId 
				--rcSlaConfigSVlanId 
				--rcSlaConfigMDLevel
				--rcSlaConfigRMepId
				--rcSlaConfigDestMacAddr
				--rcSlaConfigDestIpAddr
				--rcSlaConfigJitterInterval
				--rcSlaConfigJitterFrameNums
				--rcSlaConfigScheduleStartTime
				--rcSlaConfigScheduleLife
				--rcSlaConfigSchedulePeriod
				--rcSlaConfigScheduleStatus
				--rcSlaConfigRowStatus   
				--rcSlaConfigParam
				--rcSlaConfigDscp  
				
				            

rcSlaConfigTable  OBJECT-TYPE
    SYNTAX      SEQUENCE OF RcSlaConfigEntry
    MAX-ACCESS  not-accessible
    STATUS      current
    DESCRIPTION
        "This table contains sla  control data."
    ::= { rcSlaConfigGroup 1 }

rcSlaConfigEntry   OBJECT-TYPE
    SYNTAX      RcSlaConfigEntry
    MAX-ACCESS  not-accessible
    STATUS      current
    DESCRIPTION
        "A collection of objects that define three conceptual
    control row : slaY.1731EntryTable, slaIcmpEntryTable, slaSchEntryTable.
   		The 'slaY.1731EntryTable' is used to control y1731 operation .
    	The following objects must be specified in order to create this 
    conceptual row.
    	- rcSlaConfigOperType
    	- rcSlaConfigVlanId
    	- rcSlaConfigMDLevel
    	- rcSlaConfigDestMacAddr 
    	- rcSlaConfigRMepId
    	The ' slaIcmpEntryTable' is used to control ICMP operation .
    	The following objects must be specified in order to create this 
    conceptual row.
    	- rcSlaConfigOperType
    	- rcSlaConfigDestIpAddr
        The ' slaIcmpSchTable' is used to control operation schduled."
	INDEX        { rcSlaConfigOperId }    
    ::={ rcSlaConfigTable 1 }     
    
RcSlaConfigEntry ::= SEQUENCE {
        rcSlaConfigOperId				     Unsigned32,
    	rcSlaConfigOwner				     OCTET STRING (SIZE(0..1024)),
    	rcSlaOneWaySupport                   RcSlaOWSupport,
    	rcSlaConfigOperType		             RcSlaCfgOperType,       
	    rcSlaConfigCos                       Integer32 (0..7 ),  
	    rcSlaConfigCVlanId                   VlanId,
	    rcSlaConfigSVlanId                   VlanId,
	    rcSlaConfigMDLevel		             Dot1agCfmMDLevel,
	    rcSlaConfigRMepId                    Dot1agCfmMepId,
	    rcSlaConfigDestMacAddr               MacAddress,
	    rcSlaConfigDestIpAddr                IpAddress, 
	    rcSlaConfigJitterInterval            Unsigned32,
	    rcSlaConfigJitterFrameNums           Unsigned32,
	    rcSlaConfigScheduleStartTime         TimeStamp,     
	    rcSlaConfigScheduleLife              Unsigned32, 
	    rcSlaConfigSchedulePeriod            Unsigned32,
	    rcSlaConfigScheduleStatus            RcSlaCfgScheduleStatus,
	    rcSlaConfigRowStatus                 RowStatus,   
	    rcSlaConfigParam                     OCTET STRING (SIZE(0..255)),
	    rcSlaConfigTestPduType				       INTEGER,
	    rcSlaConfigDscp                      Integer32 (0..63 ),  
	    rcSlaConfigTestPduLength             Integer32 (64..9600 )
	    }

rcSlaConfigOperId       OBJECT-TYPE 
	SYNTAX      Unsigned32 
	MAX-ACCESS  not-accessible
    STATUS      current
    DESCRIPTION
            "This object indicates a row in the rcSlaConfigTable.
        This value is an operation number configured by user."
    ::= { rcSlaConfigEntry 1 }   
    
rcSlaConfigOwner       OBJECT-TYPE 
	SYNTAX      OCTET STRING (SIZE(0..1024))
    MAX-ACCESS  read-create
    STATUS      current
    DESCRIPTION
            "This object specifies a string which used by a managing application 
        to identify the entity that created this operation."
    ::= { rcSlaConfigEntry 2 }  
   
       
rcSlaOneWaySupport     OBJECT-TYPE 
	SYNTAX      RcSlaOWSupport
    MAX-ACCESS  read-only
    STATUS      current
    DESCRIPTION
            "Specifies the type of  decision whether to support one way test.  "
    ::= { rcSlaConfigEntry 3 }
    
rcSlaConfigOperType       OBJECT-TYPE 
	SYNTAX      RcSlaCfgOperType
    MAX-ACCESS  read-create
    STATUS      current
    DESCRIPTION
            "Specifies the type of operation to be performed. "
    ::= { rcSlaConfigEntry 4 }

rcSlaConfigCos       OBJECT-TYPE 
	SYNTAX      Integer32 (0..7 )
    MAX-ACCESS  read-create
    STATUS      current
    DESCRIPTION
          "This object specifies the Class Of Service field 
        in an frame header of SLA PDU to be used by Y.1731 operation."
    ::= { rcSlaConfigEntry 5 }    	

rcSlaConfigCVlanId       OBJECT-TYPE 
	SYNTAX      VlanId
    MAX-ACCESS  read-create
    STATUS      current
    DESCRIPTION
          "This object specifies the CVlan user configured 
          	in an frame header of SLA PDU to be used by Y.1731 operation.
          	It could be zero when there is no cunsomer vlan"
    ::= { rcSlaConfigEntry 6 }

rcSlaConfigSVlanId       OBJECT-TYPE 
	SYNTAX      VlanId
    MAX-ACCESS  read-create
    STATUS      current
    DESCRIPTION
            "This object specifies the identifier of VLAN for MA to be used by Y.1731 operation.
				It is an unique identifier for a service instance 
				within a Maintenance Domain specified by rcSlaConfigMDLevel."
    ::= { rcSlaConfigEntry 7 }                    

rcSlaConfigMDLevel       OBJECT-TYPE 
	SYNTAX      Dot1agCfmMDLevel
	MAX-ACCESS  read-create
    STATUS      current
    DESCRIPTION
            "This object specifies the maintenance domain level to be used by Y.1731 operation."
    ::= { rcSlaConfigEntry 8 }                    
             

rcSlaConfigRMepId       OBJECT-TYPE 
	SYNTAX      Dot1agCfmMepId
    MAX-ACCESS  read-create
    STATUS      current
    DESCRIPTION
            "This object specifies the Target Remote MEP Identify to be used by Y.1731 operation."
    ::= { rcSlaConfigEntry 9 }                    

rcSlaConfigDestMacAddr       OBJECT-TYPE 
	SYNTAX      MacAddress
    MAX-ACCESS  read-create
    STATUS      current
    DESCRIPTION
            "This object specifies the Target MAC Address Field to be used by Y.1731 operation."
    ::= { rcSlaConfigEntry 10 }

rcSlaConfigDestIpAddr       OBJECT-TYPE 
	SYNTAX      IpAddress
    MAX-ACCESS  read-create
    STATUS      current
    DESCRIPTION
            "This object specifies the Target IP Address Field to be used by ICMP operation."
    ::= { rcSlaConfigEntry 11 }                    

rcSlaConfigJitterInterval       OBJECT-TYPE 
	SYNTAX      Unsigned32 
    MAX-ACCESS  read-create
    STATUS      current
    DESCRIPTION
            "This value specifies the inter-frame delay between Ethernet
        frames that need to be transmitted to the target device.
        This object is applicable to 'Jitter' operation only."
   ::= { rcSlaConfigEntry 12 }                    

rcSlaConfigJitterFrameNums       OBJECT-TYPE 
	SYNTAX      Unsigned32
    MAX-ACCESS  read-create
    STATUS      current
    DESCRIPTION
           "This object specifies the number of frames that need to be transmitted to the target device.  
           		This object is applicable to 'Jitter' operation only."
    ::= { rcSlaConfigEntry 13 }                    

rcSlaConfigScheduleStartTime       OBJECT-TYPE 
	SYNTAX      TimeStamp
    MAX-ACCESS  read-only
    STATUS      current
    DESCRIPTION
            "This object specifies the time when this schedule status will become 'active'.  
            	Value of 0 puts in other status."
    ::= { rcSlaConfigEntry 14 }                    

rcSlaConfigScheduleLife       OBJECT-TYPE 
	SYNTAX      Unsigned32
    MAX-ACCESS  read-create
    STATUS      current
    DESCRIPTION
            "This object specifies the time duration over the whole schedule process. "
    ::= { rcSlaConfigEntry 15 }                    

rcSlaConfigSchedulePeriod       OBJECT-TYPE 
	SYNTAX      Unsigned32
	MAX-ACCESS  read-create
    STATUS      current
    DESCRIPTION
            "This object specifies the duration between two SLA test 
            	which includes all of probes schedule process in test. 
           	Take above example, if all of the rcSlaConfigSchedulePeriod of three operations are set to 60, 
            	then the start time of each test of SLA operation like:
			start time:   T+0 --------  T+9 ----------  T+19-----
           		operation1  operation2    operation3 
			start again:  T+60--------  T+69 ----------  T+79--
           		operation1  operation2    operation3   
			start 3rd time:T+120-------- T+129 ----------T+139--
         		operation1  operation2    operation3"
    ::= { rcSlaConfigEntry 16 }                    

rcSlaConfigScheduleStatus       OBJECT-TYPE 
	SYNTAX      RcSlaCfgScheduleStatus
    MAX-ACCESS  read-create
    STATUS      current
    DESCRIPTION
            "This object specifies the status of Schedule.  
            The status column has five defined values: 
		- `scheduleInitial', which indicates that the operation has not been scheduled ;    
		- `scheduleCreate', which is supplied by a management station wishing to create a new schedule 
				and to have its status set to active;
		- `scheduleBreak', which is supplied by a management station wishing to break a scheduling operation 
				and to have its status set to complete;   
		- `scheduleActive', which indicates that the operation is being scheduled ; 
		- `scheduleComplete', which indicates that the scheduled operation has been over;"
    ::= { rcSlaConfigEntry 17 }                    

rcSlaConfigRowStatus       OBJECT-TYPE 
	SYNTAX      RowStatus
    MAX-ACCESS  read-create
    STATUS      current
    DESCRIPTION
            "The status of the row.
			All columns must have a valid value before a row can be activated. 
			The following objects must be specified obviously in order for row status object to become active.
				rcSlaConfigOperId
				rcSlaConfigOperType
    		For ICMP operation:
    			rcSlaConfigDestIpAddr
			For Y.1731 operation:
       			rcSlaConfigVlanId
    			rcSlaConfigMDLevel
    			rcSlaConfigDestMacAddr

			The following objects about the configuration of operation cannot be modified after creating the row:
				rcSlaConfigOperId
    			rcSlaConfigOwner
    			rcSlaConfigOperType
    			rcSlaConfigCos
    			rcSlaConfigVlanId
				rcSlaConfigMDLevel
				rcSlaConfigDestMacAddr
				rcSlaConfigDestIpAddr
    			rcSlaConfigJitterInterval
				rcSlaConfigJitterFrameNums
				  rcSlaConfigDscp

			The following objects about the schedule configuration of operation can be modified even after creating the row:
    			rcSlaConfigScheduleStartTime
    			rcSlaConfigScheduleLife
    			rcSlaConfigSchedulePeriod
				rcSlaConfigScheduleStatus
			The ahead three objects of above won't be modified until another schedule of this operation start."
    ::= { rcSlaConfigEntry 18 }   
    
rcSlaConfigParam       OBJECT-TYPE 
	SYNTAX      OCTET STRING (SIZE(0..255))
	MAX-ACCESS  read-create
    STATUS      current
    DESCRIPTION
            "This object uses to restore the value of config params which is needed by  all kinds of operation.  
            The meaning of this  object decides by different operation : 
		For Y.1731 operation, this  object means:   
		    -- Type (1 - 2)   in 0 BYTE
		    -- Length  ,in 1 BYTE
		    -- mdlevel (0 - 7) in 2 BYTE
		    -- Cos (0 - 7) in 3 BYTE
		    -- Svlan (1 - 4094） in 4 - 7 BYTE     
		    -- Cvlan (0 - 4094)  in 8 - 11 BYTE
		    -- RmepId (1 - 8191 ) in 12 - 15 BYTE   
		    -- Dmac ,  in 12 - 17 BYTE
		 For ICMP operation:
			-- Ipaddress in 0 - 15 BYTE
			-- Dscp in 16 - 19 BYTE
		    
		    Type    :  the type of destination parameter(1 is Dmac and 2 is RmepId) to be used by Y.1731 operation.  
		    Length  :  the length of the rcSlaConfigParam string to be used by Y.1731 operation.
			mdlevel :  the maintenance domain level to be used by Y.1731 operation.     
			Cos     :  the Class Of Service field in an frame header of SLA PDU to be used by Y.1731 operation.  
			Svlan   :  the identifier of VLAN for MA to be used by Y.1731 operation.
					   It is an unique identifier for a service instance within a Maintenance Domain specified by rcSlaConfigMDLevel.
		    Cvlan   :  the CVlan user configured in an frame header of SLA PDU to be used by Y.1731 operation.
          			   It could be zero when there is no cunsomer vlan   
          	RmepId	:  the Target Remote MEP Identify to be used by Y.1731 operation.   
          	Dmac    ： the Target Remote MAC Address to be used by Y.1731 operation.     	
          	Ipaddress : the Target IP Address Field to be used by ICMP operation.
          	Dscp: the Differentiated Services Code Point field in header of ip	   
		"
    ::= { rcSlaConfigEntry 19 }   
                     
  rcSlaConfigTestPduType 	OBJECT-TYPE 
	SYNTAX      INTEGER {loopback(1), delayMeasurement(2),lossMeasurement(3),SyntheticLossMeasurement(4)}
	MAX-ACCESS  read-create
    STATUS      current
    DESCRIPTION      "This object specifies the type of Y1731 echo/jitter packats.
    				Two types are avalibale:
    				loopBack          (1),
					delayMeasurement  (2), 
					lossMeasurement   (3),
					SyntheticLossMeasurement(4)
					"
    ::= { rcSlaConfigEntry 20 }
   	
  rcSlaConfigDscp     OBJECT-TYPE 
	SYNTAX      Integer32 (0..63 )
    MAX-ACCESS  read-create
    STATUS      current
    DESCRIPTION
          "This object specifies the Differentiated Services Code Point field in header of ip."
    ::= { rcSlaConfigEntry 21 } 
    
  rcSlaConfigTestPduLength     OBJECT-TYPE 
	SYNTAX      Integer32 (64..9600 )
    MAX-ACCESS  read-create
    STATUS      current
    DESCRIPTION
          "This object specifies the length of test pdus.
          This object is only valid for the entity transmitting the Loss
 	  Measurement frames, type 'Slm','DM' and is ignored by the
 	  entity receiving frames. It is not applicable for the 'lmCcm' or 
 	  'lmLmm' types."
    ::= { rcSlaConfigEntry 22 }
     	
--OperScheduleGroup--               
--rcSlaScheduleGroup
	-- rcSlaLatestTable
		--rcSlaLatestEntry
			--rcSlaLatestTXNum 
			--rcSlaLatestRTTNum
	    	--rcSlaLatestRTTSum
	    	--rcSlaLatestRTTSumJitter
	    	--rcSlaLatestRTTSum2    
	    	--rcSlaLatestRTTMin                    
	    	--rcSlaLatestRTTMax 
	    	--rcSlaLatestRTTNumSD	                    
	       	--rcSlaLatestRTTSumSD                  
	    	--rcSlaLatestRTTSumJitterSD             
 	    	--rcSlaLatestRTTSum2SD                 
	    	--rcSlaLatestRTTMinSD                  
	    	--rcSlaLatestRTTMaxSD  
	    	--rcSlaLatestRTTNumDS                  
	    	--rcSlaLatestRTTSumDS                  
	    	--rcSlaLatestRTTSumJitterDS            
	    	--rcSlaLatestRTTSum2DS                 
	    	--rcSlaLatestRTTMinDS                  
	    	--rcSlaLatestRTTMaxDS   
	    	
	-- rcSlaStatisticTable
		--rcSlaStatisticEntry
			--rcSlaStatisticStartTime   
			--rcSlaStatisticScheduleLife         
        	--rcSlaStatisticSchedulePeriod 		     
	    	--rcSlaStatisticTXNum 
	    	--rcSlaStatisticRTTNum            	 
	    	--rcSlaStatisticRTTSums              	 
	    	--rcSlaStatisticRTTSumJitter   		                
	    	--rcSlaStatisticRTTSum2L               
	    	--rcSlaStatisticRTTSum2H               
	    	--rcSlaStatisticRTTMin                 
	    	--rcSlaStatisticRTTMax  
	    	--rcSlaStatisticRTTNumSD                   
	    	--rcSlaStatisticRTTSumsSD              
	    	--rcSlaStatisticRTTSumJitterSD         
	       	--rcSlaStatisticRTTSum2LSD             
	    	--rcSlaStatisticRTTSum2HSD             
	    	--rcSlaStatisticRTTMinSD                
	    	--rcSlaStatisticRTTMaxSD 
	    	--rcSlaStatisticRTTNumDS                       
	    	--rcSlaStatisticRTTSumsDS              
	    	--rcSlaStatisticRTTSumJitterDS         
	    	--rcSlaStatisticRTTSum2LDS             
	    	--rcSlaStatisticRTTSum2HDS             
	    	--rcSlaStatisticRTTMinDS               
	    	--rcSlaStatisticRTTMaxDS   

	-- rcSlaPktlmLatestTable
		--rcSlaPktlmLatestEntry
			--rcSlaLatestPktlmTXNum 
			--rcSlaLatestPktlmNum
	    	--rcSlaLatestPktlmSum
	    	--rcSlaLatestPktlmMin
	    	--rcSlaLatestPktlmMax
	    	--rcSlaLatestPktlmNumSD
	       	--rcSlaLatestPktlmSumSD
	    	--rcSlaLatestPktlmMinSD
	    	--rcSlaLatestPktlmMaxSD
	    	--rcSlaLatestPktlmNumDS
	    	--rcSlaLatestPktlmSumDS
	    	--rcSlaLatestPktlmMinDS
	    	--rcSlaLatestPktlmMaxDS
	    	            
	--rcSlaPktlmStatisticTable
		--rcSlaPktlmStatisticEntry
			--rcSlaStatisticPktlmStartTime
			--rcSlaStatisticPktlmScheduleLife
			--rcSlaStatisticPktlmSchedulePeriod
			--rcSlaStatisticPktlmTXNum
			--rcSlaStatisticPktlmNum
			--rcSlaStatisticPktlmSums
			--rcSlaStatisticPktlmMin
			--rcSlaStatisticPktlmMax
			--rcSlaStatistiPktlmNumSD
			--rcSlaStatisticPktlmSumsSD
			--rcSlaStatisticPktlmMinSD
			--rcSlaStatisticPktlmMaxSD
			--rcSlaStatisticPktlmNumDS
			--rcSlaStatisticPktlmSumsDS
			--rcSlaStatisticPktlmMinDS
			--rcSlaStatisticPktlmMaxDS
--rcSlaLatestTable

rcSlaLatestTable  OBJECT-TYPE
    SYNTAX      SEQUENCE OF RcSlaLatestEntry
    MAX-ACCESS  not-accessible
    STATUS      current
    DESCRIPTION
        "This table contains the statistics calculated for the 
        latest sent frames."
    ::= { rcSlaScheduleGroup 1 }

rcSlaLatestEntry   OBJECT-TYPE
    SYNTAX      RcSlaLatestEntry
    MAX-ACCESS  not-accessible
    STATUS      current
    DESCRIPTION
        "A collection of objects that record the latest operation.

        An entry is created only when the operation has been set and scheduled.      
        The entry will start to collect data when rcSlaConfigScheduleStatus 
        is in 'active' state.  The entry will be removed when the 
        rcSlaConfigScheduleStatus is changed to 'complete' state. "
	INDEX        { rcSlaConfigOperId }    
    ::={ rcSlaLatestTable 1 }     
    
RcSlaLatestEntry ::= SEQUENCE {
        rcSlaLatestTXNum   					 Gauge32,  
        rcSlaLatestRTTNum               	 Gauge32,
	    rcSlaLatestRTTSum   			     Gauge32,
	    rcSlaLatestRTTSumJitter   		     Gauge32,  
	    rcSlaLatestRTTSum2                   Gauge32,
	    rcSlaLatestRTTMin                    Gauge32,
	    rcSlaLatestRTTMax                    Gauge32, 
	    rcSlaLatestRTTNumSD                  Gauge32,
	    rcSlaLatestRTTSumSD                  Gauge32,
	    rcSlaLatestRTTSumJitterSD            Gauge32, 
 	    rcSlaLatestRTTSum2SD                 Gauge32,
	    rcSlaLatestRTTMinSD                  Gauge32,
	    rcSlaLatestRTTMaxSD                  Gauge32,
	    rcSlaLatestRTTNumDS                  Gauge32,
	    rcSlaLatestRTTSumDS                  Gauge32,
	    rcSlaLatestRTTSumJitterDS            Gauge32,
	    rcSlaLatestRTTSum2DS                 Gauge32,
	    rcSlaLatestRTTMinDS                  Gauge32,
	    rcSlaLatestRTTMaxDS                  Gauge32
}

rcSlaLatestTXNum       OBJECT-TYPE 
	SYNTAX      Gauge32
    MAX-ACCESS  read-only
    STATUS      current
    DESCRIPTION
            "This object specifies the number of RTT's probe sent in latest test."
    ::= { rcSlaLatestEntry 1 }    
    
rcSlaLatestRTTNum       OBJECT-TYPE 
	SYNTAX      Gauge32
    MAX-ACCESS  read-only
    STATUS      current
    DESCRIPTION
            "This object specifies the number of RTT's probe that were successfully measured in latest test."
    ::= { rcSlaLatestEntry 2 } 
    
rcSlaLatestRTTSum       OBJECT-TYPE 
	SYNTAX      Gauge32
    MAX-ACCESS  read-only
    STATUS      current
    DESCRIPTION
            "This object specifies the sum of RTT's delay that were successfully measured in latest test."
    ::= { rcSlaLatestEntry 3 }
    
rcSlaLatestRTTSumJitter       OBJECT-TYPE 
	SYNTAX      Gauge32
    MAX-ACCESS  read-only
    STATUS      current
    DESCRIPTION
            "This object specifies the number of RTT's jitter that were successfully measured in latest test.  
            	This object is applicable to 'Jitter' operation only."
    ::= { rcSlaLatestEntry 4 }

rcSlaLatestRTTSum2       OBJECT-TYPE 
	SYNTAX      Gauge32
    MAX-ACCESS  read-only
    STATUS      current
    DESCRIPTION
            "This object specifies the sum of squares of RTT's delay that are successfully measured in latest test. 
            	This object is applicable to 'Jitter' operation only."
    ::= { rcSlaLatestEntry 5 }

rcSlaLatestRTTMin       OBJECT-TYPE 
	SYNTAX      Gauge32
    MAX-ACCESS  read-only
    STATUS      current
    DESCRIPTION
            "This object specifies the minimum of RTT's that were successfully measured in latest test. 
            	This object is applicable to 'Jitter' operation only."
    ::= { rcSlaLatestEntry 6 }                    

rcSlaLatestRTTMax       OBJECT-TYPE 
	SYNTAX      Gauge32
    MAX-ACCESS  read-only
    STATUS      current
    DESCRIPTION
            "This object specifies the maximum of RTT's that were successfully measured in latest test. 
            	This object is applicable to 'Jitter' operation only."
    ::= { rcSlaLatestEntry 7 }                    
 
rcSlaLatestRTTNumSD       OBJECT-TYPE 
	SYNTAX      Gauge32
    MAX-ACCESS  read-only
    STATUS      current
    DESCRIPTION
            "This object specifies the number of RTT's probe 
            	that were successfully measured from source to destination in latest test."
    ::= { rcSlaLatestEntry 8 }        

rcSlaLatestRTTSumSD       OBJECT-TYPE 
	SYNTAX      Gauge32
    MAX-ACCESS  read-only
    STATUS      current
    DESCRIPTION
            "This object specifies the sum of RTT's delay 
            	that were successfully measured from source to destination in latest test."
    ::= { rcSlaLatestEntry 9 }                    

rcSlaLatestRTTSumJitterSD       OBJECT-TYPE 
	SYNTAX      Gauge32
    MAX-ACCESS  read-only
    STATUS      current
    DESCRIPTION
            "This object specifies the number of RTT's jitter that were successfully measured from source to destination in latest test. 
            	This object is applicable to 'Jitter' operation only."
    ::= { rcSlaLatestEntry 10 }                    

rcSlaLatestRTTSum2SD       OBJECT-TYPE 
	SYNTAX      Gauge32
    MAX-ACCESS  read-only
    STATUS      current
    DESCRIPTION
            "This object specifies the sum of squares of RTT's delay that are successfully measured from source to destination in latest test. 
            	This object is applicable to 'Jitter' operation only."
    ::= { rcSlaLatestEntry 11 }                    

rcSlaLatestRTTMinSD       OBJECT-TYPE 
	SYNTAX      Gauge32
    MAX-ACCESS  read-only
    STATUS      current
    DESCRIPTION
            "This object specifies the minimum of RTT's that were successfully measured from source to destination in latest test. 
            	This object is applicable to 'Jitter' operation only."
    ::= { rcSlaLatestEntry 12 }                    

rcSlaLatestRTTMaxSD       OBJECT-TYPE 
	SYNTAX      Gauge32
    MAX-ACCESS  read-only
    STATUS      current
    DESCRIPTION
            "This object specifies the maximum of RTT's that were successfully measured from source to destination in latest test. 
            	This object is applicable to 'Jitter' operation only."
    ::= { rcSlaLatestEntry 13 }              
                                     
rcSlaLatestRTTNumDS       OBJECT-TYPE 
	SYNTAX      Gauge32
    MAX-ACCESS  read-only
    STATUS      current
    DESCRIPTION
            "This object specifies the number of RTT's probe 
            	that were successfully measured from destination to source in latest test."
    ::= { rcSlaLatestEntry 14 }                                       

rcSlaLatestRTTSumDS       OBJECT-TYPE 
	SYNTAX      Gauge32
    MAX-ACCESS  read-only
    STATUS      current
    DESCRIPTION
            "This object specifies the sum of RTT's delay 
            	that were successfully measured from destination to source in latest test."
    ::= { rcSlaLatestEntry 15 }                    

rcSlaLatestRTTSumJitterDS       OBJECT-TYPE 
	SYNTAX      Gauge32
    MAX-ACCESS  read-only
    STATUS      current
    DESCRIPTION
            "This object specifies the number of RTT's jitter that were successfully measured from destination to source in latest test. 
            	This object is applicable to 'Jitter' operation only."
    ::= { rcSlaLatestEntry 16 }                    

rcSlaLatestRTTSum2DS       OBJECT-TYPE 
	SYNTAX      Gauge32
    MAX-ACCESS  read-only
    STATUS      current
    DESCRIPTION
            "This object specifies the sum of squares of RTT's delay that are successfully measured from destination to source in latest test. 
            	This object is applicable to 'Jitter' operation only."
    ::= { rcSlaLatestEntry 17 }                    

rcSlaLatestRTTMinDS       OBJECT-TYPE 
	SYNTAX      Gauge32
    MAX-ACCESS  read-only
    STATUS      current
    DESCRIPTION
            "This object specifies the minimum of RTT's that were successfully measured from destination to source in latest test. 
            	This object is applicable to 'Jitter' operation only."
    ::= { rcSlaLatestEntry 18 }                    

rcSlaLatestRTTMaxDS       OBJECT-TYPE 
	SYNTAX      Gauge32
    MAX-ACCESS  read-only
    STATUS      current
    DESCRIPTION
            "This object specifies the maximum of RTT's that were successfully measured from destination to source in latest test. 
            	This object is applicable to 'Jitter' operation only."
    ::= { rcSlaLatestEntry 19 }                    


-- rcSlaStatisticTable
--  

rcSlaStatisticTable  OBJECT-TYPE
    SYNTAX      SEQUENCE OF RcSlaStatisticEntry
    MAX-ACCESS  not-accessible
    STATUS      current
    DESCRIPTION
        "The 'SlaStatistic' statistics table contains summarized
    information of the results for a conceptual control row."
    ::= { rcSlaScheduleGroup 2 }

rcSlaStatisticEntry   OBJECT-TYPE
    SYNTAX      RcSlaStatisticEntry
    MAX-ACCESS  not-accessible
    STATUS      current
    DESCRIPTION
        "This entry contains the objects which accumulate the
    results of a series of 'Jitter' operations over a time 
    period stored in rcSlaConfigScheduleLife. 
        An entry is created only when the operation has been set and scheduled.      
        The entry will start to collect data when rcSlaConfigScheduleStatus 
    is in 'active' state.  The entry will stop to collect data when the 
    rcSlaConfigScheduleStatus is changed to 'complete' state.
         "
	INDEX        { rcSlaConfigOperId,
	               rcSlaStatisticStartTime
	             }    
    ::={ rcSlaStatisticTable 1 }     
    
    RcSlaStatisticEntry ::= SEQUENCE {
        rcSlaStatisticStartTime   		     TimeStamp,  
        rcSlaStatisticScheduleLife           Unsigned32,
        rcSlaStatisticSchedulePeriod         Unsigned32,
	    rcSlaStatisticTXNum             	 Counter32,
	    rcSlaStatisticRTTNum              	 Counter32,
	    rcSlaStatisticRTTSums              	 Counter32,
	    rcSlaStatisticRTTSumJitter   		 Counter32,               
	    rcSlaStatisticRTTSum2L               Counter32,
	    rcSlaStatisticRTTSum2H               Counter32,
	    rcSlaStatisticRTTMin                 Gauge32,
	    rcSlaStatisticRTTMax                 Gauge32,  
	    rcSlaStatisticRTTNumSD               Counter32,
	    rcSlaStatisticRTTSumsSD              Counter32,
	    rcSlaStatisticRTTSumJitterSD         Counter32,
	    rcSlaStatisticRTTSum2LSD             Counter32,
	    rcSlaStatisticRTTSum2HSD             Counter32,
	    rcSlaStatisticRTTMinSD               Gauge32, 
	    rcSlaStatisticRTTMaxSD               Gauge32, 
	    rcSlaStatisticRTTNumDS               Counter32,
	    rcSlaStatisticRTTSumsDS              Counter32,
	    rcSlaStatisticRTTSumJitterDS         Counter32,
	    rcSlaStatisticRTTSum2LDS             Counter32,
	    rcSlaStatisticRTTSum2HDS             Counter32,
	    rcSlaStatisticRTTMinDS               Gauge32,
	    rcSlaStatisticRTTMaxDS               Gauge32
	 
}


rcSlaStatisticStartTime       OBJECT-TYPE 
	SYNTAX      TimeStamp
    MAX-ACCESS  not-accessible
    STATUS      current
    DESCRIPTION
            "This object specifies the time when the operation starts to be scheduled."   
            
    ::= { rcSlaStatisticEntry 1 }      
     
rcSlaStatisticScheduleLife       OBJECT-TYPE 
	SYNTAX      Unsigned32
    MAX-ACCESS  read-only
    STATUS      current
    DESCRIPTION
            "This object specifies the time duration over the whole schedule process. "
    ::= { rcSlaStatisticEntry 2 }  
    
rcSlaStatisticSchedulePeriod       OBJECT-TYPE 
	SYNTAX      Unsigned32
    MAX-ACCESS  read-only
    STATUS      current
    DESCRIPTION
            "This object specifies the number of RTT's probe that were successfully measured in schedule."
    ::= { rcSlaStatisticEntry 3 }   
      
rcSlaStatisticTXNum       OBJECT-TYPE 
	SYNTAX      Counter32
    MAX-ACCESS  read-only
    STATUS      current
    DESCRIPTION
            "This object specifies the duration between two SLA test 
            	which includes all of probes schedule process in test. "
    ::= { rcSlaStatisticEntry 4 }    
    
rcSlaStatisticRTTNum       OBJECT-TYPE 
	SYNTAX      Counter32
    MAX-ACCESS  read-only
    STATUS      current
    DESCRIPTION
            "This object specifies the duration between two SLA test 
            	which includes all successful probes schedule process in test. 
           	Take above example, if all of the rcSlaConfigSchedulePeriod of three operations are set to 60, 
            	then the start time of each test of SLA operation like:
			start time:   T+0 --------  T+9 ----------  T+19-----
           		operation1  operation2    operation3 
			start again:  T+60--------  T+69 ----------  T+79--
           		operation1  operation2    operation3   
			start 3rd time:T+120-------- T+129 ----------T+139--
         		operation1  operation2    operation3"
    ::= { rcSlaStatisticEntry 5 }                   

rcSlaStatisticRTTSums        OBJECT-TYPE 
	SYNTAX      Counter32
    MAX-ACCESS  read-only
    STATUS      current
    DESCRIPTION
            "This object specifies the sum of RTT's delay that were successfully measured in schedule."
    ::= { rcSlaStatisticEntry 6 }        
    
rcSlaStatisticRTTSumJitter       OBJECT-TYPE 
	SYNTAX      Counter32
    MAX-ACCESS  read-only
    STATUS      current
    DESCRIPTION
            "This object specifies the number of RTT's jitter that were successfully measured in Schedule.  
            	This object is applicable to 'Jitter' operation only."
    ::= { rcSlaStatisticEntry 7 }

rcSlaStatisticRTTSum2L       OBJECT-TYPE 
	SYNTAX      Counter32
    MAX-ACCESS  read-only
    STATUS      current
    DESCRIPTION
            "This object specifies the sum of squares of RTT's delay that are successfully measured in Schedule.
            	 This object is applicable to 'Jitter' operation only. (low order 32 bits)"
    ::= { rcSlaStatisticEntry 8 }

rcSlaStatisticRTTSum2H       OBJECT-TYPE 
	SYNTAX      Counter32
    MAX-ACCESS  read-only
    STATUS      current
    DESCRIPTION
            "This object specifies the sum of squares of RTT's delay that are successfully measured in Schedule. 
            	This object is applicable to 'Jitter' operation only. (high order 32 bits)"
    ::= { rcSlaStatisticEntry 9 }                    

rcSlaStatisticRTTMin       OBJECT-TYPE 
	SYNTAX      Gauge32
    MAX-ACCESS  read-only
    STATUS      current
    DESCRIPTION
            "This object specifies the minimum of RTT's that were successfully measured in Schedule. 
            	This object is applicable to 'Jitter' operation only."
    ::= { rcSlaStatisticEntry 10 }                    

rcSlaStatisticRTTMax       OBJECT-TYPE 
	SYNTAX      Gauge32
    MAX-ACCESS  read-only
    STATUS      current
    DESCRIPTION
            "This object specifies the maximum of RTT's that were successfully measured in Schedule. 
            	This object is applicable to 'Jitter' operation only."
    ::= { rcSlaStatisticEntry 11 }                    
                  
rcSlaStatisticRTTNumSD       OBJECT-TYPE 
	SYNTAX      Counter32
    MAX-ACCESS  read-only
    STATUS      current
    DESCRIPTION
            "This object specifies the number of RTT's probe 
            	that were successfully measured from source to destination in Schedule."
    ::= { rcSlaStatisticEntry 12 }  
    
rcSlaStatisticRTTSumsSD       OBJECT-TYPE 
	SYNTAX      Counter32
    MAX-ACCESS  read-only
    STATUS      current
    DESCRIPTION
            "This object specifies the sum of RTT's delay 
            	that were successfully measured from source to destination in Schedule."
    ::= { rcSlaStatisticEntry 13 }                    

rcSlaStatisticRTTSumJitterSD       OBJECT-TYPE 
	SYNTAX      Counter32
    MAX-ACCESS  read-only
    STATUS      current
    DESCRIPTION
            "This object specifies the number of RTT's jitter that were successfully measured from source to destination in Schedule.
            	This object is applicable to 'Jitter' operation only."
    ::= { rcSlaStatisticEntry 14 }                    

rcSlaStatisticRTTSum2LSD       OBJECT-TYPE 
	SYNTAX      Counter32
    MAX-ACCESS  read-only
    STATUS      current
    DESCRIPTION
            "This object specifies the sum of squares of RTT's delay that are successfully measured from source to destination in Schedule. 
            	This object is applicable to 'Jitter' operation only. (low order 32 bits)"
    ::= { rcSlaStatisticEntry 15 }                    

rcSlaStatisticRTTSum2HSD       OBJECT-TYPE 
	SYNTAX      Counter32
    MAX-ACCESS  read-only
    STATUS      current
    DESCRIPTION
            "This object specifies the sum of squares of RTT's delay that are successfully measured from source to destination in Schedule. 
            	This object is applicable to 'Jitter' operation only. (high order 32 bits)"
    ::= { rcSlaStatisticEntry 16 }                    

rcSlaStatisticRTTMinSD       OBJECT-TYPE 
	SYNTAX      Gauge32
    MAX-ACCESS  read-only
    STATUS      current
    DESCRIPTION
            "This object specifies the minimum of RTT's that were successfully measured from source to destination in Schedule. 
            	This object is applicable to 'Jitter' operation only."
    ::= { rcSlaStatisticEntry 17 }                    

rcSlaStatisticRTTMaxSD       OBJECT-TYPE 
	SYNTAX      Gauge32
    MAX-ACCESS  read-only
    STATUS      current
    DESCRIPTION
            "This object specifies the maximum of RTT's that were successfully measured from source to destination in Schedule. 
            	This object is applicable to 'Jitter' operation only."
    ::= { rcSlaStatisticEntry 18 }    

rcSlaStatisticRTTNumDS       OBJECT-TYPE 
	SYNTAX      Counter32
    MAX-ACCESS  read-only
    STATUS      current
    DESCRIPTION
            "This object specifies the number of RTT's probe 
            	that were successfully measured from destination to source in Schedule."
    ::= { rcSlaStatisticEntry 19 } 
                    

rcSlaStatisticRTTSumsDS       OBJECT-TYPE 
	SYNTAX      Counter32
    MAX-ACCESS  read-only
    STATUS      current
    DESCRIPTION
            "This object specifies the sum of RTT's delay 
            that were successfully measured from destination to source in Schedule."
    ::= { rcSlaStatisticEntry 20 }                    

rcSlaStatisticRTTSumJitterDS       OBJECT-TYPE 
	SYNTAX      Counter32
    MAX-ACCESS  read-only
    STATUS      current
    DESCRIPTION
            "This object specifies the number of RTT's jitter that were successfully measured from destination to source in Schedule.  
            	This object is applicable to 'Jitter' operation only."
    ::= { rcSlaStatisticEntry 21 }                    

rcSlaStatisticRTTSum2LDS       OBJECT-TYPE 
	SYNTAX      Counter32
    MAX-ACCESS  read-only
    STATUS      current
    DESCRIPTION
            "This object specifies the sum of squares of RTT's delay that are successfully measured from destination to source in Schedule. 
            	This object is applicable to 'Jitter' operation only. (low order 32 bits)"
    ::= { rcSlaStatisticEntry 22 }  
    

rcSlaStatisticRTTSum2HDS       OBJECT-TYPE 
	SYNTAX      Counter32
    MAX-ACCESS  read-only
    STATUS      current
    DESCRIPTION
            "This object specifies the sum of squares of RTT's delay that are successfully measured from destination to source in Schedule. 
            	This object is applicable to 'Jitter' operation only. (hige order 32 bits)"
    ::= { rcSlaStatisticEntry 23 }  
    

rcSlaStatisticRTTMinDS       OBJECT-TYPE 
	SYNTAX      Gauge32
    MAX-ACCESS  read-only
    STATUS      current
    DESCRIPTION
            "This object specifies the minimum of RTT's that were successfully measured from destination to source in Schedule. 
            	This object is applicable to 'Jitter' operation only. "
    ::= { rcSlaStatisticEntry 24 }  
    

rcSlaStatisticRTTMaxDS       OBJECT-TYPE 
	SYNTAX      Gauge32
    MAX-ACCESS  read-only
    STATUS      current
    DESCRIPTION
            "This object specifies the maximum of RTT's that were successfully measured from destination to source in Schedule. 
            	This object is applicable to 'Jitter' operation only."
    ::= { rcSlaStatisticEntry 25 }        

-- rcSlaPktlmLatestTable
--      
rcSlaPktlmLatestTable  OBJECT-TYPE
    SYNTAX      SEQUENCE OF RcSlaPktlmLatestEntry
    MAX-ACCESS  not-accessible
    STATUS      current
    DESCRIPTION
        "This table contains the statistics calculated for the 
        latest sent frames."
    ::= { rcSlaScheduleGroup 3 } 
 
 rcSlaPktlmLatestEntry   OBJECT-TYPE
    SYNTAX      RcSlaPktlmLatestEntry
    MAX-ACCESS  not-accessible
    STATUS      current
    DESCRIPTION
        "A collection of objects that record the latest operation.

        An entry is created only when the operation has been set and scheduled.
        The entry will start to collect data when rcSlaConfigScheduleStatus 
        is in 'active' state.  The entry will be removed when the 
        rcSlaConfigScheduleStatus is changed to 'complete' state. "
	INDEX        { rcSlaConfigOperId }
    ::={ rcSlaPktlmLatestTable 1 }

RcSlaPktlmLatestEntry ::= SEQUENCE {
	    rcSlaLatestPktlmTXNum                  Gauge32,
	    rcSlaLatestPktlmNum                    Gauge32,
	    rcSlaLatestPktlmSum                    Gauge32,
	    rcSlaLatestPktlmMin                    Gauge32,
	    rcSlaLatestPktlmMax                    Gauge32,
	    rcSlaLatestPktlmNumSD                  Gauge32,
	    rcSlaLatestPktlmSumSD                  Gauge32,
	    rcSlaLatestPktlmMinSD                  Gauge32,
	    rcSlaLatestPktlmMaxSD                  Gauge32,
	    rcSlaLatestPktlmNumDS                  Gauge32,
	    rcSlaLatestPktlmSumDS                  Gauge32,
	    rcSlaLatestPktlmMinDS                  Gauge32,
	    rcSlaLatestPktlmMaxDS                  Gauge32,  
	    rcSlaLatestPktlmInterSumSD                  Gauge32,  
	    rcSlaLatestPktlmInterSumDS                  Gauge32


}

rcSlaLatestPktlmTXNum       OBJECT-TYPE
	SYNTAX      Gauge32
    MAX-ACCESS  read-only
    STATUS      current
    DESCRIPTION
            "This object specifies the number of packet loss measurement sent in latest test."
    ::= { rcSlaPktlmLatestEntry 1 }

rcSlaLatestPktlmNum       OBJECT-TYPE
	SYNTAX      Gauge32
    MAX-ACCESS  read-only
    STATUS      current
    DESCRIPTION
            "This object specifies the number of packet loss measurement probe that were successfully measured in latest test."
    ::= { rcSlaPktlmLatestEntry 2 }

rcSlaLatestPktlmSum       OBJECT-TYPE
	SYNTAX      Gauge32
    MAX-ACCESS  read-only
    STATUS      current
    DESCRIPTION
            "This object specifies the sum of packet loss measurement that were successfully measured in latest test."
    ::= { rcSlaPktlmLatestEntry 3 }
    
rcSlaLatestPktlmMin       OBJECT-TYPE
	SYNTAX      Gauge32
    MAX-ACCESS  read-only
    STATUS      current
    DESCRIPTION
            "This object specifies the minimum of packet loss measurement that were successfully measured in latest test."
    ::= { rcSlaPktlmLatestEntry 4 }

rcSlaLatestPktlmMax       OBJECT-TYPE
	SYNTAX      Gauge32
    MAX-ACCESS  read-only
    STATUS      current
    DESCRIPTION
            "This object specifies the maximum of packet loss measurement that were successfully measured in latest test."
    ::= { rcSlaPktlmLatestEntry 5 }

rcSlaLatestPktlmNumSD       OBJECT-TYPE
	SYNTAX      Gauge32
    MAX-ACCESS  read-only
    STATUS      current
    DESCRIPTION
            "This object specifies the number of packet loss measurement that were successfully measured from source to destination in latest test."
    ::= { rcSlaPktlmLatestEntry 6 }

rcSlaLatestPktlmSumSD       OBJECT-TYPE
	SYNTAX      Gauge32
    MAX-ACCESS  read-only
    STATUS      current
    DESCRIPTION
            "This object specifies the sum of packet loss measurement that were successfully measured from source to destination in latest test."
    ::= { rcSlaPktlmLatestEntry 7 }

rcSlaLatestPktlmMinSD       OBJECT-TYPE
	SYNTAX      Gauge32
    MAX-ACCESS  read-only
    STATUS      current
    DESCRIPTION
            "This object specifies the minimum of packet loss measurement that were successfully measured from source to destination in latest test."
    ::= { rcSlaPktlmLatestEntry 8 }

rcSlaLatestPktlmMaxSD       OBJECT-TYPE
	SYNTAX      Gauge32
    MAX-ACCESS  read-only
    STATUS      current
    DESCRIPTION
            "This object specifies the maximum of packet loss measurement that were successfully measured from source to destination in latest test."
    ::= { rcSlaPktlmLatestEntry 9 }

rcSlaLatestPktlmNumDS       OBJECT-TYPE
	SYNTAX      Gauge32
    MAX-ACCESS  read-only
    STATUS      current
    DESCRIPTION
            "This object specifies the number of packet loss measurement that were successfully measured from destination to source in latest test."
    ::= { rcSlaPktlmLatestEntry 10 }

rcSlaLatestPktlmSumDS       OBJECT-TYPE
	SYNTAX      Gauge32
    MAX-ACCESS  read-only
    STATUS      current
    DESCRIPTION
            "This object specifies the sum of packet loss measurement that were successfully measured from destination to source in latest test."
    ::= { rcSlaPktlmLatestEntry 11 }

rcSlaLatestPktlmMinDS       OBJECT-TYPE
	SYNTAX      Gauge32
    MAX-ACCESS  read-only
    STATUS      current
    DESCRIPTION
            "This object specifies the minimum of packet loss measurement that were successfully measured from destination to source in latest test."
    ::= { rcSlaPktlmLatestEntry 12 }

rcSlaLatestPktlmMaxDS       OBJECT-TYPE
	SYNTAX      Gauge32
    MAX-ACCESS  read-only
    STATUS      current
    DESCRIPTION
            "This object specifies the maximum of packet loss measurement that were successfully measured from destination to source in latest test."
    ::= { rcSlaPktlmLatestEntry 13 }  
 
rcSlaLatestPktlmInterSumSD       OBJECT-TYPE
	SYNTAX      Gauge32
    MAX-ACCESS  read-only
    STATUS      current
    DESCRIPTION
            "This object specifies the sum of packet loss measurement that were successfully measured from destination to source in interval time  test."
    ::= { rcSlaPktlmLatestEntry 14 }  
    
rcSlaLatestPktlmInterSumDS       OBJECT-TYPE
	SYNTAX      Gauge32
    MAX-ACCESS  read-only
    STATUS      current
    DESCRIPTION
            "This object specifies the sum of packet loss measurement that were successfully measured from destination to source in interval time  test."
    ::= { rcSlaPktlmLatestEntry 15 }  
   

-- rcSlaPktlmStatisticTable
--  

rcSlaPktlmStatisticTable  OBJECT-TYPE
    SYNTAX      SEQUENCE OF RcSlaPktlmStatisticEntry
    MAX-ACCESS  not-accessible
    STATUS      current
    DESCRIPTION
        "The 'SlaPktlmStatistic' statistics table contains summarized
    information of the results for a conceptual control row."
    ::= { rcSlaScheduleGroup 4 }

rcSlaPktlmStatisticEntry   OBJECT-TYPE
    SYNTAX      RcSlaPktlmStatisticEntry
    MAX-ACCESS  not-accessible
    STATUS      current
    DESCRIPTION
        "An entry is created only when the operation has been set and scheduled.      
        The entry will start to collect data when rcSlaConfigScheduleStatus 
    is in 'active' state.  The entry will stop to collect data when the 
    rcSlaConfigScheduleStatus is changed to 'complete' state.
         "
	INDEX        { rcSlaConfigOperId,
	               rcSlaStatisticPktlmStartTime
	             }    
    ::={ rcSlaPktlmStatisticTable 1 }     
    
    RcSlaPktlmStatisticEntry ::= SEQUENCE {
        rcSlaStatisticPktlmStartTime   		   TimeStamp,  
        rcSlaStatisticPktlmScheduleLife        Unsigned32,
        rcSlaStatisticPktlmSchedulePeriod      Unsigned32,
        rcSlaStatisticPktlmTXNum               Counter32,
        rcSlaStatisticPktlmNum                 Counter32,
        rcSlaStatisticPktlmSums                Counter32,
        rcSlaStatisticPktlmMin                 Gauge32,
        rcSlaStatisticPktlmMax                 Gauge32,  
        rcSlaStatistiPktlmNumSD                Counter32,
        rcSlaStatisticPktlmSumsSD              Counter32,
        rcSlaStatisticPktlmMinSD               Gauge32, 
        rcSlaStatisticPktlmMaxSD               Gauge32, 
        rcSlaStatisticPktlmNumDS               Counter32,
        rcSlaStatisticPktlmSumsDS              Counter32,
        rcSlaStatisticPktlmMinDS               Gauge32,
        rcSlaStatisticPktlmMaxDS               Gauge32
}


rcSlaStatisticPktlmStartTime       OBJECT-TYPE 
	SYNTAX      TimeStamp
    MAX-ACCESS  not-accessible
    STATUS      current
    DESCRIPTION
            "This object specifies the time when the operation starts to be scheduled."   
            
    ::= { rcSlaPktlmStatisticEntry 1 }      
     
rcSlaStatisticPktlmScheduleLife       OBJECT-TYPE 
	SYNTAX      Unsigned32
    MAX-ACCESS  read-only
    STATUS      current
    DESCRIPTION
            "This object specifies the time duration over the whole schedule process. "
    ::= { rcSlaPktlmStatisticEntry 2 }  
    
rcSlaStatisticPktlmSchedulePeriod       OBJECT-TYPE 
	SYNTAX      Unsigned32
    MAX-ACCESS  read-only
    STATUS      current
    DESCRIPTION
            "This object specifies the number of packet loss measurement probe that were successfully measured in schedule."
    ::= { rcSlaPktlmStatisticEntry 3 }   
      
rcSlaStatisticPktlmTXNum       OBJECT-TYPE 
	SYNTAX      Counter32
    MAX-ACCESS  read-only
    STATUS      current
    DESCRIPTION
            "This object specifies the duration between two SLA test 
            	which includes all of probes schedule process in test. "
    ::= { rcSlaPktlmStatisticEntry 4 }    
    
rcSlaStatisticPktlmNum       OBJECT-TYPE 
	SYNTAX      Counter32
    MAX-ACCESS  read-only
    STATUS      current
    DESCRIPTION
            "This object specifies the duration between two SLA test 
            	which includes all successful probes schedule process in test. 
           	Take above example, if all of the rcSlaConfigSchedulePeriod of three operations are set to 60, 
            	then the start time of each test of SLA operation like:
			start time:   T+0 --------  T+9 ----------  T+19-----
           		operation1  operation2    operation3 
			start again:  T+60--------  T+69 ----------  T+79--
           		operation1  operation2    operation3   
			start 3rd time:T+120-------- T+129 ----------T+139--
         		operation1  operation2    operation3"
    ::= { rcSlaPktlmStatisticEntry 5 }                   

rcSlaStatisticPktlmSums        OBJECT-TYPE 
	SYNTAX      Counter32
    MAX-ACCESS  read-only
    STATUS      current
    DESCRIPTION
            "This object specifies the sum of packet loss measurement that were successfully measured in schedule."
    ::= { rcSlaPktlmStatisticEntry 6 }        
    
rcSlaStatisticPktlmMin       OBJECT-TYPE 
	SYNTAX      Gauge32
    MAX-ACCESS  read-only
    STATUS      current
    DESCRIPTION
            "This object specifies the minimum of packet loss measurement that were successfully measured in Schedule."
    ::= { rcSlaPktlmStatisticEntry 7 }                    

rcSlaStatisticPktlmMax       OBJECT-TYPE 
	SYNTAX      Gauge32
    MAX-ACCESS  read-only
    STATUS      current
    DESCRIPTION
            "This object specifies the maximum of packet loss measurement that were successfully measured in Schedule. "
    ::= { rcSlaPktlmStatisticEntry 8 }                    
                  
rcSlaStatistiPktlmNumSD       OBJECT-TYPE 
	SYNTAX      Counter32
    MAX-ACCESS  read-only
    STATUS      current
    DESCRIPTION
            "This object specifies the number of packet loss measurement 
            	that were successfully measured from source to destination in Schedule."
    ::= { rcSlaPktlmStatisticEntry 9 }  
    
rcSlaStatisticPktlmSumsSD       OBJECT-TYPE 
	SYNTAX      Counter32
    MAX-ACCESS  read-only
    STATUS      current
    DESCRIPTION
            "This object specifies the sum of packet loss measurement  
            	that were successfully measured from source to destination in Schedule."
    ::= { rcSlaPktlmStatisticEntry 10 }                    

rcSlaStatisticPktlmMinSD       OBJECT-TYPE 
	SYNTAX      Gauge32
    MAX-ACCESS  read-only
    STATUS      current
    DESCRIPTION
            "This object specifies the minimum of packet loss measurement that were successfully measured from source to destination in Schedule. "
    ::= { rcSlaPktlmStatisticEntry 11 }                    

rcSlaStatisticPktlmMaxSD       OBJECT-TYPE 
	SYNTAX      Gauge32
    MAX-ACCESS  read-only
    STATUS      current
    DESCRIPTION
            "This object specifies the maximum of packet loss measurement that were successfully measured from source to destination in Schedule. "
    ::= { rcSlaPktlmStatisticEntry 12 }    

rcSlaStatisticPktlmNumDS       OBJECT-TYPE 
	SYNTAX      Counter32
    MAX-ACCESS  read-only
    STATUS      current
    DESCRIPTION
            "This object specifies the number of packet loss measurement  
            	that were successfully measured from destination to source in Schedule."
    ::= { rcSlaPktlmStatisticEntry 13 } 
                    

rcSlaStatisticPktlmSumsDS       OBJECT-TYPE 
	SYNTAX      Counter32
    MAX-ACCESS  read-only
    STATUS      current
    DESCRIPTION
            "This object specifies the sum of packet loss measurement  
            that were successfully measured from destination to source in Schedule."
    ::= { rcSlaPktlmStatisticEntry 14 }                    

rcSlaStatisticPktlmMinDS       OBJECT-TYPE 
	SYNTAX      Gauge32
    MAX-ACCESS  read-only
    STATUS      current
    DESCRIPTION
            "This object specifies the minimum of packet loss measurement that were successfully measured from destination to source in Schedule. "
    ::= { rcSlaPktlmStatisticEntry 15 }  
    

rcSlaStatisticPktlmMaxDS       OBJECT-TYPE 
	SYNTAX      Gauge32
    MAX-ACCESS  read-only
    STATUS      current
    DESCRIPTION
            "This object specifies the maximum of packet loss measurement that were successfully measured from destination to source in Schedule." 
    ::= { rcSlaPktlmStatisticEntry 16 }        
              
  --rcSlaThroughputGroup --  
--rcSlaThroughputGroup                                                                                              
		--rcSlaCThroughputConfigTable    
			--rcSlaThroughputConfigEntry 
				--rcSlaThroughputIndex
				--rcSlaThroughputOperId
				--rcSlaThroughputObject   
				--rcSlaThroughputPktLength
				--rcSlaThroughputCount
				--rcSlaThroughputDuration   				
				--rcSlaThroughputEnable
				--rcSlaThroughputStatus
				--rcSlaThroughputRowStatus
				--rcSlaThroughputCompleteNum
				--rcSlaThroughputMeasureStartTime
				--rcSlaThroughputMeasureLastTime
				--rcSlaThroughputMeasureEndTime
				--rcSlaThroughputFailedNum    	
				
	--rcSlaCThroughputResultTable    
			--rcSlaThroughputResultEntry 
				--rcSlaThroughputResultId
				--rcSlaThroughputCfgId
				--rcSlaThroughputStartTime   
				--rcSlaThroughputEndTime				
				--rcSlaThroughputLastTime
				--rcSlaThroughputLocalSendPStatics 	
				--rcSlaThroughputLocalSendBStatics 
				--rcSlaThroughputLocalReceivePStatics 
				--rcSlaThroughputLocalReceiveBStatics 
				--rcSlaThroughputRemoteSendPStatics 
				--rcSlaThroughputRemoteSendBStatics 
				--rcSlaThroughputRemoteReceivePStatics 
				--rcSlaThroughputRemoteReceiveBStatics 				
				            

rcSlaThroughputConfigTable  OBJECT-TYPE
    SYNTAX      SEQUENCE OF RcSlaThroughputConfigEntry
    MAX-ACCESS  not-accessible
    STATUS      deprecated
    DESCRIPTION
        "This table contains sla  control data."
    ::= { rcSlaThroughputGroup 1 }

rcSlaThroughputConfigEntry   OBJECT-TYPE
    SYNTAX      RcSlaThroughputConfigEntry
    MAX-ACCESS  not-accessible
    STATUS      deprecated
    DESCRIPTION
        "A collection of objects that define three conceptual
    control row : slaY.1731EntryTable, slaIcmpEntryTable, slaSchEntryTable.
   		The 'slaY.1731EntryTable' is used to control y1731 operation .
    	The following objects must be specified in order to create this 
    conceptual row.
    	- rcSlaConfigOperType
    	- rcSlaConfigVlanId
    	- rcSlaConfigMDLevel
    	- rcSlaConfigDestMacAddr 
    	- rcSlaConfigRMepId
    	The ' slaIcmpEntryTable' is used to control ICMP operation .
    	The following objects must be specified in order to create this 
    conceptual row.
    	- rcSlaConfigOperType
    	- rcSlaConfigDestIpAddr
        The ' slaIcmpSchTable' is used to control operation schduled."
	INDEX        { rcSlaThroughputIndex }    
    ::={ rcSlaThroughputConfigTable 1 }     
    
RcSlaThroughputConfigEntry ::= SEQUENCE {
        rcSlaThroughputIndex			     Unsigned32 (0..100 ), 
        rcSlaThroughputOperId			     Unsigned32,
    	rcSlaThroughputObject                Unsigned32 (125..1000000),
    	rcSlaThroughputPktLength             INTEGER,       
	    rcSlaThroughputCount	             Unsigned32,  
	    rcSlaThroughputDuration              Unsigned32,
	    rcSlaThroughputEnable                TruthValue,
	    rcSlaThroughputStatus                INTEGER,  
	    rcSlaThroughputFailedNum             Unsigned32,
	    rcSlaThroughputCompleteNum           Unsigned32,
	    rcSlaThroughputMeasureStartTime      Unsigned32,
		rcSlaThroughputMeasureLastTime       Unsigned32,
		rcSlaThroughputMeasureEndTime        Unsigned32,
	    rcSlaThroughputRowStatus             RowStatus
	 }

rcSlaThroughputIndex       OBJECT-TYPE 
	SYNTAX      Unsigned32 (0..100 ) 
	MAX-ACCESS  not-accessible
    STATUS      deprecated
    DESCRIPTION
            "This object indicates a row in the rcSlaConfigTable.
        This value is an operation number configured by user."
    ::= { rcSlaThroughputConfigEntry 1 }  
    
rcSlaThroughputOperId       OBJECT-TYPE 
	SYNTAX      Unsigned32 
	MAX-ACCESS  read-write
    STATUS      deprecated
    DESCRIPTION
            "This object indicates a row in the rcSlaConfigTable.
        This value is an operation number configured by user."
    ::= { rcSlaThroughputConfigEntry 2 }  
    
rcSlaThroughputObject       OBJECT-TYPE 
	SYNTAX      Unsigned32 (125..1000000) 
	MAX-ACCESS  read-write
    STATUS      deprecated
    DESCRIPTION
            "This object indicates a row in the rcSlaConfigTable.
        This value is an operation number configured by user."
    ::= { rcSlaThroughputConfigEntry 3 }  
    
rcSlaThroughputPktLength       OBJECT-TYPE 
	SYNTAX       INTEGER{
	            length64      (0),
	            length128     (1),
	            length256     (2),
	            length512     (3),
	            length1024    (4),
	            length1280    (5),
	            length1518    (6)
	            }
 
	MAX-ACCESS  read-write
    STATUS      deprecated
    DESCRIPTION
            "This object indicates a row in the rcSlaConfigTable.
        This value is an operation number configured by user."
    ::= { rcSlaThroughputConfigEntry 4 }     
    
rcSlaThroughputCount       OBJECT-TYPE 
	SYNTAX      Unsigned32 
	MAX-ACCESS  read-write
    STATUS      deprecated
    DESCRIPTION
            "This object indicates a row in the rcSlaConfigTable.
        This value is an operation number configured by user."
    ::= { rcSlaThroughputConfigEntry 5 }  
    
rcSlaThroughputDuration       OBJECT-TYPE 
	SYNTAX      Unsigned32 
	MAX-ACCESS  read-write
    STATUS      deprecated
    DESCRIPTION
            "This object indicates a row in the rcSlaConfigTable.
        This value is an operation number configured by user."
    ::= { rcSlaThroughputConfigEntry 6 }  
    
rcSlaThroughputEnable       OBJECT-TYPE 
	SYNTAX      TruthValue 
	MAX-ACCESS  read-write
    STATUS      deprecated
    DESCRIPTION
            "This object indicates a row in the rcSlaConfigTable.
        This value is an operation number configured by user."
    ::= { rcSlaThroughputConfigEntry 7 }  
    
rcSlaThroughputStatus       OBJECT-TYPE 
    SYNTAX      INTEGER {
                  	throughput-init		(1),
	              	throughput-Active   (2),
                  	throughput-Complete (3),
                 	throughput-Disturb  (4)    
                  }  
                
	MAX-ACCESS  read-only
    STATUS      deprecated
    DESCRIPTION
            "This object indicates a row in the rcSlaConfigTable.
        This value is an operation number configured by user."
    ::= { rcSlaThroughputConfigEntry 8 }     
    
rcSlaThroughputCompleteNum       OBJECT-TYPE 
	SYNTAX      Unsigned32 
	MAX-ACCESS  read-only
    STATUS      deprecated
    DESCRIPTION
            "This object indicates a row in the rcSlaConfigTable.
        This value is an operation number configured by user."
    ::= { rcSlaThroughputConfigEntry 9 } 

rcSlaThroughputFailedNum       OBJECT-TYPE 
	SYNTAX      Unsigned32 
	MAX-ACCESS  read-only
    STATUS      deprecated
    DESCRIPTION
            "This object indicates a row in the rcSlaConfigTable.
        This value is an operation number configured by user."
    ::= { rcSlaThroughputConfigEntry 10 }    
    
    
rcSlaThroughputMeasureStartTime       OBJECT-TYPE 
	SYNTAX      Unsigned32 
	MAX-ACCESS  read-write
    STATUS      deprecated
    DESCRIPTION
            "This object indicates a row in the rcSlaConfigTable.
        This value is an operation number configured by user."
    ::= { rcSlaThroughputConfigEntry 11 } 
  
rcSlaThroughputMeasureEndTime       OBJECT-TYPE 
	SYNTAX      Unsigned32 
	MAX-ACCESS  read-write
    STATUS      deprecated
    DESCRIPTION
            "This object indicates a row in the rcSlaConfigTable.
        This value is an operation number configured by user."
    ::= { rcSlaThroughputConfigEntry 12 } 


rcSlaThroughputMeasureLastTime       OBJECT-TYPE 
	SYNTAX      Unsigned32 
	MAX-ACCESS  read-write
    STATUS      deprecated
    DESCRIPTION
            "This object indicates a row in the rcSlaConfigTable.
        This value is an operation number configured by user."
    ::= { rcSlaThroughputConfigEntry 13 } 
    
    
rcSlaThroughputRowStatus       OBJECT-TYPE 
	SYNTAX      RowStatus 
	MAX-ACCESS  read-write
    STATUS      deprecated
    DESCRIPTION
            "This object indicates a row in the rcSlaConfigTable.
        This value is an operation number configured by user."
    ::= { rcSlaThroughputConfigEntry 14 } 
    
    
    
 rcSlaThroughputResultTable  OBJECT-TYPE
    SYNTAX      SEQUENCE OF RcSlaThroughputResultEntry
    MAX-ACCESS  not-accessible
    STATUS      deprecated
    DESCRIPTION
        "This table contains sla  control data."
    ::= { rcSlaThroughputGroup 2 }

rcSlaThroughputResultEntry   OBJECT-TYPE
    SYNTAX      RcSlaThroughputResultEntry
    MAX-ACCESS  not-accessible
    STATUS      deprecated
    DESCRIPTION
        "A collection of objects that define three conceptual
    control row : slaY.1731EntryTable, slaIcmpEntryTable, slaSchEntryTable.
   		The 'slaY.1731EntryTable' is used to control y1731 operation .
    	The following objects must be specified in order to create this 
    conceptual row.
    	- rcSlaConfigOperType
    	- rcSlaConfigVlanId
    	- rcSlaConfigMDLevel
    	- rcSlaConfigDestMacAddr 
    	- rcSlaConfigRMepId
    	The ' slaIcmpEntryTable' is used to control ICMP operation .
    	The following objects must be specified in order to create this 
    conceptual row.
    	- rcSlaConfigOperType
    	- rcSlaConfigDestIpAddr
        The ' slaIcmpSchTable' is used to control operation schduled."
	INDEX        {  rcSlaThroughputIndex,
					rcSlaThroughputResultId }    
    ::={ rcSlaThroughputResultTable 1 }     
    
RcSlaThroughputResultEntry ::= SEQUENCE {
        rcSlaThroughputResultId			     Unsigned32, 
       	rcSlaThroughputTestStartTime         Unsigned32,
    	rcSlaThroughputTestEndTime           Unsigned32, 
    	rcSlaThroughputTestLastTime          Unsigned32,      
	    rcSlaThroughputLocalSendPStatics     Counter64,
	    rcSlaThroughputLocalSendBStatics     Counter64,
	    rcSlaThroughputLocalReceivePStatics  Counter64,
	    rcSlaThroughputLocalReceiveBStatics  Counter64,
	    rcSlaThroughputRemoteSendPStatics    Counter64,
	    rcSlaThroughputRemoteSendBStatics    Counter64,
	    rcSlaThroughputRemoteReceivePStatics Counter64,
	    rcSlaThroughputRemoteReceiveBStatics Counter64
	}

rcSlaThroughputResultId       OBJECT-TYPE 
	SYNTAX      Unsigned32
	MAX-ACCESS  not-accessible
    STATUS      deprecated
    DESCRIPTION
            "This object indicates a row in the rcSlaConfigTable.
        This value is an operation number configured by user."
    ::= { rcSlaThroughputResultEntry 1 }  
    
    
rcSlaThroughputTestStartTime       OBJECT-TYPE 
	SYNTAX      Unsigned32 
	MAX-ACCESS  read-write
    STATUS      deprecated
    DESCRIPTION
            "This object indicates a row in the rcSlaConfigTable.
        This value is an operation number configured by user."
    ::= { rcSlaThroughputResultEntry 2 } 
  
rcSlaThroughputTestEndTime       OBJECT-TYPE 
	SYNTAX      Unsigned32 
	MAX-ACCESS  read-write
    STATUS      deprecated
    DESCRIPTION
            "This object indicates a row in the rcSlaConfigTable.
        This value is an operation number configured by user."
    ::= { rcSlaThroughputResultEntry 3 } 


rcSlaThroughputTestLastTime       OBJECT-TYPE 
	SYNTAX      Unsigned32 
	MAX-ACCESS  read-write
    STATUS      deprecated
    DESCRIPTION
            "This object indicates a row in the rcSlaConfigTable.
        This value is an operation number configured by user."
    ::= { rcSlaThroughputResultEntry 4 } 

rcSlaThroughputLocalSendPStatics       OBJECT-TYPE 
	SYNTAX      Counter64 
	MAX-ACCESS  read-write
    STATUS      deprecated
    DESCRIPTION
            "This object indicates a row in the rcSlaConfigTable.
        This value is an operation number configured by user."
    ::= { rcSlaThroughputResultEntry 5 } 

rcSlaThroughputLocalSendBStatics       OBJECT-TYPE 
	SYNTAX      Counter64 
	MAX-ACCESS  read-write
    STATUS      deprecated
    DESCRIPTION
            "This object indicates a row in the rcSlaConfigTable.
        This value is an operation number configured by user."
    ::= { rcSlaThroughputResultEntry 6 } 
    
rcSlaThroughputLocalReceivePStatics       OBJECT-TYPE 
	SYNTAX      Counter64 
	MAX-ACCESS  read-write
    STATUS      deprecated
    DESCRIPTION
            "This object indicates a row in the rcSlaConfigTable.
        This value is an operation number configured by user."
    ::= { rcSlaThroughputResultEntry 7 } 

rcSlaThroughputLocalReceiveBStatics       OBJECT-TYPE 
	SYNTAX      Counter64 
	MAX-ACCESS  read-write
    STATUS      deprecated
    DESCRIPTION
            "This object indicates a row in the rcSlaConfigTable.
        This value is an operation number configured by user."
    ::= { rcSlaThroughputResultEntry 8 } 

rcSlaThroughputRemoteSendPStatics       OBJECT-TYPE 
	SYNTAX      Counter64 
	MAX-ACCESS  read-write
    STATUS      deprecated
    DESCRIPTION
            "This object indicates a row in the rcSlaConfigTable.
        This value is an operation number configured by user."
    ::= { rcSlaThroughputResultEntry 9 } 

rcSlaThroughputRemoteSendBStatics       OBJECT-TYPE 
	SYNTAX      Counter64 
	MAX-ACCESS  read-write
    STATUS      deprecated
    DESCRIPTION
            "This object indicates a row in the rcSlaConfigTable.
        This value is an operation number configured by user."
    ::= { rcSlaThroughputResultEntry 10 } 

rcSlaThroughputRemoteReceivePStatics       OBJECT-TYPE 
	SYNTAX      Counter64 
	MAX-ACCESS  read-write
    STATUS      deprecated
    DESCRIPTION
            "This object indicates a row in the rcSlaConfigTable.
        This value is an operation number configured by user."
    ::= { rcSlaThroughputResultEntry 11 } 

rcSlaThroughputRemoteReceiveBStatics       OBJECT-TYPE 
	SYNTAX      Counter64 
	MAX-ACCESS  read-write
    STATUS      deprecated
    DESCRIPTION
            "This object indicates a row in the rcSlaConfigTable.
        This value is an operation number configured by user."
    ::= { rcSlaThroughputResultEntry 12 }   
    
rcSlaThroughputResultTrap NOTIFICATION-TYPE
        OBJECTS {   rcSlaThroughputResultId
                }
        STATUS  deprecated
        DESCRIPTION
          ""
       ::= { rcSlaThroughputGroup 4 }

            
 ---告警阈值表
rcSlaThresholdTable  OBJECT-TYPE
    SYNTAX      SEQUENCE OF RcSlaThresholdEntry
    MAX-ACCESS  not-accessible
    STATUS      current
    DESCRIPTION
        "This table contains sla trap threshold."
    ::= { rcSlaThresholdGroup 1 }

rcSlaThresholdEntry   OBJECT-TYPE
    SYNTAX      RcSlaThresholdEntry
    MAX-ACCESS  not-accessible
    STATUS      current
    DESCRIPTION
        "The entry of rcSlaThresholdTable."
	INDEX        { rcSlaTrapOperId }    
    ::={ rcSlaThresholdTable 1 }     
    
RcSlaThresholdEntry ::= SEQUENCE {
        rcSlaTrapOperId                      Unsigned32,
        rcSlaTrapEnableType			         BITS, 
       	rcSlaPktLossRateCurrThreshold        INTEGER,
    	rcSlaPktLossRateAverThreshold        INTEGER, 
    	rcSlaDelayCurrThreshold              Counter32,      
	    rcSlaDelayCurrThresholdSD            Counter32,
	    rcSlaDelayCurrThresholdDS            Counter32,
	    rcSlaDelayAverThreshold              Counter32,
	    rcSlaDelayAverThresholdSD            Counter32,
	    rcSlaDelayAverThresholdDS            Counter32,
	    rcSlaJitterCurrThreshold             Counter32,
	    rcSlaJitterCurrThresholdSD           Counter32,
	    rcSlaJitterCurrThresholdDS           Counter32,
	    rcSlaJitterAverThreshold             Counter32,
	    rcSlaJitterAverThresholdSD           Counter32,
	    rcSlaJitterAverThresholdDS           Counter32
	}
 
rcSlaTrapOperId           OBJECT-TYPE 
	SYNTAX      Unsigned32 
	MAX-ACCESS  not-accessible
    STATUS      current
    DESCRIPTION
            "This object indicates a row in the rcSlaThresholdTable.
        This value is an operation number configured by user."
    ::= { rcSlaThresholdEntry 1 }  
 
rcSlaTrapEnableType       OBJECT-TYPE 
	SYNTAX      BITS
	MAX-ACCESS  read-write
    STATUS      current
    DESCRIPTION
            "The enable status of threshold trap."
    ::= { rcSlaThresholdEntry 2 }  

rcSlaPktLossRateCurrThreshold       OBJECT-TYPE 
	SYNTAX      INTEGER(0..10000)
	MAX-ACCESS  read-write
    STATUS      current
    DESCRIPTION
            "The pkt loss rate threshold of the last test."
    ::= { rcSlaThresholdEntry 3 }
    
rcSlaPktLossRateAverThreshold       OBJECT-TYPE 
	SYNTAX      INTEGER(0..10000)
	MAX-ACCESS  read-write
    STATUS      current
    DESCRIPTION
            "The average pkt loss rate threshold of all test."
    ::= { rcSlaThresholdEntry 4 }       
    
rcSlaDelayCurrThreshold       OBJECT-TYPE 
	SYNTAX      Counter32
	MAX-ACCESS  read-write
    STATUS      current
    DESCRIPTION
            "The RTT delay threshold of the last test."
    ::= { rcSlaThresholdEntry 5 }   
    
rcSlaDelayCurrThresholdSD       OBJECT-TYPE 
	SYNTAX      Counter32
	MAX-ACCESS  read-write
    STATUS      current
    DESCRIPTION
            "The delay threshold of the last test from source to destination."
    ::= { rcSlaThresholdEntry 6 }   
    
rcSlaDelayCurrThresholdDS       OBJECT-TYPE 
	SYNTAX      Counter32
	MAX-ACCESS  read-write
    STATUS      current
    DESCRIPTION
            "The delay threshold of the last test from destination to source."
    ::= { rcSlaThresholdEntry 7 }     
    
rcSlaDelayAverThreshold       OBJECT-TYPE 
	SYNTAX      Counter32
	MAX-ACCESS  read-write
    STATUS      current
    DESCRIPTION
            "The RTT average delay threshold of all test."
    ::= { rcSlaThresholdEntry 8 }         
    
rcSlaDelayAverThresholdSD       OBJECT-TYPE 
	SYNTAX      Counter32
	MAX-ACCESS  read-write
    STATUS      current
    DESCRIPTION
            "The average delay threshold of all test from source to destination."
    ::= { rcSlaThresholdEntry 9 }     
    
rcSlaDelayAverThresholdDS       OBJECT-TYPE 
	SYNTAX      Counter32
	MAX-ACCESS  read-write
    STATUS      current
    DESCRIPTION
            "The average delay threshold of all test from destination to source."
    ::= { rcSlaThresholdEntry 10 }     
    
rcSlaJitterCurrThreshold       OBJECT-TYPE 
	SYNTAX      Counter32
	MAX-ACCESS  read-write
    STATUS      current
    DESCRIPTION
            "The RTT jitter threshold of the last test."
    ::= { rcSlaThresholdEntry 11 }       
    
rcSlaJitterCurrThresholdSD       OBJECT-TYPE 
	SYNTAX      Counter32
	MAX-ACCESS  read-write
    STATUS      current
    DESCRIPTION
            "The jitter threshold of the last test from source to destination."
    ::= { rcSlaThresholdEntry 12 }     
    
rcSlaJitterCurrThresholdDS       OBJECT-TYPE 
	SYNTAX      Counter32
	MAX-ACCESS  read-write
    STATUS      current
    DESCRIPTION
            "The jitter threshold of the last test from destination to source."
    ::= { rcSlaThresholdEntry 13 }       
    
rcSlaJitterAverThreshold       OBJECT-TYPE 
	SYNTAX      Counter32
	MAX-ACCESS  read-write
    STATUS      current
    DESCRIPTION
            "The RTT average jitter threshold of all test."
    ::= { rcSlaThresholdEntry 14 }    
        
rcSlaJitterAverThresholdSD       OBJECT-TYPE 
	SYNTAX      Counter32
	MAX-ACCESS  read-write
    STATUS      current
    DESCRIPTION
            "The average jitter threshold of all test from source to destination."
    ::= { rcSlaThresholdEntry 15 }    
    
rcSlaJitterAverThresholdDS       OBJECT-TYPE 
	SYNTAX      Counter32
	MAX-ACCESS  read-write
    STATUS      current
    DESCRIPTION
            "The average jitter threshold of all test from destination to source."
    ::= { rcSlaThresholdEntry 16 }   
    
 ---告警信息表
rcSlaThresholdTestResultTable  OBJECT-TYPE
    SYNTAX      SEQUENCE OF RcSlaThresholdTestResultEntry
    MAX-ACCESS  not-accessible
    STATUS      current
    DESCRIPTION
        "This table contains sla test result."
    ::= { rcSlaThresholdGroup 2 }

rcSlaThresholdTestResultEntry   OBJECT-TYPE
    SYNTAX      RcSlaThresholdTestResultEntry
    MAX-ACCESS  not-accessible
    STATUS      current
    DESCRIPTION
        "The entry of rcSlaThresholdTestResultTable."
	INDEX        { rcSlaTrapOperId }    
    ::={ rcSlaThresholdTestResultTable 1 }     
    
RcSlaThresholdTestResultEntry ::= SEQUENCE {
        rcSlaCurrResultTrap			         BITS, 
       	rcSlaAverResultTrap                  BITS,
    	rcSlaPktCurrLossRate                 INTEGER,    
    	rcSlaPktAverLossRate                 INTEGER,
    	rcSlaCurrDelay                       Counter32,      
	    rcSlaCurrDelaySD                     Counter32,
	    rcSlaCurrDelayDS                     Counter32,
	    rcSlaAverDelay                       Counter32,
	    rcSlaAverDelaySD                     Counter32,
	    rcSlaAverDelayDS                     Counter32,
	    rcSlaCurrJitter                      Counter32,
	    rcSlaCurrJitterSD                    Counter32,
	    rcSlaCurrJitterDS                    Counter32,
	    rcSlaAverJitter                      Counter32,
	    rcSlaAverJitterSD                    Counter32,
	    rcSlaAverJitterDS                    Counter32
	}

rcSlaCurrResultTrap       OBJECT-TYPE 
	SYNTAX      BITS
	MAX-ACCESS  read-only
    STATUS      current
    DESCRIPTION
            "The sla result trap status of the last test."
    ::= { rcSlaThresholdTestResultEntry 1 }  

rcSlaAverResultTrap       OBJECT-TYPE 
	SYNTAX      BITS
	MAX-ACCESS  read-only
    STATUS      current
    DESCRIPTION
            "The sla average result trap status of all test."
    ::= { rcSlaThresholdTestResultEntry 2 }  
    
rcSlaPktCurrLossRate       OBJECT-TYPE 
	SYNTAX      INTEGER(0..10000)
	MAX-ACCESS  read-only
    STATUS      current
    DESCRIPTION
            "The pkt loss rate of the last test."
    ::= { rcSlaThresholdTestResultEntry 3 }     
    
rcSlaPktAverLossRate       OBJECT-TYPE 
	SYNTAX      INTEGER(0..10000)
	MAX-ACCESS  read-only
    STATUS      current
    DESCRIPTION
            "The average pkt loss rate of all test."
    ::= { rcSlaThresholdTestResultEntry 4 }     
    
rcSlaCurrDelay       OBJECT-TYPE 
	SYNTAX      Counter32
	MAX-ACCESS  read-only
    STATUS      current
    DESCRIPTION
            "The RTT delay of the last test."
    ::= { rcSlaThresholdTestResultEntry 5 }     
    
rcSlaCurrDelaySD       OBJECT-TYPE 
	SYNTAX      Counter32
	MAX-ACCESS  read-only
    STATUS      current
    DESCRIPTION
            "The delay of the last test from source to destination."
    ::= { rcSlaThresholdTestResultEntry 6 }       
    
rcSlaCurrDelayDS       OBJECT-TYPE 
	SYNTAX      Counter32
	MAX-ACCESS  read-only
    STATUS      current
    DESCRIPTION
            "The delay of the last test from destination to source."
    ::= { rcSlaThresholdTestResultEntry 7 }       
    
rcSlaAverDelay       OBJECT-TYPE 
	SYNTAX      Counter32
	MAX-ACCESS  read-only
    STATUS      current
    DESCRIPTION
            "The RTT average delay of all test."
    ::= { rcSlaThresholdTestResultEntry 8 }   

rcSlaAverDelaySD       OBJECT-TYPE 
	SYNTAX      Counter32
	MAX-ACCESS  read-only
    STATUS      current
    DESCRIPTION
            "The average delay of all test from source to destination."
    ::= { rcSlaThresholdTestResultEntry 9 } 

rcSlaAverDelayDS       OBJECT-TYPE 
	SYNTAX      Counter32
	MAX-ACCESS  read-only
    STATUS      current
    DESCRIPTION
            "The average delay of all test from destination to source."
    ::= { rcSlaThresholdTestResultEntry 10 } 

rcSlaCurrJitter       OBJECT-TYPE 
	SYNTAX      Counter32
	MAX-ACCESS  read-only
    STATUS      current
    DESCRIPTION
            "The RTT jitter of the last test."
    ::= { rcSlaThresholdTestResultEntry 11 } 

rcSlaCurrJitterSD       OBJECT-TYPE 
	SYNTAX      Counter32
	MAX-ACCESS  read-only
    STATUS      current
    DESCRIPTION
            "The jitter of the last test from source to destination."
    ::= { rcSlaThresholdTestResultEntry 12 } 
    
rcSlaCurrJitterDS       OBJECT-TYPE 
	SYNTAX      Counter32
	MAX-ACCESS  read-only
    STATUS      current
    DESCRIPTION
            "The jitter of the last test from destination to source."
    ::= { rcSlaThresholdTestResultEntry 13 }    
    
rcSlaAverJitter       OBJECT-TYPE 
	SYNTAX      Counter32
	MAX-ACCESS  read-only
    STATUS      current
    DESCRIPTION
            "The RTT average jitter of all test."
    ::= { rcSlaThresholdTestResultEntry 14 }      
    
rcSlaAverJitterSD       OBJECT-TYPE 
	SYNTAX      Counter32
	MAX-ACCESS  read-only
    STATUS      current
    DESCRIPTION
            "The average jitter of all test from source to destination."
    ::= { rcSlaThresholdTestResultEntry 15 }       
    
rcSlaAverJitterDS       OBJECT-TYPE 
	SYNTAX      Counter32
	MAX-ACCESS  read-only
    STATUS      current
    DESCRIPTION
            "The average jitter of all test from destination to source."
    ::= { rcSlaThresholdTestResultEntry 16 }       

--阈值告警    
rcSlaThresholdTrapGroup  OBJECT IDENTIFIER ::= {rcSlaThresholdGroup 3} 

rcSlaCurrTestResultBeyondTrap   NOTIFICATION-TYPE
        OBJECTS {   rcSlaCurrResultTrap,
                    rcSlaPktCurrLossRate,
                    rcSlaPktLossRateCurrThreshold,
                    rcSlaCurrDelay,
                    rcSlaDelayCurrThreshold,
                    rcSlaCurrDelaySD,
                    rcSlaDelayCurrThresholdSD,
                    rcSlaCurrDelayDS,
                    rcSlaDelayCurrThresholdDS,
                    rcSlaCurrJitter,
                    rcSlaJitterCurrThreshold,
                    rcSlaCurrJitterSD,
                    rcSlaJitterCurrThresholdSD,
                    rcSlaCurrJitterDS,
                    rcSlaJitterCurrThresholdDS                   
                }
        STATUS  current
        DESCRIPTION
          "Send this trap when result beyond threshold of the last test."
       ::= { rcSlaThresholdTrapGroup 1 }

rcSlaAverTestResultBeyondTrap   NOTIFICATION-TYPE
        OBJECTS {   rcSlaAverResultTrap,
                    rcSlaPktAverLossRate,
                    rcSlaPktLossRateAverThreshold,
                    rcSlaAverDelay,
                    rcSlaDelayAverThreshold,
                    rcSlaAverDelaySD,
                    rcSlaDelayAverThresholdSD,
                    rcSlaAverDelayDS,
                    rcSlaDelayAverThresholdDS,
                    rcSlaAverJitter,
                    rcSlaJitterAverThreshold,
                    rcSlaAverJitterSD,
                    rcSlaJitterAverThresholdSD,
                    rcSlaAverJitterDS,
                    rcSlaJitterAverThresholdDS                   
                }
        STATUS  current
        DESCRIPTION
          "Send this trap when average result beyond threshold of all test."
       ::= { rcSlaThresholdTrapGroup 2 }    
       
       
                    --********************************************
 --LM last measurement interval information
 --********************************************   
rcmefSoamLmLastStatsTable OBJECT-TYPE
    SYNTAX      SEQUENCE OF RcmefSoamLmLastStatsEntry
    MAX-ACCESS  not-accessible
    STATUS      current
    DESCRIPTION
       "This table contains the results for last Measurement
        Intervals in a SOAM Loss Measurement session.

        Rows of this table object are created automatically
        by the SNMP Agent when the Loss Measurement session is running and a 
        Measurement Interval is completed.
        
        The rows and objects in this table are to be persistent upon reboot 
        or restart of a device.
       "
          
    ::= { rcmefSoamLastStatsGroup 1 }

rcmefSoamLmLastStatsEntry OBJECT-TYPE
    SYNTAX      RcmefSoamLmLastStatsEntry
    MAX-ACCESS  not-accessible
    STATUS      current
    DESCRIPTION
            "The conceptual row of mefSoamLmHistoryStatsTable"
    INDEX      {
               dot1agCfmMdIndex,
               dot1agCfmMaIndex, 
               dot1agCfmMepIdentifier, 
               rcSlaConfigOperId 
               }
    ::= { rcmefSoamLmLastStatsTable 1 }

RcmefSoamLmLastStatsEntry ::= SEQUENCE {
    rcmefSoamPmLastForwardFlr                      Unsigned32,
    rcmefSoamPmLastBackwardFlr                     Unsigned32,
    rcmefSoamPmLastForwardAvailability             Unsigned32,
    rcmefSoamPmLastBackwardAvailability            Unsigned32,  
    rcmefSoamPmLastTwoWayAvailability              Unsigned32,
    rcmefSoamPmLastIngressBandwidth                Counter64
    }
   
rcmefSoamPmLastForwardFlr OBJECT-TYPE
    SYNTAX      Unsigned32 (0..100000)
    UNITS       "milli-percent"
    MAX-ACCESS  read-only
    STATUS      current
    DESCRIPTION
       "This object contains the Last frame loss ratio in the 
       forward direction calculated by this MEP. The FLR value 
       is a ratio that is expressed as a percent with a value of 0 
       (ratio 0.00) through 100000 (ratio 1.00). 
       Units are in milli-percent, where 1 indicates 0.001 percent.
       "
       
    ::= { rcmefSoamLmLastStatsEntry 1 }
    
rcmefSoamPmLastBackwardFlr OBJECT-TYPE
    SYNTAX      Unsigned32 (0..100000)
    UNITS       "milli-percent"
    MAX-ACCESS  read-only
    STATUS      current
    DESCRIPTION
       "This object contains the Last frame loss ratio in the 
       Backward direction calculated by this MEP. The FLR value 
       is a ratio that is expressed as a percent with a value of 0 
       (ratio 0.00) through 100000 (ratio 1.00). 
       Units are in milli-percent, where 1 indicates 0.001 percent.
       "
         
    ::= { rcmefSoamLmLastStatsEntry 2 } 
    
rcmefSoamPmLastForwardAvailability OBJECT-TYPE
    SYNTAX      Unsigned32 (0..100000)
    UNITS       "milli-percent"
    MAX-ACCESS  read-only
    STATUS      current
    DESCRIPTION
       "Availability /total time.
       "
       
    ::= { rcmefSoamLmLastStatsEntry 3 } 
 
rcmefSoamPmLastBackwardAvailability OBJECT-TYPE
    SYNTAX      Unsigned32 (0..100000)
    UNITS       "milli-percent"
    MAX-ACCESS  read-only
    STATUS      current
    DESCRIPTION
       "Availability /total time.
       "
    
    ::= { rcmefSoamLmLastStatsEntry 4 } 
    
rcmefSoamPmLastTwoWayAvailability OBJECT-TYPE
    SYNTAX      Unsigned32 (0..100000)
    UNITS       "milli-percent"
    MAX-ACCESS  read-only
    STATUS      current
    DESCRIPTION
       "Availability /total time.
       "
    
    ::= { rcmefSoamLmLastStatsEntry 5 }  
        
rcmefSoamPmLastIngressBandwidth OBJECT-TYPE
    SYNTAX      Counter64 
    MAX-ACCESS  read-only
    STATUS      current
    DESCRIPTION
       "This object contains the Last Ingress bandwith.
       "
     
    ::= { rcmefSoamLmLastStatsEntry 6 } 
        
     --********************************************
 --DM last measurement interval information
 --********************************************   
rcmefSoamDmLastStatsTable OBJECT-TYPE
    SYNTAX      SEQUENCE OF RcmefSoamDmLastStatsEntry
    MAX-ACCESS  not-accessible
    STATUS      current
    DESCRIPTION
       "This table contains the results for last Measurement
        Intervals in a SOAM Loss Measurement session.

        Rows of this table object are created automatically
        by the SNMP Agent when the Loss Measurement session is running and a 
        Measurement Interval is completed.
        
        The rows and objects in this table are to be persistent upon reboot 
        or restart of a device.
       "
         
    ::= { rcmefSoamLastStatsGroup 2 }

rcmefSoamDmLastStatsEntry OBJECT-TYPE
    SYNTAX      RcmefSoamDmLastStatsEntry
    MAX-ACCESS  not-accessible
    STATUS      current
    DESCRIPTION
            "The conceptual row of mefSoamLmHistoryStatsTable"
    INDEX      {
               dot1agCfmMdIndex,
               dot1agCfmMaIndex, 
               dot1agCfmMepIdentifier, 
               rcSlaConfigOperId
               }
    ::= { rcmefSoamDmLastStatsTable 1 }

RcmefSoamDmLastStatsEntry ::= SEQUENCE {
    rcmefSoamPmLastFrameDelayTwoWay                Unsigned32,
    rcmefSoamPmLastIfdvTwoWay                      Unsigned32
    }  
    
rcmefSoamPmLastFrameDelayTwoWay OBJECT-TYPE
    SYNTAX      Unsigned32
    UNITS       "microseconds"
    MAX-ACCESS  read-only
    STATUS      current
    DESCRIPTION
       "This object contains the Last frame delay 
       in the twoway direction calculated by this MEP.      
       "
    ::= { rcmefSoamDmLastStatsEntry 1 }
 
rcmefSoamPmLastIfdvTwoWay OBJECT-TYPE
    SYNTAX      Unsigned32
    UNITS       "microseconds"
    MAX-ACCESS  read-only
    STATUS      current
    DESCRIPTION
       "This object contains the Last inter-frame delay variation 
       in the twoway direction calculated by this MEP. 
      "
    ::= { rcmefSoamDmLastStatsEntry 2 }
    
--rcSlaMaintenanceGroup
    
rcSlaMaintenanceEnable        OBJECT-TYPE
		SYNTAX      TruthValue
   		MAX-ACCESS  read-write
    	STATUS      current
    	DESCRIPTION
            "The Maintenance interval switch" 
        DEFVAL { false }
    	::= { rcSlaMaintenanceGroup 1 }

--rcSlaThresholdProfileGroup
   
-------------------------------------------------------------------------------------- 
--rcSlaThresholdProfileTable
--------------------------------------------------------------------------------------
  
   
rcSlaThresholdProfileTable  OBJECT-TYPE
    SYNTAX      SEQUENCE OF RcSlaThresholdProfileEntry
    MAX-ACCESS  not-accessible
    STATUS      current
    DESCRIPTION
        "This table contains sla  Threshold data."
    ::= { rcSlaThresholdProfileGroup 1 }

rcSlaThresholdProfileEntry   OBJECT-TYPE
    SYNTAX      RcSlaThresholdProfileEntry
    MAX-ACCESS  not-accessible
    STATUS      current
    DESCRIPTION
        "Information about the profile. This table will create
 	a profile which only contains its description, the 
 	Threshold of each Profile is defined in the associated 
 	table rcSlaThresholdCfgTable."
	INDEX        { rcSlaThresholdProfileIndex }    
    ::={ rcSlaThresholdProfileTable 1 }     
    
RcSlaThresholdProfileEntry ::= SEQUENCE {
        rcSlaThresholdProfileIndex				   Unsigned32(1..16),
    	rcSlaThresholdProfileDescription		   OCTET STRING (SIZE(0..32)),
    	rcSlaThresholdProfileRef                   Gauge32,
    	rcSlaThresholdProfileStatus		           RowStatus       
	    	    }

rcSlaThresholdProfileIndex       OBJECT-TYPE 
	SYNTAX      Unsigned32(1..16) 
	MAX-ACCESS  not-accessible
    STATUS      current
    DESCRIPTION
            "An index that uniquely identifies an entry in the sla
             profile table."
    ::= { rcSlaThresholdProfileEntry 1 }     
    
rcSlaThresholdProfileDescription OBJECT-TYPE
    SYNTAX          OCTET STRING (SIZE(0..32))
    MAX-ACCESS      read-create
    STATUS          current
    DESCRIPTION
            "Specifies description of profile." 
    ::= { rcSlaThresholdProfileEntry 2 }  
    
rcSlaThresholdProfileRef OBJECT-TYPE
    SYNTAX          Gauge32
    MAX-ACCESS      read-only
    STATUS          current
    DESCRIPTION
            "The value descrides how many times the profile is in use." 
    ::= { rcSlaThresholdProfileEntry 3 }

rcSlaThresholdProfileStatus OBJECT-TYPE
    SYNTAX          RowStatus
    MAX-ACCESS      read-create
    STATUS          current
    DESCRIPTION
            "the status of rcSlaThresholdProfileTable，
            This value is an operation number configured by user" 
    ::= { rcSlaThresholdProfileEntry 4 }

-------------------------------------------------------------------------------------- 
--rcSlaThresholdCfgTable
--------------------------------------------------------------------------------------
   
rcSlaThresholdCfgTable OBJECT-TYPE
    SYNTAX          SEQUENCE OF RcSlaThresholdCfgEntry 
    MAX-ACCESS      not-accessible
    STATUS          current
    DESCRIPTION
            "This table contains information about the profile"
    ::= { rcSlaThresholdProfileGroup 2 }

rcSlaThresholdCfgEntry OBJECT-TYPE
    SYNTAX          RcSlaThresholdCfgEntry
    MAX-ACCESS      not-accessible
    STATUS          current
    DESCRIPTION
            "Information about types of disposal of given protocols. The
            entries will be on a per profile, per protocol basis."
    INDEX           {
                        rcSlaThresholdProfileIndex,
                        rcServiceCosLabel
                    } 
    ::= { rcSlaThresholdCfgTable 1 }

RcSlaThresholdCfgEntry ::= SEQUENCE {
        rcSlaThresholdCfgFd                   Unsigned32 ,
        rcSlaThresholdCfgIfdv                 Unsigned32,
        rcSlaThresholdCfgFlr                  Unsigned32,   
        rcSlaThresholdCfgAvailbility          Unsigned32
}
   
rcSlaThresholdCfgFd       OBJECT-TYPE 
	SYNTAX      Unsigned32   
	UNITS       "microseconds"
	MAX-ACCESS  read-write
    STATUS      current
    DESCRIPTION
            "The Sla Frame delay Threshold"
    ::= { rcSlaThresholdCfgEntry 1 }     
    
rcSlaThresholdCfgIfdv OBJECT-TYPE
    SYNTAX          Unsigned32
    UNITS           "microseconds"
	MAX-ACCESS      read-write
    STATUS          current
    DESCRIPTION
            "The Ifdv Threshold " 
    ::= { rcSlaThresholdCfgEntry 2 }  
    
rcSlaThresholdCfgFlr OBJECT-TYPE
    SYNTAX          Unsigned32 
    UNITS           "milli-percent"
    MAX-ACCESS      read-write
    STATUS          current
    DESCRIPTION
            "The Flr Threshold ." 
    ::= { rcSlaThresholdCfgEntry 3 }    
    
rcSlaThresholdCfgAvailbility OBJECT-TYPE
    SYNTAX          Unsigned32 
    UNITS           "milli-percent"
    MAX-ACCESS      read-write
    STATUS          current
    DESCRIPTION
            "The Availbility Threshold ." 
    ::= { rcSlaThresholdCfgEntry 4 }


END

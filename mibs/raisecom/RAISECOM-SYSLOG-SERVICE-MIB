-- =======================================================================
-- Syslog Service info 
--
-- Version 0.1 Created 2003.12.17 by GONGGUIDONG
-- This version of MIB is created just for the use of Network Management Systems
-- display and config the syslog service.
-- log:
-- bug6602, redefine LogFacility as per RFC5424 by liujianwen 20110518
-- change raisecomSyslogService from OBJECT-TYPE to MODULE-IDENTITY  by gongguidong  20040205
-- change raisecomSyslogDirection from read-write to read-only   by gongguidong  20040205 
--
-- Copyright(c) 2003-2005 by RAISECOM TECH, Ltd.
-- =======================================================================

--RAISECOM-SYSLOG-SERVICE-MIB
--2003/2/17
-- This MIB provides a means to gather syslog messages generated
-- by the RaisecomOS

-- Terminology:
-- Various textual messages are generated by the RaisecomOS.  The RaisecomOS
-- can be configured such that these messages are sent to a "syslog"
-- server.   These messages are hereupon referred to as "syslog
-- messages" in this document. Note: Messages generated as a result 
-- of entering CLI debug commands are not made available via the SNMP
-- at this time.
-- 
-- All syslog messages have the following attributes:
--	timestamp (optional), facility name (where the message came
--	from), severity, message name, message text
--
-- The following example is often seen:
--	%SYS-5-CONFIG_I: Configured from console ...
-- where facility=SYS, severity=5, message name=CONFIG_I
-- ===========================================================================
-- RAISECOM syslog service objects
--修改信息：
--2012-09-14,ghy,ESW00001109,修改了节点raisecomLogServerIpAddress的数据类型为InetAddress

RAISECOM-SYSLOG-SERVICE-MIB    DEFINITIONS ::= BEGIN

	IMPORTS
		MODULE-IDENTITY,
		OBJECT-TYPE,
		InetAddress
			FROM INET-ADDRESS-MIB
		RowStatus,
		TruthValue
			FROM SNMPv2-TC   
		EnableVar
			FROM SWITCH-TC
		raisecomAgent		
			FROM RAISECOM-BASE-MIB;
	
--  Syslog Service MIB


	raisecomSyslogService	MODULE-IDENTITY
        LAST-UPDATED 	"200412210000Z"
        ORGANIZATION 	"RAISECOM TECH, Ltd."
        CONTACT-INFO 	"www.raisecom.com"
        DESCRIPTION  	
            "The MIB module defining objects for Syslog Service"
    ::= { raisecomAgent 4 }


-- Textual Conventions

	SyslogSeverity ::= TEXTUAL-CONVENTION
		STATUS	current
		DESCRIPTION
	   	    	"The severity of a syslog message.  The enumeration
				values are equal to the values that syslog uses + 1.
				For example, with syslog, emergency=0."
		SYNTAX	INTEGER {
			emergency(1),
			alert(2),
			critical(3),
			error(4),
			warning(5),
			notice(6),
			info(7),
			debug(8)
		}
		    
	LogFacility ::= TEXTUAL-CONVENTION
		STATUS	current
		DESCRIPTION
	   	    	"The facility of a syslog message.  The enumeration
				values are equal to the values that syslog uses + 1.
				For example, with syslog, auth=4."
		SYNTAX  INTEGER {
			kern(1),
			user(2),
			mail(3),
			daemon(4),
			auth(5),
			syslog(6),
			lpr(7),
			news(8),
			uucp(9),
			cron(10),
			security(11),
			ftp(12),
			ntp(13),
			audit(14),
			alert(15),
			clock(16),
			local0(17),
			local1(18),
			local2(19),
			local3(20),
			local4(21),
			local5(22),
			local6(23),
			local7(24)
		}
				
raisecomSyslogMibObjects OBJECT IDENTIFIER ::= { raisecomSyslogService 1 }

-- Subgroups 供以后扩展使用

raisecomLogBasic	OBJECT IDENTIFIER ::= { raisecomSyslogMibObjects 1 }
raisecomLogServer	OBJECT IDENTIFIER ::= { raisecomSyslogMibObjects 2 }
raisecomDebug		OBJECT IDENTIFIER ::= { raisecomSyslogMibObjects 3 }
raisecomLogTrapGroup	OBJECT IDENTIFIER ::= { raisecomSyslogMibObjects 4 }


	-- raisecomLogBasic
	    -- scalars
		raisecomLogEnable OBJECT-TYPE
		    SYNTAX EnableVar
			ACCESS read-write
			STATUS current
			DESCRIPTION
					"The administration status of the syslog function is enable or disable."
				::= { raisecomLogBasic 1 }     	
		 
	 	raisecomLogRateLimit OBJECT-TYPE	 	
		    SYNTAX INTEGER (0..10000)
			ACCESS read-write
			STATUS current
			DESCRIPTION
					"The Rate Limit for syslog."
				::= { raisecomLogBasic 2 }  
				
		raisecomLogDropMessages OBJECT-TYPE	 	
			SYNTAX INTEGER (0..2147483647) 
			ACCESS read-only
			STATUS current
			DESCRIPTION
					"The number of log messages that syslog droped."
				::= { raisecomLogBasic 3 }
		
	    raisecomLogConsoleLogedMessages OBJECT-TYPE	 	
			SYNTAX INTEGER (0..2147483647)
			ACCESS read-only
			STATUS deprecated
			DESCRIPTION
					"The number of messages that syslog loged to console."
				::= { raisecomLogBasic 4 }
				
		raisecomLogMonitorMessages OBJECT-TYPE	 	
			SYNTAX INTEGER (0..2147483647)
			ACCESS read-only
			STATUS deprecated
			DESCRIPTION
					"The number of messages that syslog loged to Monitor."
				::= { raisecomLogBasic 5 }   
				
		raisecomLogTimeStamp 	OBJECT-TYPE	 	
			SYNTAX INTEGER {
						no-timestamp(1),
						date-timestamp(2),
						up-timestamp(3)
						}
			ACCESS read-write
			STATUS current  
			DESCRIPTION
					"
					no-timestamp   no time stamp
					date-timestamp  : APR-26-2004 17:27:45 
					up-timestamp 17:27:45 time from start up
					"      
			DEFVAL { date-timestamp }
					::= { raisecomLogBasic 6 }	  
					
        raisecomLogDebugTimeStamp OBJECT-TYPE	 	
			SYNTAX INTEGER {
						no-timestamp(1),
						date-timestamp(2),
						up-timestamp(3)
						}
			ACCESS read-write
			STATUS current  
			DESCRIPTION
					"
					no-timestamp   no time stamp
					date-timestamp  : APR-26-2004 17:27:45 
					up-timestamp 17:27:45 time from start up
					"      
			DEFVAL { no-timestamp }
				::= { raisecomLogBasic 7 }	 
			
		raisecomLogHistoryEnable OBJECT-TYPE	 	
			SYNTAX EnableVar
			ACCESS read-write
			STATUS current
			DESCRIPTION
				"The administration status of the syslog messages to history table is enable or disable."
				::= { raisecomLogBasic 8 }
				
		raisecomLogHistorySize OBJECT-TYPE	 	
			SYNTAX INTEGER (1..500)
			ACCESS read-write
			STATUS current
			DESCRIPTION
				"Size of the history table." 
			DEFVAL { 1 }
				::= { raisecomLogBasic 9 }
											
		raisecomLogBufferSize  OBJECT-TYPE	 	
			SYNTAX INTEGER (4..256)
			ACCESS read-write
			STATUS current
			DESCRIPTION
					"Size of log buffer."  
			DEFVAL { 4 }
				::= { raisecomLogBasic 10 }
		
		raisecomLogSequenceNumEnable OBJECT-TYPE	 	
			SYNTAX EnableVar
			ACCESS read-write
			STATUS current
			DESCRIPTION
				"The administration status of the syslog message sequence number show is enable or disable."
				::= { raisecomLogBasic 11 }  
				
		raisecomDebugModuleLevel OBJECT-TYPE
		  	SYNTAX	 INTEGER {
	                          none(1),
	                          high(2),
                              normal(3),
	                          low(4)
                             } 	
			ACCESS read-write
			STATUS current
			DESCRIPTION
				"The debug level of syslog messages." 
			DEFVAL { none }
			    ::= { raisecomLogBasic 12 }  

		raisecomLogDebugDropMessages OBJECT-TYPE	 	
			SYNTAX INTEGER (0..2147483647) 
			ACCESS read-only
			STATUS current
			DESCRIPTION
					"The number of debug messages that syslog droped."
				::= { raisecomLogBasic 13 }     

		raisecomLogBufferClear OBJECT-TYPE	 	
			SYNTAX TruthValue 
			ACCESS read-write
			STATUS current
			DESCRIPTION
					"This object instructs the management entity to delete the whole syslog messages in syslog buffer."
				::= { raisecomLogBasic 14 }
     
        raisecomLogConfig OBJECT-TYPE
		    SYNTAX EnableVar
			ACCESS read-write
			STATUS current
			DESCRIPTION
					"The administration status of the logging config function is enable or disable."
				::= { raisecomLogBasic 15 } 
				
        raisecomLogConfigLevel OBJECT-TYPE
		    SYNTAX SyslogSeverity
			ACCESS read-write
			STATUS current
			DESCRIPTION
					"The severity of log messages which is generated from user command."
			DEFVAL { info }
        	    ::= { raisecomLogBasic 16 }  	
		-- raisecomLogDestinationTable
		
        raisecomLogDestinationTable OBJECT-TYPE
            SYNTAX SEQUENCE OF RaisecomLogDestinationEntry 
            ACCESS not-accessible
            STATUS current
            DESCRIPTION
                "A list of destination entries."
                ::= { raisecomLogBasic 17 }

        raisecomLogDestinationEntry OBJECT-TYPE
            SYNTAX RaisecomLogDestinationEntry 
            ACCESS not-accessible
            STATUS current
            DESCRIPTION
                 "The syslog destination list group infomation entry."
            INDEX { raisecomLogDestIndex }
              	::= { raisecomLogDestinationTable 1 }  
              	
        RaisecomLogDestinationEntry ::= SEQUENCE {
              		raisecomLogDestIndex         INTEGER,
              		raisecomLogDestEnable	     EnableVar,
              		raisecomLogDestServrity	     SyslogSeverity,
					raisecomLogDestDiscriminator INTEGER, 
					raisecomLogDestLoggedMessages INTEGER,
					raisecomLogDestDropMessages  INTEGER
          	        }
                
        raisecomLogDestIndex OBJECT-TYPE
            SYNTAX INTEGER {
                            buffer(1),
                            console(2),
                            trap(3),
                            file(4)
                           }
		    ACCESS not-accessible
			STATUS current
			DESCRIPTION
				"This object index of syslog destination entry."
				::= { raisecomLogDestinationEntry 1 }

		raisecomLogDestEnable OBJECT-TYPE
			SYNTAX EnableVar				
			ACCESS read-write
			STATUS current
			DESCRIPTION
				"The administration status of the syslog destination is enable or disable."
				::= { raisecomLogDestinationEntry 2 }

		raisecomLogDestServrity OBJECT-TYPE
			SYNTAX SyslogSeverity		
			ACCESS read-write
			STATUS current
			DESCRIPTION
				"The severity of log messages which will be sent to syslog destination."
				::= { raisecomLogDestinationEntry 3 } 
				
		raisecomLogDestDiscriminator OBJECT-TYPE
			SYNTAX INTEGER (1..5)		
			ACCESS read-write
			STATUS current
			DESCRIPTION
				"The discriminator associated with the specified destination."
				::= { raisecomLogDestinationEntry 4 } 
		
        raisecomLogDestLoggedMessages OBJECT-TYPE
			SYNTAX INTEGER 		
			ACCESS read-write
			STATUS current
			DESCRIPTION
				"The count of messages that sent to the destination."
				::= { raisecomLogDestinationEntry 5 }  
				
        raisecomLogDestDropMessages OBJECT-TYPE
			SYNTAX INTEGER 		
			ACCESS read-write
			STATUS current
			DESCRIPTION
				"The count of messages that droped by the destination."
				::= { raisecomLogDestinationEntry 6 }  
				
	    -- raisecomLogDiscriminatorTable
	    
	    raisecomLogDiscriminatorTable OBJECT-TYPE
            SYNTAX SEQUENCE OF RaisecomLogDiscriminatorEntry 
            ACCESS not-accessible
            STATUS current
            DESCRIPTION
                "A list of discriminator entries."
              	::= { raisecomLogBasic 18 }

		raisecomLogDiscriminatorEntry OBJECT-TYPE
            SYNTAX RaisecomLogDiscriminatorEntry 
            ACCESS not-accessible
            STATUS current
            DESCRIPTION
                "The syslog discriminator list group infomation entry."
            INDEX { raisecomLogDiscriminatorIndex }
              	::= { raisecomLogDiscriminatorTable 1 }  
              	
        RaisecomLogDiscriminatorEntry ::= SEQUENCE {
              		raisecomLogDiscriminatorIndex        INTEGER,
              		raisecomLogDiscriminatorFacilityAct	 INTEGER,
              		raisecomLogDiscriminatorFacilityStr	 OCTET  STRING,
					raisecomLogDiscriminatorMnemonicsAct INTEGER, 
					raisecomLogDiscriminatorMnemonicsStr OCTET  STRING,
					raisecomLogDiscriminatorMsgbodyAct   INTEGER,
					raisecomLogDiscriminatorMsgbodyStr   OCTET  STRING
          	        }
                
        raisecomLogDiscriminatorIndex OBJECT-TYPE
			SYNTAX INTEGER (1..5)	    
			ACCESS not-accessible
			STATUS current
			DESCRIPTION
				"This object index of syslog discriminator entry."
				::= { raisecomLogDiscriminatorEntry 1 }

		raisecomLogDiscriminatorFacilityAct OBJECT-TYPE
			SYNTAX INTEGER {
			                none(1),
			                drops(2),
                            includes(3)
			               } 					
			ACCESS read-write
			STATUS current
			DESCRIPTION
				"The action for facility filter."
				::= { raisecomLogDiscriminatorEntry 2 }

		raisecomLogDiscriminatorFacilityStr OBJECT-TYPE
			SYNTAX OCTET  STRING (SIZE(1..20))		
			ACCESS read-write
			STATUS current
			DESCRIPTION
				"The string content for facility filter."
				::= { raisecomLogDiscriminatorEntry 3 } 
				
		raisecomLogDiscriminatorMnemonicsAct OBJECT-TYPE
			SYNTAX INTEGER {
			                none(1),
			                drops(2),
                            includes(3)			               
                           } 			
			ACCESS read-write
			STATUS current
			DESCRIPTION
				"The action for mnemonics filter."
				::= { raisecomLogDiscriminatorEntry 4 } 
		
        raisecomLogDiscriminatorMnemonicsStr OBJECT-TYPE
			SYNTAX OCTET  STRING (SIZE(1..30))		
			ACCESS read-write
			STATUS current
			DESCRIPTION
				"The string content for mnemonics filter."
				::= { raisecomLogDiscriminatorEntry 5 }  
				
        raisecomLogDiscriminatorMsgbodyAct OBJECT-TYPE
			SYNTAX INTEGER {
			                none(1),
			                drops(2),
                            includes(3)
			               } 	 		
			ACCESS read-write
			STATUS current
			DESCRIPTION
				"The action for message body filter."
				::= { raisecomLogDiscriminatorEntry 6 }  

	    raisecomLogDiscriminatorMsgbodyStr OBJECT-TYPE
			SYNTAX OCTET  STRING (SIZE(1..64)) 		
			ACCESS read-write
			STATUS current
			DESCRIPTION
				"The string content for message body filter."
				::= { raisecomLogDiscriminatorEntry 7 } 
	
		-- raisecomLogHistoryTable
		
		raisecomLogHistoryTable OBJECT-TYPE
            SYNTAX SEQUENCE OF RaisecomLogHistoryEntry 
            ACCESS not-accessible
            STATUS current
            DESCRIPTION
                "A list of history entries."
              	::= { raisecomLogBasic 19 }

		raisecomLogHistoryEntry OBJECT-TYPE
            SYNTAX RaisecomLogHistoryEntry 
            ACCESS not-accessible
            STATUS current
            DESCRIPTION
                "The syslog history list group infomation entry."
            INDEX { raisecomLogHistIndex }
              	::= { raisecomLogHistoryTable 1 }  
              	
        RaisecomLogHistoryEntry ::= SEQUENCE {
              		raisecomLogHistIndex       INTEGER,
              		raisecomLogHistFacility	   OCTET  STRING,
              		raisecomLogHistSeverity	   SyslogSeverity,
					raisecomLogHistMnemonics   OCTET  STRING, 
					raisecomLogHistMsgbody     OCTET  STRING,
					raisecomLogHistTimestamp   INTEGER
          	        }
                
        raisecomLogHistIndex OBJECT-TYPE
			SYNTAX INTEGER 	    
			ACCESS not-accessible
			STATUS current
			DESCRIPTION
				"This object index of syslog history entry."
				::= { raisecomLogHistoryEntry 1 }

		raisecomLogHistFacility OBJECT-TYPE
			SYNTAX OCTET  STRING (SIZE(1..20))				
			ACCESS read-only
			STATUS current
			DESCRIPTION
				"The facility of message sent to hisstory table."
				::= { raisecomLogHistoryEntry 2 }

		raisecomLogHistSeverity OBJECT-TYPE
			SYNTAX SyslogSeverity		
			ACCESS read-only
			STATUS current
			DESCRIPTION
				"The severity of message sent to hisstory table."
				::= { raisecomLogHistoryEntry 3 } 
				
		raisecomLogHistMnemonics OBJECT-TYPE
			SYNTAX OCTET  STRING (SIZE(1..30))			
			ACCESS read-only
			STATUS current
			DESCRIPTION
				"The mnemonics of message sent to hisstory table."
				::= { raisecomLogHistoryEntry 4 } 
		
        raisecomLogHistMsgbody OBJECT-TYPE
			SYNTAX OCTET  STRING (SIZE(1..255)) 		
			ACCESS read-only
			STATUS current
			DESCRIPTION
				"The content of syslog message."
				::= { raisecomLogHistoryEntry 5 }  
				
        raisecomLogHistTimestamp OBJECT-TYPE
			SYNTAX INTEGER	 		
			ACCESS read-only
			STATUS current
			DESCRIPTION
				"The time stamp type of history entry."
				::= { raisecomLogHistoryEntry 6 }  
		
	-- The raisecom Syslog Service Server Control group
  	--
  	-- The raisecom syslog service server control contains 
   	-- configing syslog service logto server setting.      
	-- The raisecomSyslogServiceServerControl Table   	              	 
	             
	    raisecomLogMaxNumberOfLogServer OBJECT-TYPE
            SYNTAX INTEGER 
            ACCESS read-only
            STATUS current
            DESCRIPTION
                "The Max Number of syslog server "
                ::= { raisecomLogServer 1 }

	    raisecomLogServerNumber OBJECT-TYPE
            SYNTAX INTEGER 
            ACCESS read-only
            STATUS current
            DESCRIPTION
                "The Number of syslog server that has been configured "
              	::= { raisecomLogServer 2 }

	    raisecomLogServerTable OBJECT-TYPE
            SYNTAX SEQUENCE OF RaisecomLogServerEntry 
            ACCESS not-accessible
            STATUS current
            DESCRIPTION
                "A list of raisecomSyslogServiceServer entries."
              	::= { raisecomLogServer 3 }

	    raisecomLogServerEntry OBJECT-TYPE
            SYNTAX RaisecomLogServerEntry 
            ACCESS not-accessible
            STATUS current
            DESCRIPTION
                  	"The syslog service server list group infomation entry."
            INDEX { raisecomLogServerIpAddress }
              	::= { raisecomLogServerTable 1 }

	    RaisecomLogServerEntry ::= SEQUENCE {
              		raisecomLogServerIpAddress	    InetAddress,
              		raisecomLogServerPort	        INTEGER,
              		raisecomLogFacility	            LogFacility,
					raisecomLogServerMaxSeverity    SyslogSeverity,  
					raisecomLogServerRowStatus	    RowStatus,
					raisecomLogServerLoggedMessages INTEGER,
					raisecomLogServerDropMessages   INTEGER,
					raisecomLogServerDiscriminator	INTEGER				 					
          	        }
              
	    raisecomLogServerIpAddress OBJECT-TYPE
            SYNTAX InetAddress
            ACCESS not-accessible
            STATUS current
            DESCRIPTION
                  	"The value of this object is the IpAddress of the server to which
                  	the syslog messages will be sent."
              	::= { raisecomLogServerEntry 1 }

	    raisecomLogServerPort OBJECT-TYPE
            SYNTAX INTEGER (1..65535)
            ACCESS read-only
            STATUS current
            DESCRIPTION
                  	"The value of this object is the port of the server to which
                  	the syslog messages will be sent."
              	::= { raisecomLogServerEntry 2 }

	    raisecomLogFacility OBJECT-TYPE
            SYNTAX LogFacility
            ACCESS read-create
            STATUS current
            DESCRIPTION
                  	"The facility specifies the subsystem that produced the message, i.e. 
                  	all mail programs log with the mail facility (LOG_MAIL) if they log 
                  	using syslog.The default value is local7."
              	::= { raisecomLogServerEntry 3 }

	    raisecomLogServerMaxSeverity OBJECT-TYPE
	       	SYNTAX SyslogSeverity			
	       	ACCESS read-create
			STATUS current
			DESCRIPTION
	            "The max severity of messages which will be sent to syslog host.
	            The default value is info ."
	            ::= { raisecomLogServerEntry 4 }  
	            
	    raisecomLogServerRowStatus 	OBJECT-TYPE
	  	    SYNTAX RowStatus 	
		    ACCESS read-create
		    STATUS current
		    DESCRIPTION
			    "This object indicates the status of this entry."
		        ::= { raisecomLogServerEntry 5 }    
          	
        raisecomLogServerLoggedMessages OBJECT-TYPE
	       	SYNTAX INTEGER			
	       	ACCESS read-only
			STATUS current
			DESCRIPTION
	            "The number of log messages which send to syslog server."
	            ::= { raisecomLogServerEntry 6 } 
	              	
        raisecomLogServerDropMessages OBJECT-TYPE
	       	SYNTAX INTEGER			
	       	ACCESS read-only
			STATUS current
			DESCRIPTION
	            "The number of log messages which droped by syslog server."
	            ::= { raisecomLogServerEntry 7 }   
	              	
        raisecomLogServerDiscriminator OBJECT-TYPE
	       	SYNTAX INTEGER			
	       	ACCESS read-create
			STATUS current
			DESCRIPTION
	            "The discriminator associated with the specified syslog server."
	            ::= { raisecomLogServerEntry 8 }   		
		
    --raisecomDebug
	
	    raisecomDebugTable OBJECT-TYPE
              	SYNTAX SEQUENCE OF RaisecomDebugEntry 
              	ACCESS not-accessible
              	STATUS current
              	DESCRIPTION
                  	"A list of raisecom Debug  entries."
              	    ::= { raisecomDebug 1 }


	    raisecomDebugEntry OBJECT-TYPE
              	SYNTAX RaisecomDebugEntry 
              	ACCESS not-accessible
              	STATUS current
              	DESCRIPTION
                  	"The debug  infomation entry."
              	INDEX { raisecomDebugIndex }
              	    ::= { raisecomDebugTable 1 }

	    RaisecomDebugEntry ::= SEQUENCE {
              		raisecomDebugIndex		    INTEGER,
              		raisecomDebugModuleName  	OCTET STRING,
              		raisecomDebugModuleEnable	EnableVar,
              		raisecomDebugMsgName    OCTET STRING
          	        }

	    raisecomDebugIndex OBJECT-TYPE
		  	SYNTAX INTEGER 	
			ACCESS not-accessible
			STATUS current
			DESCRIPTION
				"This object index of system debug entry."
			    ::= { raisecomDebugEntry 1 }
		
	    raisecomDebugModuleName OBJECT-TYPE
		  	SYNTAX OCTET STRING (SIZE (0..32))
			ACCESS read-write
			STATUS current
			DESCRIPTION
				"This name of debugging module ."
			    ::= { raisecomDebugEntry 2 }

	    raisecomDebugModuleEnable OBJECT-TYPE
		  	SYNTAX EnableVar
			ACCESS read-write
			STATUS current
			DESCRIPTION
				"This switch of specific module ."
			    ::= { raisecomDebugEntry 3 }
						
        raisecomDebugMsgName OBJECT-TYPE
		  	SYNTAX	 OCTET STRING (SIZE (0..30))			
		  	ACCESS read-write
			STATUS current
			DESCRIPTION
				"The name of syslog debug message." 
			    ::= { raisecomDebugEntry 4 }  
			    
	-- raisecomLogTrapGroup
        raisecomLogTrap NOTIFICATION-TYPE
	        OBJECTS {raisecomLogHistFacility, raisecomLogHistSeverity, raisecomLogHistMnemonics, raisecomLogHistMsgbody, raisecomLogHistTimestamp }
	        STATUS  current
	        DESCRIPTION
	             "Syslog message trap."
	        ::= { raisecomLogTrapGroup 1 }
                         
END

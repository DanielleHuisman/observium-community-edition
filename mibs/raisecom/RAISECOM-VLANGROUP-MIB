--MibName=rcVlanGroup
-- *****************************************************************
-- RAISECOM-VLANGROUP-MIB.mib:   Raisecom VlanGroup MIB file 
--
-- Copyright (c) 1994-2004 by Raisecom, Inc.
-- All rights reserved.
--
-- *****************************************************************
RAISECOM-VLANGROUP-MIB  DEFINITIONS ::= BEGIN

IMPORTS
        iscomSwitch                       FROM RAISECOM-BASE-MIB 
        rcQinQ                            FROM RAISECOM-QINQ-MIB
        RowStatus,TruthValue              FROM SNMPv2-TC
        Vlanset, PortList, EnableVar      FROM SWITCH-TC
        rcPortIndex          		      FROM SWITCH-SYSTEM-MIB;
 
rcVlanGroup  MODULE-IDENTITY
    LAST-UPDATED   "200901190000Z"
    ORGANIZATION   "Raisecom, Inc."
    CONTACT-INFO  
                "       Raise Systems
                        
                Postal: Beijing,
                        China

                   Tel: 86-010-82884499

                E-mail: wangjing_rj@raisecom.com"
    DESCRIPTION
        "This MIB module defines objects to Vlan Group "
        REVISION   "200901190000Z"
        DESCRIPTION
            "The initial revision of this MIB."
        ::={ rcQinQ 2 }   

-- -------------------------------------------------------------
-- groups in the rcQinQ MIB     rcVlanGroupCfg
-- -------------------------------------------------------------
rcVlanGroupCfg                OBJECT IDENTIFIER ::= { rcVlanGroup 1 }

rcVlanGroupCfgTable           OBJECT-TYPE
        SYNTAX      SEQUENCE OF RcVlanGroupCfgEntry
        MAX-ACCESS  not-accessible
        STATUS      current
        DESCRIPTION
            "Vlan group port table"
        ::= { rcVlanGroupCfg 1 }

rcVlanGroupCfgEntry       OBJECT-TYPE
        SYNTAX      RcVlanGroupCfgEntry
        MAX-ACCESS  not-accessible
        STATUS      current
        DESCRIPTION
            "An entry in the rcVlanGroupCfgTable."
	    INDEX        { rcVlanGroupCfgIndex }    
        ::={ rcVlanGroupCfgTable 1 }
    
        RcVlanGroupCfgEntry ::= SEQUENCE
        {
    	    rcVlanGroupCfgIndex	            INTEGER,
    	    rcVlanGroupCfgPeVlanList        Vlanset,
    	    rcVlanGroupCfgCeVlanList        Vlanset,
    	    rcVlanGroupCfgPortList          PortList,
    	    rcVlanGroupCfgCosValue          INTEGER,
    	    rcVlanGroupCfgCosOverride       EnableVar,
    	    rcVlanGroupCfgCosQueue          EnableVar,
    	    rcVlanGroupCfgRateLimit         INTEGER,
    	    rcVlanGroupCfgRateBurst         INTEGER, 
    	    rcVlanGroupCfgRateOverMode      INTEGER,
    	    rcVlanGroupCfgRateMarkdownValue INTEGER,
    	    rcVlanGroupCfgDirectMode        INTEGER,
    	    rcVlanGroupCfgStatisticsEnable  EnableVar,
    	    rcVlanGroupCfgStatus            EnableVar, 
    	    rcVlanGroupCfgStatClear         TruthValue,
    	    rcVlanGroupCfgRowStatus         RowStatus
        } 
 
rcVlanGroupCfgIndex    OBJECT-TYPE
        SYNTAX        INTEGER (1..65535)
        MAX-ACCESS    not-accessible
        STATUS        current
        DESCRIPTION
            "Vlan group id, the index of vlan group table."
        ::= { rcVlanGroupCfgEntry 1 }   

rcVlanGroupCfgPeVlanList          OBJECT-TYPE
        SYNTAX        Vlanset
        MAX-ACCESS    read-create
        STATUS        current
        DESCRIPTION
            "The provider vlan ID of vlan group."
        ::= { rcVlanGroupCfgEntry 2 }
        
rcVlanGroupCfgCeVlanList          OBJECT-TYPE
        SYNTAX        Vlanset
        MAX-ACCESS    read-create
        STATUS        current
        DESCRIPTION
            "The customer vlan ID of vlan group."
        ::= { rcVlanGroupCfgEntry 3 }
        
rcVlanGroupCfgPortList            OBJECT-TYPE
        SYNTAX        PortList
        MAX-ACCESS    read-create
        STATUS        current
        DESCRIPTION
            "The portlist of the vlan group enable."
        ::= { rcVlanGroupCfgEntry 4 }

rcVlanGroupCfgCosValue             OBJECT-TYPE
        SYNTAX        INTEGER (0..8)
        MAX-ACCESS    read-create
        STATUS        current
        DESCRIPTION
            "The cos value."
        ::= { rcVlanGroupCfgEntry 5 }
        
rcVlanGroupCfgCosOverride          OBJECT-TYPE
        SYNTAX        EnableVar
        MAX-ACCESS    read-create
        STATUS        current
        DESCRIPTION
            "Whether override the default cos or not."
        ::= { rcVlanGroupCfgEntry 6 }

rcVlanGroupCfgCosQueue            OBJECT-TYPE
        SYNTAX        EnableVar
        MAX-ACCESS    read-create
        STATUS        current
        DESCRIPTION
            "Whether use the cos to queue or not."
        ::= { rcVlanGroupCfgEntry 7 } 

rcVlanGroupCfgRateLimit    OBJECT-TYPE
        SYNTAX        INTEGER  (0..1048576)       
        UNITS		  "kbps"
        MAX-ACCESS    read-create
        STATUS        current
        DESCRIPTION
            "The ingress rate( kbps) value of the vlan group."
        ::= { rcVlanGroupCfgEntry 8 }

rcVlanGroupCfgRateBurst    OBJECT-TYPE
        SYNTAX        INTEGER  (0..512)   
        UNITS		  "kB"
        MAX-ACCESS    read-create
        STATUS        current
        DESCRIPTION
            "The ingress burst( kB) value of the vlan group."
        ::= { rcVlanGroupCfgEntry 9 }

rcVlanGroupCfgRateOverMode    OBJECT-TYPE
        SYNTAX        INTEGER
                      {
                      drop(1),
                      modify-dscp(2),
                      modify-queue(3)
                      }
        MAX-ACCESS    read-create
        STATUS        current
        DESCRIPTION
            "The process mode of exceed vlan group rate limit value packets."
        ::= { rcVlanGroupCfgEntry 10 }

rcVlanGroupCfgRateMarkdownValue    OBJECT-TYPE
        SYNTAX        INTEGER  (0..65535)
        MAX-ACCESS    read-create
        STATUS        current
        DESCRIPTION
            "The value of DSCP when exceed vlan group rate limit value process
             mode is modify-dscp, or the number of queue when exceed vlan group
             rate limit value process mode is modify-queue."
        ::= { rcVlanGroupCfgEntry 11 }

rcVlanGroupCfgDirectMode    OBJECT-TYPE
        SYNTAX        INTEGER 
                      {
                      ingress(1),
                      egress(2)
                      }       
        MAX-ACCESS    read-create
        STATUS        current
        DESCRIPTION
            "The direction of vlan group."
        ::= { rcVlanGroupCfgEntry 12 }

rcVlanGroupCfgStatisticsEnable    OBJECT-TYPE
        SYNTAX        EnableVar
        MAX-ACCESS    read-create
        STATUS        current
        DESCRIPTION
            "Enable or disable vlan group statistcis."
        ::= { rcVlanGroupCfgEntry 13 }
       
rcVlanGroupCfgStatus             OBJECT-TYPE
        SYNTAX        EnableVar
        MAX-ACCESS    read-create
        STATUS        current
        DESCRIPTION
            "Enable or disable vlan group."
        ::= { rcVlanGroupCfgEntry 14 }        
        
rcVlanGroupCfgStatClear         OBJECT-TYPE
        SYNTAX        TruthValue       
        MAX-ACCESS    read-create
        STATUS        current
        DESCRIPTION
            "Clear statistics information."
        ::= { rcVlanGroupCfgEntry 15 }
        
rcVlanGroupCfgRowStatus          OBJECT-TYPE
        SYNTAX      RowStatus
        MAX-ACCESS  read-create
        STATUS      current
        DESCRIPTION
            "Operation status of this table entry."
        ::= { rcVlanGroupCfgEntry 16 }

-- -------------------------------------------------------------
-- groups in the rcQinQ MIB     rcVlanGroupStat
-- -------------------------------------------------------------
rcVlanGroupStat               OBJECT IDENTIFIER ::= { rcVlanGroup 2 }

rcVlanGroupStatPortTable          OBJECT-TYPE
        SYNTAX      SEQUENCE OF RcVlanGroupStatPortEntry
        MAX-ACCESS  not-accessible
        STATUS      current
        DESCRIPTION
            "Vlan group port statistics table."
        ::= { rcVlanGroupStat 1 }

rcVlanGroupStatPortEntry       OBJECT-TYPE
        SYNTAX      RcVlanGroupStatPortEntry
        MAX-ACCESS  not-accessible
        STATUS      current
        DESCRIPTION
            "An entry in the rcVlanGroupStatTable."
	    INDEX        { rcVlanGroupCfgIndex, rcPortIndex, rcVlanGroupStatisticsPeVid, rcVlanGroupStatisticsCeVid }    
        ::={ rcVlanGroupStatPortTable 1 }
    
        RcVlanGroupStatPortEntry ::= SEQUENCE
        {                                          
            rcVlanGroupStatisticsPeVid         INTEGER,
            rcVlanGroupStatisticsCeVid         INTEGER,
            rcVlanGroupStatisticsType          INTEGER,
    	    rcVlanGroupStatisticsInFrames      Counter64,
    	    rcVlanGroupStatisticsOutFrames 	   Counter64,
    	    rcVlanGroupStatisticsInDiscards    Counter64,
    	    rcVlanGroupStatisticsInAllBytes    Counter64,
    	    rcVlanGroupStatisticsOutAllBytes   Counter64,
    	    rcVlanGroupStatisticsInAllDiscardsBytes  Counter64    	    
        } 

rcVlanGroupStatisticsPeVid    OBJECT-TYPE
        SYNTAX        INTEGER (1..4094)      
        MAX-ACCESS    not-accessible
        STATUS        current
        DESCRIPTION
            "The provider vlan ID, index of table."
        ::= { rcVlanGroupStatPortEntry 1 }

rcVlanGroupStatisticsCeVid    OBJECT-TYPE
        SYNTAX        INTEGER (1..4094)      
        MAX-ACCESS    not-accessible
        STATUS        current
        DESCRIPTION
            "The number of valid frames received by this port from its
             segment that were classified as belonging to the VLAN of 
             VLAN group."
        ::= { rcVlanGroupStatPortEntry 2 }

rcVlanGroupStatisticsType    OBJECT-TYPE
        SYNTAX        INTEGER 
                      {
                      stat-pkts(1),
                      stat-bytes(2)
                      }    
        MAX-ACCESS    read-only
        STATUS        current
        DESCRIPTION
            "The unit of statistics data by this port of VLAN group."
        ::= { rcVlanGroupStatPortEntry 3 }   

rcVlanGroupStatisticsInFrames    OBJECT-TYPE
        SYNTAX        Counter64       
        MAX-ACCESS    read-only
        STATUS        current
        DESCRIPTION
            "The number of valid frames transmitted by this port to its
             segment from the local forwarding process for the VLAN of 
             VLAN group."
        ::= { rcVlanGroupStatPortEntry 4 }   
        
rcVlanGroupStatisticsOutFrames    OBJECT-TYPE
        SYNTAX        Counter64       
        MAX-ACCESS    read-only
        STATUS        current
        DESCRIPTION
            "The statistics of packets in egress."
        ::= { rcVlanGroupStatPortEntry 5 }

rcVlanGroupStatisticsInDiscards    OBJECT-TYPE
        SYNTAX        Counter64       
        MAX-ACCESS    read-only
        STATUS        current
        DESCRIPTION
            "The number of valid frames received by this port from its 
             segment that were classified as belonging to the VLAN of 
             VLAN group and that were discarded due to VLAN-related 
             reasons."
        ::= { rcVlanGroupStatPortEntry 6 }     
        
rcVlanGroupStatisticsInAllBytes    OBJECT-TYPE
        SYNTAX        Counter64       
        MAX-ACCESS    read-only
        STATUS        current
        DESCRIPTION
            "The number of valid bytes transmitted by this port to its
             segment from the local forwarding process for the VLAN of 
             VLAN group."
        ::= { rcVlanGroupStatPortEntry 7 }   
                                                  
rcVlanGroupStatisticsOutAllBytes    OBJECT-TYPE
        SYNTAX        Counter64       
        MAX-ACCESS    read-only
        STATUS        current
        DESCRIPTION
            "The statistics of bytes in egress."
        ::= { rcVlanGroupStatPortEntry 8 }
      
rcVlanGroupStatisticsInAllDiscardsBytes    OBJECT-TYPE
        SYNTAX        Counter64       
        MAX-ACCESS    read-only
        STATUS        current
        DESCRIPTION
            "The number of valid bytes received by this port from its 
             segment that were classified as belonging to the VLAN of 
             VLAN group and that were discarded due to VLAN-related 
             reasons."
        ::= { rcVlanGroupStatPortEntry 9 }   

END

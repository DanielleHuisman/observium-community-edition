--MibName=raisecomWred
-- *****************************************************************
-- RAISECOM-WRED-MIB.MIB:	 Raisecom Wred MIB file
--
-- Jan 2011, zhaipeng
--
-- Copyright (c) 1994-2004,	2001 by	Raisecom, Inc.
-- All rights reserved.
--
-- *****************************************************************

RAISECOM-WRED-MIB DEFINITIONS ::= BEGIN

IMPORTS
		iscomSwitch
				FROM RAISECOM-BASE-MIB;
				                   
raisecomWred MODULE-IDENTITY
		 LAST-UPDATED	  "201101110000Z"
		 ORGANIZATION	  "Raisecom, Inc."
		 CONTACT-INFO
				 "		  Raise Systems

				 Postal:  Beijing, China

				    Tel:  86-010-82884499

				 E-mail:  support@raisecom.com"
		 DESCRIPTION
                 "Description of Wred object."
         REVISION   "201101110000Z"
         DESCRIPTION                       
                 "The initial revision of this MIB."
                 ::= { iscomSwitch 60 }
--------------------------------------------------------------------
--define groups in raisecomWred                 
--------------------------------------------------------------------
	raisecomWredCfg			  OBJECT IDENTIFIER ::={ raisecomWred 1 }
--------------------------------------------------------------------
--raisecomWredCfg group rcWredEnable                  	
--------------------------------------------------------------------
rcWredEnable OBJECT-TYPE
			SYNTAX INTEGER {enable(1),disable(2)}
			MAX-ACCESS read-write
			STATUS current
			DESCRIPTION
				"Indicates whether the Wred feature is enable on the device.
				enable(1) means that the Wred feature is enabled on this device
				disable(2) means that the Wred feature is disabled."
			::= {raisecomWredCfg 1} 
--------------------------------------------------------------------
--raisecomWredCfg group rcWredPortCfgTable                  	
--------------------------------------------------------------------
rcWredPortCfgTable OBJECT-TYPE
		SYNTAX SEQUENCE OF rcWredPortCfgEntry
		MAX-ACCESS not-accessible
        STATUS current
        DESCRIPTION
        	"A configable table of Wred base on the port of switch."
        ::= {raisecomWredCfg 2}
        
rcWredPortCfgEntry OBJECT-TYPE
		SYNTAX rcWredPortCfgEntry
		MAX-ACCESS not-accessible
        STATUS current
        DESCRIPTION
            "Table entry for switch wred config based on the port." 
        INDEX {rcWredPortIndex, rcWredQueueIndex, rcWredColour}
        ::= {rcWredPortCfgTable 1}
        
rcWredPortCfgEntry ::= SEQUENCE {
		rcWredPortIndex				INTEGER,
		rcWredQueueIndex			INTEGER,
		rcWredColour    			INTEGER,
		rcWredDropStart				INTEGER (0..100),
		rcWredDropSlope				INTEGER (0..90),
		rcWredDropAverageTime		INTEGER (1..32768)
}

rcWredPortIndex OBJECT-TYPE
		SYNTAX INTEGER
		MAX-ACCESS not-accessible
		STATUS current
		DESCRIPTION
            "An index that uniquely identifies a configuration about wred."
        ::= {rcWredPortCfgEntry 1} 
        
rcWredQueueIndex OBJECT-TYPE
		SYNTAX INTEGER
		MAX-ACCESS not-accessible
		STATUS current
		DESCRIPTION
            "An index that uniquely identifies a configuration about wred."
        ::= {rcWredPortCfgEntry 2}
        
rcWredColour OBJECT-TYPE
		SYNTAX INTEGER {red(1),yellow(2),green(3)}
		MAX-ACCESS not-accessible
		STATUS current
		DESCRIPTION
            "An index that uniquely identifies a configuration about wred."
        ::= {rcWredPortCfgEntry 3}
        
rcWredDropStart OBJECT-TYPE
		SYNTAX INTEGER (0..100)
		MAX-ACCESS read-write
		STATUS current
		DESCRIPTION
            "Threshold of start discarding."
        DEFVAL {100}
        ::= {rcWredPortCfgEntry 4}    

rcWredDropSlope OBJECT-TYPE
		SYNTAX INTEGER (0..90)
		MAX-ACCESS read-write
		STATUS current
		DESCRIPTION
            "Droping slope."
        DEFVAL {90} 
        ::= {rcWredPortCfgEntry 5}    
        
rcWredDropAverageTime OBJECT-TYPE
		SYNTAX INTEGER (1..32768)
		MAX-ACCESS read-write
		STATUS current
		DESCRIPTION
            "Average time." 
        DEFVAL {4}
        ::= {rcWredPortCfgEntry 6} 
--end--     
END

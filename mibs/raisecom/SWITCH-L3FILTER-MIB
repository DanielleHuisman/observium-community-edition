--MibName=rcL3Filter
-- *****************************************************************
-- switch-filter-mib.MIB:	 switch filter MIB file
--
-- Apri 2005, yingjiangang
--
-- Copyright (c) 1994-2004,	2001 by	Raisecom, Inc.
-- All rights reserved.
-- 01, 20070724, lq, add rcL3IpSubnetFilterPorts
-- *****************************************************************

SWITCH-L3FILTER-MIB DEFINITIONS ::= BEGIN

IMPORTS
        iscomSwitch			
         		FROM RAISECOM-BASE-MIB
        RowStatus
                FROM SNMPv2-TC
        PortList
              	FROM SWITCH-TC;
                 
     rcL3Filter MODULE-IDENTITY
        LAST-UPDATED    "200504120000Z"
        ORGANIZATION    "Raisecom, Inc."
        CONTACT-INFO
                "       Raise Systems
                        
                Postal: Beijing,
                        China

                   Tel: 86-010-82884499

                E-mail: yuanqingguo@raisecom.com"
        DESCRIPTION
                "description of filter manage object."
                ::= { iscomSwitch 15}                               
                       

-------------------------------------------------------------------------------
--	define groups in SWITCH-FILTER-MIB
------------------------------------------------------------------------------
	rcL3IpSubnetFilter	OBJECT IDENTIFIER ::= {	rcL3Filter 1 }
------------------------------------------------------------------------------

--The L3IpSubnet Filter--
	rcL3IpSubnetFilterTable OBJECT-TYPE
		SYNTAX		SEQUENCE OF	RcL3IpSubnetFilterEntry
		MAX-ACCESS	not-accessible
		STATUS		current
		DESCRIPTION
			"A table of	l3IpSubnet filter.."
		::=	{ rcL3IpSubnetFilter 1}

	rcL3IpSubnetFilterEntry OBJECT-TYPE
		SYNTAX		RcL3IpSubnetFilterEntry
		MAX-ACCESS	not-accessible
		STATUS		current
		DESCRIPTION
			"Table entry for L3IpSubnet filter	and	status information."
		INDEX {rcL3IpSubnetFilterIfIndex,	rcL3IpSubnetFilterIPAclNumber}
		::=	{ rcL3IpSubnetFilterTable 1 }

	RcL3IpSubnetFilterEntry ::= SEQUENCE {
		rcL3IpSubnetFilterIfIndex			INTEGER,
		rcL3IpSubnetFilterIPAclNumber		INTEGER,
		rcL3IpSubnetFilterStatus			RowStatus, 
		rcL3IpSubnetFilterPorts			PortList
	}

	rcL3IpSubnetFilterIfIndex OBJECT-TYPE
		SYNTAX	INTEGER
		ACCESS	not-accessible
		STATUS	current
		DESCRIPTION
			"the L3IpSubnet IfIndex from which the packets are received."
		::=	{ rcL3IpSubnetFilterEntry 1 }

	rcL3IpSubnetFilterIPAclNumber OBJECT-TYPE
		SYNTAX	INTEGER
		ACCESS	not-accessible
		STATUS	current
		DESCRIPTION
			"The index nember of the ip access list ."
		::=	{ rcL3IpSubnetFilterEntry 2 }
  
	rcL3IpSubnetFilterStatus OBJECT-TYPE
		SYNTAX	RowStatus
		ACCESS	read-create
		STATUS	current
		DESCRIPTION
			"The row status	of this	entry."
		::=	{ rcL3IpSubnetFilterEntry 3 }   
		 
	rcL3IpSubnetFilterPorts OBJECT-TYPE
		SYNTAX	PortList
		ACCESS	read-create
		STATUS	current
		DESCRIPTION
			"The physical ports where the ip access list is applied."
		::=	{ rcL3IpSubnetFilterEntry 4 }


END

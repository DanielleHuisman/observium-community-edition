--MibName=rcPortPeerBackup
-- *****************************************************************
-- switch-portbackup-mib.MIB:	 switch port backup MIB file
--
-- Dec 2008, gxd
--
-- Copyright (c) 1994-2008,	2008 by	Raisecom, Inc.
-- All rights reserved.
-- Modify  
-- 02，20100325,gxd,modify this file 
-- 01，20090210,wk,rewrite this file 
-- *****************************************************************

SWITCH-PORTPEERBACKUP-MIB DEFINITIONS ::= BEGIN

IMPORTS
        iscomSwitch			   FROM RAISECOM-BASE-MIB  
        RowStatus,TruthValue   FROM SNMPv2-TC
        Vlanset		  		   FROM SWITCH-TC;
                 
     rcPortPeerBackup MODULE-IDENTITY
        LAST-UPDATED    "200812240000Z"
        ORGANIZATION    "Raisecom, Inc."
        CONTACT-INFO
                "Raisecom Systems
                        
                Postal: Beijing,
                        China

                Tel: 86-010-82884499

                E-mail: guoxiaodan@raisecom.com"
        DESCRIPTION
                "description of port backup group manage object."
                ::= { iscomSwitch 80}  
                
         rcPortPeerBackupObjects 			OBJECT IDENTIFIER ::= { rcPortPeerBackup 1 }
         rcPortPeerBackupNotifications      OBJECT IDENTIFIER ::= { rcPortPeerBackup 2 }  
                         

----------------------rcPortPeerBackupCfgTable-----------------------------------------
	rcPortPeerBackupCfgTable OBJECT-TYPE
    SYNTAX      SEQUENCE OF RcPortPeerBackupCfgEntry
    MAX-ACCESS  not-accessible
    STATUS      current
    DESCRIPTION
        "A table of port peer backup group"
    ::={ rcPortPeerBackupObjects 1 }
    

	rcPortPeerBackupCfgEntry OBJECT-TYPE
    SYNTAX      RcPortPeerBackupCfgEntry
    MAX-ACCESS  not-accessible
    STATUS      current
    DESCRIPTION
        "An entry in the rcPortPeerBackupCfgTable provides objects ."
    INDEX        { rcPortPeerBackupPortIndex}
    ::={ rcPortPeerBackupCfgTable 1 }
    
	RcPortPeerBackupCfgEntry ::= SEQUENCE {     
		rcPortPeerBackupPortIndex	INTEGER,
		rcPortPeerBackupVlanlist	Vlanset,
		rcPortPeerBackupMdName       OCTET STRING,
		rcPortPeerBackupMdLevel        Integer32,
        rcPortPeerBackupMaName       OCTET STRING,
        rcPortPeerBackupLocalMep     INTEGER,
        rcPortPeerBackupRemoteMep    INTEGER,
	    rcPortPeerBackupRowStatus   RowStatus,   
	}
 	
	rcPortPeerBackupPortIndex OBJECT-TYPE
		SYNTAX	INTEGER
		ACCESS	read-create
		STATUS	current
		DESCRIPTION
			"This object is the index of an rcPortPeerBackupCfgTable. 
			 It is the Ag port of the device."
		::=	{ rcPortPeerBackupCfgEntry 1 }
		
	rcPortPeerBackupVlanlist OBJECT-TYPE
		SYNTAX	Vlanset
		ACCESS	read-create
		STATUS	current
		DESCRIPTION
			"Port PeerBackup vlan list.Within each octet, the most significant 
			bit represents the lowest numbered vlan, and the least significant 
			bit represents the highest numbered vlan.  Thus, each vlan is 
			represented by a single bit within the value of this object. If that
			bit has a value of '1' then that vlan is included in the set of vlans; 
			the vlan is not included if its bit has a value of '0'."
		::=	{ rcPortPeerBackupCfgEntry 2 }
	rcPortPeerBackupMdName OBJECT-TYPE
        SYNTAX  OCTET STRING (SIZE(1..16))
        MAX-ACCESS read-create
        STATUS current
        DESCRIPTION
            "The Maintenance Domain name. Each Maintenance Domain has unique name amongst all 
            those used or available to a service provider or operator.  It facilitates easy 
            identification of administrative responsibility for each Maintenance Domain."
        ::= { rcPortPeerBackupCfgEntry 3 }

     rcPortPeerBackupMdLevel OBJECT-TYPE
        SYNTAX  Integer32 (0..7)
        MAX-ACCESS read-create
        STATUS current
        DESCRIPTION
            "Maintenance Domain Level field of the received CCM PDU that is used for port backup between devices."
        ::= { rcPortPeerBackupCfgEntry 4 }

        
    rcPortPeerBackupMaName OBJECT-TYPE
        SYNTAX  OCTET STRING(SIZE(1..13))
        MAX-ACCESS read-create
        STATUS current
        DESCRIPTION
            "The Short Maintenance Association name. The type/format of this object is determined 
            by the value of the dot1agCfmMaNetNameType object.  This name must be unique 
            within a maintenance domain."
        ::= { rcPortPeerBackupCfgEntry 5 } 
        
    rcPortPeerBackupRemoteMep OBJECT-TYPE
        SYNTAX  INTEGER(1..8191)
        MAX-ACCESS read-create
        STATUS current
        DESCRIPTION
            "Remote MEPId of working or protection entity, identifying a specific MEP."     
        ::= { rcPortPeerBackupCfgEntry 6 }
		
	rcPortPeerBackupRowStatus OBJECT-TYPE
		SYNTAX	RowStatus
		ACCESS	read-create
		STATUS	current
		DESCRIPTION
			"This object allows entries to be created and deleted
			 in the rcPortPeerBackupCfgTable. Deletion of an entry in
			 this table results in a deletion of all corresponding (same
			 rcPortPeerBackupPortIndex index values) rcPortPeerBackupCfgTable."
		::=	{ rcPortPeerBackupCfgEntry 7 }    


----------------------rcPortPeerBackupStatusTable-----------------------------------------
	rcPortPeerBackupStatusTable OBJECT-TYPE
    SYNTAX      SEQUENCE OF RcPortPeerBackupStatusEntry
    MAX-ACCESS  not-accessible
    STATUS      current
    DESCRIPTION
        "A table of port peer backup group"
    ::={ rcPortPeerBackupObjects 2 }
    

	rcPortPeerBackupStatusEntry OBJECT-TYPE
    SYNTAX      RcPortPeerBackupStatusEntry
    MAX-ACCESS  not-accessible
    STATUS      current
    DESCRIPTION
        "An entry in the rcPortPeerBackupCfgTable provides objects ."
    INDEX        { rcPortPeerBackupPortIndex}
    ::={ rcPortPeerBackupStatusTable 1 }
    
	RcPortPeerBackupStatusEntry ::= SEQUENCE {     
		rcPortPeerBackupLocalPortStatus	INTEGER,
		rcPortPeerBackupRemotePortStatus INTEGER,
		rcPortPeerBackupPeerMacAddress   OCTET STRING,
        rcPortPeerBackupStatusDuration   INTEGER,
        rcPortPeerBackupSwitchCnt     INTEGER, 
	}
 	
	
    rcPortPeerBackupLocalPortStatus OBJECT-TYPE
        SYNTAX INTEGER	{
            	blocking(1),
    			forwarding(2)
        			}
		ACCESS	read-only
		STATUS	current
		DESCRIPTION
			"Local port status，including two states: discarding and 
			forwarding. If a primary port is at discarding state, the 
			port only reiceive and send BPDU;If a primary port is at 
			forwarding state,the port  reiceive and send not only 
			BPDU but other frames."
		::=	{ rcPortPeerBackupStatusEntry 1 }
		
	 rcPortPeerBackupRemotePortStatus OBJECT-TYPE
        SYNTAX INTEGER	{
            	blocking(1),
    			forwarding(2),
    			unknown(3)
        			}
		ACCESS	read-only
		STATUS	current
		DESCRIPTION
			"Remote port status，including three states: blocking and 
			forwarding unknown. If a primary port is at discarding state, the 
			port only reiceive and send BPDU;If a primary port is at 
			forwarding state,the port  reiceive and send not only 
			BPDU but other frames."
		::=	{ rcPortPeerBackupStatusEntry 2 }
		       
    rcPortPeerBackupStatusDuration OBJECT-TYPE
		SYNTAX	INTEGER
		ACCESS	read-only
		STATUS	current
		DESCRIPTION
			"The duration is the time ever lasting from the device changing to forwarding or blocking."
		::=	{ rcPortPeerBackupStatusEntry 3 }
	rcPortPeerBackupSwitchCnt OBJECT-TYPE
		SYNTAX	INTEGER
		ACCESS	read-only
		STATUS	current
		DESCRIPTION
			"The object is for computing the times of local port switching between forwarding and blocking status."
		::=	{ rcPortPeerBackupStatusEntry 4 }
------------------------------------------------------------------------------------        
    rcPortPeerBackupLocalPortForward NOTIFICATION-TYPE
        OBJECTS {
				  rcPortPeerBackupLocalPortStatus
            	}
        STATUS  current
        DESCRIPTION
          "Peer Backup PORT Restore TRAP"
       ::= { rcPortPeerBackupNotifications 1 } 
       
    rcPortPeerBackupLocalPortBlock NOTIFICATION-TYPE
        OBJECTS { 
				  rcPortPeerBackupLocalPortStatus
            	}
        STATUS  current
        DESCRIPTION
          "Peer Backup PORT Switch TRAP"
       ::= { rcPortPeerBackupNotifications 2 }  
       			
END

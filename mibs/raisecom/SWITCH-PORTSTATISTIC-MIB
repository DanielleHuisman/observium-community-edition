--MibName=rcPortStatistics
-- *****************************************************************
-- RAISECOM-PORTSTATISTIC-MIB.mi2:  Raisecom port statistic MIB file
--
-- Nov 2004, gaohongwei
--
-- Copyright (c) 1994-2000, 2004 by Raisecom, Inc.
-- All rights reserved.
-- 01, 20140825, zhoujw, ESW00019189, 增加端口统计相关MIBs

-- *****************************************************************
SWITCH-PORTSTATISTIC-MIB  DEFINITIONS ::= BEGIN
 
IMPORTS
       iscomSwitch         				FROM RAISECOM-BASE-MIB 
       TruthValue  	FROM SNMPv2-TC
       NOTIFICATION-TYPE,Counter64      FROM SNMPv2-SMI; 
                
	rcPortStatistics MODULE-IDENTITY
        LAST-UPDATED    "200412200000Z"
        ORGANIZATION    "Raisecom, Inc." 
        CONTACT-INFO
                "       Raise Systems
                        
                Postal: Beijing,
                        China

                   Tel: 86-010-82884499

                E-mail: surport@raisecom.com"
        DESCRIPTION
                "port statistic mib."
                ::= { iscomSwitch 7}  
--
	rcPortStatsTrap       	    OBJECT IDENTIFIER ::= { rcPortStatistics 1 }
	rcPortStatsObject       	OBJECT IDENTIFIER ::= { rcPortStatistics 2 }
	rcPortStatsConformance      OBJECT IDENTIFIER ::= { rcPortStatistics 3 }
	rcPortStatsScalar		    OBJECT IDENTIFIER ::= { rcPortStatsObject 1 }
            
--  rcPortStatsScalar         
    rcPortStatsPeriod OBJECT-TYPE
        SYNTAX INTEGER
        MAX-ACCESS read-write
        STATUS current
        DESCRIPTION
            "Port state statistical cycle." 
        DEFVAL { 2000}                      --周期默认值2000ms
    	::= { rcPortStatsScalar 1 }

--  rcPortStatsTable
    rcPortStatsTable OBJECT-TYPE
        SYNTAX SEQUENCE OF RcPortStatsEntry
        MAX-ACCESS not-accessible
        STATUS current
        DESCRIPTION
            "A table of port statistic."
        ::= { rcPortStatsObject 2 }

    rcPortStatsEntry OBJECT-TYPE
        SYNTAX RcPortStatsEntry
        MAX-ACCESS not-accessible
        STATUS current
        DESCRIPTION
            "Table entry of port statistic."
        INDEX { ifIndex }
        ::= { rcPortStatsTable 1 }

    RcPortStatsEntry ::= SEQUENCE {
        rcPortStatsEnable                           TruthValue,
        rcPortStatsHistoryPortStatsNextIndex		INTEGER,
        rcPortStatsClear			                TruthValue
        }      
     
   	rcPortStatsEnable OBJECT-TYPE
        SYNTAX TruthValue 
        MAX-ACCESS read-write
        STATUS current
        DESCRIPTION
            "It is a dynamic statistical switch."
        ::= { rcPortStatsEntry 1 }
                    
   	rcPortStatsHistoryPortStatsNextIndex OBJECT-TYPE
        SYNTAX  INTEGER 
        ACCESS  read-only
        STATUS  current
        DESCRIPTION
                "The index for the current Measurement Interval. 
                This value will become the value for rcHistoryStatsIndex 
                once the Measurement Interval is completed.  
                The first Measurement Interval that occurs after the session 
                is started is assigned index 1. "
        ::= { rcPortStatsEntry 2 }   
                        
        rcPortStatsClear OBJECT-TYPE
    	SYNTAX      TruthValue 
    	MAX-ACCESS  read-write
    	STATUS      current
    	DESCRIPTION
            "Clear port statistics."  
    	::= { rcPortStatsEntry 3 }           
   	 	       
--  rcCurrentPortStatsTable
    rcCurrentPortStatsTable OBJECT-TYPE
        SYNTAX SEQUENCE OF RcCurrentPortStatsEntry
        MAX-ACCESS not-accessible
        STATUS current
        DESCRIPTION
            "A table of current port statistic."
        ::= { rcPortStatsObject 3 }

    rcCurrentPortStatsEntry OBJECT-TYPE
        SYNTAX RcCurrentPortStatsEntry
        MAX-ACCESS not-accessible
        STATUS current
        DESCRIPTION
            "Table entry of current port statistic."
        INDEX { ifIndex }
        ::= { rcCurrentPortStatsTable 1 }

    RcCurrentPortStatsEntry ::= SEQUENCE {
        rcCurrentPortStatsInPacket					Counter64,
        rcCurrentPortStatsOutPacket					Counter64,
        rcCurrentPortStatsInAllBits					Counter64,  
        rcCurrentPortStatsOutAllBits				Counter64,
        rcCurrentPortStatsInBandwidthUtilization	INTEGER, 
        rcCurrentPortStatsEBandwidthUtilization	    INTEGER
        }      
     
   	rcCurrentPortStatsInPacket OBJECT-TYPE
        SYNTAX     Counter64 
        MAX-ACCESS read-only
        STATUS     current
        DESCRIPTION
            "Count of packets received."
        ::= { rcCurrentPortStatsEntry 1 }
                    
   	rcCurrentPortStatsOutPacket OBJECT-TYPE
        SYNTAX  Counter64 
        ACCESS  read-only
        STATUS  current
        DESCRIPTION
                "Count of packets transmitted."
        ::= { rcCurrentPortStatsEntry 2 }   
                        
    rcCurrentPortStatsInAllBits OBJECT-TYPE
    	SYNTAX      Counter64 
    	MAX-ACCESS  read-only
    	STATUS      current
    	DESCRIPTION
            "The total number of bits received on the interface,
            including framing characters.Discontinuities in the value 
            of this counter can occur at re-initialization of the management system, 
            and at other times as indicated by the value of ifCounterDiscontinuityTime."  
    	::= { rcCurrentPortStatsEntry 3 }           
   	 
                                     
   	rcCurrentPortStatsOutAllBits OBJECT-TYPE
        SYNTAX  Counter64 
        ACCESS  read-only
        STATUS  current
        DESCRIPTION
            "The total number of bits transmitted out of the interface, 
            including framing characters.Discontinuities in the value 
            of this counter can occur at re-initialization of the management system, 
            and at other times as indicated by the value of ifCounterDiscontinuityTime."
        ::= { rcCurrentPortStatsEntry 4 }   
                                   
  	rcCurrentPortStatsInBandwidthUtilization OBJECT-TYPE
   		SYNTAX      INTEGER 
    	MAX-ACCESS  read-only
    	STATUS      current
    	DESCRIPTION
            "The ingress of port bandwidth Utilization."  
    	::= { rcCurrentPortStatsEntry 5 } 	
        
    rcCurrentPortStatsEBandwidthUtilization OBJECT-TYPE
    	SYNTAX      INTEGER
    	MAX-ACCESS  read-only
    	STATUS      current
    	DESCRIPTION
            "The egress of port bandwidth Utilization."
   	::= { rcCurrentPortStatsEntry 6 }  
   	
--  rcHistoryPortStatsTable
    rcHistoryPortStatsTable OBJECT-TYPE
        SYNTAX SEQUENCE OF RcHistoryPortStatsEntry
        MAX-ACCESS not-accessible
        STATUS current
        DESCRIPTION
            "A table of history port statistic."
        ::= { rcPortStatsObject 4 }

    rcHistoryPortStatsEntry OBJECT-TYPE
        SYNTAX RcHistoryPortStatsEntry
        MAX-ACCESS not-accessible
        STATUS current
        DESCRIPTION
            "Table entry of history port statistic."
        INDEX { ifIndex,
                rcHistoryStatsIndex 
                }
        ::= { rcHistoryPortStatsTable 1 } 
        
    RcHistoryPortStatsEntry ::= SEQUENCE {
    	rcHistoryPortStatsIndex                     INTEGER,
        rcHistoryPortStatsInPacket					Counter64,
        rcHistoryPortStatsOutPacket					Counter64,
        rcHistoryPortStatsInAllBits					Counter64,  
        rcHistoryPortStatsOutAllBits				Counter64,
        rcHistoryPortStatsInBandwidthUtilization	INTEGER, 
        rcHistoryPortStatsEBandwidthUtilization	    INTEGER
        }
              
    rcHistoryPortStatsIndex OBJECT-TYPE
        SYNTAX     INTEGER 
        MAX-ACCESS not-accessible
        STATUS     current
        DESCRIPTION
            "The index for the history Measurement Interval. 
            The first Measurement Interval that occurs after the session 
            is started is assigned index 1. 
            Referential integrity is necessary, i.e., the index needs to 
            be persistent upon a reboot or restart of a device.  The index 
            is never reused while this session is active until it wraps to zero.
            The index value keeps increasing up to that time.Count of packets received."
        ::= { rcHistoryPortStatsEntry 1 } 
            
   	rcHistoryPortStatsInPacket OBJECT-TYPE
        SYNTAX     Counter64 
        MAX-ACCESS read-only
        STATUS     current
        DESCRIPTION
            "Count of packets received in history."
        ::= { rcHistoryPortStatsEntry 2 }
                    
   	rcHistoryPortStatsOutPacket OBJECT-TYPE
        SYNTAX  Counter64 
        ACCESS  read-only
        STATUS  current
        DESCRIPTION
            "Count of packets transmitted in history. "
        ::= { rcHistoryPortStatsEntry 3 }   
                        
    rcHistoryPortStatsInAllBits OBJECT-TYPE
    	SYNTAX      Counter64 
    	MAX-ACCESS  read-only
    	STATUS      current
    	DESCRIPTION
            "The total history number of bits received on the interface,
            including framing characters.
            Discontinuities in the value of this counter can occur at 
            re-initialization of the management system, and at other times 
            as indicated by the value of ifCounterDiscontinuityTime."  
    	::= { rcHistoryPortStatsEntry 4 }           
   	 
                                     
   	rcHistoryPortStatsOutAllBits OBJECT-TYPE
        SYNTAX  Counter64 
        ACCESS  read-only
        STATUS  current
        DESCRIPTION
            "The total history number of bits transmitted out of the interface, 
            including framing characters. 
            Discontinuities in the value of this counter can occur at 
            re-initialization of the management system, and at other times 
            as indicated by the value of ifCounterDiscontinuityTime."
        ::= { rcHistoryPortStatsEntry 5 }   
                                   
  	rcHistoryPortStatsInBandwidthUtilization OBJECT-TYPE
   		SYNTAX      INTEGER 
    	MAX-ACCESS  read-only
    	STATUS      current
    	DESCRIPTION
            "The ingress of port bandwidth Utilization in History."  
    	::= { rcHistoryPortStatsEntry 6 } 	
        
    rcHistoryPortStatsEBandwidthUtilization OBJECT-TYPE
    	SYNTAX      INTEGER
    	MAX-ACCESS  read-only
    	STATUS      current
    	DESCRIPTION
            "The egress of port bandwidth Utilization in history."
   	    ::= { rcHistoryPortStatsEntry 7 } 
 	
END

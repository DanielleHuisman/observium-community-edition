--MibName=rcRateLimit
-- *****************************************************************
-- RAISECOM-RC3026BANDWIDTHMANAGE-MIB.MIB:  Raisecom Bandwidth Manage MIB file
--
-- May 2003, yuanqingguo
--
-- Copyright (c) 1994-2000, 2001 by Raisecom, Inc.
-- All rights reserved.       
-- 
-- *****************************************************************
SWITCH-RATELIMIT-MIB  DEFINITIONS ::= BEGIN

IMPORTS 
       Counter64
                FROM SNMPv2-SMI
       iscomSwitch     
                FROM RAISECOM-BASE-MIB
       RowStatus
                FROM SNMPv2-TC
       EnableVar
                FROM SWITCH-TC;
                 
       rcRateLimit MODULE-IDENTITY
       LAST-UPDATED    "200412200000Z"
       ORGANIZATION    "Raisecom, Inc."
       CONTACT-INFO
                       "Raise Systems
                        
                        Postal: Beijing,
                        China

                        Tel: 86-010-82884499

                        E-mail: yuanqingguo@raisecom.com"
       DESCRIPTION
                       "description of rate limit manage object."
       ::= { iscomSwitch 2}    


rcUplinkPort OBJECT-TYPE 
    SYNTAX       INTEGER 
    MAX-ACCESS   read-write
    STATUS       deprecated
    DESCRIPTION
      "The uplink port based 1."
    ::= { rcRateLimit 1}
--rate-limit for port--  
rcRateLimitPortTable OBJECT-TYPE
    SYNTAX SEQUENCE OF RcRateLimitPortEntry
    MAX-ACCESS   not-accessible
    STATUS       current
    DESCRIPTION
      "A table of rate-limit for port and associated properties."
    ::= { rcRateLimit 2}

rcRateLimitPortEntry OBJECT-TYPE
    SYNTAX      RcRateLimitPortEntry
    MAX-ACCESS  not-accessible
    STATUS      current
    DESCRIPTION
      "Table entry for rate-limit of port and status information."
    INDEX { rcRateLimitPortIndex }
    ::= { rcRateLimitPortTable 1 }

RcRateLimitPortEntry ::= SEQUENCE 
{
    rcRateLimitPortIndex             INTEGER,
    rcRateLimitPortRule              INTEGER,
    rcRateLimitPortIngressRate       INTEGER,
    rcRateLimitPortIngressBurst      INTEGER,
    rcRateLimitPortEgressRate        INTEGER,
    rcRateLimitPortEgressBurst       INTEGER  
}
             
rcRateLimitPortIndex   OBJECT-TYPE
    SYNTAX      INTEGER 
    ACCESS      read-only
    STATUS      current
    DESCRIPTION
      "The value of ifIndex that identifies the rate-limit of port which based 1."    
    ::= { rcRateLimitPortEntry 1 }    
    
rcRateLimitPortRule   OBJECT-TYPE
    SYNTAX    INTEGER 
    {   
       none(0),   
       ingress(1),
       egress(2),
       both(3)             
    }
    ACCESS     read-create
    STATUS     obsolete
    DESCRIPTION
       "A rule of rate-limit for the port."  
    DEFVAL {none}    
    ::= { rcRateLimitPortEntry 2 }    
    
rcRateLimitPortIngressRate   OBJECT-TYPE
    SYNTAX    INTEGER  (0..1048576)  
    UNITS     "kbps"
    ACCESS    read-create
    STATUS    current
    DESCRIPTION
      "The value is the ingress rate( kbps) of the port."    
    ::= { rcRateLimitPortEntry 3 }    
    
rcRateLimitPortIngressBurst   OBJECT-TYPE
    SYNTAX    INTEGER (0..512)   
    UNITS     "kB"            
    ACCESS    read-create
    STATUS    current
    DESCRIPTION
      "The value is the ingress burst( kB) of the port."    
    ::= { rcRateLimitPortEntry 4 } 
        
rcRateLimitPortEgressRate   OBJECT-TYPE
    SYNTAX    INTEGER  (0..1048576)   
    UNITS     "kbps"
    ACCESS    read-create
    STATUS    current
    DESCRIPTION
       "The value is the egress rate( kbps) of the port."    
    ::= { rcRateLimitPortEntry 5 }    
    
rcRateLimitPortEgressBurst   OBJECT-TYPE
    SYNTAX    INTEGER  (0..512)  
    UNITS     "kB"                
    ACCESS    read-create
    STATUS    current
    DESCRIPTION
      "The value is the egress burst( kB) of the port."    
    ::= { rcRateLimitPortEntry 6 }  
        
----------------------------------rate-limit for vlan  
rcRateLimitVlanTable OBJECT-TYPE
    SYNTAX SEQUENCE OF RcRateLimitVlanEntry
    MAX-ACCESS not-accessible
    STATUS current
    DESCRIPTION
      "A table of rate-limit for vlan and associated properties."
    ::= { rcRateLimit 3}

rcRateLimitVlanEntry OBJECT-TYPE
    SYNTAX      RcRateLimitVlanEntry
    MAX-ACCESS  not-accessible
    STATUS      current
    DESCRIPTION
       "Table entry for rate-limit of vlan and status information."
    INDEX { rcRateLimitVlanType,rcRateLimitVlanCVlanID,rcRateLimitVlanSPVlanID }
    ::= { rcRateLimitVlanTable 1 }

RcRateLimitVlanEntry ::= SEQUENCE 
{
    rcRateLimitVlanType                INTEGER,
    rcRateLimitVlanCVlanID             INTEGER,
    rcRateLimitVlanSPVlanID            INTEGER,
    rcRateLimitVlanRate                INTEGER,
    rcRateLimitVlanBurst               INTEGER,  
    rcRateLimitVlanRowStatus           RowStatus,
    rcRateLimitVlanStatsEnable         EnableVar,
    rcRateLimitVlanStatHwStatus        EnableVar
}
             
rcRateLimitVlanType   OBJECT-TYPE
     SYNTAX    INTEGER {single(1),double(2)}
     ACCESS    not-accessible
     STATUS    current
     DESCRIPTION
       "vlan type,single(1), double(2)?"    
     ::= { rcRateLimitVlanEntry 1 }    
    
rcRateLimitVlanCVlanID   OBJECT-TYPE
     SYNTAX    INTEGER (1..4094)
     ACCESS    not-accessible
     STATUS    current
     DESCRIPTION
       "The vlan ID which identifies the customer vlan  of rate limitation."    
     ::= { rcRateLimitVlanEntry 2 }    
    
rcRateLimitVlanSPVlanID   OBJECT-TYPE
     SYNTAX    INTEGER (1..4094)
     ACCESS    not-accessible
     STATUS    current
     DESCRIPTION
       "The vlan ID which identifies the service provider vlan  of rate limitation."    
     ::= { rcRateLimitVlanEntry 3 }    

rcRateLimitVlanRate   OBJECT-TYPE
     SYNTAX    INTEGER  (0..1048576)       
     UNITS     "kbps"
     ACCESS    read-create
     STATUS    current
     DESCRIPTION
       "The value is the input rate( kbps) of the vlan."    
     ::= { rcRateLimitVlanEntry 4 }    
    
rcRateLimitVlanBurst   OBJECT-TYPE
     SYNTAX    INTEGER  (0..512)   
     UNITS     "kB"
     ACCESS    read-create
     STATUS    current
     DESCRIPTION
       "The value is the input burst( kB) of the vlan." 
     ::= { rcRateLimitVlanEntry 5 }  
       
rcRateLimitVlanRowStatus   OBJECT-TYPE
     SYNTAX      RowStatus
     MAX-ACCESS  read-create
     STATUS      current
     DESCRIPTION
       "The status of this entry."
    ::= { rcRateLimitVlanEntry 6 }   

rcRateLimitVlanStatsEnable   OBJECT-TYPE
     SYNTAX      EnableVar
     MAX-ACCESS  read-create
     STATUS      current
     DESCRIPTION
       "enable statistics or not."
    ::= { rcRateLimitVlanEntry 7 }

rcRateLimitVlanStatHwStatus   OBJECT-TYPE
     SYNTAX      EnableVar
     MAX-ACCESS  read-create
     STATUS      current
     DESCRIPTION
       "in hardware or not."
     ::= { rcRateLimitVlanEntry 8 }
    

rcRateLimitVlanStatisticsTable OBJECT-TYPE
     SYNTAX    SEQUENCE OF RcRateLimitVlanStatisticsEntry
     MAX-ACCESS  not-accessible
     STATUS      current
     DESCRIPTION
       "A table of vlan rate limit  statistics."
     ::= { rcRateLimit 4}

rcRateLimitVlanStatisticsEntry OBJECT-TYPE
     SYNTAX      RcRateLimitVlanStatisticsEntry
     MAX-ACCESS  not-accessible
     STATUS      current
     DESCRIPTION
       "Table entry for vlan rate limit statistics ."
     AUGMENTS { rcRateLimitVlanEntry }
     ::= { rcRateLimitVlanStatisticsTable 1 }

RcRateLimitVlanStatisticsEntry ::= SEQUENCE 
{
     rcRateLimitVlanCounterReset             EnableVar,
     rcRateLimitVlanCounterInprofilePkt64    Counter64,
     rcRateLimitVlanCounterInprofileByte64   Counter64,
     rcRateLimitVlanCounterOutprofilePkt64   Counter64,
     rcRateLimitVlanCounterOutprofileByte64  Counter64,
     rcRateLimitVlanCounterStatisticUnit     INTEGER
}
    
rcRateLimitVlanCounterReset OBJECT-TYPE 
     SYNTAX     EnableVar   
     ACCESS     read-write
     STATUS     current
     DESCRIPTION
       "clear the statistics."
     ::= { rcRateLimitVlanStatisticsEntry 1 }
    
rcRateLimitVlanCounterInprofilePkt64  OBJECT-TYPE
     SYNTAX     Counter64
     ACCESS     read-only
     STATUS     current
     DESCRIPTION
       "The pkt64 of the inprofile statistics."
    ::= { rcRateLimitVlanStatisticsEntry 2 }
    
rcRateLimitVlanCounterInprofileByte64 OBJECT-TYPE
     SYNTAX     Counter64
     ACCESS     read-only
     STATUS     current
     DESCRIPTION
       "The Byte64 of the inprofile statistics."
     ::= { rcRateLimitVlanStatisticsEntry 3 }

rcRateLimitVlanCounterOutprofilePkt64 OBJECT-TYPE
     SYNTAX  Counter64
     ACCESS  read-only
     STATUS  current
     DESCRIPTION
       "The pkt64 of the outprofile statistics."
     ::= { rcRateLimitVlanStatisticsEntry 4 }
    
rcRateLimitVlanCounterOutprofileByte64  OBJECT-TYPE
     SYNTAX  Counter64
     ACCESS  read-only
     STATUS  current
     DESCRIPTION
       "The Byte64 of the outprofile statistics."
    ::= { rcRateLimitVlanStatisticsEntry 5 }
rcRateLimitVlanCounterStatisticUnit  OBJECT-TYPE
     SYNTAX  INTEGER
     ACCESS  read-only
     STATUS  current
     DESCRIPTION
       "Vlan rate-limit statistics unit."
    ::= { rcRateLimitVlanStatisticsEntry 6 }
END

--MibName=rcRstp
SWITCH-RSTP-MIB DEFINITIONS ::= BEGIN

IMPORTS
    MODULE-IDENTITY, OBJECT-TYPE    	 	FROM SNMPv2-SMI
    TruthValue  	FROM SNMPv2-TC   
    dot1dStpPortEntry   			FROM BRIDGE-MIB 
    iscomSwitch	            			FROM RAISECOM-BASE-MIB;


rcRstp MODULE-IDENTITY
    LAST-UPDATED "9411010000Z"
    ORGANIZATION "IETF SNMPv2 Working Group"
    CONTACT-INFO
            " 
             Phone:  01082884499
             Email:  support@raisecom.com"
    DESCRIPTION
            "The MIB module for managing  trunk  in rc2126."
    REVISION      "9103310000Z"
    DESCRIPTION
            ""
    ::= { iscomSwitch 9}

--
	rcRstpConfig       	OBJECT IDENTIFIER ::= { rcRstp 1 }  
	rcRstpStatistics     	OBJECT IDENTIFIER ::= { rcRstp 2 }
--


rcRstpEnable OBJECT-TYPE
    SYNTAX      TruthValue
    MAX-ACCESS  read-write
    STATUS      current
    DESCRIPTION
            "."    
    DEFVAL { 1}
    ::= { rcRstpConfig 1 }

-- rcRstpPortConfigTable

rcRstpPortConfigTable OBJECT-TYPE
    SYNTAX      SEQUENCE OF RcRstpPortConfigEntry
    MAX-ACCESS  not-accessible
    STATUS      current
    DESCRIPTION
            "Rstp config table"
    ::= { rcRstpConfig 2 }

rcRstpPortConfigEntry OBJECT-TYPE
    SYNTAX      RcRstpPortConfigEntry
    MAX-ACCESS  not-accessible
    STATUS      current
    DESCRIPTION
            "Rstp config table"
    AUGMENTS    { dot1dStpPortEntry }
    ::= { rcRstpPortConfigTable 1 }

RcRstpPortConfigEntry ::= SEQUENCE {
        rcRstpPortRstpEnable          TruthValue,
        rcRstpPortOperEnable          TruthValue
        }

rcRstpPortRstpEnable OBJECT-TYPE
    SYNTAX      TruthValue
    MAX-ACCESS  read-write
    STATUS      current
    DESCRIPTION
            "port Rstp enable"
    ::= { rcRstpPortConfigEntry 1 } 
    
rcRstpPortOperEnable OBJECT-TYPE
    SYNTAX      TruthValue
    MAX-ACCESS  read-only
    STATUS      current
    DESCRIPTION
            "port Rstp enable operater state"
    ::= { rcRstpPortConfigEntry 2 }

-- rcRstpStatistics     
rcRstpPortStatsTable OBJECT-TYPE
    SYNTAX      SEQUENCE OF RcRstpPortStatsEntry
    MAX-ACCESS  not-accessible
    STATUS      current
    DESCRIPTION
            "Rstp config table"
    ::= { rcRstpStatistics 1 }

rcRstpPortStatsEntry OBJECT-TYPE
    SYNTAX      RcRstpPortStatsEntry
    MAX-ACCESS  not-accessible
    STATUS      current
    DESCRIPTION
            "Rstp config table"
    AUGMENTS    { dot1dStpPortEntry }
    ::= { rcRstpPortStatsTable 1 }

RcRstpPortStatsEntry ::= SEQUENCE {
        rcRstpPortRxStpBPDUs       Counter,
        rcRstpPortRxTCNs           Counter,
        rcRstpPortRxRstpBPDUs      Counter,
        rcRstpPortTxStpBPDUs        Counter,
        rcRstpPortTxTCNs             Counter,
        rcRstpPortTxRstpBPDUs        Counter,
        rcRstpPortStatisticsClear          TruthValue
        }

rcRstpPortRxStpBPDUs OBJECT-TYPE
    SYNTAX      Counter
    MAX-ACCESS  read-only
    STATUS      current
    DESCRIPTION
            "port receive STP BPDUs"
    ::= { rcRstpPortStatsEntry 1 }   
    
    rcRstpPortRxTCNs OBJECT-TYPE
    SYNTAX      Counter
    MAX-ACCESS  read-only
    STATUS      current
    DESCRIPTION
            "port receive TCNs"
    ::= { rcRstpPortStatsEntry 2 }

rcRstpPortRxRstpBPDUs OBJECT-TYPE
    SYNTAX      Counter
    MAX-ACCESS  read-only
    STATUS      current
    DESCRIPTION
            "port receive RSTP BPDUs"
    ::= { rcRstpPortStatsEntry 3 }

rcRstpPortTxStpBPDUs OBJECT-TYPE
    SYNTAX      Counter
    MAX-ACCESS  read-only
    STATUS      current
    DESCRIPTION
            "port send STP BPDUs"
    ::= { rcRstpPortStatsEntry 4 }

rcRstpPortTxTCNs OBJECT-TYPE
    SYNTAX      Counter
    MAX-ACCESS  read-only
    STATUS      current
    DESCRIPTION
            "port send TCNs"
    ::= { rcRstpPortStatsEntry 5 }

rcRstpPortTxRstpBPDUs OBJECT-TYPE
    SYNTAX      Counter
    MAX-ACCESS  read-only
    STATUS      current
    DESCRIPTION
            "port send RSTP BPDUs"
    ::= { rcRstpPortStatsEntry 6 }     
    
rcRstpPortStatisticsClear OBJECT-TYPE
    SYNTAX      TruthValue
    MAX-ACCESS  read-write
    STATUS      current
    DESCRIPTION
            "clear port statistics"
    ::= { rcRstpPortStatsEntry 7 }
END

--MibName=raisecomSlotCardmgmt
-- *****************************************************************
-- Version 1.0 Created 2011.01.04 by zengliang
-- This version of MIB is created just for the Management of CARD .
--
-- Copyright(c) 2002-2012 by RAISECOM TECH, Ltd. 
-- All rights reserved.
--
-- modify history 
--
-- *****************************************************************
SWITCH-SLOTCARDMGMT-MIB  DEFINITIONS ::= BEGIN

IMPORTS
        raisecomAgent
            FROM RAISECOM-BASE-MIB 
        EnableVar                
            FROM SWITCH-TC    
        Unsigned32                        
        	FROM SNMPv2-SMI;

	raisecomSlotCardmgmt MODULE-IDENTITY
        LAST-UPDATED    "201101040000Z"
        ORGANIZATION    "Raisecom, Inc."
        CONTACT-INFO
                "       Raise Systems

                Postal: Beijing,
                        China

                   Tel: 86-010-82884499

                E-mail: support@raisecom.com"
        DESCRIPTION
                "Configuration of synce object." 
-- -------------------------------------------------------------
-- modify history
-- -------------------------------------------------------------       
        REVISION    "201101040000Z"
        DESCRIPTION "The initial revision of this MIB."
                ::= { raisecomAgent 23}         

-- -------------------------------------------------------------
-- groups in the CARDMGMT MIB
-- -------------------------------------------------------------
raisecomSlotCardNotification  OBJECT IDENTIFIER ::= { raisecomSlotCardmgmt 1 }  
raisecomSlotCardMibObjects    OBJECT IDENTIFIER ::= { raisecomSlotCardmgmt 2 }  

-- -------------------------------------------------------------
-- raisecomSlotCardNotification
-- -------------------------------------------------------------    
    raisecomSlotCardStateChange NOTIFICATION-TYPE
        OBJECTS { raisecomSlotCardState }
        STATUS current
        DESCRIPTION
                "Card in this slot is up or down."            
        ::= { raisecomSlotCardNotification 1 }  
        
-- -------------------------------------------------------------
-- raisecomSlotCardMibObjects
-- -------------------------------------------------------------  
raisecomSlotCardGlobalGroup   OBJECT IDENTIFIER ::= { raisecomSlotCardMibObjects 1 }   

-- -------------------------------------------------------------
-- raisecomSlotCardGlobalGroup
-- -------------------------------------------------------------          
    raisecomSlotCardNum OBJECT-TYPE
        SYNTAX	Unsigned32
        MAX-ACCESS  read-only
        STATUS      current
        DESCRIPTION
           	"The maximum card number device supported."
        ::= { raisecomSlotCardGlobalGroup 1 }   
        
    raisecomSlotCardTrapEnable OBJECT-TYPE
        SYNTAX	EnableVar
        MAX-ACCESS  read-write
        STATUS      current
        DESCRIPTION
           	"Indicates whether the slot card management feature is enabled on the device.
             Enable(1) means that the slot card management feature is enabled on this device.
             Disable(2) means that the slot card management feature is disabled."
        ::= { raisecomSlotCardGlobalGroup 2 } 
                            
-- -------------------------------------------------------------
-- raisecomSlotCardTable
-- -------------------------------------------------------------
    raisecomSlotCardTable OBJECT-TYPE
        SYNTAX SEQUENCE OF RaisecomSlotCardEntry
        MAX-ACCESS not-accessible
        STATUS current
        DESCRIPTION
            "Slot card table."
        ::= { raisecomSlotCardMibObjects 2 }

    raisecomSlotCardEntry OBJECT-TYPE
        SYNTAX RaisecomSlotCardEntry
        MAX-ACCESS not-accessible
        STATUS current
        DESCRIPTION
            "Slot card table entry."
        INDEX { raisecomSlotCardIndex }
        ::= { raisecomSlotCardTable 1 }

    RaisecomSlotCardEntry ::= SEQUENCE {
        raisecomSlotCardIndex               Unsigned32, 
        raisecomSlotCardSerialNumber        OCTET STRING (SIZE (32)),              
        raisecomSlotCardState          		INTEGER,
        raisecomSlotCardType                INTEGER,
        raisecomSlotCardDescr               OCTET STRING (SIZE (240))
    }
    
    raisecomSlotCardIndex OBJECT-TYPE
        SYNTAX  Unsigned32  
        MAX-ACCESS not-accessible
        STATUS current
        DESCRIPTION
            "The index of slot."
        ::= { raisecomSlotCardEntry 1 }   
    
    raisecomSlotCardSerialNumber OBJECT-TYPE
        SYNTAX  OCTET STRING (SIZE (32))
        MAX-ACCESS read-only
        STATUS current
        DESCRIPTION
            "Slot card serial number."
        ::= { raisecomSlotCardEntry 2 } 
        
    raisecomSlotCardState OBJECT-TYPE
        SYNTAX  INTEGER
		{
		    up(1),
		    down(2)
		}
	    MAX-ACCESS read-only
        STATUS current
        DESCRIPTION
            "Indicates whether the slot's card is up:
			 Up(1) means that the slot's card is up
			 Down(2) means that the slot's card is down."
        ::= { raisecomSlotCardEntry 3 }
    
    raisecomSlotCardType OBJECT-TYPE
        SYNTAX  INTEGER
		{
		    card-ptp-synce(1),
		    card-tdmop(2),
		    null(255)
		}
        MAX-ACCESS read-only
        STATUS current
        DESCRIPTION
            "Card type in the slot."
        ::= { raisecomSlotCardEntry 4 }    
        
    raisecomSlotCardDescr OBJECT-TYPE
        SYNTAX  OCTET STRING (SIZE (240))
        MAX-ACCESS read-only
        STATUS current
        DESCRIPTION
            "Description of card detail."
        ::= { raisecomSlotCardEntry 5 }  
END

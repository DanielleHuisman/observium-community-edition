--MibName=rcService
-- *****************************************************************
-- switch-service-mib.mib:  Raisecom service MIB file
--
-- 5 2013, yingjiangang
--
-- Copyright (c) 1996-2013 by Raisecom, Inc.
-- All rights reserved.  
--modify 
-- 04,20131223, guohm, add node rcServicePerfermanceTestType in  table rcServiceTable 
-- 03,20130913, guohm add rcServiceFarEndPointCosLabelCurrentTable add modify  rcServiceFarEndPointCosLabelTable
-- 02.20130725, yangzh,add node rcServiceEtherSamClearResult in table rcServiceTable 
-- 01.20130723, guohm,rcServiceNetworkInterfaceType节点增加枚举类型channel 
-- *****************************************************************
SWTICH-SERVICE-MIB  DEFINITIONS ::= BEGIN

IMPORTS
	iscomSwitch
		FROM RAISECOM-BASE-MIB
    Unsigned32               			
    	FROM SNMPv2-SMI    -- [RFC2578]  
	InetAddressType, InetAddress  
		FROM INET-ADDRESS-MIB  
	DateAndTime,TruthValue,TimeInterval,RowStatus,MacAddress
		FROM SNMPv2-TC;
        
	rcService MODULE-IDENTITY
		LAST-UPDATED    "201305130000Z"
		ORGANIZATION    "Raisecom, Inc."
		CONTACT-INFO                                    
                "       Raise Systems
                        
                Postal: Beijing,
                        China

                   Tel: 86-010-82884499

                E-mail: yingjiangang@raisecom.com"
        DESCRIPTION
                "description of Carrier Ethernet Service manage object."
                ::= { iscomSwitch 75} 
 
-- -------------------------------------------------------------
-- groups in the MIB
-- -------------------------------------------------------------
 
rcServiceScalar		OBJECT IDENTIFIER ::= {	rcService 1 }

rcServiceDefaultSdp1PortIndex OBJECT-TYPE           
        SYNTAX        INTEGER  
		MAX-ACCESS  read-write
        STATUS      current
        DESCRIPTION
               "The default service distribute point 1 port index."
        DEFVAL { 0 }
        ::= { rcServiceScalar 1 }

rcServiceDefaultSdp2PortIndex OBJECT-TYPE           
        SYNTAX        INTEGER  
		MAX-ACCESS  read-write
        STATUS      current
        DESCRIPTION
               "The default service distribute point 2 port index."
        DEFVAL { 0 }
        ::= { rcServiceScalar 2 }   
        
rcServiceEtherSamTrapEnable OBJECT-TYPE           
        SYNTAX        TruthValue  
		MAX-ACCESS  read-write
        STATUS      current
        DESCRIPTION
               "The service EtherSam Trap switch."
        ::= { rcServiceScalar 3 }


-- rcServiceCosLabelNameTable   

rcServiceCosLabelNameTable OBJECT-TYPE
    SYNTAX      SEQUENCE OF RcServiceCosLabelNameEntry
    MAX-ACCESS  not-accessible
    STATUS      current
    DESCRIPTION
        "CoS label name table"
    ::= { rcService 2 }

rcServiceCosLabelNameEntry   OBJECT-TYPE
    SYNTAX      RcServiceCosLabelNameEntry
    MAX-ACCESS  not-accessible
    STATUS      current
    DESCRIPTION
        "An entry in the rcServiceCosLabelTable. It define the name of the CoSLabel 1-8."
	INDEX        { rcServiceCosLabel }    
    ::={ rcServiceCosLabelNameTable 1 }
    
    RcServiceCosLabelNameEntry ::= SEQUENCE {
    rcServiceCosLabel			     INTEGER,
	rcServiceCosLabelName			 OCTET STRING		
	}

rcServiceCosLabel        OBJECT-TYPE
	SYNTAX      INTEGER(0..7)
    MAX-ACCESS  not-accessible
    STATUS      current
    DESCRIPTION
            "The Class of service label." 
	::= { rcServiceCosLabelNameEntry 1 }
	
rcServiceCosLabelName        OBJECT-TYPE
	SYNTAX      OCTET STRING(SIZE (0..16))
    MAX-ACCESS  read-write
    STATUS      current
    DESCRIPTION
            "The name of the CoSLabel, it may define like 'Gold','Sliver','Copper'. "   
    ::= { rcServiceCosLabelNameEntry 2 }    

-- rcServiceNetworkInterfaceTable   

rcServiceNetworkInterfaceTable OBJECT-TYPE
    SYNTAX      SEQUENCE OF RcServiceNetworkInterfaceEntry
    MAX-ACCESS  not-accessible
    STATUS      current
    DESCRIPTION
        "Service Network Interface table"
    ::= { rcService 3 }

rcServiceNetworkInterfaceEntry   OBJECT-TYPE
    SYNTAX      RcServiceNetworkInterfaceEntry
    MAX-ACCESS  not-accessible
    STATUS      current
    DESCRIPTION
        "An entry in the rcServiceNetworkInterfaceTable. It specifies the UNI/ENNI/INNI service attributes."
	INDEX        { rcServiceNetworkInterfacePortIndex }    
    ::={ rcServiceNetworkInterfaceTable 1 }
    
    RcServiceNetworkInterfaceEntry ::= SEQUENCE {
    rcServiceNetworkInterfacePortIndex				INTEGER,
	rcServiceNetworkInterfaceType					INTEGER,		
	rcServiceNetworkInterfaceID						OCTET STRING,		
	rcServiceNetworkInterfacePhysicalMedium			INTEGER,		
	rcServiceNetworkInterfaceSpeed					INTEGER,		
	rcServiceNetworkInterfaceDuplexMode				INTEGER,		
	rcServiceNetworkInterfaceMacLayer				INTEGER,		
	rcServiceNetworkInterfaceMtu					INTEGER,		
	rcServiceNetworkInterfaceServiceMultiplexing	INTEGER,		
	rcServiceNetworkInterfaceBundling				INTEGER,		
	rcServiceNetworkInterfaceAllToOneBundling		INTEGER,		
	rcServiceNetworkInterfaceDefaultCVlan			INTEGER,		
	rcServiceNetworkInterfacMaxEvcs					INTEGER,		
	rcServiceNetworkInterfaceMaxOvcs				INTEGER,		
	rcServiceNetworkInterfaceMaxCVlanPerOvcs		INTEGER,		
	rcServiceNetworkInterfaceInBwProfileIndex		INTEGER,		
	rcServiceNetworkInterfaceOutBwProfileIndex		INTEGER,		
	rcServiceNetworkInterfaceL2cpProfileIndex		INTEGER,		
	rcServiceNetworkInterfaceFrameFormat			INTEGER,		
	rcServiceNetworkInterfaceLinks					INTEGER,		
	rcServiceNetworkInterfaceResiliencyMechanisms	INTEGER,		
	rcServiceNetworkInterfaceMaxEndPointPerOvc		INTEGER		
	}

rcServiceNetworkInterfacePortIndex        OBJECT-TYPE
	SYNTAX      INTEGER
    MAX-ACCESS  not-accessible
    STATUS      current
    DESCRIPTION
            "The port index of the UNI/ENNI/INNI." 
	::= { rcServiceNetworkInterfaceEntry 1 }
	
rcServiceNetworkInterfaceType        OBJECT-TYPE
	SYNTAX      INTEGER {inni(0), enni(1), uni(2),channel(3)}
    MAX-ACCESS  read-write
    STATUS      current
    DESCRIPTION
            "The tye of the network interface. there are 3 type interface, inni(Internal-Network-to-Network Interface),
             enni(External-Network-to-Network Interface) and uni(User-to-Network Interface)."   
    ::= { rcServiceNetworkInterfaceEntry 2 }    
       
rcServiceNetworkInterfaceID        OBJECT-TYPE
	SYNTAX      OCTET STRING(SIZE (0..45))
    MAX-ACCESS  read-write
    STATUS      current
    DESCRIPTION
            "UNI/ENNI/INNI Identifier, Arbitrary text string to identify the UNI/ENNI/INNI."   
    ::= { rcServiceNetworkInterfaceEntry 3 }    

rcServiceNetworkInterfacePhysicalMedium        OBJECT-TYPE
	SYNTAX      INTEGER {dot3-unknownPhy(0), dot3-10BASE-T(5), dot3-100BASE-TX(16), dot3-100BASE-FX(18),
						dot3-1000BASE-X(22), dot3-1000BASE-T(30), dot3-10GBASE-X(31), dot3-10GBASE-R(33), dot3-10GBASE-W(37)}
	MAX-ACCESS  read-only
    STATUS      current
    DESCRIPTION
            "Physical Medium, UNI Type 2 Physical Interface except for PON interfaces."   
    ::= { rcServiceNetworkInterfaceEntry 4 }    

rcServiceNetworkInterfaceSpeed        OBJECT-TYPE
	SYNTAX      INTEGER {speedUnknown(0), m10(1), m100(2), autonegom10-100(3), autonegom10-100-1000(4),
						g1(5), g10(6), autonegofiber1000(7)}
	MAX-ACCESS  read-only
    STATUS      current
    DESCRIPTION
            "Speed, 10 Mbps, 100 Mbps, 10/100 Mbps Auto-negotiation, 10/100/1000 Mbps Auto-negotiation, 1 Gbps, 0 Gbps
            or  Auto-negotiation fiber 1G."   
    ::= { rcServiceNetworkInterfaceEntry 5 }    

rcServiceNetworkInterfaceDuplexMode        OBJECT-TYPE
	SYNTAX      INTEGER {duplexUnknown(0), duplexAutoNego(1), duplexFull(2), duplexHalf(3)}
	MAX-ACCESS  read-only
    STATUS      current
    DESCRIPTION
            "Duplex mode."   
    ::= { rcServiceNetworkInterfaceEntry 6 }    

rcServiceNetworkInterfaceMacLayer        OBJECT-TYPE
	SYNTAX      INTEGER {ieee802dot3-2005(0)}
	MAX-ACCESS  read-only
    STATUS      current
    DESCRIPTION
            "MAC Layer, IEEE 802.3-2005."   
    ::= { rcServiceNetworkInterfaceEntry 7 }    

rcServiceNetworkInterfaceMtu        OBJECT-TYPE
	SYNTAX      INTEGER 
	MAX-ACCESS  read-only
    STATUS      current
    DESCRIPTION
            "MTU Size, MUST be ≥ 1522."   
    ::= { rcServiceNetworkInterfaceEntry 8 }    

rcServiceNetworkInterfaceServiceMultiplexing        OBJECT-TYPE
	SYNTAX      TruthValue 
	MAX-ACCESS  read-only
    STATUS      current
    DESCRIPTION
            "Service Multiplexing, Yes or No. MUST be No if All to One Bundling is Yes."   
    ::= { rcServiceNetworkInterfaceEntry 9 }    

rcServiceNetworkInterfaceBundling        OBJECT-TYPE
	SYNTAX      TruthValue 
	MAX-ACCESS  read-only
    STATUS      current
    DESCRIPTION
            "Bundling, Yes or No. MUST be No if All to One Bundling is Yes."   
    ::= { rcServiceNetworkInterfaceEntry 10 }    

rcServiceNetworkInterfaceAllToOneBundling        OBJECT-TYPE
	SYNTAX      TruthValue 
	MAX-ACCESS  read-only
    STATUS      current
    DESCRIPTION
            "All to One Bundling, Yes or No. MUST be No if Bundling or Service Multiplexing is Yes."   
    ::= { rcServiceNetworkInterfaceEntry 11 }    

rcServiceNetworkInterfaceDefaultCVlan        OBJECT-TYPE
	SYNTAX      INTEGER(1..4094) 
	MAX-ACCESS  read-only
    STATUS      current
    DESCRIPTION
            "CE-VLAN ID for untagged and priority tagged Service Frames, MUST specify CE-VLAN ID 
            for untagged and priority tagged Service Frames in the range of 1-4094. This requirement 
            does not apply for services with all to one bundling at the UNI."   
    ::= { rcServiceNetworkInterfaceEntry 12 }    

rcServiceNetworkInterfacMaxEvcs        OBJECT-TYPE
	SYNTAX      INTEGER
	MAX-ACCESS  read-only
    STATUS      current
    DESCRIPTION
            "Maximum number of EVCs, MUST be an integer ≥ 1."   
    ::= { rcServiceNetworkInterfaceEntry 13 }    

rcServiceNetworkInterfaceMaxOvcs        OBJECT-TYPE
	SYNTAX      INTEGER 
	MAX-ACCESS  read-only
    STATUS      current
    DESCRIPTION
            "The maximum number of OVCst that the Operator can support at the ENNI.An integer greater than or equal to 1."   
    ::= { rcServiceNetworkInterfaceEntry 14 }    

rcServiceNetworkInterfaceInBwProfileIndex        OBJECT-TYPE
	SYNTAX      INTEGER 
	MAX-ACCESS  read-only
    STATUS      current
    DESCRIPTION
            "Ingress Bandwidth Profile Per UNI/ENNI.OPTIONAL. If supported, MUST specify <CIR, CBS, EIR, EBS, CM, CF>. 
            MUST NOT be combined with any other type of ingress bandwidth profile."   
    ::= { rcServiceNetworkInterfaceEntry 15 }    

rcServiceNetworkInterfaceOutBwProfileIndex      OBJECT-TYPE
	SYNTAX      INTEGER 
	MAX-ACCESS  read-only
    STATUS      current
    DESCRIPTION
            "Egress Bandwidth Profile Per UNI/ENNI.OPTIONAL. OPTIONAL. If supported, MUST specify <CIR, CBS, EIR, EBS, CM, CF>. 
            MUST NOT be combined with any other type of egress bandwidth profile."   
    ::= { rcServiceNetworkInterfaceEntry 16 }    

rcServiceNetworkInterfaceL2cpProfileIndex      OBJECT-TYPE
	SYNTAX      INTEGER 
	MAX-ACCESS  read-only
    STATUS      current
    DESCRIPTION
            "Layer 2 Control Protocols Processing Profile.OPTIONAL. OPTIONAL. For each protocol, MUST specify one of:
             Peer, Discard, Pass to EVC, or Peer and Pass to EVC."   
    ::= { rcServiceNetworkInterfaceEntry 17 }    

rcServiceNetworkInterfaceFrameFormat      OBJECT-TYPE
	SYNTAX      INTEGER {untag(0), tag(1), dtag(2)}
	MAX-ACCESS  read-only
    STATUS      current
    DESCRIPTION
            "The format of the PDUs at the ENNI. OPTIONAL. Frame formats as specified in  MEF26.1 Section 7.1.3."   
    ::= { rcServiceNetworkInterfaceEntry 18 }    

rcServiceNetworkInterfaceLinks      OBJECT-TYPE
	SYNTAX      INTEGER(1..2) 
	MAX-ACCESS  read-only
    STATUS      current
    DESCRIPTION
            "The number of physical links in the ENNI. An integer with value 1 or 2."   
    ::= { rcServiceNetworkInterfaceEntry 19 }    

rcServiceNetworkInterfaceResiliencyMechanisms      OBJECT-TYPE
	SYNTAX      INTEGER{none(0), linkaggregation(1), other(2)} 
	MAX-ACCESS  read-only
    STATUS      current
    DESCRIPTION
            "The method for protection, if any, against a failure. Link Aggregation, none, or other."   
    ::= { rcServiceNetworkInterfaceEntry 20 }    

rcServiceNetworkInterfaceMaxEndPointPerOvc      OBJECT-TYPE
	SYNTAX      INTEGER 
	MAX-ACCESS  read-only
    STATUS      current
    DESCRIPTION
            "The maximum number of OVCs that the Operator can support at the ENNI, An integer greater than or equal to 1."   
    ::= { rcServiceNetworkInterfaceEntry 21 }    

-- rcServiceNetworkInterfaceEndPointMapTable   

rcServiceNetworkInterfaceEndPointMapTable OBJECT-TYPE
    SYNTAX      SEQUENCE OF RcServiceNetworkInterfaceEndPointMapEntry
    MAX-ACCESS  not-accessible
    STATUS      current
    DESCRIPTION
        "Service Network Interface EndPoint mapping table"
    ::= { rcService 4 }

rcServiceNetworkInterfaceEndPointMapEntry   OBJECT-TYPE
    SYNTAX      RcServiceNetworkInterfaceEndPointMapEntry
    MAX-ACCESS  not-accessible
    STATUS      current
    DESCRIPTION
        "An entry in the rcServiceNetworkInterfaceEndPointMapTable. The map that associates each STagged ENNI Frame with an End Point."
	INDEX        { rcServiceNetworkInterfacePortIndex, rcServiceNetworkInterfaceEndPointMapSVlan }    
    ::={ rcServiceNetworkInterfaceEndPointMapTable 1 }
    
    RcServiceNetworkInterfaceEndPointMapEntry ::= SEQUENCE {
	rcServiceNetworkInterfaceEndPointMapSVlan					INTEGER,		
	rcServiceNetworkInterfaceEndPointMapEndPointID				OCTET STRING,		
	rcServiceNetworkInterfaceEndPointMapEndPointType			INTEGER		
	}

rcServiceNetworkInterfaceEndPointMapSVlan        OBJECT-TYPE
	SYNTAX      INTEGER
    MAX-ACCESS  not-accessible
    STATUS      current
    DESCRIPTION
            "The map that associates each STagged ENNI Frame with an EndPoint." 
	::= { rcServiceNetworkInterfaceEndPointMapEntry 1 }
	
rcServiceNetworkInterfaceEndPointMapEndPointID        OBJECT-TYPE
	SYNTAX       OCTET STRING(SIZE (0..91))
	MAX-ACCESS  read-only
    STATUS      current
    DESCRIPTION
            "Each S-Tagged ENNI Frame is associated with an OVC EndPoint."   
    ::= { rcServiceNetworkInterfaceEndPointMapEntry 2 }    

rcServiceNetworkInterfaceEndPointMapEndPointType        OBJECT-TYPE
	SYNTAX       INTEGER{ovc-endpoint(0), typex(1)}
	MAX-ACCESS  read-only
    STATUS      current
    DESCRIPTION
            "There are two types of End Point, OVC and Type X."   
    ::= { rcServiceNetworkInterfaceEndPointMapEntry 3 }    

-- rcServiceTable   

rcServiceTable OBJECT-TYPE
    SYNTAX      SEQUENCE OF RcServiceEntry
    MAX-ACCESS  not-accessible
    STATUS      current
    DESCRIPTION
        "EVC/OVC attribute table"
    ::= { rcService 5 }

rcServiceEntry   OBJECT-TYPE
    SYNTAX      RcServiceEntry
    MAX-ACCESS  not-accessible
    STATUS      current
    DESCRIPTION
        "An entry in the rcServiceTable. It specifies the EVC/OVC service attributes."
	INDEX        { rcServiceID}    
    ::={ rcServiceTable 1 }
    
    RcServiceEntry ::= SEQUENCE {
	rcServiceID								OCTET STRING,		
	rcServiceType							INTEGER,		
	rcServiceCustomerNameID					OCTET STRING,
	rcServiceMaxUnis						INTEGER,		
	rcServiceMaxEnnis						INTEGER,		
	rcServiceMTU							INTEGER,		
	rcServiceCVlanPreservation				TruthValue,		
	rcServiceCCosPreservation				TruthValue,		
	rcServiceSVlanPreservation				TruthValue,		
	rcServiceSCosPreservation				TruthValue,		
	rcServiceColorForward					TruthValue,		
	rcServiceUnicastDelivery				TruthValue,		
	rcServiceMulticastDelivery				TruthValue,		
	rcServiceBroadcastDelivery				TruthValue,		
	rcServiceL2cpPass						TruthValue,		
	rcServiceCosType						INTEGER,		
	rcServiceVCCosLabel						INTEGER,		
	rcServiceCosMapProfileIndex				INTEGER,		
	rcServiceDscpMapProfileIndex			INTEGER,		
	rcServiceSdpType						INTEGER,		
	rcServiceSdpIndex						INTEGER,		
	rcServicePTIndex						INTEGER,		
	rcServiceMaintenanceTimeStart			DateAndTime,		
	rcServiceMaintenanceTimeStop			DateAndTime,		
	rcServicePerfermanceTestScheduleLife	Unsigned32,		
	rcServicePerfermanceTestSchedulePeriod	Unsigned32,		
	rcServicePerfermanceTestScheduleInterval Unsigned32,		
	rcServicePerfermanceTestOperate			TruthValue,		
	rcServiceL2LoopbackEtherType			INTEGER,		
	rcServiceL2LoopbackOperate				TruthValue,		
	rcServiceEtherSamPerformanceDuration	INTEGER,		
	rcServiceEtherSamPerformanceBW			Unsigned32,		
	rcServiceEtherSamFlowProfileIndex		INTEGER,		
	rcServiceEtherSamCfgBypassUni	     	TruthValue,
	rcServiceEtherSamTestElapsedTime		TimeInterval,		
	rcServiceEtherSamTestType				INTEGER,		
	rcServiceEtherSamOperate				TruthValue,		
	rcServiceEtherSamTestResult				INTEGER,
	rcServiceEtherSamTimeCfgWillTake		TimeInterval,	
	rcServiceEtherSamClearResult			TruthValue,					
	rcServiceMdIndex						Unsigned32,		
	rcServiceMaIndex						Unsigned32,		
	rcServiceOperStatus						TruthValue,
	rcServiceCcStatus                       INTEGER,
	rcServicePerfermanceTestType		    INTEGER,
	rcServiceEtherSamSlaJitterType          INTEGER,
	rcServiceRowStatus						RowStatus	
	}

rcServiceID        OBJECT-TYPE
	SYNTAX      OCTET STRING(SIZE (0..45))
    MAX-ACCESS  not-accessible
    STATUS      current
    DESCRIPTION
            "An arbitrary string, unique across the MEN, for the EVC/OVC supporting the service instance.." 
	::= { rcServiceEntry 1 }
	
rcServiceType        OBJECT-TYPE
	SYNTAX      INTEGER{eline(0), elan(1), etree(2), eaccess(3)}
	MAX-ACCESS  read-create
    STATUS      current
    DESCRIPTION
            "An indication of the number and roles of the EVC/OVC EndPoints associated by the EVC/OVC.eline, elan, etree or eaccess."   
    ::= { rcServiceEntry 2 }    

rcServiceCustomerNameID        OBJECT-TYPE
	SYNTAX      OCTET STRING(SIZE (0..128))
	MAX-ACCESS  read-create
    STATUS      current
    DESCRIPTION
            "The customer of the service."   
    ::= { rcServiceEntry 3 }    

rcServiceMaxUnis        OBJECT-TYPE
	SYNTAX      INTEGER
	MAX-ACCESS  read-only
    STATUS      current
    DESCRIPTION
            "Maximum Number of UNIs."   
    ::= { rcServiceEntry 4 }    

rcServiceMaxEnnis        OBJECT-TYPE
	SYNTAX      INTEGER
	MAX-ACCESS  read-only
    STATUS      current
    DESCRIPTION
            "Maximum Number of ENNIs."   
    ::= { rcServiceEntry 5 }    

rcServiceMTU        OBJECT-TYPE
	SYNTAX      INTEGER
	MAX-ACCESS  read-only
    STATUS      current
    DESCRIPTION
            "EVC/OVC MTU size. MUST be ≤ minimum of UNI MTU sizes."   
    ::= { rcServiceEntry 6 }    

rcServiceCVlanPreservation        OBJECT-TYPE
	SYNTAX      TruthValue
	MAX-ACCESS  read-only
    STATUS      current
    DESCRIPTION
            "CE-VLAN ID Preservation. MUST be either Yes or No."   
    ::= { rcServiceEntry 7 }    

rcServiceCCosPreservation        OBJECT-TYPE
	SYNTAX      TruthValue
	MAX-ACCESS  read-only
    STATUS      current
    DESCRIPTION
            "CE-VLAN CoS Preservation. MUST be either Yes or No."   
    ::= { rcServiceEntry 8 }    

rcServiceSVlanPreservation        OBJECT-TYPE
	SYNTAX      TruthValue
	MAX-ACCESS  read-only
    STATUS      current
    DESCRIPTION
            "A relationship between the S-VLAN ID value of a frame at one ENNI and the S-VLAN ID value of the
				corresponding frame at another ENNI."   
    ::= { rcServiceEntry 9 }    

rcServiceSCosPreservation        OBJECT-TYPE
	SYNTAX      TruthValue
	MAX-ACCESS  read-only
    STATUS      current
    DESCRIPTION
            "A relationship between the S-VLAN PCP value of a frame at one ENNI and the S-VLAN PCP value of the
				corresponding frame at another ENNI."   
    ::= { rcServiceEntry 10 }    

rcServiceColorForward        OBJECT-TYPE
	SYNTAX      TruthValue
	MAX-ACCESS  read-only
    STATUS      current
    DESCRIPTION
            "The relationship between the Color of an egress ENNI Frame and the Color of the corresponding ingress
				ENNI Frame or Service Frame."   
    ::= { rcServiceEntry 11 }    

rcServiceUnicastDelivery        OBJECT-TYPE
	SYNTAX       TruthValue
	MAX-ACCESS  read-only
    STATUS      current
    DESCRIPTION
            "This attribute describes how ingress frames mapped to an EVC/OVC End Point with a unicast destination MAC address
				are delivered to the other External Interfaces with EVC/OVC End Points associated by the EVC/OVC."   
    ::= { rcServiceEntry 12 }    

rcServiceMulticastDelivery        OBJECT-TYPE
	SYNTAX       TruthValue
	MAX-ACCESS  read-only
    STATUS      current
    DESCRIPTION
            "This attribute describes how ingress frames mapped to an EVC/OVC End Point with a multicast destination MAC
			address are delivered to the other External Interfaces with EVC/OVC End Points associated by the EVC/OVC."   
    ::= { rcServiceEntry 13 }    

rcServiceBroadcastDelivery        OBJECT-TYPE
	SYNTAX       TruthValue
	MAX-ACCESS  read-only
    STATUS      current
    DESCRIPTION
            "This attribute describes how ingress frames mapped to an EVC/OVC End Point with the broadcast destination MAC
				address are delivered to the other External Interfaces with EVC/OVC End Points associated by the EVC/OVC."   
    ::= { rcServiceEntry 14 }    

rcServiceL2cpPass        OBJECT-TYPE
	SYNTAX      TruthValue
	MAX-ACCESS  read-only
    STATUS      current
    DESCRIPTION
            "The Layer 2 Control Protocols that are tunneled by the EVC/OVC."   
    ::= { rcServiceEntry 15 }    

rcServiceCosType        OBJECT-TYPE
	SYNTAX      INTEGER{cos-unknown(0), cos-baseon-service(1), cos-baseon-cos(2), cos-baseon-dscp(3)}
	MAX-ACCESS  read-only
    STATUS      current
    DESCRIPTION
            "Class of Service Identifier Based on EVC/OVC, Priority Code Point Field or DSCP."   
    ::= { rcServiceEntry 16 }    

rcServiceVCCosLabel        OBJECT-TYPE
	SYNTAX      INTEGER
	MAX-ACCESS  read-only
    STATUS      current
    DESCRIPTION
            "Class of Service Identifier Based on EVC/OVC."   
    ::= { rcServiceEntry 17 }    

rcServiceCosMapProfileIndex        OBJECT-TYPE
	SYNTAX      INTEGER
	MAX-ACCESS  read-only
    STATUS      current
    DESCRIPTION
            "The index rcQosCosToPriIndex of the table rcQosMappingCosToPriEntry."   
    ::= { rcServiceEntry 18 }    

rcServiceDscpMapProfileIndex        OBJECT-TYPE
	SYNTAX      INTEGER
	MAX-ACCESS  read-only
    STATUS      current
    DESCRIPTION
            "The index rcQosDscpToPriIndex of the table rcQosMappingDscpToPriEntry."   
    ::= { rcServiceEntry 19 }    

rcServiceSdpType        OBJECT-TYPE
	SYNTAX      INTEGER{sdp-none(0), sdp-vlan(1), sdp-mpls(2)}
	MAX-ACCESS  read-create
    STATUS      current
    DESCRIPTION
            "The type of service distribution point."   
    ::= { rcServiceEntry 20 }    

rcServiceSdpIndex        OBJECT-TYPE
	SYNTAX       INTEGER
	MAX-ACCESS  read-create
    STATUS      current
    DESCRIPTION
            "When rcServiceSdpType is sdp-vlan, this field mean S-Vlan ID."   
    ::= { rcServiceEntry 21 }    

rcServicePTIndex        OBJECT-TYPE
	SYNTAX      INTEGER
	MAX-ACCESS  read-create
    STATUS      current
    DESCRIPTION
            "rcSlaThresholdProfileNum of rcSlaThresholdProfileEntry, the Frame delivery performance definitions and objectives for frames between External Interfaces."   
    ::= { rcServiceEntry 22 }    

rcServiceMaintenanceTimeStart        OBJECT-TYPE
	SYNTAX      DateAndTime
	MAX-ACCESS  read-create
    STATUS      current
    DESCRIPTION
            "The Service Maintenance Start Time."   
    ::= { rcServiceEntry 23 }    

rcServiceMaintenanceTimeStop        OBJECT-TYPE
	SYNTAX      DateAndTime
	MAX-ACCESS  read-create
    STATUS      current
    DESCRIPTION
            "The Service Maintenance Stop Time."   
    ::= { rcServiceEntry 24 }    

rcServicePerfermanceTestScheduleLife        OBJECT-TYPE
	SYNTAX      Unsigned32
	MAX-ACCESS  read-create
    STATUS      current
    DESCRIPTION
            "This object specifies the time duration over the whole schedule process."   
    ::= { rcServiceEntry 25 }    

rcServicePerfermanceTestSchedulePeriod        OBJECT-TYPE
	SYNTAX      Unsigned32
	MAX-ACCESS  read-create
    STATUS      current
    DESCRIPTION
            "This object specifies the duration between two SLA test 
            	which includes all of probes schedule process in test."   
    ::= { rcServiceEntry 26 }    

rcServicePerfermanceTestScheduleInterval        OBJECT-TYPE
	SYNTAX      Unsigned32
	MAX-ACCESS  read-create
    STATUS      current
    DESCRIPTION
            "This value specifies the inter-frame delay between Ethernet
        frames that need to be transmitted to the target device.
        This object is applicable to 'Jitter' operation only."   
    ::= { rcServiceEntry 27 }    

rcServicePerfermanceTestOperate        OBJECT-TYPE
	SYNTAX      TruthValue
	MAX-ACCESS  read-create
    STATUS      current
    DESCRIPTION
            "enable/disable perfermance test of the service."   
    ::= { rcServiceEntry 28 }    

rcServiceL2LoopbackEtherType        OBJECT-TYPE
	SYNTAX      INTEGER
	MAX-ACCESS  read-create
    STATUS      current
    DESCRIPTION
            "Ethertype of etherSam test frame.the default value is 0x08a0"      
    DEFVAL{ 2208 }  
    ::= { rcServiceEntry 29 }    

rcServiceL2LoopbackOperate        OBJECT-TYPE
	SYNTAX      TruthValue
	MAX-ACCESS  read-create
    STATUS      current
    DESCRIPTION
            "enable/disable L2 loopback of the service."   
    ::= { rcServiceEntry 30 }    

rcServiceEtherSamPerformanceDuration        OBJECT-TYPE
	SYNTAX      INTEGER(0|5..1440)
	MAX-ACCESS  read-create
    STATUS      current
    DESCRIPTION
            "EtherSam Performance Test Duration(in Min),'0' means testing untill doing stop operation."   
    ::= { rcServiceEntry 31 }    

rcServiceEtherSamPerformanceBW        OBJECT-TYPE
	SYNTAX      Unsigned32 (0..100000)
    UNITS       "milli-percent"
	MAX-ACCESS  read-create
    STATUS      current
    DESCRIPTION
            "The percentage oPerformation bandWidth.if this value is not configed,
            it will be the same as cir of the service."  
    ::= { rcServiceEntry 32 }   
     
rcServiceEtherSamFlowProfileIndex        OBJECT-TYPE
	SYNTAX      INTEGER(1..10)
	MAX-ACCESS  read-create
    STATUS      current
    DESCRIPTION
             "Number of EtherSam profile."  
    ::= { rcServiceEntry 33 }    

rcServiceEtherSamCfgBypassUni OBJECT-TYPE
    SYNTAX      TruthValue
    MAX-ACCESS  read-create
    STATUS      current
    DESCRIPTION
            "This objest controls the test flow whether bypass the uni during the configuration test." 
    DEFVAL { false }            
    ::= { rcServiceEntry 34 }    

rcServiceEtherSamTestElapsedTime        OBJECT-TYPE
	SYNTAX      TimeInterval
	MAX-ACCESS  read-only
    STATUS      current
    DESCRIPTION
             "The pass time after the EthernetSam test start(0.01 seconds)."  
    ::= { rcServiceEntry 35 }    
    
rcServiceEtherSamTestType        OBJECT-TYPE
	SYNTAX      INTEGER{
	            configuration (1),
                performance   (2),
                both          (3),
                rfc2544       (4),
                performance-inservice(5)
                }
	MAX-ACCESS  read-create
    STATUS      current
    DESCRIPTION
             "Service Test Type of EtherSam."  
    ::= { rcServiceEntry 36 } 
       
rcServiceEtherSamOperate        OBJECT-TYPE
	SYNTAX      TruthValue
	MAX-ACCESS  read-create
    STATUS      current
    DESCRIPTION
             "Enable/Disable EtherSam Test."  
    ::= { rcServiceEntry 37 }                  
    
rcServiceEtherSamTestResult        OBJECT-TYPE
	SYNTAX      INTEGER{
	            pass   (1),
	            fail   (2)
	            }
	MAX-ACCESS  read-only
    STATUS      current
    DESCRIPTION
             "Result of all the etherSam service test."  
    ::= { rcServiceEntry 38 }  

rcServiceEtherSamTimeCfgWillTake OBJECT-TYPE
    SYNTAX      TimeInterval
    MAX-ACCESS  read-only
    STATUS      current
    DESCRIPTION
            "The time that will be took if starting the configuration test(0.01 seconds)." 
    ::= { rcServiceEntry 39 }   

rcServiceEtherSamClearResult OBJECT-TYPE
    SYNTAX      TruthValue
    MAX-ACCESS  read-create
    STATUS      current
    DESCRIPTION
            "Set this object TRUE to clear the result of service ethernetsam test. 
             When reading this object, it is always FALSE." 
    DEFVAL { false }            
    ::= { rcServiceEntry 40 }    
          
rcServiceMdIndex        OBJECT-TYPE
	SYNTAX      Unsigned32
	MAX-ACCESS  read-only
    STATUS      current
    DESCRIPTION
             "The index to the Maintenance Domain table."  
    ::= { rcServiceEntry 41 }   
     
rcServiceMaIndex        OBJECT-TYPE
	SYNTAX      Unsigned32
	MAX-ACCESS  read-only
    STATUS      current
    DESCRIPTION
       "Index of the MA table dot1agCfmMdMaNextIndex needs to
        be inspected to find an available index for row-creation.
       "
    ::= { rcServiceEntry 42 }    
    
rcServiceOperStatus        OBJECT-TYPE
	SYNTAX      TruthValue
	MAX-ACCESS  read-only
    STATUS      current
    DESCRIPTION
       "Service Operate status.
       "
    ::= { rcServiceEntry 43 }    
    
rcServiceCcStatus           OBJECT-TYPE 
	SYNTAX      INTEGER{
	            full-work(0),
                part-work(1),
                no-work(2)
                }
	MAX-ACCESS  read-only
    STATUS      current
    DESCRIPTION
            "The CC status of the Service."   
    ::= { rcServiceEntry 44 }   
    
rcServicePerfermanceTestType        OBJECT-TYPE
	SYNTAX      INTEGER{
	            lmLmm (1),
                lmSlm   (2)
                }
	MAX-ACCESS  read-create
    STATUS      current
    DESCRIPTION
             "This object specifies what type of Loss Measurementwill be performed. 	
 	          lmLmm(1)        LMM SOAM PDU generated and received LMR responses tracked
 	          lmSlm(2)        SLM SOAM PDU generated and received SLR responses tracked."  
    ::= { rcServiceEntry 45 }

rcServiceEtherSamSlaJitterType        OBJECT-TYPE
	SYNTAX      INTEGER{
	            dm (1),
                l2loopback   (2)
                }
	MAX-ACCESS  read-create
    STATUS      current
    DESCRIPTION
             "This object specifies what type of Delay Measurement the far-end support. 	
 	          dm(1)                The far-end support DM test
 	          l2loopback(2)        The far-end support l2 loopback test."  
    ::= { rcServiceEntry 46 }
    
rcServiceRowStatus        OBJECT-TYPE
	SYNTAX      RowStatus
	MAX-ACCESS  read-create
    STATUS      current
    DESCRIPTION
      "The status of the row.
       "
    ::= { rcServiceEntry 100 }    
    
    
-- rcServiceCustomerTable   

rcServiceCustomerTable OBJECT-TYPE
    SYNTAX      SEQUENCE OF RcServiceCustomerEntry
    MAX-ACCESS  not-accessible
    STATUS      current
    DESCRIPTION
        "Customer attribute table."
    ::= { rcService 6 }

rcServiceCustomerEntry   OBJECT-TYPE
    SYNTAX      RcServiceCustomerEntry
    MAX-ACCESS  not-accessible
    STATUS      current
    DESCRIPTION
        "An entry in the rcServiceCustomerTable. It specifies the customer attributes."
	INDEX        { rcServiceCustomerName}    
    ::={ rcServiceCustomerTable 1 }
    
    RcServiceCustomerEntry ::= SEQUENCE {
	rcServiceCustomerName					OCTET STRING,		
	rcServiceCustomerContact				OCTET STRING,		
	rcServiceCustomerPhone					OCTET STRING,
	rcServiceCustomerRowStatus				RowStatus	
	}

rcServiceCustomerName        OBJECT-TYPE
	SYNTAX      OCTET STRING(SIZE (0..128))
    MAX-ACCESS  not-accessible
    STATUS      current
    DESCRIPTION
            "The name of the customer." 
	::= { rcServiceCustomerEntry 1 }
	
rcServiceCustomerContact        OBJECT-TYPE
	SYNTAX      OCTET STRING(SIZE (0..128))
	MAX-ACCESS  read-create
    STATUS      current
    DESCRIPTION
            "The customer contact information."   
    ::= { rcServiceCustomerEntry 2 }    

rcServiceCustomerPhone        OBJECT-TYPE
	SYNTAX      OCTET STRING(SIZE (0..32))
	MAX-ACCESS  read-create
    STATUS      current
    DESCRIPTION
            "The customer's phone bunber."   
    ::= { rcServiceCustomerEntry 3 }    
    
rcServiceCustomerRowStatus        OBJECT-TYPE
	SYNTAX      RowStatus
	MAX-ACCESS  read-create
    STATUS      current
    DESCRIPTION
      "The status of the row.
       "
    ::= { rcServiceCustomerEntry 4 }  
      
-- rcServiceCosLabelTable   

rcServiceCosLabelTable OBJECT-TYPE
    SYNTAX      SEQUENCE OF RcServiceCosLabelEntry
    MAX-ACCESS  not-accessible
    STATUS      current
    DESCRIPTION
        "Service CoSLabel attribute table."
    ::= { rcService 7 }

rcServiceCosLabelEntry   OBJECT-TYPE
    SYNTAX      RcServiceCosLabelEntry
    MAX-ACCESS  not-accessible
    STATUS      current
    DESCRIPTION
        "An entry in the rcServiceCosLabelTable. It specifies the service CoSLabel attributes."
	INDEX        { rcServiceID,rcServiceCosLabel}    
    ::={ rcServiceCosLabelTable 1 }
    
    RcServiceCosLabelEntry ::= SEQUENCE {
	rcServiceCosLabelPerfermanceTestEnable	TruthValue,		
	rcServiceCosLabelEtherSAMEnable			TruthValue
	}

	
rcServiceCosLabelPerfermanceTestEnable        OBJECT-TYPE
	SYNTAX      TruthValue
	MAX-ACCESS  read-write
    STATUS      current
    DESCRIPTION
            "Enable/disable the Perfermance Test at this service CoSLabel."   
    ::= { rcServiceCosLabelEntry 1 }    

rcServiceCosLabelEtherSAMEnable        OBJECT-TYPE
	SYNTAX      TruthValue
	MAX-ACCESS  read-write
    STATUS      current
    DESCRIPTION
            "Enable/disable the EtherSAM at this service CoSLabel."   
    ::= { rcServiceCosLabelEntry 2 }    

-- rcServiceEndPointTable   

rcServiceEndPointTable OBJECT-TYPE
    SYNTAX      SEQUENCE OF RcServiceEndPointEntry
    MAX-ACCESS  not-accessible
    STATUS      current
    DESCRIPTION
        "Service EndPoint attribute table."
    ::= { rcService 8 }

rcServiceEndPointEntry   OBJECT-TYPE
    SYNTAX      RcServiceEndPointEntry
    MAX-ACCESS  not-accessible
    STATUS      current
    DESCRIPTION
        "An entry in the rcServiceEndPointTable. It specifies the service EndPoint attributes."
	INDEX        { rcServiceID,rcServiceNetworkInterfaceID}    
    ::={ rcServiceEndPointTable 1 }
    
    RcServiceEndPointEntry ::= SEQUENCE {
	rcServiceEndPointType				INTEGER,		
	rcServiceEndPointMPType				INTEGER,
	rcServiceEndPointMapCVlans			OCTET STRING,
	rcServiceEndPointInBwProfileIndex	INTEGER,
	rcServiceEndPointOutBwProfileIndex	INTEGER,
	rcServiceEndPointLMep				Unsigned32,
	rcServiceEndPointCCEnable			TruthValue,
	rcServiceEndPointPMEnable			TruthValue,
	rcServiceEndPointRowStatus			RowStatus
	}
	
rcServiceEndPointType        OBJECT-TYPE
	SYNTAX      INTEGER{
	            evc-per-uni (1),
                ovc-per-uni (2),
                ovc-per-enni (3)
                }
	MAX-ACCESS  read-only
    STATUS      current
    DESCRIPTION
            "The Endpoint type, evcPerUni/ovcPerUni/ovcPerEnni."   
    ::= { rcServiceEndPointEntry 1 }    

rcServiceEndPointMPType        OBJECT-TYPE
	SYNTAX      INTEGER{
	            root (1),
                leaf (2)
                }
	MAX-ACCESS  read-create
    STATUS      current
    DESCRIPTION
            "EndPoint MultiPoint type."   
    ::= { rcServiceEndPointEntry 2 }    

rcServiceEndPointMapCVlans        OBJECT-TYPE
	SYNTAX      OCTET STRING (SIZE (512))
	MAX-ACCESS  read-only
    STATUS      current
    DESCRIPTION
      "The mapping table of CE-VLAN IDs to the EVC/OVC at the UNI."
    ::= { rcServiceEndPointEntry 3 }    
     
rcServiceEndPointInBwProfileIndex        OBJECT-TYPE
	SYNTAX      INTEGER 
	MAX-ACCESS  read-only
    STATUS      current
    DESCRIPTION
            "If supported, MUST specify <CIR, CBS, EIR, EBS, CM, CF> Ingress Bandwidth Profile Per EVC/OVC.
             MUST NOT be combined with any other type of ingress bandwidth profile."   
    ::= { rcServiceEndPointEntry 4 }    

rcServiceEndPointOutBwProfileIndex        OBJECT-TYPE
	SYNTAX      INTEGER 
	MAX-ACCESS  read-only
    STATUS      current
    DESCRIPTION
            "If supported, MUST specify <CIR, CBS, EIR, EBS, CM, CF> Ingress Bandwidth Profile Per EVC/OVC.
             MUST NOT be combined with any other type of egress bandwidth profile."   
    ::= { rcServiceEndPointEntry 5 }    

rcServiceEndPointLMep        OBJECT-TYPE
	SYNTAX      Unsigned32 (1..8191) 
	MAX-ACCESS  read-only
    STATUS      current
    DESCRIPTION
            "identifying a specific Maintenance  association End Point."   
    ::= { rcServiceEndPointEntry 6 }    

rcServiceEndPointCCEnable        OBJECT-TYPE
	SYNTAX      TruthValue
	MAX-ACCESS  read-only
    STATUS      current
    DESCRIPTION
            "Enable/disable the cc at the EndPoint."   
    ::= { rcServiceEndPointEntry 7 }
        
rcServiceEndPointPMEnable        OBJECT-TYPE
	SYNTAX      TruthValue
	MAX-ACCESS  read-only
    STATUS      current
    DESCRIPTION
            "Enable/disable the PM at the EndPoint."   
    ::= { rcServiceEndPointEntry 8 }     
    
rcServiceEndPointRowStatus        OBJECT-TYPE
	SYNTAX      RowStatus
	MAX-ACCESS  read-create
    STATUS      current
    DESCRIPTION
      "The status of the row.
       "
    ::= { rcServiceEndPointEntry 100 }    

-- rcServicesEndPointCosLabelTable   

rcServicesEndPointCosLabelTable OBJECT-TYPE
    SYNTAX      SEQUENCE OF RcServicesEndPointCosLabelEntry
    MAX-ACCESS  not-accessible
    STATUS      current
    DESCRIPTION
        "End Point CoSLabel attribute table."
    ::= { rcService 9 }

rcServicesEndPointCosLabelEntry   OBJECT-TYPE
    SYNTAX      RcServicesEndPointCosLabelEntry
    MAX-ACCESS  not-accessible
    STATUS      current
    DESCRIPTION
        "An entry in the rcServicesEndPointCosLabelTable. It specifies the EndPoint CoSLabel attributes."
	INDEX        { rcServiceID,rcServiceNetworkInterfaceID,rcServiceCosLabel}    
    ::={ rcServicesEndPointCosLabelTable 1 }
    
    RcServicesEndPointCosLabelEntry ::= SEQUENCE {
	rcServiceEndPointCosLabelInBwProfileIndex	INTEGER,		
	rcServiceEndPointCosLabelOutBwProfileIndex	INTEGER
	}

	
rcServiceEndPointCosLabelInBwProfileIndex        OBJECT-TYPE
	SYNTAX      INTEGER 
	MAX-ACCESS  read-only
    STATUS      current
    DESCRIPTION
            "If supported, MUST specify <CIR, CBS, EIR, EBS, CM, CF> Ingress Bandwidth Profile Per CoS ID.
             MUST NOT be combined with any other type of ingress bandwidth profile."   
    ::= { rcServicesEndPointCosLabelEntry 1 }    

rcServiceEndPointCosLabelOutBwProfileIndex        OBJECT-TYPE
	SYNTAX      INTEGER 
	MAX-ACCESS  read-only
    STATUS      current
    DESCRIPTION
            "If supported, MUST specify <CIR, CBS, EIR, EBS, CM, CF> Ingress Bandwidth Profile Per CoS ID.
             MUST NOT be combined with any other type of egress bandwidth profile."   
    ::= { rcServicesEndPointCosLabelEntry 2 }    


-- rcServiceFarEndPointTable   

rcServiceFarEndPointTable OBJECT-TYPE
    SYNTAX      SEQUENCE OF RcServiceFarEndPointEntry
    MAX-ACCESS  not-accessible
    STATUS      current
    DESCRIPTION
        "Service FarEndPoint attribute table."
    ::= { rcService 10 }

rcServiceFarEndPointEntry   OBJECT-TYPE
    SYNTAX      RcServiceFarEndPointEntry
    MAX-ACCESS  not-accessible
    STATUS      current
    DESCRIPTION
        "An entry in the rcServiceFarEndPointTable. It specifies the service FarEndPoint attributes."
	INDEX        { rcServiceID,rcServiceNetworkInterfaceID,rcServiceFarEndNetworkInterfaceID}    
    ::={ rcServiceFarEndPointTable 1 }
    
    RcServiceFarEndPointEntry ::= SEQUENCE {
	rcServiceFarEndNetworkInterfaceID			OCTET STRING,		
	rcServiceFarEndPointRMep					Unsigned32,
	rcServiceFarEndPointPerfermanceTestEnable	TruthValue,
	rcServiceFarEndPointEtherSAMEnable			TruthValue,
	rcServiceFarEndPointL2LoopbackEnable		TruthValue,
	rcServiceFarEndPointCcStatus                INTEGER,
	rcServiceFarEndPointIPAddressType           InetAddressType,  
	rcServiceFarEndPointIPAddress               InetAddress,
	rcServiceFarEndPointMacAddress              MacAddress,
	rcServiceFarEndPointType                    INTEGER,
	rcServiceFarEndPointRowStatus				RowStatus
	}
	
rcServiceFarEndNetworkInterfaceID        OBJECT-TYPE
	SYNTAX      OCTET STRING(SIZE (0..45))
    MAX-ACCESS  read-create
    STATUS      current
    DESCRIPTION
            "Remote UNI/ENNI Identifier, Arbitrary text string to identify the UNI/ENNI."   
    ::= { rcServiceFarEndPointEntry 1 }    

rcServiceFarEndPointRMep        OBJECT-TYPE
	SYNTAX      Unsigned32 (1..8191) 
	MAX-ACCESS  read-create
    STATUS      current
    DESCRIPTION
            "identifying a specific Maintenance point association remote End Point."   
    ::= { rcServiceFarEndPointEntry 2 }    

rcServiceFarEndPointPerfermanceTestEnable        OBJECT-TYPE
	SYNTAX      TruthValue
	MAX-ACCESS  read-create
    STATUS      current
    DESCRIPTION
            "Enable/disable the PerfermanceTest to the remote EndPoint."   
    ::= { rcServiceFarEndPointEntry 3 }     

rcServiceFarEndPointEtherSAMEnable        OBJECT-TYPE
	SYNTAX      TruthValue
	MAX-ACCESS  read-create
    STATUS      current
    DESCRIPTION
            "Enable/disable the EtherSAM to the remote EndPoint."   
    ::= { rcServiceFarEndPointEntry 4 }     

rcServiceFarEndPointL2LoopbackEnable        OBJECT-TYPE
	SYNTAX      TruthValue
	MAX-ACCESS  read-create
    STATUS      current
    DESCRIPTION
            "Enable/disable the L2 Loopback to the FarEndPoint."   
    ::= { rcServiceFarEndPointEntry 5 }   
    
rcServiceFarEndPointCcStatus           OBJECT-TYPE 
	SYNTAX      INTEGER{  
	            DEFECT-NONE(0),
                DEFECT-RDI-CCM(1),
                DEFECT-MAC-STATUS(2),
                DEFECT-REMOTE-CCM(3),
                DEFECT-ERROR-CCM(4),
                DEFECT-XCON-CCM(5)
	                  }
	MAX-ACCESS  read-only
    STATUS      current
    DESCRIPTION
            "The CC status to the FarEndPoint."   
    ::= { rcServiceFarEndPointEntry 6 }   

rcServiceFarEndPointIPAddressType  OBJECT-TYPE
	    SYNTAX     InetAddressType
	    MAX-ACCESS read-create
	    STATUS     current
	    DESCRIPTION 
	       	 	"The type of Internet address for all the objects with SYNTAX
         		InetAddress and  in this entry."
	    ::= { rcServiceFarEndPointEntry 7 }
	    
rcServiceFarEndPointIPAddress  OBJECT-TYPE
	    SYNTAX     InetAddress
	    MAX-ACCESS read-create
	    STATUS     current
	    DESCRIPTION 
	       	 	"identifying a IP address association remote End Point."
	    ::= { rcServiceFarEndPointEntry 8 } 

rcServiceFarEndPointMacAddress  OBJECT-TYPE
	    SYNTAX     MacAddress
	    MAX-ACCESS read-create
	    STATUS     current
	    DESCRIPTION 
	       	 	"identifying a MAC address association remote End Point."
	    ::= { rcServiceFarEndPointEntry 9 } 		

rcServiceFarEndPointType           OBJECT-TYPE 
	SYNTAX      INTEGER{  
                farend-rmep(1),
                farend-ip(2),
                farend_mac(3)
 	                  }
	MAX-ACCESS  read-create
    STATUS      current
    DESCRIPTION
            "The Type of the FarEndPoint."   
    ::= { rcServiceFarEndPointEntry 10 }   
	
rcServiceFarEndPointRowStatus        OBJECT-TYPE
	SYNTAX     RowStatus
	MAX-ACCESS  read-create
    STATUS      current
    DESCRIPTION
      "The status of the row.
       "
    ::= { rcServiceFarEndPointEntry 100 }    

-- rcServiceFarEndPointCosLabelTable   

rcServiceFarEndPointCosLabelTable OBJECT-TYPE
    SYNTAX      SEQUENCE OF RcServiceFarEndPointCosLabelEntry
    MAX-ACCESS  not-accessible
    STATUS      current
    DESCRIPTION
        "Service FarEndPoint CosLabel attribute table."
    ::= { rcService 11 }

rcServiceFarEndPointCosLabelEntry   OBJECT-TYPE
    SYNTAX      RcServiceFarEndPointCosLabelEntry
    MAX-ACCESS  not-accessible
    STATUS      current
    DESCRIPTION
        "An entry in the rcServiceFarEndPointCosLabelTable. It specifies the service FarEndPoint CosLabel attributes."
	INDEX        { rcServiceID,rcServiceNetworkInterfaceID,rcServiceFarEndNetworkInterfaceID,rcServiceCosLabel}    
    ::={ rcServiceFarEndPointCosLabelTable 1 }
    
    RcServiceFarEndPointCosLabelEntry ::= SEQUENCE {
	rcServiceFarEndPointCosLabelShortStartTime		        DateAndTime,		
	rcServiceFarEndPointCosLabelShortTwowayFD		        Unsigned32, 
	rcServiceFarEndPointCosLabelShortTwowayMaxFD	        Unsigned32,    --new
	rcServiceFarEndPointCosLabelShortTwowayMinFD	        Unsigned32,    --new
	rcServiceFarEndPointCosLabelShortTwowayMFD		        Unsigned32,
	rcServiceFarEndPointCosLabelShortTwowayFDR		        Unsigned32,
	rcServiceFarEndPointCosLabelShortTwowayIFDV		        Unsigned32,
	rcServiceFarEndPointCosLabelShortTwowayMaxIFDV	        Unsigned32,    --new
    rcServiceFarEndPointCosLabelShortTwowayMinIFDV	        Unsigned32,    --new
    rcServiceFarEndPointCosLabelShortTwowayMIFDV	        Unsigned32,    --new
	rcServiceFarEndPointCosLabelShortForwardFLR		        Unsigned32,
	rcServiceFarEndPointCosLabelShortBackwardFLR	        Unsigned32, 
	rcServiceFarEndPointCosLabelShortForwardAvail	        Unsigned32,
	rcServiceFarEndPointCosLabelShortBackwardAvail	        Unsigned32,
	rcServiceFarEndPointCosLabelShortForwardHLI		        Unsigned32,
	rcServiceFarEndPointCosLabelShortBackwardHLI	        Unsigned32,
	rcServiceFarEndPointCosLabelShortForwardCHLI	        Unsigned32,
	rcServiceFarEndPointCosLabelShortBackwardCHLI	        Unsigned32, 
    rcServiceFarEndPointCosLabelShortForwardFrameLost       Unsigned32,      --new
	rcServiceFarEndPointCosLabelShortBackwardFrameLost      Unsigned32,      --new
	rcServiceFarEndPointCosLabelShortForwardUnAvailSeconds  Unsigned32,      --new
	rcServiceFarEndPointCosLabelShortBackwardUnAvailSeconds Unsigned32, 	 --new
	rcServiceFarEndPointCosLabelLongStartTime		        DateAndTime,		
	rcServiceFarEndPointCosLabelLongTwowayFD		        Unsigned32,
	rcServiceFarEndPointCosLabelLongTwowayFDR		        Unsigned32,
	rcServiceFarEndPointCosLabelLongTwowayMFD		        Unsigned32,
	rcServiceFarEndPointCosLabelSlaConfigDMOperId	        Unsigned32,
	rcServiceFarEndPointCosLabelSlaConfigLMOperId	        Unsigned32,
	rcServiceFarEndPointCosLabelEtherSamServiceIndex        INTEGER,   
	rcServiceFarEndPointCosLabelLongTwowayMaxFD	            Unsigned32,      --new
	rcServiceFarEndPointCosLabelLongTwowayMinFD	            Unsigned32, 	 --new
	rcServiceFarEndPointCosLabelLongTwowayIFDV		        Unsigned32, 
	rcServiceFarEndPointCosLabelLongTwowayMaxIFDV	        Unsigned32,      --new
    rcServiceFarEndPointCosLabelLongTwowayMinIFDV	        Unsigned32,      --new
    rcServiceFarEndPointCosLabelLongTwowayMIFDV	            Unsigned32,      --new
	rcServiceFarEndPointCosLabelLongForwardFLR		        Unsigned32,
	rcServiceFarEndPointCosLabelLongBackwardFLR		        Unsigned32,
	rcServiceFarEndPointCosLabelLongForwardAvail	        Unsigned32,
	rcServiceFarEndPointCosLabelLongBackwardAvail		    Unsigned32,
	rcServiceFarEndPointCosLabelLongForwardHLI		        Unsigned32,
	rcServiceFarEndPointCosLabelLongBackwardHLI		        Unsigned32,
	rcServiceFarEndPointCosLabelLongForwardCHLI		        Unsigned32,
	rcServiceFarEndPointCosLabelLongBackwardCHLI	        Unsigned32,
    rcServiceFarEndPointCosLabelLongForwardFrameLost        Unsigned32,      --new
	rcServiceFarEndPointCosLabelLongBackwardFrameLost       Unsigned32,      --new
	rcServiceFarEndPointCosLabelLongForwardUnAvailSeconds   Unsigned32,      --new
	rcServiceFarEndPointCosLabelLongBackwardUnAvailSeconds  Unsigned32       --new

	}
	

rcServiceFarEndPointCosLabelShortStartTime        OBJECT-TYPE
	SYNTAX       DateAndTime
	MAX-ACCESS  read-only
    STATUS      current
    DESCRIPTION
            "The short period Start Time."   
    ::= { rcServiceFarEndPointCosLabelEntry 1 }    


rcServiceFarEndPointCosLabelShortTwowayFD        OBJECT-TYPE
    SYNTAX      Unsigned32
    UNITS       "microseconds"
    MAX-ACCESS  read-only
    STATUS      current
    DESCRIPTION
       "This object contains the Last short period frame delay 
       in the twoway direction calculated .      
       "
    ::= { rcServiceFarEndPointCosLabelEntry 2 }       
    
rcServiceFarEndPointCosLabelShortTwowayMaxFD        OBJECT-TYPE
    SYNTAX      Unsigned32
    UNITS       "microseconds"
    MAX-ACCESS  read-only
    STATUS      current
    DESCRIPTION
       "This object contains the Last short period max frame delay 
       in the twoway direction calculated .      
       "
    ::= { rcServiceFarEndPointCosLabelEntry 3 }

rcServiceFarEndPointCosLabelShortTwowayMinFD        OBJECT-TYPE
    SYNTAX      Unsigned32
    UNITS       "microseconds"
    MAX-ACCESS  read-only
    STATUS      current
    DESCRIPTION
       "This object contains the Last short period min frame delay 
       in the twoway direction calculated .      
       "
    ::= { rcServiceFarEndPointCosLabelEntry 4 }

rcServiceFarEndPointCosLabelShortTwowayMFD        OBJECT-TYPE
    SYNTAX      Unsigned32
    UNITS       "microseconds"
    MAX-ACCESS  read-only
    STATUS      current
    DESCRIPTION
       "This object contains the Last short period mean frame delay 
       in the twoway direction calculated.      
       "
    ::= { rcServiceFarEndPointCosLabelEntry 5 } 
    
rcServiceFarEndPointCosLabelShortTwowayFDR        OBJECT-TYPE
    SYNTAX      Unsigned32
    UNITS       "microseconds"
    MAX-ACCESS  read-only
    STATUS      current
    DESCRIPTION
       "This object contains the Last short period frame delay range 
       in the twoway direction calculated.      
       "
    ::= { rcServiceFarEndPointCosLabelEntry 6 }   
    
rcServiceFarEndPointCosLabelShortTwowayIFDV        OBJECT-TYPE
    SYNTAX      Unsigned32
    UNITS       "microseconds"
    MAX-ACCESS  read-only
    STATUS      current
    DESCRIPTION
       "This object contains the Last short period two-way inter-frame delay
        interval calculated "
    ::= { rcServiceFarEndPointCosLabelEntry 7 }
    
rcServiceFarEndPointCosLabelShortTwowayMaxIFDV        OBJECT-TYPE
    SYNTAX      Unsigned32
    UNITS       "microseconds"
    MAX-ACCESS  read-only
    STATUS      current
    DESCRIPTION
       "This object contains the Last short period two-way max inter-frame delay
        interval calculated "
    ::= { rcServiceFarEndPointCosLabelEntry 8 }

rcServiceFarEndPointCosLabelShortTwowayMinIFDV        OBJECT-TYPE
    SYNTAX      Unsigned32
    UNITS       "microseconds"
    MAX-ACCESS  read-only
    STATUS      current
    DESCRIPTION
       "This object contains the Last short period two-way min inter-frame delay
        interval calculated "
    ::= { rcServiceFarEndPointCosLabelEntry 9 }

rcServiceFarEndPointCosLabelShortTwowayMIFDV        OBJECT-TYPE
    SYNTAX      Unsigned32
    UNITS       "microseconds"
    MAX-ACCESS  read-only
    STATUS      current
    DESCRIPTION
       "This object contains the Last short period two-way mean inter-frame delay
        interval calculated "
    ::= { rcServiceFarEndPointCosLabelEntry 10 }

rcServiceFarEndPointCosLabelShortForwardFLR OBJECT-TYPE
    SYNTAX      Unsigned32 (0..100000)
    UNITS       "milli-percent"
    MAX-ACCESS  read-only
    STATUS      current
    DESCRIPTION
       "This object contains the Last short period frame loss ratio in the 
       Forward direction calculated. The FLR value 
       is a ratio that is expressed as a percent with a value of 0 
       (ratio 0.00) through 100000 (ratio 1.00). 
       Units are in milli-percent, where 1 indicates 0.001 percent.
       "
    ::= { rcServiceFarEndPointCosLabelEntry 11 } 

rcServiceFarEndPointCosLabelShortBackwardFLR OBJECT-TYPE
    SYNTAX      Unsigned32 (0..100000)
    UNITS       "milli-percent"
    MAX-ACCESS  read-only
    STATUS      current
    DESCRIPTION
       "This object contains the Last short period frame loss ratio in the 
       Backward direction calculated. The FLR value 
       is a ratio that is expressed as a percent with a value of 0 
       (ratio 0.00) through 100000 (ratio 1.00). 
       Units are in milli-percent, where 1 indicates 0.001 percent.
       "
    ::= { rcServiceFarEndPointCosLabelEntry 12 } 

rcServiceFarEndPointCosLabelShortForwardAvail OBJECT-TYPE
    SYNTAX      Unsigned32 (0..100000)
    UNITS       "milli-percent"
    MAX-ACCESS  read-only
    STATUS      current
    DESCRIPTION
       "This object contains the Last short period Availability /total time in forward direction.
       "
     ::= { rcServiceFarEndPointCosLabelEntry 13 } 

rcServiceFarEndPointCosLabelShortBackwardAvail OBJECT-TYPE
    SYNTAX      Unsigned32 (0..100000)
    UNITS       "milli-percent"
    MAX-ACCESS  read-only
    STATUS      current
    DESCRIPTION
       "This object contains the Last short period Availability /total time in backward direction.
       "
     ::= { rcServiceFarEndPointCosLabelEntry 14 } 

rcServiceFarEndPointCosLabelShortForwardHLI OBJECT-TYPE
    SYNTAX      Unsigned32
    MAX-ACCESS  read-only
    STATUS      current
    DESCRIPTION
       "This object is contains the Last short period the number of high loss intervals (HLI) over
        time in the forward direction. 

        The value starts at 0 and increments for every HLI that occurs.
        This parameter is equivalent to 'L Sub T' found in MEF 10.2.1.
       "
    REFERENCE
       "[MEF 10.2.1] 6.9.9; [MEF SOAM-PM] R87"
    ::= { rcServiceFarEndPointCosLabelEntry 15 }

rcServiceFarEndPointCosLabelShortBackwardHLI OBJECT-TYPE
    SYNTAX      Unsigned32
    MAX-ACCESS  read-only
    STATUS      current
    DESCRIPTION
       "This object is contains the Last short period the number of high loss intervals (HLI) over
        time in the backward direction. 

        The value starts at 0 and increments for every HLI that occurs.
        This parameter is equivalent to 'L Sub T' found in MEF 10.2.1.
       "
    REFERENCE
       "[MEF 10.2.1] 6.9.9; [MEF SOAM-PM] R87"
    ::= { rcServiceFarEndPointCosLabelEntry 16 }

rcServiceFarEndPointCosLabelShortForwardCHLI OBJECT-TYPE
    SYNTAX      Unsigned32
    MAX-ACCESS  read-only
    STATUS      current
    DESCRIPTION
       "This object is contains the Last short period the number of consecutive high loss intervals
        (CHLI) over time in the forward direction. 

        The value starts at 0 and increments for every HLI that occurs 
        that is determined to fall within a CHLI.
        This parameter is equivalent to 'B Sub T' found in MEF 10.2.1.
       "
    REFERENCE
       "[MEF 10.2.1] 6.9.9; [MEF SOAM-PM] R87"
    ::= { rcServiceFarEndPointCosLabelEntry 17 }

rcServiceFarEndPointCosLabelShortBackwardCHLI OBJECT-TYPE
    SYNTAX      Unsigned32
    MAX-ACCESS  read-only
    STATUS      current
    DESCRIPTION
       "This object is contains the Last short period the number of consecutive high loss intervals
        (CHLI) over time in the backward direction. 

        The value starts at 0 and increments for every HLI that occurs 
        that is determined to fall within a CHLI.
        This parameter is equivalent to 'B Sub T' found in MEF 10.2.1.
       "
    REFERENCE
       "[MEF 10.2.1] 6.9.9; [MEF SOAM-PM] R87"
    ::= { rcServiceFarEndPointCosLabelEntry 18 }
 
rcServiceFarEndPointCosLabelShortForwardFrameLost OBJECT-TYPE
    SYNTAX      Unsigned32
    MAX-ACCESS  read-only
    STATUS      current
    DESCRIPTION
       "This object is contains the Last short period  number of lost frame in the Forward direction. 
       "
    REFERENCE
       "[MEF 10.2.1] 6.9.9; [MEF SOAM-PM] R87"
    ::= { rcServiceFarEndPointCosLabelEntry 19 }

rcServiceFarEndPointCosLabelShortBackwardFrameLost OBJECT-TYPE
    SYNTAX      Unsigned32
    MAX-ACCESS  read-only
    STATUS      current
    DESCRIPTION
       "This object is contains the Last short period  number of lost frame in the Backward direction. 
       "
    REFERENCE
       "[MEF 10.2.1] 6.9.9; [MEF SOAM-PM] R87"
    ::= { rcServiceFarEndPointCosLabelEntry 20 }     
    
rcServiceFarEndPointCosLabelShortForwardUnAvailSeconds OBJECT-TYPE
    SYNTAX      Unsigned32
    MAX-ACCESS  read-only
    STATUS      current
    DESCRIPTION
       "This object is contains the Last short period  time of unavailable in the Forward direction. 
       "
    REFERENCE
       "[MEF 10.2.1] 6.9.9; [MEF SOAM-PM] R87"
    ::= { rcServiceFarEndPointCosLabelEntry 21 }

rcServiceFarEndPointCosLabelShortBackwardUnAvailSeconds OBJECT-TYPE
    SYNTAX      Unsigned32
    MAX-ACCESS  read-only
    STATUS      current
    DESCRIPTION
       "This object is contains the Last short period  time of unavailable in the Backward direction. 
       "
    REFERENCE
       "[MEF 10.2.1] 6.9.9; [MEF SOAM-PM] R87"
    ::= { rcServiceFarEndPointCosLabelEntry 22 }

 
rcServiceFarEndPointCosLabelLongStartTime        OBJECT-TYPE
	SYNTAX       DateAndTime
	MAX-ACCESS  read-only
    STATUS      current
    DESCRIPTION
            "The long period Start Time."   
    ::= { rcServiceFarEndPointCosLabelEntry 23 }    


rcServiceFarEndPointCosLabelLongTwowayFD        OBJECT-TYPE
    SYNTAX      Unsigned32
    UNITS       "microseconds"
    MAX-ACCESS  read-only
    STATUS      current
    DESCRIPTION
       "This object contains the Last long period frame delay 
       in the twoway direction calculated.      
       "
    ::= { rcServiceFarEndPointCosLabelEntry 24 }   
    
rcServiceFarEndPointCosLabelLongTwowayMaxFD       OBJECT-TYPE
    SYNTAX      Unsigned32
    UNITS       "microseconds"
    MAX-ACCESS  read-only
    STATUS      current
    DESCRIPTION
       "This object contains the Last long period max frame delay 
       in the twoway direction calculated.      
       "
    ::= { rcServiceFarEndPointCosLabelEntry 25 }

rcServiceFarEndPointCosLabelLongTwowayMinFD        OBJECT-TYPE
    SYNTAX      Unsigned32
    UNITS       "microseconds"
    MAX-ACCESS  read-only
    STATUS      current
    DESCRIPTION
       "This object contains the Last long period min frame delay 
       in the twoway direction calculated.      
       "
    ::= { rcServiceFarEndPointCosLabelEntry 26 }  
    
rcServiceFarEndPointCosLabelSlaConfigDMOperId       OBJECT-TYPE 
	SYNTAX      Unsigned32 
	MAX-ACCESS  read-only
    STATUS      current
    DESCRIPTION
            "This object indicates a row in the rcSlaConfigTable.
        This value is an operation number auto assigned."
    ::= { rcServiceFarEndPointCosLabelEntry 27 } 

rcServiceFarEndPointCosLabelSlaConfigLMOperId       OBJECT-TYPE 
	SYNTAX      Unsigned32 
	MAX-ACCESS  read-only
    STATUS      current
    DESCRIPTION
            "This object indicates a row in the rcSlaConfigTable.
        This value is an operation number auto assigned."
    ::= { rcServiceFarEndPointCosLabelEntry 28 } 
      
rcServiceFarEndPointCosLabelEtherSamServiceIndex       OBJECT-TYPE 
	SYNTAX      INTEGER
	MAX-ACCESS  read-only
    STATUS      current
    DESCRIPTION
            "Index of EtherSam Service profile auto assigned." 
    ::= { rcServiceFarEndPointCosLabelEntry 29 } 

rcServiceFarEndPointCosLabelLongTwowayMFD        OBJECT-TYPE
    SYNTAX      Unsigned32
    UNITS       "microseconds"
    MAX-ACCESS  read-only
    STATUS      current
    DESCRIPTION
       "This object contains the Last long period mean frame delay 
       in the twoway direction calculated.      
       "
    ::= { rcServiceFarEndPointCosLabelEntry 30 }  
     
rcServiceFarEndPointCosLabelLongTwowayFDR        OBJECT-TYPE
    SYNTAX      Unsigned32
    UNITS       "microseconds"
    MAX-ACCESS  read-only
    STATUS      current
    DESCRIPTION
       "This object contains the Last long period frame delay range 
       in the twoway direction calculated.      
       "
    ::= { rcServiceFarEndPointCosLabelEntry 31 }
     
rcServiceFarEndPointCosLabelLongTwowayIFDV        OBJECT-TYPE
    SYNTAX      Unsigned32
    UNITS       "microseconds"
    MAX-ACCESS  read-only
    STATUS      current
    DESCRIPTION
       "This object contains the Last long period two-way inter-frame delay
        interval calculated "
    ::= { rcServiceFarEndPointCosLabelEntry 32 }
 
rcServiceFarEndPointCosLabelLongTwowayMaxIFDV      OBJECT-TYPE
    SYNTAX      Unsigned32
    UNITS       "microseconds"
    MAX-ACCESS  read-only
    STATUS      current
    DESCRIPTION
       "This object contains the Last long period two-way max inter-frame delay
        interval calculated "
    ::= { rcServiceFarEndPointCosLabelEntry 33 }
 
rcServiceFarEndPointCosLabelLongTwowayMinIFDV       OBJECT-TYPE
    SYNTAX      Unsigned32
    UNITS       "microseconds"
    MAX-ACCESS  read-only
    STATUS      current
    DESCRIPTION
       "This object contains the Last long period two-way min inter-frame delay
        interval calculated "
    ::= { rcServiceFarEndPointCosLabelEntry 34 }
 
rcServiceFarEndPointCosLabelLongTwowayMIFDV          OBJECT-TYPE
    SYNTAX      Unsigned32
    UNITS       "microseconds"
    MAX-ACCESS  read-only
    STATUS      current
    DESCRIPTION
       "This object contains the Last long period two-way mean inter-frame delay
        interval calculated "
    ::= { rcServiceFarEndPointCosLabelEntry 35 }

rcServiceFarEndPointCosLabelLongForwardFLR OBJECT-TYPE
    SYNTAX      Unsigned32 (0..100000)
    UNITS       "milli-percent"
    MAX-ACCESS  read-only
    STATUS      current
    DESCRIPTION
       "This object contains the Last long period frame loss ratio in the 
       Forward direction calculated. The FLR value 
       is a ratio that is expressed as a percent with a value of 0 
       (ratio 0.00) through 100000 (ratio 1.00). 
       Units are in milli-percent, where 1 indicates 0.001 percent.
       "
    ::= { rcServiceFarEndPointCosLabelEntry 36 } 

rcServiceFarEndPointCosLabelLongBackwardFLR OBJECT-TYPE
    SYNTAX      Unsigned32 (0..100000)
    UNITS       "milli-percent"
    MAX-ACCESS  read-only
    STATUS      current
    DESCRIPTION
       "This object contains the Last long period frame loss ratio in the 
       Backward direction calculated. The FLR value 
       is a ratio that is expressed as a percent with a value of 0 
       (ratio 0.00) through 100000 (ratio 1.00). 
       Units are in milli-percent, where 1 indicates 0.001 percent.
       "
    ::= { rcServiceFarEndPointCosLabelEntry 37 } 

rcServiceFarEndPointCosLabelLongForwardAvail OBJECT-TYPE
    SYNTAX      Unsigned32 (0..100000)
    UNITS       "milli-percent"
    MAX-ACCESS  read-only
    STATUS      current
    DESCRIPTION
       "This object contains the Last long period Availability /total time in forward direction.
       "
     ::= { rcServiceFarEndPointCosLabelEntry 38 } 

rcServiceFarEndPointCosLabelLongBackwardAvail OBJECT-TYPE
    SYNTAX      Unsigned32 (0..100000)
    UNITS       "milli-percent"
    MAX-ACCESS  read-only
    STATUS      current
    DESCRIPTION
       "This object contains the Last long period Availability /total time in backward direction.
       "
     ::= { rcServiceFarEndPointCosLabelEntry 39 } 

rcServiceFarEndPointCosLabelLongForwardHLI OBJECT-TYPE
    SYNTAX      Unsigned32
    MAX-ACCESS  read-only
    STATUS      current
    DESCRIPTION
       "This object is contains the Last long period the number of high loss intervals (HLI) over
        time in the forward direction. 

        The value starts at 0 and increments for every HLI that occurs.
        This parameter is equivalent to 'L Sub T' found in MEF 10.2.1.
       "
    REFERENCE
       "[MEF 10.2.1] 6.9.9; [MEF SOAM-PM] R87"
    ::= { rcServiceFarEndPointCosLabelEntry 40 }

rcServiceFarEndPointCosLabelLongBackwardHLI OBJECT-TYPE
    SYNTAX      Unsigned32
    MAX-ACCESS  read-only
    STATUS      current
    DESCRIPTION
       "This object is contains the Last long period the number of high loss intervals (HLI) over
        time in the backward direction. 

        The value starts at 0 and increments for every HLI that occurs.
        This parameter is equivalent to 'L Sub T' found in MEF 10.2.1.
       "
    REFERENCE
       "[MEF 10.2.1] 6.9.9; [MEF SOAM-PM] R87"
    ::= { rcServiceFarEndPointCosLabelEntry 41 }

rcServiceFarEndPointCosLabelLongForwardCHLI OBJECT-TYPE
    SYNTAX      Unsigned32
    MAX-ACCESS  read-only
    STATUS      current
    DESCRIPTION
       "This object is contains the Last long period the number of consecutive high loss intervals
        (CHLI) over time in the forward direction. 

        The value starts at 0 and increments for every HLI that occurs 
        that is determined to fall within a CHLI.
        This parameter is equivalent to 'B Sub T' found in MEF 10.2.1.
       "
    REFERENCE
       "[MEF 10.2.1] 6.9.9; [MEF SOAM-PM] R87"
    ::= { rcServiceFarEndPointCosLabelEntry 42 }

rcServiceFarEndPointCosLabelLongBackwardCHLI OBJECT-TYPE
    SYNTAX      Unsigned32
    MAX-ACCESS  read-only
    STATUS      current
    DESCRIPTION
       "This object is contains the Last long period the number of consecutive high loss intervals
        (CHLI) over time in the backward direction. 

        The value starts at 0 and increments for every HLI that occurs 
        that is determined to fall within a CHLI.
        This parameter is equivalent to 'B Sub T' found in MEF 10.2.1.
       "
    REFERENCE
       "[MEF 10.2.1] 6.9.9; [MEF SOAM-PM] R87"
    ::= { rcServiceFarEndPointCosLabelEntry 43 }
 
rcServiceFarEndPointCosLabelLongForwardFrameLost  OBJECT-TYPE
    SYNTAX      Unsigned32
    MAX-ACCESS  read-only
    STATUS      current
    DESCRIPTION
       "This object is contains the Last Long period  number of lost frame in the Forward direction. 
       "
    REFERENCE
       "[MEF 10.2.1] 6.9.9; [MEF SOAM-PM] R87"
    ::= { rcServiceFarEndPointCosLabelEntry 44 }

rcServiceFarEndPointCosLabelLongBackwardFrameLost    OBJECT-TYPE
    SYNTAX      Unsigned32
    MAX-ACCESS  read-only
    STATUS      current
    DESCRIPTION
       "This object is contains the Last Long period  number of lost frame in the Backward direction. 
       "
    REFERENCE
       "[MEF 10.2.1] 6.9.9; [MEF SOAM-PM] R87"
    ::= { rcServiceFarEndPointCosLabelEntry 45 }     
    
rcServiceFarEndPointCosLabelLongForwardUnAvailSeconds  OBJECT-TYPE
    SYNTAX      Unsigned32
    MAX-ACCESS  read-only
    STATUS      current
    DESCRIPTION
       "This object is contains the Last Long period  time of unavailable in the Forward direction. 
       "
    REFERENCE
       "[MEF 10.2.1] 6.9.9; [MEF SOAM-PM] R87"
    ::= { rcServiceFarEndPointCosLabelEntry 46 }

rcServiceFarEndPointCosLabelLongBackwardUnAvailSeconds  OBJECT-TYPE
    SYNTAX      Unsigned32
    MAX-ACCESS  read-only
    STATUS      current
    DESCRIPTION
       "This object is contains the Last Long period  time of unavailable in the Backward direction. 
       "
    REFERENCE
       "[MEF 10.2.1] 6.9.9; [MEF SOAM-PM] R87"
    ::= { rcServiceFarEndPointCosLabelEntry 47 }

-- rcServiceSdpTable   

rcServiceSdpTable OBJECT-TYPE
    SYNTAX      SEQUENCE OF RcServiceSdpEntry
    MAX-ACCESS  not-accessible
    STATUS      current
    DESCRIPTION
        "Service Distribution Point attribute table."
    ::= { rcService 12 }

rcServiceSdpEntry   OBJECT-TYPE
    SYNTAX      RcServiceSdpEntry
    MAX-ACCESS  not-accessible
    STATUS      current
    DESCRIPTION
        "An entry in the rcServiceSdpTable. It specifies the Service Distribution Point attributes."
	INDEX        { rcServiceID,rcServiceNetworkInterfacePortIndex}    
    ::={ rcServiceSdpTable 1 }
    
    RcServiceSdpEntry ::= SEQUENCE {
	rcServiceSdpRowStatus			RowStatus
	}
	
rcServiceSdpRowStatus        OBJECT-TYPE
	SYNTAX      RowStatus
	MAX-ACCESS  read-create
    STATUS      current
    DESCRIPTION
      "The status of the row.
       "
    ::= { rcServiceSdpEntry 100 }   
    
--rcServiceFarEndPointCosLabelCurrentTable   
    rcServiceFarEndPointCosLabelCurrentTable OBJECT-TYPE
    SYNTAX      SEQUENCE OF RcServiceFarEndPointCosLabelCurrentEntry
    MAX-ACCESS  not-accessible
    STATUS      current
    DESCRIPTION
        "Service FarEndPoint CosLabel Current attribute table."
    ::= { rcService 13 }

rcServiceFarEndPointCosLabelCurrentEntry   OBJECT-TYPE
    SYNTAX      RcServiceFarEndPointCosLabelCurrentEntry
    MAX-ACCESS  not-accessible
    STATUS      current
    DESCRIPTION
        "An entry in the rcServiceFarEndPointCosLabelCurrentTable. It specifies the service FarEndPoint CosLabel Current attributes."
	INDEX        { rcServiceID,rcServiceNetworkInterfaceID,rcServiceFarEndNetworkInterfaceID,rcServiceCosLabel}    
    ::={ rcServiceFarEndPointCosLabelCurrentTable 1 }
    
    RcServiceFarEndPointCosLabelCurrentEntry ::= SEQUENCE {		
	rcServiceFarEndPointCosLabelCurrentTwowayFD		        Unsigned32,
	rcServiceFarEndPointCosLabelCurrentTwowayIFDV		    Unsigned32,
	rcServiceFarEndPointCosLabelCurrentForwardFLR		    Unsigned32,
	rcServiceFarEndPointCosLabelCurrentBackwardFLR	        Unsigned32,
	rcServiceFarEndPointCosLabelCurrentForwardFrameLost	    Unsigned32,
	rcServiceFarEndPointCosLabelCurrentBackwardFrameLost	Unsigned32,
	rcServiceFarEndPointCosLabelCurrentForwardAvailStatus	INTEGER,
	rcServiceFarEndPointCosLabelCurrentBackwardAvailStatus	INTEGER                         
	}  
	
rcServiceFarEndPointCosLabelCurrentTwowayFD OBJECT-TYPE
    SYNTAX      Unsigned32    
    UNITS       "microseconds"
    MAX-ACCESS  read-only
    STATUS      current
    DESCRIPTION
       "This object contains the two-way frame delay calculated from the last received SOAM PDU.
       "
    REFERENCE
       "[MEF SOAM-PM] R66"
    ::= { rcServiceFarEndPointCosLabelCurrentEntry 1 }   
    
rcServiceFarEndPointCosLabelCurrentTwowayIFDV OBJECT-TYPE
    SYNTAX      Unsigned32    
    UNITS       "microseconds"
    MAX-ACCESS  read-only
    STATUS      current
    DESCRIPTION
       "This object contains the last two-way inter-frame delay
 	interval calculated .  
 	     "
    REFERENCE
       "[MEF SOAM-PM] R66"
    ::= { rcServiceFarEndPointCosLabelCurrentEntry 2 }

rcServiceFarEndPointCosLabelCurrentForwardFLR OBJECT-TYPE
    SYNTAX      Unsigned32 (0..100000)
    UNITS       "milli-percent"
    MAX-ACCESS  read-only
    STATUS      current
    DESCRIPTION
       "This object contains the last frame loss ratio in the forward direction
 	calculated . The FLR value
 	is a ratio that is expressed as a percent with a value of 0 (ratio 
 	0.00) through 100000 (ratio 1.00).
 	
 	Units are in milli-percent, where 1 indicates 0.001 percent.
       "    
    REFERENCE
       "[MEF SOAM-PM] D37"

     ::= { rcServiceFarEndPointCosLabelCurrentEntry 3 } 

        
rcServiceFarEndPointCosLabelCurrentBackwardFLR OBJECT-TYPE
    SYNTAX      Unsigned32 (0..100000)
    UNITS       "milli-percent"
    MAX-ACCESS  read-only
    STATUS      current
    DESCRIPTION
       "This object contains the last frame loss ratio in the Backward direction
 	calculated . The FLR value
 	is a ratio that is expressed as a percent with a value of 0 (ratio 
 	0.00) through 100000 (ratio 1.00).
 	
 	Units are in milli-percent, where 1 indicates 0.001 percent.
       "    
    REFERENCE
       "[MEF SOAM-PM] D37"

     ::= { rcServiceFarEndPointCosLabelCurrentEntry 4 } 
          
rcServiceFarEndPointCosLabelCurrentForwardFrameLost OBJECT-TYPE
    SYNTAX      Unsigned32
    MAX-ACCESS  read-only
    STATUS      current
    DESCRIPTION
       "This object contains the number of lost frames in the
 	Forward direction .  
 	     "
    ::= { rcServiceFarEndPointCosLabelCurrentEntry 5 }          
    
rcServiceFarEndPointCosLabelCurrentBackwardFrameLost OBJECT-TYPE
    SYNTAX      Unsigned32
    MAX-ACCESS  read-only
    STATUS      current
    DESCRIPTION
       "This object contains the number of lost frames in the
 	Backward direction .  
 	     "
    ::= { rcServiceFarEndPointCosLabelCurrentEntry 6 }

rcServiceFarEndPointCosLabelCurrentForwardAvailStatus OBJECT-TYPE
    SYNTAX      INTEGER{
	            available (1),
                unavailable (2),
                unknown (3)
                }
    MAX-ACCESS  read-only
    STATUS      current
    DESCRIPTION
       "This object indicates the availability status (the outcome of the
 	last known availability indicator) in the forward direction.
 	Note that the status of an availability indicator is not known until
 	the loss for a number of subsequent availability indicators has been
 	calculated .  
 	     "  
 	REFERENCE
       "[MEF SOAM-PM] R83"

    ::= { rcServiceFarEndPointCosLabelCurrentEntry 7 }   
    
rcServiceFarEndPointCosLabelCurrentBackwardAvailStatus OBJECT-TYPE
    SYNTAX      INTEGER{
	            available (1),
                unavailable (2),
                unknown (3)
                }
    MAX-ACCESS  read-only
    STATUS      current
    DESCRIPTION
       "This object indicates the availability status (the outcome of the
 	last known availability indicator) in the Backward direction.
 	Note that the status of an availability indicator is not known until
 	the loss for a number of subsequent availability indicators has been
 	calculated .  
 	     "  
 	REFERENCE
       "[MEF SOAM-PM] R83"

    ::= { rcServiceFarEndPointCosLabelCurrentEntry 8 }   
    
-- rcServiceTrap    

rcServiceTrapGroup		OBJECT IDENTIFIER ::= {	rcService 14}

rcServiceEtherSamCfgTestFailTrap
NOTIFICATION-TYPE
    OBJECTS     { rcServiceID,rcServiceNetworkInterfaceID,rcServiceFarEndNetworkInterfaceID
                }
    STATUS      current
    DESCRIPTION
       "when the service EtherSam config test is FAIL, the trap will be sent.
        and the Index points out which service."
    ::= { rcServiceTrapGroup 1 }   
    
rcServiceEtherSamCfgTestSuccessTrap
NOTIFICATION-TYPE
    OBJECTS     { rcServiceID,rcServiceNetworkInterfaceID,rcServiceFarEndNetworkInterfaceID
                }
    STATUS      current
    DESCRIPTION
       "when the service EtherSam config test is success, the trap will be sent.
        and the Index points out which service."
    ::= { rcServiceTrapGroup 2 }
    
rcServiceEtherSamPfmTestFailTrap
NOTIFICATION-TYPE
    OBJECTS     { rcServiceID,rcServiceNetworkInterfaceID,rcServiceFarEndNetworkInterfaceID
                }
    STATUS      current
    DESCRIPTION
       "when the service EtherSam config test is FAIL, the trap will be sent.
        and the Index points out which service."
    ::= { rcServiceTrapGroup 3 }    
    
    
rcServiceEtherSamPfmTestSuccessTrap
NOTIFICATION-TYPE
    OBJECTS     { rcServiceID,rcServiceNetworkInterfaceID,rcServiceFarEndNetworkInterfaceID
                }
    STATUS      current
    DESCRIPTION
       "when the service EtherSam config test is success, the trap will be sent.
        and the Index points out which service."
    ::= { rcServiceTrapGroup 4 }  
    
    


       


                 
END

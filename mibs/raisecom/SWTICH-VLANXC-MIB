--MibName=rcVlanxc
-- *****************************************************************
-- switch-vlanxc-mib.mib:  Raisecom vlan-xc MIB file
--
-- 7 2012, fanmanjie
--
-- Copyright (c) 1994-2000, 2001 by Raisecom, Inc.
-- All rights reserved.
-- 
-- *****************************************************************
SWTICH-VLANXC-MIB  DEFINITIONS ::= BEGIN

IMPORTS
	iscomSwitch
		FROM RAISECOM-BASE-MIB
                
	RowStatus
		FROM SNMPv2-TC;
        
	rcVlanxc MODULE-IDENTITY
		LAST-UPDATED    "201207100000Z"
		ORGANIZATION    "Raisecom, Inc."
		CONTACT-INFO
                "       Raise Systems
                        
                Postal: Beijing,
                        China

                   Tel: 86-010-82884499

                E-mail: fanmanjie@raisecom.com"
        DESCRIPTION
                "description of vlan_xc manage object."
                ::= { iscomSwitch 72} 
 
-- 
-- groups in the MIB
-- 
 
rcVlanxcCurrentEntryCount    OBJECT-TYPE   
        SYNTAX   INTEGER (0..1024)
        ACCESS   read-only
        STATUS   current
        DESCRIPTION
                 "This object indicates the current count of vlan_xc entry"   
        ::= { rcVlanxc 1 }  
-- 
-- groups in the rcVlanxc MIB     rcVlanxcTable
-- 

rcVlanxcTable OBJECT-TYPE
        SYNTAX SEQUENCE OF RcVlanxcEntry
        MAX-ACCESS not-accessible
        STATUS current
        DESCRIPTION
            "This table provides objects to vlan-xc entry."
        ::= { rcVlanxc 2}    

rcVlanxcEntry OBJECT-TYPE
        SYNTAX RcVlanxcEntry
        MAX-ACCESS not-accessible
        STATUS current
        DESCRIPTION
            "Table entry for vlan-xc."
        INDEX { rcVlanxcOuterVid , rcVlanxcInnerVid}
        ::= { rcVlanxcTable 1 }    
        
RcVlanxcEntry ::= SEQUENCE {
        rcVlanxcOuterVid        INTEGER,
        rcVlanxcInnerVid        INTEGER,
        rcVlanxcPort1           INTEGER,
        rcVlanxcPort2           INTEGER,
        rcVlanxcRowStatus       RowStatus
    }  
      
rcVlanxcOuterVid   OBJECT-TYPE
          SYNTAX    INTEGER (1..4094)    
          ACCESS    not-accessible
          STATUS    current
          DESCRIPTION
                 "The index outer vid of vlan_xc entry."    
          ::= { rcVlanxcEntry 1 } 
          
rcVlanxcInnerVid OBJECT-TYPE
          SYNTAX    INTEGER (1..4094 | 4096)
          ACCESS    not-accessible
          STATUS    current
          DESCRIPTION
                 "The index inner vid of vlan_xc entry."
          ::= { rcVlanxcEntry 2 } 
          
rcVlanxcPort1 OBJECT-TYPE
          SYNTAX    INTEGER
          ACCESS    read-create
          STATUS    current
          DESCRIPTION
                 "This object indicates one port of the vlan_xc entry.If one is the
                  destination port, and the other is the source port."
          ::= { rcVlanxcEntry 3 } 

rcVlanxcPort2 OBJECT-TYPE
          SYNTAX    INTEGER
          ACCESS    read-create
          STATUS    current
          DESCRIPTION
                 "This object indicates another port of the vlan_xc entry.If one is the
                  destination port, and the other is the source port."
          ::= { rcVlanxcEntry 4 } 
                     
rcVlanxcRowStatus OBJECT-TYPE
          SYNTAX    RowStatus
          ACCESS    read-create
          STATUS    current
          DESCRIPTION
                 "The status of this entry."
          ::= { rcVlanxcEntry 5 } 

--vlanIndex table--
rcVlanxcVlanTable  OBJECT-TYPE 
        SYNTAX   SEQUENCE OF RcVlanxcVlanEntry
        ACCESS	 not-accessible
        STATUS   current
        DESCRIPTION
                 "This object indicates the vlan index"
        ::= { rcVlanxc 3 }

rcVlanxcVlanEntry  OBJECT-TYPE
        SYNTAX   RcVlanxcVlanEntry
        ACCESS   not-accessible
        STATUS   current
        DESCRIPTION
                 "An entry in rcVlanxcVlanTable" 
        INDEX { rcVlanxcVlanIndex }
        ::= { rcVlanxcVlanTable 1 } 
        
RcVlanxcVlanEntry ::= SEQUENCE {
        rcVlanxcVlanIndex       INTEGER,
        rcVlanxcVlanMode        INTEGER,
        rcVlanxcVlanRowStatus   RowStatus
    }  
      
rcVlanxcVlanIndex   OBJECT-TYPE
          SYNTAX    INTEGER (1..4094)    
          ACCESS    not-accessible
          STATUS    current
          DESCRIPTION
                 "This object indicates the vlan index."    
          ::= { rcVlanxcVlanEntry 1 } 

rcVlanxcVlanMode OBJECT-TYPE
          SYNTAX    INTEGER{
                    bridge(0),
                    vlan-xc(1),
                    extend-vlan-xc(2)
                    }
          ACCESS    read-write
          STATUS    current
          DESCRIPTION
                 "This object indicates the mode of this vlan index."
          ::= { rcVlanxcVlanEntry 2 } 
                     
rcVlanxcVlanRowStatus OBJECT-TYPE
          SYNTAX    RowStatus
          ACCESS    read-write
          STATUS    current
          DESCRIPTION
                 "The status of this entry."
          ::= { rcVlanxcVlanEntry 3 } 
        
END

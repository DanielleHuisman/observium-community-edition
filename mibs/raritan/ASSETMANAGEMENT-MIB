ASSETMANAGEMENT-MIB DEFINITIONS ::= BEGIN

IMPORTS
    MODULE-IDENTITY, OBJECT-TYPE, NOTIFICATION-TYPE     FROM SNMPv2-SMI
    enterprises, Integer32, Unsigned32                  FROM SNMPv2-SMI
    MODULE-COMPLIANCE, OBJECT-GROUP, NOTIFICATION-GROUP FROM SNMPv2-CONF
    TEXTUAL-CONVENTION, DisplayString, TruthValue       FROM SNMPv2-TC
    InetAddressType, InetAddress, InetPortNumber        FROM INET-ADDRESS-MIB
    sysContact, sysName, sysLocation                    FROM RFC1213-MIB;

raritan MODULE-IDENTITY
    LAST-UPDATED "201811140000Z"      -- November 14, 2018
    ORGANIZATION "Raritan"
    CONTACT-INFO "Author:       Raritan Americas, Inc.
                  postal:       Raritan Americas, Inc.
                                400 Cottontail Lane
                                Somerset, NJ 08873
                  email:        tech@raritan.com
                  phone:        +1 732 764 8886"

    DESCRIPTION  "This MIB describes the SNMP functions of the
                  asset management capable products from Raritan Computer."

    REVISION     "201811140000Z"      -- November 14, 2018
    DESCRIPTION  "The following changes were made.
                    1) Added deviceSerialNumber under trapInformation
                    2) Added deviceSerialNumber to the OBJECTS clause of all traps
                    3) change SYNTAX for assetStripNumberOfRackUnits, logRackUnitNumber, logAssetStripNumber,
                       assetStripCascadePosition and rackUnitRelativePosition
                    4) change MAX-ACCESS of deviceName, deviceInetAddressType, deviceInetIPAddress,
                       deviceUserName and deviceSerialNumber to accessible-for-notify"

    REVISION     "201501050000Z"      -- January 5, 2015
    DESCRIPTION  "The following changes were made.
                    1) Added agentInetPortNumber under trapInformation
                    2) Added agentInetPortNumber as a varbind to all traps"

    REVISION     "201409250000Z"      -- September 25, 2014
    DESCRIPTION  "The following changes were made.
                    1) added assetStripCascadePosition to the assetManagement table
                    2) added rackUnitRelativePosition to the assetManagement table.
                    3) added assetStripNumberOfRackUnits to the assetManagement table.
                    4) added assetStripType, assetStripCascadePosition,
                       rackUnitRelativePosition, assetStripNumberOfRackUnits
                       to the following traps.
                         assetTagConnected
                         assetTagDisconnected
                         bladeExtensionConnected
                         bladeExtensionDisconnected"

    REVISION     "201404040000Z"      -- April 4, 2014
    DESCRIPTION  "The following changes were made.
                    1) added bladeTagID to assetTagConnected and assetTagDisconnected traps
                    2) added rackUnitCount to the following traps.
                         assetTagConnected
                         assetTagDisconnected
                         bladeExtensionConnected
                         bladeExtensionDisconnected
                         assetStripStateChange"

    REVISION     "201203290000Z"      -- March 29, 2012
    DESCRIPTION  "The following changes were made.
                    1) add logParentBladeID to AssetManagementLogEntryStruct"

    REVISION     "201203260000Z"      -- March 26, 2012
    DESCRIPTION  "The following changes were made.
                    1) clarify documentation of LED operation mode:
                       setting ledMode, ledColor or ledColorStr automatically switches
                       the ledOperationMode to manual."

    REVISION     "201202140000Z"      -- February 14, 2012
    DESCRIPTION  "The following changes were made.
                    1) add logAssetStripState and extend logEventType
                       with assetStripStateChange"

    REVISION     "201202100000Z"      -- February 10, 2012
    DESCRIPTION  "The following changes were made.
                    1) clarify documentation regarding logSlotNumber:
                       it is 0 a) indicating a tag on the main strip
                               b) in case no strip is connected or
                                  the value is not valid for a certain log entry"

    REVISION     "201202080000Z"      -- February 8, 2012
    DESCRIPTION  "The following changes were made.
                    1) added bladeExtensionSize to bladeExtensionConnected and
                       bladeExtensionDisconnected traps"

    REVISION     "201202070000Z"      -- February 7, 2012
    DESCRIPTION  "The following changes were made.
                    1) added logSize, oldestLogID, newestLogID and logEventCount
                    2) added assetManagementLogTable and assetManagementLogEntry"

    REVISION     "201202030000Z"      -- February 3, 2012
    DESCRIPTION  "1) Added assetStripDefaultLEDColorConnected, assetStripDefaultLEDColorConnectedStr,
                     assetStripDefaultLEDColorDisconnected, assetStripDefaultLEDColorDisconnectedStr
                      to AssetStripConfigurationEntryStruct
                  2) Deprecated defaultLEDColorConnected, defaultLEDColorConnectedStr,
                     defaultLEDColorDisconnected, defaultLEDColorDisconnectedStr"

    REVISION     "201201170000Z"      -- January 17, 2012
    DESCRIPTION  "1) add rackUnitPosition to the following traps:
                     assetTagConnected, assetTagDisconnected,
                     bladeExtensionConnected, bladeExtensionDisconnected,
                     rackUnitConfigurationChanged
                  2) rackUnitNumber in the traps now always corresponds with
                     rackUnitID, clarify documentation accordingly"

    REVISION     "201201040000Z"      -- January 4, 2012
    DESCRIPTION  "1) extended AssetStripConfigurationEntryStruct by assetStripType and numberOfComponentAssetStrips
                  2) added compositeAssetStripCompositionChanged trap"

    REVISION     "201112080000Z"      -- December 8, 2011
    DESCRIPTION  "1) removed bladeSlotNumberingMode from AssetManagementEntryStruct
                  2) removed BladeSlotNumberingModeEnumeration
                  3) removed bladeSlotNumberingMode from the rackUnitConfigurationChanged trap"

    REVISION     "201111110000Z"      -- November 11, 2011
    DESCRIPTION  "The following changes were made.
                    1) allow 0 in rackUnitPosition in case there is no strip connected
                    2) added none (nothing connected) and unknown (strip disconnected) to rackUnitType"

    REVISION     "201111090000Z"      -- November 9, 2011
    DESCRIPTION  "The following changes were made.
                    1) allow a 0 in bladeExtensionSize in case there is no blade
                       extension connected or the asset strip is disconnected."

    REVISION     "201110250000Z"      -- October 25, 2011
    DESCRIPTION  "The following changes were made.
                    1) added sysContact,sysName, sysLocation to all traps
                    2) added currentMainTagCount, currentBladeTagCount
                    3) added maxMainTagCount, maxBladeTagCount
                    4) added bladeExtensionOverflow
                    5) added traps bladeExtensionOverflowOccured, bladeExtensionOverflowCleared"

    REVISION     "201110050000Z"      -- October 5, 2011
    DESCRIPTION  "The following changes were made.
                    1)   Added assetStripName to all traps"

    REVISION     "201109050000Z"      -- Sep. 5, 2011
    DESCRIPTION  "1) added rackUnitName"

    REVISION     "201109010000Z"      -- Sep. 1, 2011
    DESCRIPTION  "1) added bladeExtensionConnected, bladeExtensionDisconnected traps
                  2) in AssetManagementEntryStruct renamed rackUnitSize to bladeExtensionSize
                  3) added bladeSlotPosition to BladeExtensionEntryStruct
                  4) added bladeSlotNumberingMode to AssetManagementEntryStruct
                  5) added BladeSlotNumberingModeEnumeration
                  6) added bladeSlotNumberingMode to the rackUnitConfigurationChanged trap"

    REVISION     "201108230000Z"      -- Aug 23, 2011
    DESCRIPTION  "Support blade server extension segments:
                  1) added rackUnitType, rackUnitSize
                  2) added bladeExtensionTable and bladeExtensionEntry
                  3) added slotNumber to assetTagConnected and assetTagDisconnected traps"

    REVISION     "201105180000Z"      -- May 18, 2011
    DESCRIPTION  "The following changes were made.
                    1) Modified blinking speeds in AssetManagementLEDModeEnumeration
                       to fastBlink, slowBlink"

    REVISION     "201105040000Z"      -- May 4, 2011
    DESCRIPTION  "The following changes were made.
                    1) Added ledOperationMode to the Tag Connected and Tag Disconnected Traps.
                    2) Modified the DESCRIPTION of rackUnitNumberingOffset.
                    3) Modified blinking speeds in AssetManagementLEDModeEnumeration
                       to blinkFastest, blink2ndFastest"

    REVISION     "201104150000Z"      -- April 15, 2011
    DESCRIPTION  "The following changes were made.
                    1) Added DeviceConfigurationParameterEnumeration, RackUnitNumberingModeEnumeration,
                         AssetStripOrientationEnumeration
                    2) Added deviceConfigurationChanged Trap
                    3) Added deviceUserName, deviceChangedParameter, changedParameterNewValue
                         to trapInformationGroup
                    4) Added blinking2(4) to AssetManagementLEDModeEnumeration
                    5) Add led mode and led color information to the Tag Connected and Tag Disconnected Traps.
                    6) Added rackUnitNumberingMode, rackUnitNumberingOffset, assetStripOrientation
                         to AssetStripConfigurationEntryStruct
                    7) Added rackUnitPosition to AssetManagementEntryStruct
                    8) Added rackUnitConfigurationChanged Trap"

    REVISION     "201102180000Z"      -- February 18, 2011
    DESCRIPTION  "The first version of the MIB."

    ::= { enterprises 13742 }

assetManager    OBJECT IDENTIFIER ::= { raritan 7 }
traps           OBJECT IDENTIFIER ::= { assetManager 0 }
trapInformation OBJECT IDENTIFIER ::= { traps 0 }
configuration   OBJECT IDENTIFIER ::= { assetManager 1 }
conformance     OBJECT IDENTIFIER ::= { assetManager 2 }
log             OBJECT IDENTIFIER ::= { assetManager 3 }
assetStrip      OBJECT IDENTIFIER ::= { configuration 6 }
assetManagement OBJECT IDENTIFIER ::= { configuration 7 }
compliances     OBJECT IDENTIFIER ::= { conformance 1 }
groups          OBJECT IDENTIFIER ::= { conformance 2 }

-- Conformance Information
-- compliance statements

complianceRev1 MODULE-COMPLIANCE
    STATUS deprecated
    DESCRIPTION
        "The requirements for conformance to the ASSETMANAGEMENT-MIB.
         This is deprecated in favor of complianceRev2"
    MODULE -- this module

    GROUP configGroup
    DESCRIPTION "The configuration group."

    GROUP assetManagementGroup
    DESCRIPTION "The asset management group."

    GROUP trapInformationGroup
    DESCRIPTION "The information group."

    GROUP trapsGroup
    DESCRIPTION "The information group."

    GROUP logGroup
    DESCRIPTION "The log group."

    ::= { compliances 1 }

complianceRev2 MODULE-COMPLIANCE
    STATUS current
    DESCRIPTION "The requirements for conformance to the ASSETMANAGEMENT-MIB."
    MODULE -- this module

    GROUP configGroup2
    DESCRIPTION "The configuration group."

    GROUP assetManagementGroup
    DESCRIPTION "The asset management group."

    GROUP trapInformationGroup
    DESCRIPTION "The information group."

    GROUP trapsGroup
    DESCRIPTION "The information group."

    ::= { compliances 2 }

-- units of conformance

configGroup OBJECT-GROUP
    OBJECTS {
        defaultLEDColorConnected,
        defaultLEDColorConnectedStr,
        defaultLEDColorDisconnected,
        defaultLEDColorDisconnectedStr
    }
    STATUS deprecated
    DESCRIPTION "A collection of objects representing configuration data."
    ::= { groups 1 }

configGroup2 OBJECT-GROUP
    OBJECTS {
        assetStripCount,
        assetStripState,
        assetStripName,
        rackUnitCount,
        rackUnitNumberingMode,
        rackUnitNumberingOffset,
        assetStripOrientation,
        currentMainTagCount,
        currentBladeTagCount,
        maxMainTagCount,
        maxBladeTagCount,
        bladeExtensionOverflow,
        assetStripType,
        numberOfComponentAssetStrips,
        assetStripDefaultLEDColorConnected,
        assetStripDefaultLEDColorConnectedStr,
        assetStripDefaultLEDColorDisconnected,
        assetStripDefaultLEDColorDisconnectedStr
    }
    STATUS current
    DESCRIPTION "A collection of objects representing configuration data."
    ::= { groups 5 }

assetManagementGroup OBJECT-GROUP
    OBJECTS {
        ledOperationMode,
        ledMode,
        ledColor,
        ledColorStr,
        tagID,
        bladeTagID,
        tagFamily,
        rackUnitPosition,
        rackUnitType,
        bladeExtensionSize,
        bladeSlotPosition,
        rackUnitName,
        assetStripCascadePosition,
        rackUnitRelativePosition,
        assetStripNumberOfRackUnits
    }
    STATUS current
    DESCRIPTION "A collection of objects providing the ability to control the asset management strip."
    ::= { groups 2 }

trapsGroup NOTIFICATION-GROUP
    NOTIFICATIONS {
        assetStripStateChange,
        assetTagConnected,
        assetTagDisconnected,
        assetStripFirmwareUpdate,
        deviceConfigurationChanged,
        rackUnitConfigurationChanged,
        bladeExtensionConnected,
        bladeExtensionDisconnected,
        bladeExtensionOverflowOccured,
        bladeExtensionOverflowCleared,
        compositeAssetStripCompositionChanged
    }
    STATUS current
    DESCRIPTION "A collection of traps."
    ::= { groups 3 }

trapInformationGroup OBJECT-GROUP
    OBJECTS {
        deviceName,
        deviceInetAddressType,
        deviceInetIPAddress,
        assetStripNumber,
        rackUnitNumber,
        slotNumber,
        assetStripFirmwareUpdateState,
        deviceUserName,
        deviceChangedParameter,
        changedParameterNewValue,
        oldNumberOfComponentAssetStrips,
        agentInetPortNumber,
        deviceSerialNumber
    }
    STATUS current
    DESCRIPTION "A collection of objects providing information in the traps."
    ::= { groups 4 }

logGroup OBJECT-GROUP
    OBJECTS {
        logSize,
        oldestLogID,
        newestLogID,
        logEventCount,
        logTimeStamp,
        logEventType,
        logAssetStripNumber,
        logRackUnitNumber,
        logRackUnitPosition,
        logSlotNumber,
        logTagID,
        logAssetStripState,
        logParentBladeID
    }
    STATUS current
    DESCRIPTION "A collection of objects representing log data."
    ::= { groups 6 }

-- Textual Conventions

AssetManagementLEDModeEnumeration ::= TEXTUAL-CONVENTION
    STATUS current
    DESCRIPTION "The mode of an LED for the asset manager."
    SYNTAX INTEGER {
        on(1),
        off(2),
        fastBlink(3),
        slowBlink(4)
    }

AssetManagementLEDOperationModeEnumeration ::= TEXTUAL-CONVENTION
    STATUS current
    DESCRIPTION "The operation mode of an LED for the asset manager."
    SYNTAX INTEGER {
        manual(1),
        automatic(2)
    }

AssetStripStateEnumeration ::= TEXTUAL-CONVENTION
    STATUS current
    DESCRIPTION "The state of an asset strip."
    SYNTAX INTEGER {
        disconnected(1),
        firmwareUpdate(2),
        unsupported(3),
        available(4)
    }

AssetStripFirmwareUpdateStateEnumeration ::= TEXTUAL-CONVENTION
    STATUS current
    DESCRIPTION "The state of an asset strip firmware update."
    SYNTAX INTEGER {
        started(1),
        successful(2),
        failed(3)
    }

RackUnitTypeEnumeration ::= TEXTUAL-CONVENTION
    STATUS current
    DESCRIPTION "Type of an asset tag."
    SYNTAX INTEGER {
        single(1),
        blade(2),
        none(30),
        unknown(31)
    }

RGBCOLOR ::= TEXTUAL-CONVENTION
    DISPLAY-HINT "1d;"
    STATUS current
    DESCRIPTION "An RGB color value."
    SYNTAX OCTET STRING (SIZE (3))

RackUnitNumberingModeEnumeration ::= TEXTUAL-CONVENTION
    STATUS current
    DESCRIPTION "The configurable parameters."
    SYNTAX INTEGER {
        topDown(0),
        bottomUp(1)
    }

AssetStripOrientationEnumeration ::= TEXTUAL-CONVENTION
    STATUS current
    DESCRIPTION "The configurable parameters."
    SYNTAX INTEGER {
        topConnector(0),
        bottomConnector(1)
    }

DeviceConfigurationParameterEnumeration ::= TEXTUAL-CONVENTION
    STATUS current
    DESCRIPTION "The configurable parameters."
    SYNTAX INTEGER {
        defaultLEDColorConnected(0),
        defaultLEDColorDisconnected(1),
        rackUnitCount(2),
        assetStripName(3),
        assetStripRackUnitNumberingMode(4),
        assetStripRackUnitNumberingOffset(5),
        assetStripOrientation(6)
    }

AssetStripTypeEnumeration ::= TEXTUAL-CONVENTION
    STATUS current
    DESCRIPTION "The asset strip types."
    SYNTAX INTEGER {
        simple(0),
        composite(1)
    }

LogEventTypeEnumeration ::= TEXTUAL-CONVENTION
    STATUS current
    DESCRIPTION "The type of a log event."
    SYNTAX INTEGER {
        empty(0),
        assetTagConnected(1),
        assetTagDisconnected(2),
        assetStripStateChange(3)
    }

-- Implementation for managing

assetStripCount OBJECT-TYPE
    SYNTAX Integer32(1..255)
    MAX-ACCESS read-only
    STATUS current
    DESCRIPTION "The number of asset management strip units supported."
    ::= { configuration 1 }

defaultLEDColorConnected OBJECT-TYPE
    SYNTAX RGBCOLOR
    MAX-ACCESS read-write
    STATUS deprecated
    DESCRIPTION
        "Default color of all LEDs (RGB) when a tag is connected
         during automatic operation; in binary format.
         This is deprecated in favor of assetStripDefaultLEDColorConnected
         For SET operations, the value will be applied to all asset strips
         For GET operations, the value returned will be the value corresponding to asset strip 1"
    ::= { configuration 2 }

defaultLEDColorConnectedStr OBJECT-TYPE
    SYNTAX DisplayString
    MAX-ACCESS read-write
    STATUS deprecated
    DESCRIPTION
        "Default color of all LEDs (RGB) when a tag is connected
         during automatic operation; string with 3 hex octets
         This is deprecated in favor of assetStripDefaultLEDColorConnectedStr
         For SET operations, the value will be applied to all asset strips
         For GET operations, the value returned will be the value corresponding to asset strip 1"
    ::= { configuration 3 }

defaultLEDColorDisconnected OBJECT-TYPE
    SYNTAX RGBCOLOR
    MAX-ACCESS read-write
    STATUS deprecated
    DESCRIPTION
        "Default color of all LEDs (RGB) when no tag is connected
         during automatic operation; in binary format.
         This is deprecated in favor of assetStripDefaultLEDColorDisConnected
         For SET operations, the value will be applied to all asset strips
         For GET operations, the value returned will be the value corresponding to asset strip 1"
    ::= { configuration 4 }

defaultLEDColorDisconnectedStr OBJECT-TYPE
    SYNTAX DisplayString
    MAX-ACCESS read-write
    STATUS deprecated
    DESCRIPTION
        "Default color of all LEDs (RGB) when no tag is connected
         during automatic operation; string with 3 hex octets
         This is deprecated in favor of assetStripDefaultLEDColorDisconnectedStr
         For SET operations, the value will be applied to all asset strips
         For GET operations, the value returned will be the value corresponding to asset strip 1"
    ::= { configuration 5 }

-- the StripConfiguration table

-- The StripConfiguration table contains information on the configuration of an asset management strip unit.

assetStripConfigurationTable OBJECT-TYPE
    SYNTAX SEQUENCE OF AssetStripConfigurationEntryStruct
    MAX-ACCESS not-accessible
    STATUS current
    DESCRIPTION "A list of configuration entries. The number of entries is given by the value of assetStripCount."
    ::= { assetStrip 1 }

assetStripConfigurationEntry OBJECT-TYPE
    SYNTAX AssetStripConfigurationEntryStruct
    MAX-ACCESS not-accessible
    STATUS current
    DESCRIPTION "An entry containing configuration objects for a particular asset management strip unit."
    INDEX { assetStripID }

 ::= { assetStripConfigurationTable 1 }

AssetStripConfigurationEntryStruct ::= SEQUENCE {
    assetStripID Integer32,
    rackUnitCount Integer32,
    assetStripState AssetStripStateEnumeration,
    assetStripName DisplayString,
    rackUnitNumberingMode RackUnitNumberingModeEnumeration,
    rackUnitNumberingOffset Integer32,
    assetStripOrientation AssetStripOrientationEnumeration,
    currentMainTagCount Integer32,
    currentBladeTagCount Integer32,
    maxMainTagCount Integer32,
    maxBladeTagCount Integer32,
    bladeExtensionOverflow TruthValue,
    assetStripType AssetStripTypeEnumeration,
    numberOfComponentAssetStrips Integer32,
    assetStripDefaultLEDColorConnected RGBCOLOR,
    assetStripDefaultLEDColorConnectedStr DisplayString,
    assetStripDefaultLEDColorDisconnected RGBCOLOR,
    assetStripDefaultLEDColorDisconnectedStr DisplayString
}

assetStripID OBJECT-TYPE
    SYNTAX Integer32(1..256)
    MAX-ACCESS not-accessible
    STATUS current
    DESCRIPTION "A unique value for each asset strip. Its value ranges between 1 and the value of assetStripCount."
    ::= { assetStripConfigurationEntry 1 }

rackUnitCount OBJECT-TYPE
    SYNTAX Integer32(8..64)
    MAX-ACCESS read-write
    STATUS current
    DESCRIPTION "The number of rack-units for the asset management."
    ::= { assetStripConfigurationEntry 2 }

assetStripState OBJECT-TYPE
    SYNTAX AssetStripStateEnumeration
    MAX-ACCESS read-only
    STATUS current
    DESCRIPTION "Asset management strip state."
    ::= { assetStripConfigurationEntry 3 }

assetStripName OBJECT-TYPE
    SYNTAX DisplayString
    MAX-ACCESS read-write
    STATUS current
    DESCRIPTION "Asset management strip name."
    ::= { assetStripConfigurationEntry 4 }

rackUnitNumberingMode OBJECT-TYPE
    SYNTAX RackUnitNumberingModeEnumeration
    MAX-ACCESS read-write
    STATUS current
    DESCRIPTION "The rack unit nmbering mode for this asset strip."
    ::= { assetStripConfigurationEntry 5 }

rackUnitNumberingOffset OBJECT-TYPE
    SYNTAX Integer32
    MAX-ACCESS read-write
    STATUS current
    DESCRIPTION
        "The offset (starting value) for rack Unit Numbering;
         This takes care of the case in which the asset strip
         is monitoring not all the assets but a subset of it,
         starting from racknumberingOffset. For example, the
         asset strip may be monitoring assets from 10 through 26;
         default value is 1 "
    ::= { assetStripConfigurationEntry 6 }

assetStripOrientation OBJECT-TYPE
    SYNTAX AssetStripOrientationEnumeration
    MAX-ACCESS read-write
    STATUS current
    DESCRIPTION
        "Is the asset strip oriented such that the connector is at the top or the bottom?
         If the asset strip has a tilt sensor, then this varaible is read-only and an
         to set (write) it will result in an error.
         If the asset strip does not have a tilt sensor, then this variable is read-write"
    ::= { assetStripConfigurationEntry 7 }

currentMainTagCount OBJECT-TYPE
    SYNTAX Integer32
    MAX-ACCESS read-only
    STATUS current
    DESCRIPTION "Number of tags currently connected to the main strip."
    ::= { assetStripConfigurationEntry 8 }

currentBladeTagCount OBJECT-TYPE
    SYNTAX Integer32
    MAX-ACCESS read-only
    STATUS current
    DESCRIPTION
        "Number of tags currently connected to blade extensions.
         This may be larger than the maxBladeTagCount. In this case
         an overflow occured and all tags over maxBladeTagCount are
         not recognized."
    ::= { assetStripConfigurationEntry 9 }

maxMainTagCount OBJECT-TYPE
    SYNTAX Integer32
    MAX-ACCESS read-only
    STATUS current
    DESCRIPTION "Maximum number of tags on the main asset strip."
    ::= { assetStripConfigurationEntry 10 }

maxBladeTagCount OBJECT-TYPE
    SYNTAX Integer32
    MAX-ACCESS read-only
    STATUS current
    DESCRIPTION "Maximum number of blade tags supported."
    ::= { assetStripConfigurationEntry 11 }

bladeExtensionOverflow OBJECT-TYPE
    SYNTAX TruthValue
    MAX-ACCESS read-only
    STATUS current
    DESCRIPTION
        "Set if the maximum number of supported tags on blade extensions is reached.
         When this flag is set, new tags on blade extensions won't be discovered anymore
         until other tags on blade extensions are removed."
    ::= { assetStripConfigurationEntry 12 }

assetStripType OBJECT-TYPE
    SYNTAX AssetStripTypeEnumeration
    MAX-ACCESS read-only
    STATUS current
    DESCRIPTION "The asset strip type."
    ::= { assetStripConfigurationEntry 13 }

numberOfComponentAssetStrips OBJECT-TYPE
    SYNTAX Integer32(0..255)
    MAX-ACCESS read-only
    STATUS current
    DESCRIPTION  "The number of components building a composite asset strip."
    ::= { assetStripConfigurationEntry 14 }

assetStripDefaultLEDColorConnected OBJECT-TYPE
    SYNTAX RGBCOLOR
    MAX-ACCESS read-write
    STATUS current
    DESCRIPTION "Default color of all LEDs (RGB) when a tag is connected during automatic operation; in binary format."
    ::= { assetStripConfigurationEntry 15 }

assetStripDefaultLEDColorConnectedStr OBJECT-TYPE
    SYNTAX DisplayString
    MAX-ACCESS read-write
    STATUS current
    DESCRIPTION
        "Default color of all LEDs (RGB) when a tag is connected
         during automatic operation; string with 3 hex octets"
    ::= { assetStripConfigurationEntry 16 }

assetStripDefaultLEDColorDisconnected OBJECT-TYPE
    SYNTAX RGBCOLOR
    MAX-ACCESS read-write
    STATUS current
    DESCRIPTION "Default color of all LEDs (RGB) when no tag is connected during automatic operation; in binary format."
    ::= { assetStripConfigurationEntry 17 }

assetStripDefaultLEDColorDisconnectedStr OBJECT-TYPE
    SYNTAX DisplayString
    MAX-ACCESS read-write
    STATUS current
    DESCRIPTION
        "Default color of all LEDs (RGB) when no tag is connected
         during automatic operation; string with 3 hex octets"
    ::= { assetStripConfigurationEntry 18 }

-- The assetManagement table is used to access asset tags and LEDs of the asset manager

assetManagementTable OBJECT-TYPE
    SYNTAX SEQUENCE OF AssetManagementEntryStruct
    MAX-ACCESS not-accessible
    STATUS current
    DESCRIPTION
        "A list of asset management extries containing tag information and LED state.
         The number of entries is given by the value of rackUnitCount."
    ::= { assetManagement 1 }

assetManagementEntry OBJECT-TYPE
    SYNTAX AssetManagementEntryStruct
    MAX-ACCESS not-accessible
    STATUS current
    DESCRIPTION "An entry containing tag information and LED state for a rack unit."
    INDEX { assetStripID, rackUnitID }
    ::= { assetManagementTable 1 }

AssetManagementEntryStruct ::= SEQUENCE {
    rackUnitID Integer32,
    ledOperationMode AssetManagementLEDOperationModeEnumeration,
    ledMode AssetManagementLEDModeEnumeration,
    ledColor RGBCOLOR,
    ledColorStr DisplayString,
    tagID DisplayString,
    tagFamily DisplayString,
    rackUnitPosition Integer32,
    rackUnitType RackUnitTypeEnumeration,
    bladeExtensionSize Integer32,
    rackUnitName DisplayString,
    assetStripCascadePosition Integer32,
    rackUnitRelativePosition Integer32,
    assetStripNumberOfRackUnits Integer32
}

rackUnitID OBJECT-TYPE
    SYNTAX Integer32(1..256)
    MAX-ACCESS not-accessible
    STATUS current
    DESCRIPTION "A unique value for each rack unit. Its value ranges between 1 and the value of rackUnitCount."
    ::= { assetManagementEntry 1 }

ledOperationMode OBJECT-TYPE
    SYNTAX AssetManagementLEDOperationModeEnumeration
    MAX-ACCESS read-write
    STATUS current
    DESCRIPTION "Operation mode of the LED (manual or automatic, based on tag connection)."
    ::= { assetManagementEntry 2 }

ledMode OBJECT-TYPE
    SYNTAX AssetManagementLEDModeEnumeration
    MAX-ACCESS read-write
    STATUS current
    DESCRIPTION
        "Mode of the LED (on, off, fastBlink,slowBlink).
         Setting this value automatically switches the ledOperationMode to manual."
    ::= { assetManagementEntry 3 }

ledColor OBJECT-TYPE
    SYNTAX RGBCOLOR
    MAX-ACCESS read-write
    STATUS current
    DESCRIPTION
        "Color of the LED (RGB) in binary format.
         Setting this value automatically switches the ledOperationMode to manual."
    ::= { assetManagementEntry 4 }

ledColorStr OBJECT-TYPE
    SYNTAX DisplayString
    MAX-ACCESS read-write
    STATUS current
    DESCRIPTION
        "Color of the LED (RGB) in string format.
         It contains 3 hex octets for the RGB colors.
         Setting this value automatically switches the ledOperationMode to manual."
    ::= { assetManagementEntry 5 }

tagID OBJECT-TYPE
    SYNTAX DisplayString
    MAX-ACCESS read-only
    STATUS current
    DESCRIPTION "Asset management tag attached to the rack unit. Empty in case there is no tag attached."
    ::= { assetManagementEntry 6 }

tagFamily OBJECT-TYPE
    SYNTAX DisplayString
    MAX-ACCESS read-only
    STATUS current
    DESCRIPTION "Family of the asset management tag attached to the rack unit. Empty in case there is no tag attached."
    ::= { assetManagementEntry 7 }

rackUnitPosition OBJECT-TYPE
    SYNTAX Integer32(0..256)
    MAX-ACCESS read-only
    STATUS current
    DESCRIPTION
        "A number associated with each rack unit. Its value
         depends on the rack unit numbering mode. It ranges
         between 1 and the value of rackUnitCount.
         If the asset strip is disconnected, then the value is 0."
    ::= { assetManagementEntry 8 }

rackUnitType OBJECT-TYPE
    SYNTAX RackUnitTypeEnumeration
    MAX-ACCESS read-only
    STATUS current
    DESCRIPTION
        "Type of the connected tag (single server or blade extension).
         If the asset strip is disconnected, then the value is unknown.
         If the asset tag is disconnected, then the value is none."
    ::= { assetManagementEntry 9 }

bladeExtensionSize OBJECT-TYPE
    SYNTAX Integer32(0..16)
    MAX-ACCESS read-only
    STATUS current
    DESCRIPTION
        "In case a blade extension is connected this returns the
         number of slots on the extension.
         If the asset strip is disconnected or no blade is connected,
         then the value is 0."
    ::= { assetManagementEntry 10 }

rackUnitName OBJECT-TYPE
    SYNTAX DisplayString
    MAX-ACCESS read-write
    STATUS current
    DESCRIPTION "Name for a specific rackunit, may be feeely chosen."
    ::= { assetManagementEntry 12 }

assetStripCascadePosition OBJECT-TYPE
    SYNTAX Integer32(0..99)
    MAX-ACCESS read-only
    STATUS current
    DESCRIPTION
        "This is the position of the asset Strip in a cascaded chain. Numbered in ascending
         order starting with the asset strip connected to the device (EMX/PX).
         For non-cascaded asset strips, value = 1. If the asset strip is disconnected, then the value is 0."
    ::= { assetManagementEntry 13 }

rackUnitRelativePosition OBJECT-TYPE
    SYNTAX Integer32(0..99)
    MAX-ACCESS read-only
    STATUS current
    DESCRIPTION
        "This is the relative position of the rackUnit within the assetStrip. For cascaded asset
         strips such as the AMS-M2-Z and AMS-M3-Z, it is numbered in ascending order starting
         with the rackunit closest to the asset strip edge with the connector.
         For non-cascaded asset strips, value = 1. If the asset strip is disconnected, then the value is 0."
    ::= { assetManagementEntry 14 }

assetStripNumberOfRackUnits OBJECT-TYPE
    SYNTAX Integer32(0..256)
    MAX-ACCESS read-only
    STATUS current
    DESCRIPTION
        "For non-cascaded asset strips, value = rackUnitCount
         For cascaded asset strips, it is the number of rack units in the asset Strip.
         Examples: 2 for AMS-M2-Z, 3 for AMS-M3-Z."
    ::= { assetManagementEntry 15 }

bladeExtensionTable OBJECT-TYPE
    SYNTAX SEQUENCE OF BladeExtensionEntryStruct
    MAX-ACCESS not-accessible
    STATUS current
    DESCRIPTION "A list of blade server extension entries containing tag information."
    ::= { assetManagement 2 }

bladeExtensionEntry OBJECT-TYPE
    SYNTAX BladeExtensionEntryStruct
    MAX-ACCESS not-accessible
    STATUS current
    DESCRIPTION "An entry containing tag information for a blade server extension."
    INDEX { assetStripID, rackUnitID, bladeSlotID }
    ::= { bladeExtensionTable 1 }

BladeExtensionEntryStruct ::= SEQUENCE {
    bladeSlotID Integer32,
    bladeTagID DisplayString,
    bladeSlotPosition Integer32
}

bladeSlotID OBJECT-TYPE
    SYNTAX Integer32(1..16)
    MAX-ACCESS not-accessible
    STATUS current
    DESCRIPTION "A unique value for each slot on a blade extension."
    ::= { bladeExtensionEntry 1 }

bladeTagID OBJECT-TYPE
    SYNTAX DisplayString
    MAX-ACCESS read-only
    STATUS current
    DESCRIPTION
        "Asset management tag attached to a blade extension at the rack unit. Empty in case there is no tag attached."
    ::= { bladeExtensionEntry 2 }

bladeSlotPosition OBJECT-TYPE
    SYNTAX Integer32(1..256)
    MAX-ACCESS read-only
    STATUS current
    DESCRIPTION "A number associated with each blade slot. It ranges between 1 and the value of bladeExtensionSize."
    ::= { bladeExtensionEntry 3 }

-- Information (no configuration options yet) about the asset management log

logConfiguration OBJECT IDENTIFIER ::= { log 1 }

logSize OBJECT-TYPE
    SYNTAX Integer32
    MAX-ACCESS read-only
    STATUS current
    DESCRIPTION "The number of entries in the asset management log table."
    ::= { logConfiguration 1 }

oldestLogID OBJECT-TYPE
    SYNTAX Integer32
    MAX-ACCESS read-only
    STATUS current
    DESCRIPTION "The index of the oldest entry in the log table."
    ::= { logConfiguration 2 }

newestLogID OBJECT-TYPE
    SYNTAX Integer32
    MAX-ACCESS read-only
    STATUS current
    DESCRIPTION "The index of the newest entry in the log table."
    ::= { logConfiguration 3 }

logEventCount OBJECT-TYPE
    SYNTAX Integer32
    MAX-ACCESS read-only
    STATUS current
    DESCRIPTION "The total number of logged events."
    ::= { logConfiguration 4 }

-- The assetManagementLog table provides a history of asset management events

assetManagementLogTable OBJECT-TYPE
    SYNTAX SEQUENCE OF AssetManagementLogEntryStruct
    MAX-ACCESS not-accessible
    STATUS current
    DESCRIPTION "A ring buffer containing asset management events."
    ::= { log 2 }

assetManagementLogEntry OBJECT-TYPE
    SYNTAX AssetManagementLogEntryStruct
    MAX-ACCESS not-accessible
    STATUS current
    DESCRIPTION "An entry in the asset management log table."
    INDEX { logIndex }
    ::= { assetManagementLogTable 1 }

AssetManagementLogEntryStruct ::= SEQUENCE {
    logIndex Integer32,
    logTimeStamp Unsigned32,
    logEventType LogEventTypeEnumeration,
    logAssetStripNumber Integer32,
    logRackUnitNumber Integer32,
    logRackUnitPosition Integer32,
    logSlotNumber Integer32,
    logTagID DisplayString,
    logAssetStripState AssetStripStateEnumeration,
    logParentBladeID DisplayString
}

logIndex OBJECT-TYPE
    SYNTAX Integer32(1..5000)
    MAX-ACCESS not-accessible
    STATUS current
    DESCRIPTION "The index of an entry in the log ring buffer. Its value ranges between 1 and logSize."
    ::= { assetManagementLogEntry 1 }

logTimeStamp OBJECT-TYPE
    SYNTAX Unsigned32
    MAX-ACCESS read-only
    STATUS current
    DESCRIPTION "The time of the log entry in seconds relative to January 1, 1970 00:00 UTC."
    ::= { assetManagementLogEntry 2 }

logEventType OBJECT-TYPE
    SYNTAX LogEventTypeEnumeration
    MAX-ACCESS read-only
    STATUS current
    DESCRIPTION "The type of this log entry."
    ::= { assetManagementLogEntry 3 }

logAssetStripNumber OBJECT-TYPE
    SYNTAX Integer32(0..256)
    MAX-ACCESS read-only
    STATUS current
    DESCRIPTION
        "A unique value for each asset strip. Its value ranges between 1 and the value of assetStripCount.
         This value is only valid for non-empty log entries"
    ::= { assetManagementLogEntry 4 }

logRackUnitNumber OBJECT-TYPE
    SYNTAX Integer32(0..256)
    MAX-ACCESS read-only
    STATUS current
    DESCRIPTION
        "A unique value for each rack unit. Its value ranges between 1 and the value of rackUnitCount.
         It corresponds with rackUnitID, the fixed ordinal index of each rack unit.
         This value is only valid for assetTagConnected and assetTagDisconnected events; it is 0 otherwise."
    ::= { assetManagementLogEntry 5 }

logRackUnitPosition OBJECT-TYPE
    SYNTAX Integer32(0..256)
    MAX-ACCESS read-only
    STATUS current
    DESCRIPTION
        "A number associated with each rack unit. Its value depends on the rack unit numbering mode. It ranges
         between 1 and the value of rackUnitCount. If the asset strip is disconnected, then the value is 0.
         This value is only valid for non-empty log entries"
    ::= { assetManagementLogEntry 6 }

logSlotNumber OBJECT-TYPE
    SYNTAX Integer32(0..16)
    MAX-ACCESS read-only
    STATUS current
    DESCRIPTION
        "A unique value for each slot on a blade extension. Value of 0 indicates a tag on the main strip.
         If the asset strip is disconnected, the value is 0 as well. Use logEventType to distinguish the validity."
    ::= { assetManagementLogEntry 7 }

logTagID OBJECT-TYPE
    SYNTAX DisplayString
    MAX-ACCESS read-only
    STATUS current
    DESCRIPTION "Asset management tag attached to the rack unit. Empty in case there is no tag attached."
    ::= { assetManagementLogEntry 8 }

logAssetStripState OBJECT-TYPE
    SYNTAX AssetStripStateEnumeration
    MAX-ACCESS read-only
    STATUS current
    DESCRIPTION "Asset management strip state."
    ::= { assetManagementLogEntry 9 }

logParentBladeID OBJECT-TYPE
    SYNTAX DisplayString
    MAX-ACCESS read-only
    STATUS current
    DESCRIPTION
        "In case the tag is attached to a blade extension, this indicates the tagID of the extension.
         Empty in case there is no tag attached or the tag is attached on the main strip."
    ::= { assetManagementLogEntry 10 }

-- the TrapInformation

deviceName OBJECT-TYPE
    SYNTAX DisplayString
    MAX-ACCESS accessible-for-notify
    STATUS current
    DESCRIPTION "The user-defined name for the Device."
    ::= { trapInformation 1 }

deviceInetAddressType OBJECT-TYPE
    SYNTAX InetAddressType
    MAX-ACCESS accessible-for-notify
    STATUS current
    DESCRIPTION "The type of address format"
    ::= { trapInformation 2 }

deviceInetIPAddress OBJECT-TYPE
    SYNTAX InetAddress
    MAX-ACCESS accessible-for-notify
    STATUS current
    DESCRIPTION "The current IP address. A value of 0.0.0.0 indicates an error or an unset option."
    ::= { trapInformation 3 }

assetStripNumber OBJECT-TYPE
    SYNTAX Integer32(1..256)
    MAX-ACCESS accessible-for-notify
    STATUS current
    DESCRIPTION "A unique value for each asset strip. Its value ranges between 1 and the value of assetStripCount."
    ::= { trapInformation 4 }

rackUnitNumber OBJECT-TYPE
    SYNTAX Integer32(1..256)
    MAX-ACCESS accessible-for-notify
    STATUS current
    DESCRIPTION
        "A unique value for each rack unit. Its value ranges between 1 and the value of rackUnitCount.
         It corresponds with rackUnitID, the fixed ordinal index of each rack unit."
    ::= { trapInformation 5 }

assetStripFirmwareUpdateState OBJECT-TYPE
    SYNTAX AssetStripFirmwareUpdateStateEnumeration
    MAX-ACCESS accessible-for-notify
    STATUS current
    DESCRIPTION "The new asset strip firmware update state."
    ::= { trapInformation 6}

deviceUserName OBJECT-TYPE
    SYNTAX DisplayString
    MAX-ACCESS accessible-for-notify
    STATUS current
    DESCRIPTION "The user currently logged in."
    ::= { trapInformation 7 }

deviceChangedParameter OBJECT-TYPE
    SYNTAX DeviceConfigurationParameterEnumeration
    MAX-ACCESS accessible-for-notify
    STATUS current
    DESCRIPTION "Description of the parameter(s) that changed."
    ::= { trapInformation 8 }

changedParameterNewValue OBJECT-TYPE
    SYNTAX DisplayString
    MAX-ACCESS accessible-for-notify
    STATUS current
    DESCRIPTION "The new value of the changed parameter."
    ::= { trapInformation 9 }

slotNumber OBJECT-TYPE
    SYNTAX Integer32(0..16)
    MAX-ACCESS accessible-for-notify
    STATUS current
    DESCRIPTION
    "A unique value for each slot on a blade extension. Value of 0 indicates a tag on the main strip."
    ::= { trapInformation 10 }

oldNumberOfComponentAssetStrips OBJECT-TYPE
    SYNTAX Integer32(0..255)
    MAX-ACCESS accessible-for-notify
    STATUS current
    DESCRIPTION "The old number of components building a composite asset strip."
    ::= { trapInformation 11 }

agentInetPortNumber OBJECT-TYPE
    SYNTAX InetPortNumber
    MAX-ACCESS accessible-for-notify
    STATUS current
    DESCRIPTION
    "The UDP port number used for accessing the SNMP agent on the device.
     Examples:
       If the associated device MIB (PX2-MIB, EMD-MIB) has deviceCascadeType set to portForwarding, then
         master: 50500
         slave 1: 50501
         slave 2: 50502
         ......
       If cascading mode is not portForwarding and default (Standard) ports are being used, then
         port: 161"
    ::= { trapInformation 12 }

deviceSerialNumber OBJECT-TYPE
    SYNTAX DisplayString
    MAX-ACCESS accessible-for-notify
    STATUS current
    DESCRIPTION "The device Serial Number."
    ::= { trapInformation 13 }

-- Start the traps

assetTagConnected NOTIFICATION-TYPE
    OBJECTS {
        deviceName,
        sysContact,
        sysName,
        sysLocation,
        deviceInetAddressType,
        deviceInetIPAddress,
        agentInetPortNumber,
        assetStripNumber,
        assetStripName,
        rackUnitNumber,
        rackUnitPosition,
        rackUnitName,
        slotNumber,
        tagID,
        bladeTagID,
        ledColor,
        ledMode,
        ledOperationMode,
        rackUnitCount,
        assetStripType,
        assetStripCascadePosition,
        rackUnitRelativePosition,
        assetStripNumberOfRackUnits,
        deviceSerialNumber
    }
    STATUS current
    DESCRIPTION
        "The asset tag of a rack unit was connected.
         bladeTagID is empty if the asset tag is not on a blade extension."
    ::= { traps 1 }

assetTagDisconnected NOTIFICATION-TYPE
    OBJECTS {
        deviceName,
        sysContact,
        sysName,
        sysLocation,
        deviceInetAddressType,
        deviceInetIPAddress,
        agentInetPortNumber,
        assetStripNumber,
        assetStripName,
        rackUnitNumber,
        rackUnitPosition,
        rackUnitName,
        slotNumber,
        tagID,
        bladeTagID,
        ledColor,
        ledMode,
        ledOperationMode,
        rackUnitCount,
        assetStripType,
        assetStripCascadePosition,
        rackUnitRelativePosition,
        assetStripNumberOfRackUnits,
        deviceSerialNumber
    }
    STATUS current
    DESCRIPTION
        "The asset tag of a rack unit was disconnected.
         bladeTagID is empty if the asset tag is not on a blade extension."
    ::= { traps 2 }

assetStripStateChange NOTIFICATION-TYPE
    OBJECTS {
        deviceName,
        sysContact,
        sysName,
        sysLocation,
        deviceInetAddressType,
        deviceInetIPAddress,
        agentInetPortNumber,
        assetStripNumber,
        assetStripName,
        assetStripState,
        rackUnitCount,
        deviceSerialNumber
    }
    STATUS current
    DESCRIPTION "The asset strip unit changed its state."
    ::= { traps 3 }

assetStripFirmwareUpdate NOTIFICATION-TYPE
    OBJECTS {
        deviceName,
        sysContact,
        sysName,
        sysLocation,
        deviceInetAddressType,
        deviceInetIPAddress,
        agentInetPortNumber,
        assetStripNumber,
        assetStripName,
        assetStripFirmwareUpdateState,
        deviceSerialNumber
    }
    STATUS current
    DESCRIPTION "Asset strip firmware update state change."
    ::= { traps 4 }

deviceConfigurationChanged NOTIFICATION-TYPE
    OBJECTS {
        deviceName,
        sysContact,
        sysName,
        sysLocation,
        deviceInetAddressType,
        deviceInetIPAddress,
        agentInetPortNumber,
        deviceUserName,
        assetStripNumber,
        assetStripName,
        deviceChangedParameter,
        changedParameterNewValue,
        deviceSerialNumber
    }
    STATUS current
    DESCRIPTION "Assetstrip configuration has changed"
    ::= { traps 5 }

rackUnitConfigurationChanged NOTIFICATION-TYPE
    OBJECTS {
        deviceName,
        sysContact,
        sysName,
        sysLocation,
        deviceInetAddressType,
        deviceInetIPAddress,
        agentInetPortNumber,
        deviceUserName,
        assetStripNumber,
        assetStripName,
        rackUnitNumber,
        rackUnitPosition,
        rackUnitName,
        ledColor,
        ledMode,
        ledOperationMode,
        deviceSerialNumber
    }
    STATUS current
    DESCRIPTION "Assetstrip configuration has changed"
    ::= { traps 6 }

bladeExtensionConnected NOTIFICATION-TYPE
    OBJECTS {
        deviceName,
        sysContact,
        sysName,
        sysLocation,
        deviceInetAddressType,
        deviceInetIPAddress,
        agentInetPortNumber,
        assetStripNumber,
        assetStripName,
        rackUnitNumber,
        rackUnitPosition,
        rackUnitName,
        tagID,
        bladeExtensionSize,
        ledColor,
        ledMode,
        ledOperationMode,
        rackUnitCount,
        assetStripType,
        assetStripCascadePosition,
        rackUnitRelativePosition,
        assetStripNumberOfRackUnits,
        deviceSerialNumber
    }
    STATUS current
    DESCRIPTION "A blade extension has been connected to the rackunit."
    ::= { traps 7 }

bladeExtensionDisconnected NOTIFICATION-TYPE
    OBJECTS {
        deviceName,
        sysContact,
        sysName,
        sysLocation,
        deviceInetAddressType,
        deviceInetIPAddress,
        agentInetPortNumber,
        assetStripNumber,
        assetStripName,
        rackUnitNumber,
        rackUnitPosition,
        rackUnitName,
        tagID,
        bladeExtensionSize,
        ledColor,
        ledMode,
        ledOperationMode,
        rackUnitCount,
        assetStripType,
        assetStripCascadePosition,
        rackUnitRelativePosition,
        assetStripNumberOfRackUnits,
        deviceSerialNumber
    }
    STATUS current
    DESCRIPTION "A blade extension has been disconnected from the rackunit."
    ::= { traps 8 }

bladeExtensionOverflowOccured NOTIFICATION-TYPE
    OBJECTS {
        deviceName,
        sysContact,
        sysName,
        sysLocation,
        deviceInetAddressType,
        deviceInetIPAddress,
        agentInetPortNumber,
        assetStripNumber,
        assetStripName,
        deviceSerialNumber
    }
    STATUS current
    DESCRIPTION
        "Maximum number of supported tags on blade extension was reached.
         The asset strip won't detect any new tags on blade extensions until some are removed."
    ::= { traps 9 }

bladeExtensionOverflowCleared NOTIFICATION-TYPE
    OBJECTS {
        deviceName,
        sysContact,
        sysName,
        sysLocation,
        deviceInetAddressType,
        deviceInetIPAddress,
        agentInetPortNumber,
        assetStripNumber,
        assetStripName,
        deviceSerialNumber
    }
    STATUS current
    DESCRIPTION "Free space for new tags on blade extensions is available again."
    ::= { traps 10 }

compositeAssetStripCompositionChanged NOTIFICATION-TYPE
    OBJECTS {
        deviceName,
        sysContact,
        sysName,
        sysLocation,
        deviceInetAddressType,
        deviceInetIPAddress,
        agentInetPortNumber,
        assetStripNumber,
        assetStripName,
        oldNumberOfComponentAssetStrips,
        numberOfComponentAssetStrips,
        deviceSerialNumber
    }
    STATUS current
    DESCRIPTION "The composition of an composite asset strip changed."
    ::= { traps 11 }

END

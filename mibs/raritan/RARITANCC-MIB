-- Enterprise MIB for CC Traps
-- New CC-6.0 version - Test
-- Author: Raritan
--
-- Raritan CC Enterprise MIB.
-- Copyright (C) 2007 Raritan Inc
-- Raritan Private Enterprise is registered with IANA organization
-- Version 1.1 Draft for CC-SG release 3.1.1
-- SNMP V1 MIBS

--  private    	OBJECT IDENTIFIER ::= { internet 4 }
--		enterprises	OBJECT IDENTIFIER ::= { private 1 }


RARITANCC-MIB DEFINITIONS ::= BEGIN
	IMPORTS
		mgmt, NetworkAddress, IpAddress, Counter, Gauge, TimeTicks, enterprises
			 FROM RFC1155-SMI
		OBJECT-TYPE
			 FROM RFC-1212
                TRAP-TYPE
			 FROM RFC-1215
		DisplayString
                         FROM RFC1213-MIB;

-- Raritan is registered with IANA for an enterprise MIB


raritan OBJECT IDENTIFIER ::= { enterprises 13742 }
products OBJECT IDENTIFIER ::= { raritan 1 }
enterpriseManagement  OBJECT IDENTIFIER ::= { products 1 }
commandCenter  OBJECT IDENTIFIER ::= { enterpriseManagement 1 }
ccObject OBJECT IDENTIFIER ::= { commandCenter  0 }
ccNotify OBJECT IDENTIFIER ::= { commandCenter  1 }



-- Define Traps for CC
--
-- Define all the Trap ASN variables
--


ccObjectName OBJECT-TYPE
	SYNTAX	DisplayString
	ACCESS   read-write
	STATUS	mandatory
	DESCRIPTION
		 " Object class name - CC "
	::= { ccObject 1 }


ccObjectInstance OBJECT-TYPE
	SYNTAX	DisplayString
	ACCESS   read-write
	STATUS	mandatory
	DESCRIPTION
		 " Object class instance - datacenter- CC1  "
	::= { ccObject 2}


ccUserName OBJECT-TYPE
	SYNTAX	DisplayString
	ACCESS   read-write
	STATUS	mandatory
	DESCRIPTION
		 " User Name  "
	::= { ccObject 3}



ccUserSessionId OBJECT-TYPE
	SYNTAX	DisplayString
	ACCESS   read-write
	STATUS	mandatory
	DESCRIPTION
		 " User name session ID  "
	::= { ccObject 4}



ccUserNameInitiated OBJECT-TYPE
	SYNTAX	DisplayString
	ACCESS   read-write
	STATUS	mandatory
	DESCRIPTION
		 " User Name, who initiated the session termination  "
	::= { ccObject 5 }



ccUserNameTerminated OBJECT-TYPE
	SYNTAX	DisplayString
	ACCESS   read-write
	STATUS	mandatory
	DESCRIPTION
		 " User Name, whose session got terminated  "
	::= { ccObject 6 }



ccImageType OBJECT-TYPE
	SYNTAX	DisplayString
	ACCESS   read-write
	STATUS	mandatory
	DESCRIPTION
		 " Image Type to tftp  "
	::= { ccObject 7 }



ccImageVersion OBJECT-TYPE
	SYNTAX	DisplayString
	ACCESS   read-write
	STATUS	mandatory
	DESCRIPTION
		 " Image version "
	::= { ccObject 8}


ccImageVersionStatus OBJECT-TYPE
	SYNTAX	INTEGER {
			success(1),
			failure(2)
			}
	ACCESS   read-write
	STATUS	mandatory
	DESCRIPTION
		 " Download image status "
	::= { ccObject 9 }



ccUserWhoAdded OBJECT-TYPE
	SYNTAX	DisplayString
	ACCESS   read-write
	STATUS	mandatory
	DESCRIPTION
		 " CC User who added an User to the system"
	::= { ccObject 10}



ccUserWhoDeleted OBJECT-TYPE
	SYNTAX	DisplayString
	ACCESS   read-write
	STATUS	mandatory
	DESCRIPTION
		 " CC User who Deleted an User to the system"
	::= { ccObject 11}



ccUserWhoModified OBJECT-TYPE
	SYNTAX	DisplayString
	ACCESS   read-write
	STATUS	mandatory
	DESCRIPTION
		 " CC User who added an User to the system"
	::= { ccObject 12}


ccNodeName OBJECT-TYPE
	SYNTAX	DisplayString
	ACCESS   read-write
	STATUS	mandatory
	DESCRIPTION
		 "CC Leaf Node Name  "
	::= { ccObject 13}


ccLanCard OBJECT-TYPE
	SYNTAX	INTEGER {
			 primary(1),
			 backup(2)
			}
	ACCESS   read-write
	STATUS	mandatory
	DESCRIPTION
		 "CC Lan Card "
	::= { ccObject 14}


ccHardDisk OBJECT-TYPE
	SYNTAX	INTEGER {
			 primary(1),
			 backup(2)
			}
	ACCESS   read-write
	STATUS	mandatory
	DESCRIPTION
		 "CC Disk "
	::= { ccObject 15}


ccSessionType OBJECT-TYPE
	SYNTAX	INTEGER {
			 serial(1),
			 kvm(2),
			 powerOutlet(3),
			 admin(4),
			 diagnostics(5)

			}
	ACCESS   read-write
	STATUS	mandatory
	DESCRIPTION
		 "CC Lan Card "
	::= { ccObject 16}



ccClusterState OBJECT-TYPE
	SYNTAX	INTEGER {
			 primary(1),
			 secondary(2),
			 standAlone(3)
			 			}
	ACCESS   read-write
	STATUS	mandatory
	DESCRIPTION
		 "CC Cluster State "
	::= { ccObject 17}



ccLeafNodeName OBJECT-TYPE
	SYNTAX	DisplayString
	ACCESS   read-write
	STATUS	mandatory
	DESCRIPTION
		 "CC Leaf Node Name  "
	::= { ccObject 18}



ccLeafNodeIPAddress OBJECT-TYPE
	SYNTAX	DisplayString
	ACCESS   read-write
	STATUS	mandatory
	DESCRIPTION
		 "CC Leaf Node IP address  "
	::= { ccObject 19}

ccLeafNodeFirmwareVersion OBJECT-TYPE
	SYNTAX	DisplayString
	ACCESS   read-write
	STATUS	mandatory
	DESCRIPTION
		 "CC Leaf Node Firmware Version  "
	::= { ccObject 20}

-- CC 3.0 Trap ASN variables


ccScheduledTaskDescription OBJECT-TYPE
	SYNTAX	DisplayString
	ACCESS   read-write
	STATUS	mandatory
	DESCRIPTION
		 "CC Scheduled Task Description  "
	::= { ccObject 21}

ccScheduledTaskFailureReason OBJECT-TYPE
	SYNTAX	DisplayString
	ACCESS   read-write
	STATUS	mandatory
	DESCRIPTION
		 "CC Scheduled Task Failure Reason "
	::= { ccObject 22}




ccDiagnosticConsoleAccessLevel OBJECT-TYPE
	SYNTAX	DisplayString
	ACCESS   read-write
	STATUS	mandatory
	DESCRIPTION
		 "CC Diagnostic Console Access Level  "
	::= { ccObject 23}



ccDeviceName OBJECT-TYPE
	SYNTAX	DisplayString
	ACCESS   read-write
	STATUS	mandatory
	DESCRIPTION
		 " Device Name  "
	::= { ccObject 24}


-- CC 3.1 Trap ASN variables


ccUserGroupName OBJECT-TYPE
	SYNTAX	DisplayString
	ACCESS   read-write
	STATUS	mandatory
	DESCRIPTION
		 " User Group Name  "
	::= { ccObject 25}

ccBannerChanges OBJECT-TYPE
	SYNTAX	INTEGER {
			 enabled(1),
			 disabled(2),
			 modified(3)
			 			}
	ACCESS   read-write
	STATUS	mandatory
	DESCRIPTION
		 "CC Banner Changes "
	::= { ccObject 26}

ccMOTDChanges OBJECT-TYPE
	SYNTAX	INTEGER {
			 enabled(1),
			 disabled(2),
			 modified(3)
			 			}
	ACCESS   read-write
	STATUS	mandatory
	DESCRIPTION
		 "CC MOTD Changes "
	::= { ccObject 27}

ccOldNumberOfOutlets OBJECT-TYPE
	SYNTAX	DisplayString
	ACCESS   read-write
	STATUS	mandatory
	DESCRIPTION
		 " Old number of outlets "
	::= { ccObject 28}

ccNewNumberOfOutlets OBJECT-TYPE
	SYNTAX	DisplayString
	ACCESS   read-write
	STATUS	mandatory
	DESCRIPTION
		 " New number of outlets "
	::= { ccObject 29}

ccSystemMonitorNotificationLevel OBJECT-TYPE
	SYNTAX	DisplayString
	ACCESS   read-write
	STATUS	mandatory
	DESCRIPTION
		 " Notification Level  "
	::= { ccObject 30}

ccSystemMonitorNotificationMessage OBJECT-TYPE
	SYNTAX	DisplayString
	ACCESS   read-write
	STATUS	mandatory
	DESCRIPTION
		 " Notification message  "
	::= { ccObject 31}

ccClusterPeer OBJECT-TYPE
    SYNTAX  DisplayString
    ACCESS   read-write
    STATUS  mandatory
    DESCRIPTION
         " Cluster peer  "
    ::= { ccObject 32}


ccClusterOperation OBJECT-TYPE
    SYNTAX  DisplayString
    ACCESS   read-write
    STATUS  mandatory
    DESCRIPTION
         " Cluster operation  "
    ::= { ccObject 33}


ccClusterOperationStatus OBJECT-TYPE
    SYNTAX  INTEGER {
            success(1),
            failure(2)
            }
    ACCESS   read-write
    STATUS  mandatory
    DESCRIPTION
         " Cluster operation status "
    ::= { ccObject 34 }

-- Start v1 the Traps




ccUnavailable		TRAP-TYPE
                ENTERPRISE raritan
		VARIABLES	{ccObjectName,
			 ccObjectInstance,
			 ccUserName,
                                     ccClusterState
			 }
	DESCRIPTION
		"CC Application is unavailable"
	::=   1



ccAvailable 	TRAP-TYPE
                ENTERPRISE raritan
		VARIABLES	{ccObjectName,
			 ccObjectInstance,
			 ccUserName,
                                     ccClusterState
			 }
                      DESCRIPTION
		"CC Application is Available "
	::= 2



ccUserLogin 		TRAP-TYPE
                ENTERPRISE raritan
		VARIABLES	{ccObjectName,
			 ccObjectInstance,
			 ccUserName
			 }

	DESCRIPTION
		"CC User Log in "
	::= 3


ccUserLogout 		TRAP-TYPE
                ENTERPRISE raritan
		VARIABLES	{ccObjectName,
			 ccObjectInstance,
			 ccUserName
			 }

	DESCRIPTION
		"CC User Log out "
	::= 4


-- A sesssion can be Serial/KVM/power supply

ccSPortConnectionStarted  	TRAP-TYPE
                ENTERPRISE raritan
		VARIABLES	{ccObjectName,
			 ccObjectInstance,
			 ccUserName,
			 ccSessionType,
			 ccUserSessionId
			 }
	DESCRIPTION
		"CC  Session started "
	::= 5


ccPortConnectionStopped 	TRAP-TYPE
                ENTERPRISE raritan
		VARIABLES	{ccObjectName,
			 ccObjectInstance,
			 ccUserName,
			 ccSessionType,
			 ccUserSessionId
			 }

	DESCRIPTION
		"CC  Session stopped "
	::= 6


ccPortConnectionTerminated 	TRAP-TYPE
                ENTERPRISE raritan
		VARIABLES	{ccObjectName,
			 ccObjectInstance,
			 ccUserNameInitiated,
			 ccUserNameTerminated,
			 ccSessionType,
			 ccUserSessionId
			 }

	DESCRIPTION
		"CC  Session Terminated "
	::= 7


ccImageUpgradeStarted	 TRAP-TYPE
                ENTERPRISE raritan
		VARIABLES	{ccObjectName,
			 ccObjectInstance,
			 ccUserName,
			 ccImageType,
			 ccImageVersion
			 }

	DESCRIPTION
		"CC Image Upgrade started "
	::= 8


ccImageUpgradeResults 	TRAP-TYPE
                ENTERPRISE raritan
		VARIABLES	{ccObjectName,
			 ccObjectInstance,
			 ccUserName,
			 ccImageType,
			 ccImageVersion,
			 ccImageVersionStatus
			 }

	DESCRIPTION
		"CC Image Upgrade results"
	::= 9


ccUserAdded		TRAP-TYPE
                ENTERPRISE raritan
		VARIABLES	{ccObjectName,
			 ccObjectInstance,
			 ccUserName,
			 ccUserWhoAdded

			 }

	DESCRIPTION
		"CC - A new user added "
	::= 10


ccUserDeleted		 TRAP-TYPE
                ENTERPRISE raritan
		VARIABLES	{ccObjectName,
			 ccObjectInstance,
			 ccUserName,
			 ccUserWhoDeleted
			 }
	DESCRIPTION
		"CC - A user deleted "
	::= 11


ccUserModified  		TRAP-TYPE
                ENTERPRISE raritan
		VARIABLES	{ccObjectName,
			 ccObjectInstance,
			 ccUserName,
			 ccUserWhoModified
			 }

	DESCRIPTION
		"CC user modified "
	::= 12


ccUserAuthenticationFailure	TRAP-TYPE
                ENTERPRISE raritan
		VARIABLES	{ccObjectName,
			 ccObjectInstance,
			 ccUserName
			 }

	DESCRIPTION
		"CC user authentication failure "
	::= 13






ccRootPasswordChanged	TRAP-TYPE
                ENTERPRISE raritan
		VARIABLES	{ccObjectName,
			 ccObjectInstance,
			 ccUserWhoModified
			 }

	DESCRIPTION
		"CC root password changed "
	::= 14



-- Added Cluster State attribute for Hard disk failure and Lan Card failure
-- CC Lan Card - Primary/Backup information

ccLanCardFailure 	TRAP-TYPE
	ENTERPRISE raritan
	VARIABLES	{ccObjectName,
			 ccObjectInstance,
			 ccLanCard,
			 ccClusterState
			 }
	DESCRIPTION
		"CC detected a Lan Card Failure"
	::= 15


ccHardDiskFailure	TRAP-TYPE
	ENTERPRISE raritan
	VARIABLES	{ccObjectName,
			 ccObjectInstance,
			 ccHardDisk,
			 ccClusterState
			 }
	DESCRIPTION
		"CC detected a Hard Disk Failure"
	::= 16


ccLeafNodeUnavailable 	TRAP-TYPE
	ENTERPRISE raritan
	VARIABLES	{ccObjectName,
			 ccObjectInstance,
			 ccLeafNodeName,
			 ccLeafNodeIPAddress
			 }

	DESCRIPTION
		"CC detected a connection failure to a leaf node"
	::= 17


ccLeafNodeAvailable 	TRAP-TYPE
	ENTERPRISE raritan
	VARIABLES	{ccObjectName,
			 ccObjectInstance,
			 ccLeafNodeName,
			 ccLeafNodeIPAddress
			 }

	DESCRIPTION
		"CC detected  leaf node reachable "
	::= 18


ccIncompatibleDeviceFirmware 	TRAP-TYPE
	ENTERPRISE raritan
	VARIABLES	{ccObjectName,
			 ccObjectInstance,
                         ccUserName,
			 ccLeafNodeIPAddress,
                         ccLeafNodeFirmwareVersion
			 }

	DESCRIPTION
		"CC detected  device with incompatible firmware "
	::= 19

ccDeviceUpgrade 	TRAP-TYPE
	ENTERPRISE raritan
	VARIABLES	{ccObjectName,
			 ccObjectInstance,
                         ccUserName,
			 ccLeafNodeIPAddress,
                         ccLeafNodeFirmwareVersion,
                         ccImageVersionStatus
			 }

	DESCRIPTION
		"CC has upgraded the firmware on a device "
	::= 20


-- CC 3.0 Traps


ccEnterMaintenanceMode	TRAP-TYPE
	ENTERPRISE raritan
	VARIABLES	{ccObjectName,
			 ccObjectInstance,
			 ccUserName
			 }
	DESCRIPTION
		"CC entered Maintenance Mode"
	::= 21

ccExitMaintenanceMode	TRAP-TYPE
	ENTERPRISE raritan
	VARIABLES	{ccObjectName,
			 ccObjectInstance,
			 ccUserName
			 }
	DESCRIPTION
		"CC exited Maintenance Mode"
	::= 22

ccUserLockedOut  	TRAP-TYPE
                ENTERPRISE raritan
		VARIABLES	{ccObjectName,
			         ccObjectInstance,
			         ccUserName
			 }

	DESCRIPTION
		"CC user ahas been locked out "
	::= 23


ccDeviceAddedAfterCCNOCNotification	TRAP-TYPE
	ENTERPRISE raritan
	VARIABLES	{ccObjectName,
			 ccObjectInstance,
			 ccDeviceName,
			 ccLeafNodeIPAddress
			 }

	DESCRIPTION
		"CC has added a Generic Device after receiving a notification from CC-NOC "
	::= 24


ccScheduledTaskExecutionFailure	TRAP-TYPE
	ENTERPRISE raritan
	VARIABLES	{ccObjectName,
			 ccObjectInstance,
			 ccScheduledTaskDescription,
			 ccScheduledTaskFailureReason
			 }

	DESCRIPTION
		"The reason why the execution of a scheduled task failed "
	::= 25

ccDiagnosticConsoleLogin	TRAP-TYPE
                ENTERPRISE raritan
		VARIABLES	{ccObjectName,
			 ccObjectInstance,
			 ccUserName,
                         ccDiagnosticConsoleAccessLevel
			 }

	DESCRIPTION
		"User has logged into the CC Diagnostic Console"
	::= 26


ccDiagnosticConsoleLogout	TRAP-TYPE
                ENTERPRISE raritan
		VARIABLES	{ccObjectName,
			 ccObjectInstance,
			 ccUserName,
                         ccDiagnosticConsoleAccessLevel
			 }

	DESCRIPTION
		"User has logged out of the CC Diagnostic Console"
	::= 27





ccNOCAvailable	TRAP-TYPE
                ENTERPRISE raritan
		VARIABLES	{ccObjectName,
			 ccObjectInstance,
                         ccLeafNodeIPAddress
			 }

	DESCRIPTION
		"CC has detected that CC-NOC is available"
	::= 28


ccNOCUnavailable	TRAP-TYPE
                ENTERPRISE raritan
		VARIABLES	{ccObjectName,
			 ccObjectInstance,
                         ccLeafNodeIPAddress
			 }

	DESCRIPTION
		"CC has detected that CC-NOC is unavailable"
	::= 29

-- CC-SG 3.1 Traps

ccUserGroupAdded		TRAP-TYPE
                ENTERPRISE raritan
		VARIABLES	{ccObjectName,
			 ccObjectInstance,
			 ccUserGroupName,
			 ccUserWhoAdded

			 }

	DESCRIPTION
		"CC-SG - A new user group has been added "
	::= 30


ccUserGroupDeleted		 TRAP-TYPE
                ENTERPRISE raritan
		VARIABLES	{ccObjectName,
			 ccObjectInstance,
			 ccUserGroupName,
			 ccUserWhoDeleted
			 }
	DESCRIPTION
		"CC-SG - A user group has been deleted "
	::= 31


ccUserGroupModified  		TRAP-TYPE
                ENTERPRISE raritan
		VARIABLES	{ccObjectName,
			 ccObjectInstance,
			 ccUserGroupName,
			 ccUserWhoModified
			 }

	DESCRIPTION
		"CC-SG - A user group has been modifed "
	::= 32

ccSuperuserNameChanged	TRAP-TYPE
                ENTERPRISE raritan
		VARIABLES	{ccObjectName,
			 ccObjectInstance,
			 ccUserWhoModified
			 }

	DESCRIPTION
		"CC-SG Superuser password changed "
	::= 33


ccSuperuserPasswordChanged	TRAP-TYPE
                ENTERPRISE raritan
		VARIABLES	{ccObjectName,
			 ccObjectInstance,
			 ccUserWhoModified
			 }

	DESCRIPTION
		"CC-SG Superuser password changed "
	::= 34

ccLoginBannerChanged	TRAP-TYPE
                ENTERPRISE raritan
		VARIABLES	{ccObjectName,
			 ccObjectInstance,
			 ccUserWhoModified,
                         ccBannerChanges
			 }

	DESCRIPTION
		"CC-SG Login Banner has changed "
	::= 35

ccMOTDChanged	TRAP-TYPE
                ENTERPRISE raritan
		VARIABLES	{ccObjectName,
			 ccObjectInstance,
			 ccUserWhoModified,
                         ccMOTDChanges
			 }

	DESCRIPTION
		"CC-SG Messsage of the Day (MOTD) has changed "
	::= 36

ccDominionPXReplaced		TRAP-TYPE
                ENTERPRISE raritan
		VARIABLES	{ccObjectName,
			 ccObjectInstance,
			 ccOldNumberOfOutlets,
			 ccNewNumberOfOutlets
			 }

	DESCRIPTION
		"CC-SG - A Dominion PX has been replaced "
	::= 37

ccSystemMonitorNotification		TRAP-TYPE
                ENTERPRISE raritan
		VARIABLES	{ccObjectName,
			 ccObjectInstance,
			 ccSystemMonitorNotificationLevel,
			 ccSystemMonitorNotificationMessage
			 }

	DESCRIPTION
		"CC-SG SystemMonitor notification"
	::= 38

ccNeighborhoodActivated		TRAP-TYPE
                ENTERPRISE raritan
		VARIABLES	{ccObjectName,
			 ccObjectInstance
			 }

	DESCRIPTION
		"CC-SG - Network neighborhood has been activated "
	::= 39

ccNeighborhoodUpdated		TRAP-TYPE
                ENTERPRISE raritan
		VARIABLES	{ccObjectName,
			 ccObjectInstance
			 }

	DESCRIPTION
		"CC-SG - Network neighborhood has been updated "
	::= 40

ccDominionPXFirmwareVersion OBJECT-TYPE
	SYNTAX	DisplayString
	ACCESS   read-write
	STATUS	mandatory
	DESCRIPTION
		 " Dominion PX Firmware Version  "
	::= { ccObject 32}

ccDominionPXFirmwareChanged		TRAP-TYPE
                ENTERPRISE raritan
		VARIABLES	{ccObjectName,
			 ccObjectInstance,
			 ccDominionPXFirmwareVersion
			 }

	DESCRIPTION
		"CC-SG - A Dominion PX firmware version has been changed "
	::= 41

ccClusterFailover   TRAP-TYPE
    ENTERPRISE raritan
    VARIABLES {ccObjectName,
               ccObjectInstance,
               ccClusterPeer
              }

    DESCRIPTION
        "CC-SG - The Primary has failed and the Backup is now operational as the new Primary "
    ::= 42


ccClusterBackupFailed   TRAP-TYPE
    ENTERPRISE raritan
    VARIABLES {ccObjectName,
               ccObjectInstance,
               ccClusterPeer
              }

    DESCRIPTION
        "CC-SG - The Backup has failed  "
    ::= 43


ccClusterWaitingPeerDetected    TRAP-TYPE
    ENTERPRISE raritan
    VARIABLES {ccObjectName,
               ccObjectInstance,
               ccClusterPeer
              }

    DESCRIPTION
        "CC-SG - The Primary detected a peer in Waiting mode "
    ::= 44


ccClusterOperation    TRAP-TYPE
    ENTERPRISE raritan
    VARIABLES {ccObjectName,
               ccObjectInstance,
               ccClusterOperation,
               ccClusterOperationStatus
              }

    DESCRIPTION
        "CC-SG - A cluster operation has been executed "
    ::= 45

END

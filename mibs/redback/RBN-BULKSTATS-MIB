-- *****************************************************************
-- RBN-BULKSTATS-MIB	Bulk Statistics MIB
--
-- Copyright (c) 2002-2003 RedBack Networks, Inc.
-- All rights reserved.
-- 
-- *****************************************************************

RBN-BULKSTATS-MIB DEFINITIONS ::= BEGIN

IMPORTS
	MODULE-IDENTITY,
	NOTIFICATION-TYPE,
	OBJECT-TYPE
		FROM SNMPv2-SMI
	MODULE-COMPLIANCE,
	NOTIFICATION-GROUP,
	OBJECT-GROUP
		FROM SNMPv2-CONF
	SnmpAdminString
		FROM SNMP-FRAMEWORK-MIB
	vacmContextName 
		FROM SNMP-VIEW-BASED-ACM-MIB
	InetAddressType,
	InetAddress
		FROM INET-ADDRESS-MIB
	rbnMgmt
		FROM RBN-SMI;

rbnBulkStatsMIB MODULE-IDENTITY
	LAST-UPDATED	"200302280000Z" -- Feb 28, 2003
	ORGANIZATION	"RedBack Networks, Inc."
	CONTACT-INFO
		"	RedBack Networks, Inc.

		Postal:	300 Holger Way
			San Jose, CA  95134-1362
			USA

		 Phone:	+1 408 750 3500
		   Fax: +1 408 750 3599

		E-mail:	mib-info@redback.com"
	DESCRIPTION
		"The MIB used to generically manage Bulk Statistics
		Gathering functionality on RedBack Networks devices."
	REVISION	"200302280000Z" -- Feb 28, 2003
	DESCRIPTION
		"Added a new table rbnBulkStatsLastTrfrTable, to
		accommodate the Multi-Instance Bulkstats feature.
		Also obsoleted the old objects."
	REVISION	"200205030000Z" -- May 03, 2002
	DESCRIPTION
		"Initial version. This version includes objects for
		notifying the failure of bulk statistics data transfer
		only."
	::= { rbnMgmt 21 }

rbnBulkStatsMIBNotifications OBJECT IDENTIFIER
	::= { rbnBulkStatsMIB 0 }

rbnBulkStatsMIBObjects OBJECT IDENTIFIER
	::= { rbnBulkStatsMIB 1 }

rbnBulkStatsMIBConformance OBJECT IDENTIFIER
	::= { rbnBulkStatsMIB 2 }


-- groups

rbnBulkStatsLastTrfr OBJECT IDENTIFIER
	::= { rbnBulkStatsMIBObjects 1 }


-- rbnBulkStatsLastTrfr group

-- This group contains information about the last attempted transfer of
-- the bulk statistics data.

rbnBulkStatsLastTrfrIpAddrType OBJECT-TYPE
	SYNTAX	    InetAddressType
	MAX-ACCESS  read-only
	STATUS	    obsolete
	DESCRIPTION
		"The address type contained in rbnBulkStatsLastTrfrIpAddr."
	::= { rbnBulkStatsLastTrfr 1 }

rbnBulkStatsLastTrfrIpAddr OBJECT-TYPE
	SYNTAX	    InetAddress
	MAX-ACCESS  read-only
	STATUS	    obsolete
	DESCRIPTION
		"The IP Address of the receiver station to which transfer
		of bulk statistics data was last attempted.
		If the IP address type is unknown, or if no transfers have
		occured, a zero-length string will be returned."
	::= { rbnBulkStatsLastTrfr 2 }

rbnBulkStatsLastTrfrStatus OBJECT-TYPE
	SYNTAX	    INTEGER {
			none(1),             -- no trfr attempted
			success(2),          -- trfr success
			genError(3),         -- memory alloc failed, etc
			loginFailed(4),      -- bad username, passwd
			badFilename(5),      -- bad remote filename, invalid dir
			remoteHostFailed(6), -- bad ip addr, conn refused
			other(7)
		    }
	MAX-ACCESS  read-only
	STATUS	    obsolete
	DESCRIPTION
		"The status of the last bulk statistics data transfer."
	::= { rbnBulkStatsLastTrfr 3 }

rbnBulkStatsLastTrfrTable OBJECT-TYPE
	SYNTAX      SEQUENCE OF RbnBulkStatsLastTrfrEntry
	MAX-ACCESS  not-accessible
	STATUS      current
	DESCRIPTION
		"A table which is used to monitor the last attempted transfer
		of the bulk statistics data for each bulkstats policy. All
		rows in this table are accessible when the context 'local' is
		specified in the snmp message. Snmp requests using other
		contexts shall return only the row which matches the context."
	::= { rbnBulkStatsLastTrfr 4 }

rbnBulkStatsLastTrfrEntry OBJECT-TYPE
	SYNTAX      RbnBulkStatsLastTrfrEntry
	MAX-ACCESS  not-accessible
	STATUS      current
	DESCRIPTION
		"An entry that indicates the status of the last attempted
		transfer of the bulk statistics data for each policy."
	INDEX { vacmContextName, rbnBulkStatsLastTrfrPolicy }
	::= { rbnBulkStatsLastTrfrTable 1 }

RbnBulkStatsLastTrfrEntry ::= SEQUENCE {
    rbnBulkStatsLastTrfrPolicy		SnmpAdminString,
    rbnBulkStatsLastTrfrIpAddrType2	InetAddressType,
    rbnBulkStatsLastTrfrIpAddr2		InetAddress,
    rbnBulkStatsLastTrfrStatus2		INTEGER
}

rbnBulkStatsLastTrfrPolicy OBJECT-TYPE
	SYNTAX      SnmpAdminString (SIZE (1..20))
	MAX-ACCESS  not-accessible
	STATUS      current
	DESCRIPTION
		"The bulkstats policy name."
	::= { rbnBulkStatsLastTrfrEntry 1 }

rbnBulkStatsLastTrfrIpAddrType2 OBJECT-TYPE
	SYNTAX	    InetAddressType
	MAX-ACCESS  read-only
	STATUS	    current
	DESCRIPTION
		"The address type contained in rbnBulkStatsLastTrfrIpAddr2."
	::= { rbnBulkStatsLastTrfrEntry 2 }

rbnBulkStatsLastTrfrIpAddr2 OBJECT-TYPE
	SYNTAX	    InetAddress
	MAX-ACCESS  read-only
	STATUS	    current
	DESCRIPTION
		"The IP Address of the receiver station to which transfer
		of bulk statistics data was last attempted.
		If the IP address type is unknown, or if no transfers have
		occured, a zero-length string will be returned."
	::= { rbnBulkStatsLastTrfrEntry 3 }

rbnBulkStatsLastTrfrStatus2 OBJECT-TYPE
	SYNTAX	    INTEGER {
			none(1),             -- no trfr attempted
			success(2),          -- trfr success
			genError(3),         -- memory alloc failed, etc
			loginFailed(4),      -- bad username, passwd
			badFilename(5),      -- bad remote filename, invalid dir
			remoteHostFailed(6), -- bad ip addr, conn refused
			other(7)
		    }
	MAX-ACCESS  read-only
	STATUS	    current
	DESCRIPTION
		"The status of the last bulk statistics data transfer."
	::= { rbnBulkStatsLastTrfrEntry 4 }


-- Notifications

rbnBulkStatsTrfrFail NOTIFICATION-TYPE
	OBJECTS	    {	rbnBulkStatsLastTrfrIpAddrType,
			rbnBulkStatsLastTrfrIpAddr, 
			rbnBulkStatsLastTrfrStatus
		    }
	STATUS	    obsolete
	DESCRIPTION
		"A rbnBulkStatsTrfrFail notification signifies
		that there has been a failure in the transfer of
		the bulk statistics data onto the receiver."
	::= { rbnBulkStatsMIBNotifications 1 }

rbnBulkStatsTrfrFail2 NOTIFICATION-TYPE
	OBJECTS	    {	rbnBulkStatsLastTrfrIpAddrType2,
			rbnBulkStatsLastTrfrIpAddr2, 
			rbnBulkStatsLastTrfrStatus2
		    }
	STATUS	    current
	DESCRIPTION
		"A rbnBulkStatsTrfrFail2 notification signifies
		that there has been a failure in the transfer of
		the bulk statistics data onto the receiver."
	::= { rbnBulkStatsMIBNotifications 2 }


-- Conformance Statements

rbnBulkStatsMIBGroups OBJECT IDENTIFIER
	::= { rbnBulkStatsMIBConformance 1 }

rbnBulkStatsMIBCompliances OBJECT IDENTIFIER
	::= { rbnBulkStatsMIBConformance 2 }


rbnBulkStatsMIBObjectGroup OBJECT-GROUP
	OBJECTS	    {	rbnBulkStatsLastTrfrIpAddrType,
			rbnBulkStatsLastTrfrIpAddr,
			rbnBulkStatsLastTrfrStatus
		    }
	STATUS	    obsolete
	DESCRIPTION
		"A collection of objects providing bulk statistics
		transfer information.
		The rbnBulkStatsMIBObjectGroup is mandatory when 
		the rbnBulkStatsMIBNotificationGroup is implemented."
	::= { rbnBulkStatsMIBGroups 1 }

rbnBulkStatsMIBNotificationGroup NOTIFICATION-GROUP
	NOTIFICATIONS {	rbnBulkStatsTrfrFail
		    }
	STATUS	    obsolete
	DESCRIPTION
		"A collection of notifications providing Bulk
		Statistics transfer information."
	::= { rbnBulkStatsMIBGroups 2 }

rbnBulkStatsMIBObjectGroup2 OBJECT-GROUP
	OBJECTS	    {	rbnBulkStatsLastTrfrIpAddrType2,
			rbnBulkStatsLastTrfrIpAddr2,
			rbnBulkStatsLastTrfrStatus2
		    }
	STATUS	    current
	DESCRIPTION
		"A collection of objects providing bulk statistics
		transfer information.
		The rbnBulkStatsMIBObjectGroup2 is mandatory when 
		the rbnBulkStatsMIBNotificationGroup2 is implemented."
	::= { rbnBulkStatsMIBGroups 3 }

rbnBulkStatsMIBNotificationGroup2 NOTIFICATION-GROUP
	NOTIFICATIONS {	rbnBulkStatsTrfrFail2
		    }
	STATUS	    current
	DESCRIPTION
		"A collection of notifications providing Bulk
		Statistics transfer failure information."
	::= { rbnBulkStatsMIBGroups 4 }


rbnBulkStatsMIBCompliance MODULE-COMPLIANCE
	STATUS	    obsolete
	DESCRIPTION
		"The compliance statement for the BulkStats MIB"
	MODULE	    -- this module
	GROUP	    rbnBulkStatsMIBNotificationGroup
	DESCRIPTION
		"This group is optional for devices which support
		Bulk Statistics collection capabilities"
	::= { rbnBulkStatsMIBCompliances 1 }

rbnBulkStatsMIBCompliance2 MODULE-COMPLIANCE
	STATUS	    current
	DESCRIPTION
		"The compliance statement for the BulkStats MIB"
	MODULE	    -- this module
	GROUP	    rbnBulkStatsMIBNotificationGroup2
	DESCRIPTION
		"This group is optional for devices which support
		Bulk Statistics collection capabilities"
	::= { rbnBulkStatsMIBCompliances 2 }

END

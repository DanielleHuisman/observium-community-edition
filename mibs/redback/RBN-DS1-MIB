-- *****************************************************************
-- RBN-DS1-MIB
--
-- Copyright (c) 2005 RedBack Networks, Inc.
-- All rights reserved.
--
-- *****************************************************************

RBN-DS1-MIB DEFINITIONS ::= BEGIN

IMPORTS
        MODULE-IDENTITY,
        OBJECT-TYPE
                FROM SNMPv2-SMI
        MODULE-COMPLIANCE,
        OBJECT-GROUP
                FROM SNMPv2-CONF
        RbnAlarmPerceivedSeverity,
        RbnAlarmServiceAffecting
                FROM RBN-ALARM-TC
        dsx1ConfigEntry
                FROM DS1-MIB
        rbnMgmt
                FROM RBN-SMI;

rbnDS1MIB MODULE-IDENTITY
        LAST-UPDATED    "200505090000Z" -- May 9, 2005
        ORGANIZATION    "RedBack Networks, Inc."
        CONTACT-INFO
                "       RedBack Networks, Inc.

                Postal: 300 Holger Way
                        San Jose, CA  95134
                        USA

                 Phone: +1 408 750 5000
                   Fax: +1 408 750 5599

                E-mail: mib-info@redback.com"
        DESCRIPTION
                "The MIB to describe DS1, E1, DS2, and E2 interfaces
                objects beyond those instrumented by standards-track
                MIBs."
        REVISION        "200505090000Z" -- May 9, 2005
        DESCRIPTION
                "Initial version"
        ::= { rbnMgmt 37 }


rbnDs1MIBObjects OBJECT IDENTIFIER ::= { rbnDS1MIB 1 }

rbnDsx1ConfigTable   OBJECT-TYPE
        SYNTAX       SEQUENCE OF RbnDsx1ConfigEntry
        MAX-ACCESS   not-accessible
        STATUS       current
        DESCRIPTION
                "The DS1 Configuration table."
        ::= { rbnDs1MIBObjects 1 }

rbnDsx1ConfigEntry    OBJECT-TYPE
        SYNTAX       RbnDsx1ConfigEntry
        MAX-ACCESS   not-accessible
        STATUS       current
        DESCRIPTION
                "An entry in the DS1 Configuration table."
        AUGMENTS { dsx1ConfigEntry }
        ::= { rbnDsx1ConfigTable 1 }

RbnDsx1ConfigEntry ::=
        SEQUENCE {
                rbnDsx1AlarmSeverity           RbnAlarmPerceivedSeverity,
                rbnDsx1AlarmServiceAffecting   RbnAlarmServiceAffecting
        }

rbnDsx1AlarmSeverity OBJECT-TYPE
        SYNTAX      RbnAlarmPerceivedSeverity
        MAX-ACCESS  read-only
        STATUS      current
        DESCRIPTION
                "The perceived severity of the interface alarm."
        ::= { rbnDsx1ConfigEntry 1 }


rbnDsx1AlarmServiceAffecting OBJECT-TYPE
        SYNTAX      RbnAlarmServiceAffecting
        MAX-ACCESS  read-only
        STATUS      current
        DESCRIPTION
                "Indicates whether the interface alarm is service affecting."
        ::= { rbnDsx1ConfigEntry 2 }


-- Conformance Information

rbnDs1MIBConformance OBJECT IDENTIFIER ::=
        { rbnDS1MIB 2 }

rbnDs1MIBGroups OBJECT IDENTIFIER ::=
        { rbnDs1MIBConformance 1 }

rbnDs1MIBCompliances OBJECT IDENTIFIER ::=
        { rbnDs1MIBConformance 2 }


-- Compliance Statements

rbnDs1MIBCompliance MODULE-COMPLIANCE
        STATUS      current
        DESCRIPTION
                "The compliance statement for using this MIB for all DS1
                interfaces"
        MODULE      -- this module
        MANDATORY-GROUPS {
                rbnDs1Group
                }
        ::= { rbnDs1MIBCompliances 1 }

-- Units of Conformance

rbnDs1Group OBJECT-GROUP
        OBJECTS {
                rbnDsx1AlarmSeverity,
                rbnDsx1AlarmServiceAffecting
        }
        STATUS      current
        DESCRIPTION
                "A collection of objects providing supplemental
                configuration information applicable to all DS1 interfaces."
        ::= { rbnDs1MIBGroups 1 }

END

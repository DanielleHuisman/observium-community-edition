-- *****************************************************************
-- RBN-IF-MIB       Extension of IF-MIB.my
--
-- 
-- *****************************************************************

RBN-IF-MIB DEFINITIONS ::= BEGIN

IMPORTS
    MODULE-IDENTITY, OBJECT-TYPE, Counter64
                FROM SNMPv2-SMI

    MODULE-COMPLIANCE, OBJECT-GROUP
                FROM SNMPv2-CONF

    rbnMgmt
                FROM RBN-SMI

    ifEntry
                FROM IF-MIB;

rbnIfMib MODULE-IDENTITY
    LAST-UPDATED "201207181800Z" -- July 18, 2012
    ORGANIZATION "ERICSSON AM"
    CONTACT-INFO
            "       Ericsson AB.

                Postal: 100 Headquarters Dr
                        San Jose, CA  95134
                        USA

                 Phone: +1 408 750 5000
                   Fax: +1 408 750 5599

             "
    DESCRIPTION
            "This MIB defines rbnIfTable which extends IF-MIB's ifTable"

    REVISION      "201207181800Z" -- July 18, 2012
    DESCRIPTION
        "Initial version - defines rbnIfMIB"
    ::= { rbnMgmt 57 }

rbnIfMIBObjects     OBJECT IDENTIFIER ::= { rbnIfMib 0 }
rbnIfMIBConformance OBJECT IDENTIFIER ::= { rbnIfMib 1 }

--
-- Textual Conventions
--

rbnIfTable OBJECT-TYPE
        SYNTAX       SEQUENCE OF RbnIfEntry
        MAX-ACCESS   not-accessible
        STATUS       current
        DESCRIPTION
            "A list of interface entries.  The number of entries is
            given by the value of rbnIfNumber.  This table contains
            extension objects for the ifTable interface table."
        ::= { rbnIfMIBObjects 1 }

rbnIfEntry      OBJECT-TYPE
    SYNTAX      RbnIfEntry
    MAX-ACCESS  not-accessible
    STATUS      current
    DESCRIPTION
            "An entry containing additional management information
            applicable to a particular interface."
    AUGMENTS    { ifEntry }
    ::= { rbnIfTable 1 }

RbnIfEntry ::=
    SEQUENCE {
        rbnIfHCInIPv4Octets           Counter64,
        rbnIfHCOutIPv4Octets          Counter64,        
        rbnIfHCInIPv4MulticastPkts    Counter64,
        rbnIfHCOutIPv4MulticastPkts   Counter64,
        rbnIfHCInIPv6Octets           Counter64,
        rbnIfHCOutIPv6Octets          Counter64, 
        rbnIfHCInIPv6MulticastPkts    Counter64,
        rbnIfHCOutIPv6MulticastPkts   Counter64
    }

rbnIfHCInIPv4Octets OBJECT-TYPE
    SYNTAX      Counter64
    MAX-ACCESS  read-only
    STATUS      current
    DESCRIPTION
            "The total number of IPv4 octets received on the interface,
            including framing characters.  

            Discontinuities in the value of this counter can occur at
            re-initialization of the management system, and at other
            times as indicated by the value of
            ifCounterDiscontinuityTime in ifXTable in IF-MIB."
    ::= { rbnIfEntry 1 }

rbnIfHCOutIPv4Octets OBJECT-TYPE
    SYNTAX      Counter64
    MAX-ACCESS  read-only
    STATUS      current
    DESCRIPTION
            "The total number of IPv4 octets transmitted out of the
            interface, including framing characters. 

            Discontinuities in the value of this counter can occur at
            re-initialization of the management system, and at other
            times as indicated by the value of
            ifCounterDiscontinuityTime in ifXTable in IF-MIB."
    ::= { rbnIfEntry 2 }

rbnIfHCInIPv4MulticastPkts  OBJECT-TYPE
    SYNTAX      Counter64
    MAX-ACCESS  read-only
    STATUS      current
    DESCRIPTION
            "The number of IPv4 packets, delivered by this sub-layer to a
            higher (sub-)layer, which were addressed to a multicast
            address at this sub-layer.  For a MAC layer protocol, this
            includes both Group and Functional addresses.
  
            Discontinuities in the value of this counter can occur at
            re-initialization of the management system, and at other
            times as indicated by the value of
            ifCounterDiscontinuityTime in ifXTable in IF-MIB."
    ::= { rbnIfEntry 3 }

rbnIfHCOutIPv4MulticastPkts OBJECT-TYPE
SYNTAX      Counter64
    MAX-ACCESS  read-only
    STATUS      current
    DESCRIPTION
            "The total number of IPv4 packets that higher-level protocols
            requested be transmitted, and which were addressed to a
            multicast address at this sub-layer, including those that
            were discarded or not sent.  For a MAC layer protocol, this
            includes both Group and Functional addresses. 

            Discontinuities in the value of this counter can occur at
            re-initialization of the management system, and at other
            times as indicated by the value of
            ifCounterDiscontinuityTime in ifXTable in IF-MIB."
    ::= { rbnIfEntry 4 }

rbnIfHCInIPv6Octets OBJECT-TYPE
    SYNTAX      Counter64
    MAX-ACCESS  read-only
    STATUS      current
    DESCRIPTION
            "The total number of IPv6 octets received on the interface,
            including framing characters.  

            Discontinuities in the value of this counter can occur at
            re-initialization of the management system, and at other
            times as indicated by the value of
            ifCounterDiscontinuityTime in ifXTable in IF-MIB."
    ::= { rbnIfEntry 5 }

rbnIfHCOutIPv6Octets OBJECT-TYPE
    SYNTAX      Counter64
    MAX-ACCESS  read-only
    STATUS      current
    DESCRIPTION
            "The total number of IPv6 octets transmitted out of the
            interface, including framing characters. 

            Discontinuities in the value of this counter can occur at
            re-initialization of the management system, and at other
            times as indicated by the value of
            ifCounterDiscontinuityTime in ifXTable in IF-MIB."
    ::= { rbnIfEntry 6 }

rbnIfHCInIPv6MulticastPkts  OBJECT-TYPE
    SYNTAX      Counter64
    MAX-ACCESS  read-only
    STATUS      current
    DESCRIPTION
            "The number of IPv6 packets, delivered by this sub-layer to a
            higher (sub-)layer, which were addressed to a multicast
            address at this sub-layer.  For a MAC layer protocol, this
            includes both Group and Functional addresses.
  
            Discontinuities in the value of this counter can occur at
            re-initialization of the management system, and at other
            times as indicated by the value of
            ifCounterDiscontinuityTime in ifXTable in IF-MIB."
    ::= { rbnIfEntry 7 }

rbnIfHCOutIPv6MulticastPkts OBJECT-TYPE
SYNTAX      Counter64
    MAX-ACCESS  read-only
    STATUS      current
    DESCRIPTION
            "The total number of IPv6 packets that higher-level protocols
            requested be transmitted, and which were addressed to a
            multicast address at this sub-layer, including those that
            were discarded or not sent.  For a MAC layer protocol, this
            includes both Group and Functional addresses. 

            Discontinuities in the value of this counter can occur at
            re-initialization of the management system, and at other
            times as indicated by the value of
            ifCounterDiscontinuityTime in ifXTable in IF-MIB."
    ::= { rbnIfEntry 8 }

--
-- compliance statements
--

rbnIfMIBCompliances OBJECT IDENTIFIER ::= { rbnIfMIBConformance 1 }
rbnIfMIBGroups   OBJECT IDENTIFIER ::= { rbnIfMIBConformance 2 }

rbnIfCompliance MODULE-COMPLIANCE
        STATUS current      
        DESCRIPTION
                "The compliance statement for RBN-IF-MIB"
        MODULE      -- this module
        MANDATORY-GROUPS {
                rbnIfMIBGroup
        }
        ::= { rbnIfMIBCompliances 1 }

rbnIfMIBGroup OBJECT-GROUP
    OBJECTS  {
        rbnIfHCInIPv4Octets,
        rbnIfHCOutIPv4Octets,
        rbnIfHCInIPv4MulticastPkts,
        rbnIfHCOutIPv4MulticastPkts,
        rbnIfHCInIPv6Octets,
        rbnIfHCOutIPv6Octets,
        rbnIfHCInIPv6MulticastPkts,
        rbnIfHCOutIPv6MulticastPkts   
    }
    STATUS current
    DESCRIPTION
       "Conformance group for RBN-IF-MIB objects."
    ::= { rbnIfMIBGroups 1 }

END

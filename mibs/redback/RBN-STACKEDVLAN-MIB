-- *****************************************************************
-- RBN-STACKEDVLAN-MIB
--
-- Copyright (c) 2007 RedBack Networks, Inc.
-- All rights reserved.
--
-- *****************************************************************
RBN-STACKEDVLAN-MIB DEFINITIONS ::= BEGIN
     
IMPORTS
     MODULE-IDENTITY, OBJECT-TYPE, 
     Counter64                       FROM SNMPv2-SMI 
     MODULE-COMPLIANCE,
     OBJECT-GROUP
                                     FROM SNMPv2-CONF
     InterfaceIndex                  FROM IF-MIB
     rbnMgmt                         FROM RBN-SMI;

rbnStackedVlanMIB MODULE-IDENTITY 
     LAST-UPDATED    "200702270000Z" -- February 27, 2007
     ORGANIZATION    "RedBack Networks, Inc."
     CONTACT-INFO
             "       RedBack Networks, Inc.
   
          Postal:    300 Holger Way
                     San Jose, CA  95134-1362
                     USA
  
             Phone:   +1 408 750-5000
             Fax:     +1 408 750-5599
    
          E-mail:    mib-info@redback.com"
     DESCRIPTION
          "This management information module defines the
          objects necessary to support the management of
          stacked VLAN interfaces"
     REVISION        "200702270000Z" -- February 27, 2007 
     DESCRIPTION
             "Initial version"
     ::= { rbnMgmt 40 }

-- MIB Objects

rbnStackedVlanMIBObjects OBJECT IDENTIFIER
     ::= { rbnStackedVlanMIB 1 }

rbnStackedVlanAggrStatsTable OBJECT-TYPE
     SYNTAX      SEQUENCE OF RbnStackedVlanAggrStatsEntry
     MAX-ACCESS  not-accessible
     STATUS      current
     DESCRIPTION
           "A table containing aggregated statistics of inner 
           VLAN's related to an outer VLAN."
     ::= { rbnStackedVlanMIBObjects 1}

rbnStackedVlanAggrStatsEntry OBJECT-TYPE
     SYNTAX      RbnStackedVlanAggrStatsEntry
     MAX-ACCESS  not-accessible
     STATUS      current
     DESCRIPTION
           "An entry in the rbnStackedVlanStatisticsTable." 
     INDEX   { rbnStackedVlanIndex }
     ::= { rbnStackedVlanAggrStatsTable 1 }

RbnStackedVlanAggrStatsEntry ::= 
     SEQUENCE {
         rbnStackedVlanIndex                     InterfaceIndex,
         rbnStackedVlanHCInOctets                Counter64,
         rbnStackedVlanHCInUcastPkts             Counter64,
         rbnStackedVlanHCInMulticastPkts         Counter64,
         rbnStackedVlanHCInBroadcastPkts         Counter64,
         rbnStackedVlanHCOutOctets               Counter64,
         rbnStackedVlanHCOutUcastPkts            Counter64,
         rbnStackedVlanHCOutMulticastPkts        Counter64,
         rbnStackedVlanHCOutBroadcastPkts        Counter64
}

--
-- High Capacity Counter objects.   
--
 
rbnStackedVlanIndex OBJECT-TYPE
SYNTAX      InterfaceIndex
MAX-ACCESS  not-accessible 
STATUS      current
DESCRIPTION "An index value that uniquely identifies an
             interface to an ethernet-like medium.  The
             interface identified by a particular value of
             this index is the same interface as identified
             by the same value of ifIndex."
      REFERENCE   "RFC 2233, ifIndex"
::= { rbnStackedVlanAggrStatsEntry 1 }

rbnStackedVlanHCInOctets OBJECT-TYPE
     SYNTAX      Counter64
     MAX-ACCESS  read-only
     STATUS      current
     DESCRIPTION
           "The aggregate of the total number of octets received on each 
           outer vlan and its inner vlans, including framing characters." 
         
     ::= { rbnStackedVlanAggrStatsEntry 2 } 
 
rbnStackedVlanHCInUcastPkts OBJECT-TYPE
     SYNTAX      Counter64
     MAX-ACCESS  read-only
     STATUS      current
     DESCRIPTION
           "The  aggregate of the number of packets, delivered by this 
           sub-layer to a higher (sub-)layer, which were not addressed to 
           a multicast or broadcast address at this sub-layer for each outer 
           vlan  and its inner vlans."

     ::= { rbnStackedVlanAggrStatsEntry 3 }

rbnStackedVlanHCInMulticastPkts OBJECT-TYPE
     SYNTAX      Counter64
     MAX-ACCESS  read-only
     STATUS      current
     DESCRIPTION
           "The aggregate number of packets, delivered by this sub-layer to a
           higher (sub-)layer, which were addressed to a multicast address at
           this sub-layer for each outer vlan and its inner vlans.  For a
           MAC layer protocol, this includes both Group and Functional 
           addresses."

   ::= { rbnStackedVlanAggrStatsEntry 4 }

rbnStackedVlanHCInBroadcastPkts OBJECT-TYPE
     SYNTAX      Counter64
     MAX-ACCESS  read-only
     STATUS      current
     DESCRIPTION
           "The aggregate number of packets, delivered by this sub-layer to a
           higher (sub-)layer, which were addressed to a broadcast address at
           this sub-layer for each outer vlan and its inner vlans."
   
     ::= { rbnStackedVlanAggrStatsEntry 5 }

rbnStackedVlanHCOutOctets OBJECT-TYPE
     SYNTAX      Counter64
     MAX-ACCESS  read-only
     STATUS      current
     DESCRIPTION
           "The aggregate of the total number of octets transmitted out of the
           interface, including framing characters for each outer vlan and its 
	   inner vlans."

     ::= { rbnStackedVlanAggrStatsEntry 6 }

rbnStackedVlanHCOutUcastPkts OBJECT-TYPE
     SYNTAX      Counter64
     MAX-ACCESS  read-only
     STATUS      current
     DESCRIPTION
           "The aggregate of the total number of packets that higher-level  
           protocols requested be transmitted, and which were not addressed to 
           a multicast or broadcast address at this sub-layer, including those
           that were discarded or not sent for each outer vlan and its
	   inner vlans."
 
     ::= { rbnStackedVlanAggrStatsEntry 7 }

rbnStackedVlanHCOutMulticastPkts OBJECT-TYPE
     SYNTAX      Counter64
     MAX-ACCESS  read-only
     STATUS      current
     DESCRIPTION
           "The  aggregate of the total number of packets that higher-level 
           protocols requested be transmitted, and which were addressed to a
           multicast address at this sub-layer, including those that were 
           discarded or not sent for each outer vlan and its inner vlans.  
           For a MAC layer protocol, this includes both Group and Functional 
           addresses."
 
     ::= { rbnStackedVlanAggrStatsEntry 8 }

rbnStackedVlanHCOutBroadcastPkts OBJECT-TYPE
     SYNTAX      Counter64
     MAX-ACCESS  read-only
     STATUS      current
     DESCRIPTION
           "The aggregate of the total number of packets that higher-level
           protocols requested be transmitted, and which were addressed to 
           a broadcast address at this sub-layer, including those that were 
           discarded or not sent for each outer vlan and its inner vlans."

     ::= { rbnStackedVlanAggrStatsEntry 9 }

-- Conformance Information

rbnStackedVlanMIBConformance OBJECT IDENTIFIER ::=
       { rbnStackedVlanMIB 2 }

rbnStackedVlanMIBGroups OBJECT IDENTIFIER ::=
         { rbnStackedVlanMIBConformance 1 }

rbnStackedVlanMIBCompliances OBJECT IDENTIFIER ::=
         { rbnStackedVlanMIBConformance 2 }

-- Compliance Statements

rbnStackedVlanMIBCompliance MODULE-COMPLIANCE
         STATUS      current
         DESCRIPTION
                "The compliance statement for using this MIB." 
         MODULE      -- this module
         MANDATORY-GROUPS {
             rbnStackedVlanMIBGroup
             }
         ::= { rbnStackedVlanMIBCompliances 1 }

-- Units of Conformance

rbnStackedVlanMIBGroup OBJECT-GROUP
        OBJECTS {
               rbnStackedVlanHCInOctets,
               rbnStackedVlanHCInUcastPkts, 
               rbnStackedVlanHCInMulticastPkts ,
               rbnStackedVlanHCInBroadcastPkts,
               rbnStackedVlanHCOutOctets, 
               rbnStackedVlanHCOutUcastPkts,
               rbnStackedVlanHCOutMulticastPkts,
               rbnStackedVlanHCOutBroadcastPkts
        }
        STATUS      current
        DESCRIPTION
                "A collection of objects providing statistical information."
        ::= { rbnStackedVlanMIBGroups 1 }

END

-- *****************************************************************
-- RBN-AAL5-VCL-STAT-MIB
--
-- Copyright (c) 1998 RedBack Networks, Inc.
-- All rights reserved.
-- 
-- *****************************************************************

RBN-X-AAL5-VCL-STAT-MIB DEFINITIONS ::= BEGIN

IMPORTS
	MODULE-IDENTITY,
	OBJECT-TYPE,
	Counter32
		FROM SNMPv2-SMI
	MODULE-COMPLIANCE,
	OBJECT-GROUP
		FROM SNMPv2-CONF
	ifIndex
		FROM IF-MIB
	atmVclVpi,
	atmVclVci
		FROM ATM-MIB
	rbnExperiment
		FROM RBN-SMI;

rbnXAal5VclStatMIB MODULE-IDENTITY
	LAST-UPDATED	"9804171645Z"
	ORGANIZATION	"RedBack Networks, Inc."
	CONTACT-INFO
		"	RedBack Networks, Inc.

		Postal:	1389 Moffett Park Drive
			Sunnyvale, CA  94089-1134
			USA

		 Phone:	+1 408 548 3500
		   Fax: +1 408 548 3599

		E-mail:	mib-info@RedBackNetworks.com"
	DESCRIPTION
		"The MIB for instrumenting statistics associated with
		an ATM VCL.  This MIB is positioned in the RedBack
		Networks experimental MIB space because it mirrors MIB
		objects currently being developed by the IETF atommib
		Working Group, namely the atmAal5VclStatTable objects
		found in the ATM2-MIB (draft-ietf-atommib-atm2-XX.txt).
		At such time as the ATM2-MIB is placed on the IETF
		standards track, this MIB will be obsoleted in favor
		of the IETF one"
	::= { rbnExperiment 1 }


rbnXAal5VclStatMIBObjects OBJECT IDENTIFIER ::= { rbnXAal5VclStatMIB 1 }

rbnXAtmAal5VclStatTable   OBJECT-TYPE
	SYNTAX       SEQUENCE OF RbnXAtmAal5VclStatEntry
	MAX-ACCESS   not-accessible
	STATUS       deprecated
	DESCRIPTION
		"This table provides a collection of objects
		providing AAL5 configuration and performance
		statistics of a VCL."
	::= { rbnXAal5VclStatMIBObjects 1 }

rbnXAtmAal5VclStatEntry    OBJECT-TYPE
	SYNTAX       RbnXAtmAal5VclStatEntry
	MAX-ACCESS   not-accessible
	STATUS       deprecated
	DESCRIPTION
		"Each entry in this table represents a VCL."
	INDEX { ifIndex, atmVclVpi, atmVclVci }
	::= { rbnXAtmAal5VclStatTable 1 }


RbnXAtmAal5VclStatEntry ::=
	SEQUENCE {
		rbnXAtmAal5VclInPkts        Counter32,
		rbnXAtmAal5VclOutPkts       Counter32,
		rbnXAtmAal5VclInOctets      Counter32,
		rbnXAtmAal5VclOutOctets     Counter32
	}


rbnXAtmAal5VclInPkts      OBJECT-TYPE
	SYNTAX       Counter32
	MAX-ACCESS   read-only
	STATUS       deprecated
	DESCRIPTION
		"The number of AAL5 CPCS PDUs received on the AAL5
		VCC at the interface identified by the ifIndex."
	::= { rbnXAtmAal5VclStatEntry 1 }

rbnXAtmAal5VclOutPkts   OBJECT-TYPE
	SYNTAX       Counter32
	MAX-ACCESS   read-only
	STATUS       deprecated
	DESCRIPTION
		"The number of AAL5 CPCS PDUs transmitted on the
		AAL5 VCC at the interface identified by the
		ifIndex."
	::= { rbnXAtmAal5VclStatEntry 2 }

rbnXAtmAal5VclInOctets   OBJECT-TYPE
	SYNTAX       Counter32
	MAX-ACCESS   read-only
	STATUS       deprecated
	DESCRIPTION
		"The number of octets contained in AAL5 CPCS PDUs
		received on the AAL5 VCC at the interface
		identified by the ifIndex."
	::= { rbnXAtmAal5VclStatEntry 3 }

rbnXAtmAal5VclOutOctets   OBJECT-TYPE
	SYNTAX       Counter32
	MAX-ACCESS   read-only
	STATUS       deprecated
	DESCRIPTION
		"The number of octets contained in AAL5 CPCS PDUs
		transmitted on the AAL5 VCC at the interface
		identified by the ifIndex."
	::= { rbnXAtmAal5VclStatEntry 4 }

-- Conformance Information

rbnXAal5VclStatMIBConformance OBJECT IDENTIFIER ::=
	{ rbnXAal5VclStatMIB 2 }

rbnXAal5VclStatMIBGroups OBJECT IDENTIFIER ::= 
	{ rbnXAal5VclStatMIBConformance 1 }

rbnXAal5VclStatMIBCompliances OBJECT IDENTIFIER ::=
	{ rbnXAal5VclStatMIBConformance 2 }


-- Compliance Statements

rbnXAal5VclStatMIBCompliance MODULE-COMPLIANCE
	STATUS	    current
	DESCRIPTION
		"The compliance statement for RedBack Networks
		SNMP entities which represent AAL5 VCL statistics"
	MODULE	    -- this module
	MANDATORY-GROUPS {
		rbnXAal5VclStatGroup
		}
	::= { rbnXAal5VclStatMIBCompliances 1 }

-- Units of Conformance

rbnXAal5VclStatGroup OBJECT-GROUP
	OBJECTS {
		rbnXAtmAal5VclInPkts,
		rbnXAtmAal5VclOutPkts,
		rbnXAtmAal5VclInOctets,
		rbnXAtmAal5VclOutOctets
	}
	STATUS	    current
	DESCRIPTION
		"A collection of objects providing supplemental
		AAL5 VCL information beyond that supplied by
		IETF standards-track MIBs"
	::= { rbnXAal5VclStatMIBGroups 1 }

END

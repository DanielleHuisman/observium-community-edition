CL-PKTC-EUE-USER-MIB DEFINITIONS ::= BEGIN
IMPORTS
    PktcEUETCIDType,
    PktcEUETCID,
    PktcEUETCCredsType,
    PktcEUETCCreds,
    PktcEUETCUsrElementIndexType,
    PktcEUETCUsrAppIndexType,
    PktcEUETCAppOrgIdentifier,
    PktcEUETCAppIdentifier,
    PktcEUETCAdminStatus,
    PktcEUETCOperStatus,
    PktcEUETCStatusInfo
                    FROM CL-PKTC-EUE-TC-MIB
    MODULE-IDENTITY,
    OBJECT-TYPE
                    FROM SNMPv2-SMI
    OBJECT-GROUP,
    MODULE-COMPLIANCE
                    FROM SNMPv2-CONF
    SnmpAdminString
                    FROM SNMP-FRAMEWORK-MIB
    TruthValue,
    RowStatus
                    FROM SNMPv2-TC
    pktcEUEMibs    
                    FROM CLAB-DEF-MIB;

pktcEUEUserMIB MODULE-IDENTITY
    LAST-UPDATED "201108050000Z" -- August 05, 2011
    ORGANIZATION "Cable Television Laboratories, Inc."
    CONTACT-INFO
            "Broadband Network Services
             Cable Television Laboratories, Inc.
             858 Coal Creek Circle,
             Louisville, CO 80027, USA  
             Phone: +1 303-661-3307
             Email: mibs@cablelabs.com
             Acknowledgements:
             Thomas Clack, Broadcom - Primary author,
             Eugene Nechamkin, Broadcom
             Sumanth Channabasappa, CableLabs
             John Berg, CableLabs
             Eduardo Cardona, CableLabs
             and members of the PacketCable 2.0 Provisioning Focus Team."
    DESCRIPTION
            "This MIB module contains configuration MIB  
             objects for the PacketCable Users as  
             required by the PacketCable  
             E-UE Provisioning Framework."
    REVISION "201108050000Z" -- August 05, 2011
    DESCRIPTION
    	    "Revised Version, published as part of the CableLabs
	    E-UE Provisioning Data Model Specification
	    PKT-SP-EUE-DATA-I06-110127"
    REVISION "201006160000Z" -- June 16, 2010
    DESCRIPTION
    	    "Revised Version, published as part of the CableLabs
	    E-UE Provisioning Data Model Specification
	    PKT-SP-EUE-DATA-I05-100527"
    REVISION "200807100000Z" -- July 10, 2008
    DESCRIPTION
            "Revised Version includes ECN EUE-DATA-N-08.0524-5
            and published as I02"            
    REVISION "200711060000Z" -- Nov 6, 2007
    DESCRIPTION
            "Initial version, published as part of the CableLabs
            E-UE Provisioning Data Model Specification
            PKT-SP-EUE-DATA-I01-071106
            Copyright 1999-2007 Cable Television Laboratories, Inc.
            All rights reserved."            
    ::= { pktcEUEMibs 4 }

-- Administrative assignments      
pktcEUEUsrNotification      OBJECT IDENTIFIER ::= { pktcEUEUserMIB 0 }  
pktcEUEUsrObjects           OBJECT IDENTIFIER ::= { pktcEUEUserMIB 1 }  
pktcEUEUsrConformance       OBJECT IDENTIFIER ::= { pktcEUEUserMIB 2 }  
pktcEUEUsrCompliances       OBJECT IDENTIFIER ::= { pktcEUEUsrConformance 1 }  
pktcEUEUsrGroups            OBJECT IDENTIFIER ::= { pktcEUEUsrConformance 2 }

-- ---------------------------------------------------------------------                    
--  User Profile Information
-- ---------------------------------------------------------------------                    
pktcEUEUsrProfile           OBJECT IDENTIFIER ::= { pktcEUEUsrObjects 1 }  
pktcEUEUsrProfileVersion OBJECT-TYPE
    SYNTAX      SnmpAdminString(SIZE(0..6))
    MAX-ACCESS  read-only
    STATUS      current
    DESCRIPTION
        " This MIB Object represents the User Profile Version for this
          MIB module. The eUE MUST set this MIB Object to value of '1.0'."
    ::= { pktcEUEUsrProfile 1 }

-- ---------------------------------------------------------------------                    
--  User table
-- ---------------------------------------------------------------------                    
pktcEUEUsrIMPUTable OBJECT-TYPE
    SYNTAX      SEQUENCE OF PktcEUEUsrIMPUEntry
    MAX-ACCESS  not-accessible
    STATUS      current
    DESCRIPTION
        " This data table represents Users associated with  
          the eUE. Specifically it provides information related
          to the IM Public Identity (IMPU) of the User."
    ::= { pktcEUEUsrProfile 2 }  
pktcEUEUsrIMPUEntry OBJECT-TYPE
    SYNTAX      PktcEUEUsrIMPUEntry
    MAX-ACCESS  not-accessible
    STATUS      current
    DESCRIPTION
        " Each entry in this data table describes an association
          of a user IMPU with the eUE, indexed by a IMPU Identifier.
          The eUE uses the entries in this table to register the  
          user in a PacketCable Network.  
          The credentials for registration are obtained using the  
          association with an IMPI in the MIB table  
          pktcEUEUsrIMPITable, referenced via the MIB Object
          pktcEUEUsrIMPIIndexRef.
          If two or more active entries have the same IMPU ID,
          the eUE uses the entry with the lowest Index.
          The eUE MAY store pre-configured associations in NVRAM."
    INDEX  { pktcEUEUsrIMPUIndex }
    ::= { pktcEUEUsrIMPUTable 1 }  
PktcEUEUsrIMPUEntry ::=
    SEQUENCE {
             pktcEUEUsrIMPUIndex              PktcEUETCUsrElementIndexType,
             pktcEUEUsrIMPUIdType             PktcEUETCIDType,
             pktcEUEUsrIMPUId                 PktcEUETCID,
             pktcEUEUsrIMPUIMPIIndexRef       PktcEUETCUsrElementIndexType,
             pktcEUEUsrIMPUDispInfo           SnmpAdminString,
             pktcEUEUsrIMPUOpIndexRefs        SnmpAdminString,
             pktcEUEUsrIMPUAdminStat          PktcEUETCAdminStatus,
             pktcEUEUsrIMPUAdminStatInfo      PktcEUETCStatusInfo,
             pktcEUEUsrIMPUOperStat           PktcEUETCOperStatus,
             pktcEUEUsrIMPUOperStatInfo       PktcEUETCStatusInfo,
             pktcEUEUsrIMPUSigSecurity        TruthValue,
             pktcEUEUsrIMPUAdditionalInfo     SnmpAdminString,
             pktcEUEUsrIMPURowStatus          RowStatus
             }
pktcEUEUsrIMPUIndex  OBJECT-TYPE
    SYNTAX      PktcEUETCUsrElementIndexType
    MAX-ACCESS  not-accessible
    STATUS      current
    DESCRIPTION
        " This MIB Object provides a user IMPU index.
          When the user IMPU is referenced elsewhere, such as
          to associate the device and a user IMPU, this  
          MIB Object MUST be used as an index reference.
          A value of '0' MUST NOT be used."
    ::= { pktcEUEUsrIMPUEntry 1 }
pktcEUEUsrIMPUIdType  OBJECT-TYPE
    SYNTAX      PktcEUETCIDType
    MAX-ACCESS  read-create
    STATUS      current
    DESCRIPTION
        " This MIB Object MUST indicate the 'Identifier  
          type' of the data value contained in 'pktcEUEUsrIMPUId'.
          Valid types include other(1), publicIdentity(3) and
          username(6)."
    DEFVAL   { other }
    ::= { pktcEUEUsrIMPUEntry 2 }
pktcEUEUsrIMPUId  OBJECT-TYPE
    SYNTAX      PktcEUETCID
    MAX-ACCESS  read-create  
    STATUS      current
    DESCRIPTION
        " This MIB Object MUST identify the User IMPU being
          associated with the eUE.
          The type of Identifier is indicated by the  
          MIB Object 'pktcEUEUsrIMPUIdType'."
    DEFVAL   { "" }
    ::= { pktcEUEUsrIMPUEntry 3 }
pktcEUEUsrIMPUIMPIIndexRef  OBJECT-TYPE
    SYNTAX      PktcEUETCUsrElementIndexType
    MAX-ACCESS  read-create  
    STATUS      current
    DESCRIPTION
        " This MIB Object MUST provide an index reference
          to a IMPI associated with the corresponding IMPU  
          specified in this table entry.
          The index reference points to an entry in the MIB
          table 'pktcEUEUsrIMPITable'.

          If this contains a value of '0', it indicates that
          the user IMPU is not yet associated with an IMPI
          and cannot be used in networks requiring  
          authentication. "
    DEFVAL {0}
    ::= { pktcEUEUsrIMPUEntry 4 }

pktcEUEUsrIMPUDispInfo  OBJECT-TYPE
    SYNTAX      SnmpAdminString
    MAX-ACCESS  read-create
    STATUS      current
    DESCRIPTION
        " This optional MIB Object MAY contain human readable  
          text describing User characteristics. Examples include
          User Display Name, Subscriber Identifier etc."
    DEFVAL   { "" }
    ::= { pktcEUEUsrIMPUEntry 5 }
pktcEUEUsrIMPUOpIndexRefs  OBJECT-TYPE
    SYNTAX      SnmpAdminString
    MAX-ACCESS  read-create
    STATUS      current
    DESCRIPTION
        " This optional MIB Object MAY contain a list of comma
          separated Operator domain entries where the user specified
          in this entry 'pktcEUEUsrIMPUId' can be used.
          The entries MUST be index references to the operator
          table associated with the eUE.
          The eUE MAY attempt to use the user entry in a  
          domain or sub-domain specified by the operator table,
          corresponding to the entries listed here.
          The eUE MUST NOT attempt to use the user entry in a  
          domain that is not specified by this entry.  
          If unspecified, the eUE MUST use the domain identified
          by the IMPU."
    DEFVAL   { "" }
    ::= { pktcEUEUsrIMPUEntry 6 }

pktcEUEUsrIMPUAdminStat OBJECT-TYPE
    SYNTAX      PktcEUETCAdminStatus
    MAX-ACCESS  read-create
    STATUS      current
    DESCRIPTION
        " This MIB Object contains the administratively desired
          activation status of the user IMPU.
          The eUE MUST allow access to the User identified in  
          'pktcEUEUsrIMPUId' if the value is set to 'active',  
          unless determined otherwise and reported in  
          pktcEUEUsrIMPUOperStat.
          The eUE SHOULD attempt to register a User identified in  
          'pktcEUEUsrIMPUId' if the value is set to 'active'.
          PacketCable Applications can specify additional  
          requirements for registration.
          If this object is set to 'inactive', all applicable  
          sessions (e.g. SIP registration) are gracefully terminated.
          The eUE MUST disallow access to the User identified in
          'pktcEUEUsrIMPUId' if the value is set to 'inactive'"
    DEFVAL   { active }
    ::= { pktcEUEUsrIMPUEntry 7 }
pktcEUEUsrIMPUAdminStatInfo OBJECT-TYPE
    SYNTAX      PktcEUETCStatusInfo
    MAX-ACCESS  read-create
    STATUS      current
    DESCRIPTION
        " This MIB Object MAY contain information that describes
          the activation status indicated in 'pktcEUEIMPUAdminStat'.
          Indicates Administratively added information associated  
          with administrative status of the User IMPU.  
          For example 'User temporarily deactivated for  
          maintenance'."
    DEFVAL   { "" }
    ::= { pktcEUEUsrIMPUEntry 8 }
pktcEUEUsrIMPUOperStat OBJECT-TYPE
    SYNTAX      PktcEUETCOperStatus  
    MAX-ACCESS  read-only
    STATUS      current
    DESCRIPTION
        " This MIB Object contains the operational activation status
          of the user IMPU.
          This object returns the following values:
          'active'  
          When pktcEUEUsrIMPUAdminStat is 'active' and there are  
          no run-time conditions and/or configuration errors that prohibit the users
          from communicating with the operator.  
          'inactive'  
          When pktcEUEUsrIMPUAdminStat is 'inactive'  
          or
          When pktcEUEUsrIMPUAdminStat is 'active' and there  
          are run-time conditions that prohibit the users from  
          communicating with the operator.  
          'notPresent'
          This value is not applicable.  
          'unknown'  
          Other conditions not covered by the previous values.
          An example of run-time condition that can result in a value
          of 'inactive' is unsuccessful registration.
          PacketCable applications can specify additional conditions for  
          how an IMPU is considered 'active', 'inactive' or 'notPresent',  
          and corresponding state machine."
    ::= { pktcEUEUsrIMPUEntry 9 }
pktcEUEUsrIMPUOperStatInfo OBJECT-TYPE
    SYNTAX      PktcEUETCStatusInfo
    MAX-ACCESS  read-only
    STATUS      current
    DESCRIPTION
        " This MIB Object contains information that describes the  
          activation status indicated in 'pktcEUEUsrIMPUOperStat' or  
          the zero-length string is not detail information is available.
          For example 'User deactivated based on user interface input."
    DEFVAL   { "" }
    ::= { pktcEUEUsrIMPUEntry 10 }
pktcEUEUsrIMPUSigSecurity OBJECT-TYPE
    SYNTAX      TruthValue
    MAX-ACCESS  read-write
    STATUS      current  
    DESCRIPTION
        " This element indicates the network requirement for
          SIP signaling with the P-CSCF.
          If set to 'true', the UE MUST attempt secure SIP  
          signaling with the P-CSCF.
          If set to 'false', the UE MUST attempt to communicate  
          without a secure SIP communication channel with the P-CSCF.
          The P-CSCF is considered to be authoritative and the UE will
          follow the requirements in PKT 24.229.
          After the P-CSCF confirm or set the SIP secure mode
          the UE MUST report such state."
    REFERENCE
        "PacketCable IMS Delta Session Initiation Protocol (SIP)  
        and Session Description Protocol (SDP), Stage 3  
        Specification 3GPP TS 24.229"
    DEFVAL      {true}
    ::= { pktcEUEUsrIMPUEntry 11 }  

pktcEUEUsrIMPUAdditionalInfo OBJECT-TYPE
    SYNTAX      SnmpAdminString
    MAX-ACCESS  read-create
    STATUS      current
    DESCRIPTION
        " This MIB Object MAY contain information that describes
          additional information defined by PacketCable specifications,  
          including those defining PacketCable features.
          PacketCable specifications are expected to use this data
          element to obtain additional information.
          To specify such additional info, the following rules apply:
          - Each specification planning to use this MIB Object
            MUST specify data in the following format:
            '<Keyword>#<value>', # being the delimiter
               e.g. FEATURE_X#ABC
                    FEATURE_Y#<value of XYZ>
          - This MIB Object MUST be a semi-colon separated
            concatenation of such '<keyword>#<value>' pairs. e.g.
            FEATURE_X#ABC;FEATURE_Z#DEF
          - Since the '#' and ';' characters are used as delimiters,
            they SHOULD not be specified in the keyword. If specified, any
            occurrence of these characters in the value field MUST be  
            preceded by the escape character '\' (e.g. FEATURE_X#A\#C).
            Occurrences of '\' MUST be preceded by itself
           (e.g. FEATURE_X#A\\C\#).
           The following rules apply on the eUE:
          - The eUE MUST first separate all the keyword value pairs,
            using a '#' that is not preceded by '\' as the delimiter  
          - The eUE MUST, For all recognized keywords, decipher the value
            by interpreting the data after considering the use of '\' as  
            defined in this definition
          - The eUE MUST ignore and report all unrecognized keywords  
            using PacketCable Management"
    DEFVAL   { "" }
    ::= { pktcEUEUsrIMPUEntry 12 }
pktcEUEUsrIMPURowStatus OBJECT-TYPE
    SYNTAX      RowStatus
    MAX-ACCESS  read-create
    STATUS      current
    DESCRIPTION
        " This MIB Object defines the row status associated with this
          particular User in the pktcEUEUsrIMPUTable.
          An entry in this table is not qualified for activation
          until the object instances of all corresponding columns
          have been initialized, either by default values or via
          explicit SET operations.  Until all object instances in
          this row are initialized, the status value for this realm
          must be 'notReady(3)'.
          In particular, two columnar objects must be SET: the
          'pktcEUEUsrIMPUIdType' and the 'pktcEUEUsrIMPUId. Once these  
          two objects have been set the row status may be SET to 'active(1)'
          The eUE MUST not allow these two objects to be changed while
          the row is 'active'. The value of this object has no effect on
          whether other columnar objects in this row can be modified."
    ::= { pktcEUEUsrIMPUEntry 13 }    

-- ---------------------------------------------------------------------                    
-- User IMPI Table
-- ---------------------------------------------------------------------                    
pktcEUEUsrIMPITable OBJECT-TYPE
    SYNTAX      SEQUENCE OF PktcEUEUsrIMPIEntry
    MAX-ACCESS  not-accessible
    STATUS      current
    DESCRIPTION
        " This data table contains the user IMPI information
          associated with users provisioned on the device."
    ::= { pktcEUEUsrProfile 3 }
pktcEUEUsrIMPIEntry OBJECT-TYPE
    SYNTAX      PktcEUEUsrIMPIEntry
    MAX-ACCESS  not-accessible
    STATUS      current
    DESCRIPTION
        "Each entry in this data table contains an instance
         of a user IMPI and associated credentials.
         Each IMPU provisioned in the eUE SHOULD be associated
         with an entry in this table. The exception is in networks
         where certain users are unauthenticated for application
         access.
	 At boot time the eUE MUST populate conceptual rows in this
	 order:
	 - First, instances provisioned via device configuration (e.g.,
	 config file, dynamically created via SNMP). These instances
	 MUST NOT persist across reboots.
	 - Second, entries provisioned via Certificate Bootstrapping
	 File. These entries may appear again after device
	 re-initialization, depending on Certificate Bootstrapping
	 file persistence requirements defined elsewhere.
	 As a side effect, if an instance loaded from a Certificate
	 Bootstrapping file is updated via SNMP later on, those changes
	 are not required to be reflected in the CB file persistence
	 storage (if CB file persistence is supported). Instead, the
	 trigger of a new CB file download is preferred to update CB
	 information."
    INDEX  { pktcEUEUsrIMPIIndex }
    ::= { pktcEUEUsrIMPITable 1 }  
PktcEUEUsrIMPIEntry ::=
    SEQUENCE {
              pktcEUEUsrIMPIIndex             PktcEUETCUsrElementIndexType,
              pktcEUEUsrIMPIIdType            PktcEUETCIDType,
              pktcEUEUsrIMPIId                PktcEUETCID,
              pktcEUEUsrIMPICredsType         PktcEUETCCredsType,
              pktcEUEUsrIMPICredentials       PktcEUETCCreds,
              pktcEUEUsrIMPIRowStatus         RowStatus
             }
pktcEUEUsrIMPIIndex OBJECT-TYPE              
    SYNTAX      PktcEUETCUsrElementIndexType
    MAX-ACCESS  not-accessible
    STATUS      current
    DESCRIPTION
        " This MIB Object provides a user IMPI index.
          When the user IMPI is referenced elsewhere, such as
          to associate the IMPU and an IMPI, this  
          MIB Object MUST be used as an index reference.
          A value of '0' MUST NOT be used."
    ::= { pktcEUEUsrIMPIEntry 1 }
pktcEUEUsrIMPIIdType  OBJECT-TYPE
    SYNTAX      PktcEUETCIDType
    MAX-ACCESS  read-create
    STATUS      current
    DESCRIPTION
        " This MIB Object MUST indicate the 'Identifier  
          type' of the data value contained in 'pktcEUEUsrIMPIId'.
          Valid types include other(1), privateIdentity(4) and
          username(6)."
    DEFVAL   { other }
    ::= { pktcEUEUsrIMPIEntry 2 }
pktcEUEUsrIMPIId  OBJECT-TYPE
    SYNTAX      PktcEUETCID
    MAX-ACCESS  read-create  
    STATUS      current
    DESCRIPTION
        " This MIB Object MUST identify a User IMPI being
          specified in this table.
          The type of Identifier is indicated by the  
          MIB Object 'pktcEUEUsrIMPIIdType'."
    DEFVAL   { "" }
    ::= { pktcEUEUsrIMPIEntry 3 }

pktcEUEUsrIMPICredsType  OBJECT-TYPE
    SYNTAX      PktcEUETCCredsType
    MAX-ACCESS  read-create
    STATUS      current
    DESCRIPTION
        " This MIB Object contains the type of credentials
          contained in the MIB Object 'pktcEUEUsrIMPICredentials'."
    DEFVAL   { none }
    ::= { pktcEUEUsrIMPIEntry 4 }  
pktcEUEUsrIMPICredentials  OBJECT-TYPE
    SYNTAX      PktcEUETCCreds
    MAX-ACCESS  read-create
    STATUS      current
    DESCRIPTION
        " This MIB Object allows the Operator to configure credentials  
          associated with an IMPI. This value is used with, and must  
          be consistent with, the value
          of the associated 'pktcEUEUsrIMPIcredsType' object.  
          If read this MIB Object MUST always return an empty  
          string value for privacy reasons.
          A Operator SHOULD provide this MIB Object only
          over a secured configuration interface to avoid
          security threats due to compromised credentials. "
    DEFVAL   { "" }
    ::= { pktcEUEUsrIMPIEntry 5 }  
pktcEUEUsrIMPIRowStatus  OBJECT-TYPE
    SYNTAX      RowStatus
    MAX-ACCESS  read-create
    STATUS      current
    DESCRIPTION
        " This MIB Object defines the row status associated with this
          entry.
          The value of the 'pktcEUEUsrIMPICredsType' object MUST NOT be
          modified while this object is 'active'.  
          The value of 'pktcEUEUsrIMPICredentials' MAY be modified  
          while this object is active if the value is consistent with  
          the type specified by the 'pktcEUEUsrIMPICredsType' object. "
     ::= { pktcEUEUsrIMPIEntry 6 }
-- ---------------------------------------------------------------------                    
-- User to Apps Mapping Table
-- ---------------------------------------------------------------------                    
pktcEUEUsrAppMapTable OBJECT-TYPE
    SYNTAX      SEQUENCE OF PktcEUEUsrAppMapEntry
    MAX-ACCESS  not-accessible
    STATUS      current
    DESCRIPTION
        " This data table represents Applications associated with  
          a User IMPU."
    ::= { pktcEUEUsrProfile 4 }
pktcEUEUsrAppMapEntry OBJECT-TYPE
    SYNTAX      PktcEUEUsrAppMapEntry
    MAX-ACCESS  not-accessible
    STATUS      current
    DESCRIPTION
        " Each entry in this data table identifies an application
          associated with the user, the application profile index
          reference, administrative status and the operational  
          status information.
	  The conceptual rows MUST NOT persist across eUE resets."
    INDEX   { pktcEUEUsrIMPUIndex, pktcEUEUsrAppMapAppIndex }
    ::= { pktcEUEUsrAppMapTable 1 }
PktcEUEUsrAppMapEntry ::=  
    SEQUENCE    {
                 pktcEUEUsrAppMapAppIndex             PktcEUETCUsrAppIndexType,
                 pktcEUEUsrAppMapAppOrgID             PktcEUETCAppOrgIdentifier,
                 pktcEUEUsrAppMapAppIdentifier        PktcEUETCAppIdentifier,
                 pktcEUEUsrAppMapAppIndexRef          PktcEUETCUsrAppIndexType,
                 pktcEUEUsrAppMapAppAdminStat         PktcEUETCAdminStatus,
                 pktcEUEUsrAppMapAppAdminStatInfo     PktcEUETCStatusInfo,
                 pktcEUEUsrAppMapAppOperStat          PktcEUETCOperStatus,
                 pktcEUEUsrAppMapAppOperStatInfo      PktcEUETCStatusInfo,
                 pktcEUEUsrAppMapRowStatus            RowStatus
                }
pktcEUEUsrAppMapAppIndex OBJECT-TYPE
    SYNTAX      PktcEUETCUsrAppIndexType
    MAX-ACCESS  not-accessible
    STATUS      current
    DESCRIPTION
        " This MIB Object represents an index to map
          an Application instance associated with the User  
          IMPU."
    ::= { pktcEUEUsrAppMapEntry 1 }


pktcEUEUsrAppMapAppOrgID OBJECT-TYPE
    SYNTAX      PktcEUETCAppOrgIdentifier
    MAX-ACCESS  read-create
    STATUS      current
    DESCRIPTION
        " This MIB Object identifies the Organization
          specifying the app identifier contained in  
          the MIB Object 'pktcEUEUsrAppMapAppIdentifier'."
    ::= { pktcEUEUsrAppMapEntry 2 }

pktcEUEUsrAppMapAppIdentifier OBJECT-TYPE
    SYNTAX      PktcEUETCAppIdentifier
    MAX-ACCESS  read-create
    STATUS      current
    DESCRIPTION
        " This MIB Object represents the identifier  
          for a Application associated with the User.
          The application identifier MUST represent
          an application specified by the organization
          specified in 'pktcEUEUsrAppMapAppOrgID'."
    ::= { pktcEUEUsrAppMapEntry 3 }

pktcEUEUsrAppMapAppIndexRef OBJECT-TYPE
    SYNTAX      PktcEUETCUsrAppIndexType
    MAX-ACCESS  read-create
    STATUS      current
    DESCRIPTION
        " This MIB Object represents the index reference  
          to an application profile for the application
          identified by the MIB Object  
          'pktcEUEUsrAppMapAppIDentifier'.
          If this value is set to a value of '0' then  
          the following conditions apply:
          - If the application has no specific configuration
          data, the network activation status MUST be  
          considered by the eUE
          - If the application has configuration data elements
          the eUE MUST deactivate the application. The deactivation
          is reported by 'pktcEUEUsrAppMapAppOperStat'."
    DEFVAL {0}
    ::= { pktcEUEUsrAppMapEntry 4 }

pktcEUEUsrAppMapAppAdminStat OBJECT-TYPE
    SYNTAX      PktcEUETCAdminStatus
    MAX-ACCESS  read-create
    STATUS      current
    DESCRIPTION
        " This MIB Object contains the administratively desired
          activation status of this instance.
          If 'active' the User can use the application.
          If 'inactive' the user can not use the application  
        "
    DEFVAL {active}
    ::= { pktcEUEUsrAppMapEntry 5 }

pktcEUEUsrAppMapAppAdminStatInfo OBJECT-TYPE
    SYNTAX      PktcEUETCStatusInfo
    MAX-ACCESS  read-create
    STATUS      current
    DESCRIPTION
        " This MIB Object represents additional  
          information for the status information
          represented by 'pktcEUEUsrAppMapAppAdminStat'."
    ::= { pktcEUEUsrAppMapEntry 6 }

pktcEUEUsrAppMapAppOperStat OBJECT-TYPE
    SYNTAX      PktcEUETCOperStatus
    MAX-ACCESS  read-only
    STATUS      current
    DESCRIPTION
        " This MIB Object represents the current operational status  
          of the user using the application specified in this entry.
          This object returns the following values:
          'active'  
          When pktcEUEUsrAppMapAppAdminStat is 'active' and there are  
          no run-time conditions and/or configuration errors that prohibit
          the IMPU to use this application.  
          'inactive'  
          When pktcEUEUsrAppMapAppAdminStat is 'inactive'  
          or
          When pktcEUEUsrAppMapAppAdminStat is 'active' and there  
          are run-time conditions and/or configuration errors that  
          prohibit the IMPU to use this application.
          'notPresent'
          When the application is not available or unknown to the UE.  
          'unknown'  
          Other conditions not covered by the previous values.
          An example of a run-time condition that can result in a value
          of 'inactive' is unsuccessful user registration.
          PacketCable applications can specify additional conditions for  
          how an application is considered 'active', 'inactive' or
          'notPresent' for an IMPU."          
    ::= { pktcEUEUsrAppMapEntry 7 }
pktcEUEUsrAppMapAppOperStatInfo OBJECT-TYPE
    SYNTAX      PktcEUETCStatusInfo
    MAX-ACCESS  read-only
    STATUS      current
    DESCRIPTION
        " This MIB Object represents additional  
          information for the status information
          represented by 'pktcEUEUsrAppMapAppOperStat'.
          For example, the  pktcEUEUsrAppMapAppOperStat value  
          'notPresent'  can report in this object the value
          'UE does not support this application'."
    ::= { pktcEUEUsrAppMapEntry 8 }
pktcEUEUsrAppMapRowStatus  OBJECT-TYPE
    SYNTAX      RowStatus
    MAX-ACCESS  read-create
    STATUS      current
    DESCRIPTION
        " This MIB Object defines the row status associated with this
          particular User in the pktcEUEUsrAppMapTable.
          An entry in this table is not qualified for activation
          until the object instances of all corresponding columns
          have been initialized, either by default values or via
          explicit SET operations.  Until all object instances in
          this row are initialized, the status value for this realm
          must be 'notReady(3)'.
          In particular, two columnar objects must be SET: the
          'pktcEUEUsrAppMapAppOrgID' and pktcEUEUsrAppMapAppIdentifier.  
          Once these two objects have been set the row status may be SET  
          to 'active(1)'.
          The eUE MUST not allow these two objects to be changed while
          the row is 'active'. The value of this object has no effect on
          whether other columnar objects in this row can be modified."
     ::= { pktcEUEUsrAppMapEntry 9 }

-- ---------------------------------------------------------------------
-- Conformance Information  
-- ---------------------------------------------------------------------
-- ----------------------
-- Compliance Statements
-- ----------------------
pktcEUEUsrMIBCompliance MODULE-COMPLIANCE
    STATUS      current
    DESCRIPTION
            "The compliance statement for implementations of the User Mib "
    MODULE   -- this module
        MANDATORY-GROUPS {
                 pktcEUEUsrProfileGroup,
                 pktcEUEUsrIMPUGroup,
                 pktcEUEUsrIMPIGroup,
                 pktcEUEUsrAppMapGroup
                 }
    ::= { pktcEUEUsrCompliances 1 }
pktcEUEUsrProfileGroup OBJECT-GROUP
      OBJECTS {  
         pktcEUEUsrProfileVersion
      }
      STATUS  current
      DESCRIPTION
            "The eUE Usr Profile Group."
      ::= { pktcEUEUsrGroups 1 }

pktcEUEUsrIMPUGroup OBJECT-GROUP
      OBJECTS {            
         pktcEUEUsrIMPUIdType,
         pktcEUEUsrIMPUId,
         pktcEUEUsrIMPUIMPIIndexRef,
         pktcEUEUsrIMPUDispInfo,
         pktcEUEUsrIMPUOpIndexRefs,
         pktcEUEUsrIMPUAdminStat,
         pktcEUEUsrIMPUAdminStatInfo,
         pktcEUEUsrIMPUOperStat,
         pktcEUEUsrIMPUOperStatInfo,
         pktcEUEUsrIMPUSigSecurity,
         pktcEUEUsrIMPUAdditionalInfo,
         pktcEUEUsrIMPURowStatus
      }
      STATUS  current
      DESCRIPTION
            "The user IMPU Group."
      ::= { pktcEUEUsrGroups 2}  
pktcEUEUsrIMPIGroup OBJECT-GROUP
      OBJECTS {            
          pktcEUEUsrIMPICredsType,
          pktcEUEUsrIMPICredentials,
          pktcEUEUsrIMPIIdType,
          pktcEUEUsrIMPIId,
          pktcEUEUsrIMPIRowStatus
      }
      STATUS  current
      DESCRIPTION
            "The user IMPI Group."
      ::= { pktcEUEUsrGroups 3 }  
pktcEUEUsrAppMapGroup OBJECT-GROUP
      OBJECTS {            
           pktcEUEUsrAppMapAppOrgID,
           pktcEUEUsrAppMapAppIdentifier,
           pktcEUEUsrAppMapAppIndexRef,
           pktcEUEUsrAppMapAppAdminStat,
           pktcEUEUsrAppMapAppAdminStatInfo,
           pktcEUEUsrAppMapAppOperStat,
           pktcEUEUsrAppMapAppOperStatInfo,
           pktcEUEUsrAppMapRowStatus
      }
      STATUS  current
      DESCRIPTION
            "The User to Applications Mapping Group."
      ::= { pktcEUEUsrGroups 4 }  

END

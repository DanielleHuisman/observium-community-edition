IEEE8023-DOT3-LLDP-EXT-V2-MIB DEFINITIONS ::= BEGIN

IMPORTS
    MODULE-IDENTITY,
    OBJECT-TYPE,
    Unsigned32,
    Integer32,
    org
        FROM SNMPv2-SMI
    TruthValue
        FROM SNMPv2-TC
    MODULE-COMPLIANCE,
    OBJECT-GROUP
        FROM SNMPv2-CONF
    ifGeneralInformationGroup
        FROM IF-MIB
    lldpV2LocPortIfIndex,
    lldpV2RemLocalIfIndex,
    lldpV2RemTimeMark,
    lldpV2RemLocalDestMACAddress,
    lldpV2RemIndex,
    lldpV2PortConfigEntry
        FROM LLDP-V2-MIB
 -- http://www.ieee802.org/1/files/public/MIBs/LLDP-V2-MIB-200906080000Z.txt
    LldpV2PowerPortClass
        FROM LLDP-V2-TC-MIB
 -- http://www.ieee802.org/1/files/public/MIBs/LLDP-V2-TC-MIB-200906080000Z.txt
;

ieee8023lldpV2Xdot3MIB MODULE-IDENTITY
    LAST-UPDATED "201304110000Z" -- April 11, 2013
    ORGANIZATION "IEEE 802.3 Working Group"
    CONTACT-INFO
            "WG-URL: http://www.ieee802.org/3/index.html
            WG-EMail: STDS-802-3-MIB@LISTSERV.IEEE.ORG

            Contact: Howard Frazier
            Postal:  3151 Zanker Road
                     San Jose, CA 95134
                     USA
            Tel:     +1.408.922.8164
            E-mail:  hfrazier@broadcom.com"
    DESCRIPTION
            "The LLDP Management Information Base extension module for
            IEEE 802.3 organizationally defined discovery information."

       REVISION    "201304110000Z" -- April 11, 2013
       DESCRIPTION
           "Revision, based on an earlier version in IEEE Std 802.3.1-2011."


       REVISION "201102020000Z" -- February 2, 2011
       DESCRIPTION
            "This revision incorporated changes to the MIB module to
            add objects to support management of Energy Efficient
            Ethernet (EEE) and Enhanced DTE Power via the MDI (PoE+)."



   ::= { org ieee(111)
         standards-association-numbers-series-standards(2)
         lan-man-stds(802)ieee802dot3(3) ieee802dot3dot1mibs(1) 5 }

------------------------------------------------------------------------------
------------------------------------------------------------------------------
--
-- Organizationally Defined Information Extension - IEEE 802.3
--
------------------------------------------------------------------------------
------------------------------------------------------------------------------

lldpV2Xdot3Objects    OBJECT IDENTIFIER ::= { ieee8023lldpV2Xdot3MIB 1 }

-- LLDP IEEE 802.3 extension MIB groups
lldpV2Xdot3Config     OBJECT IDENTIFIER ::= { lldpV2Xdot3Objects 1 }
lldpV2Xdot3LocalData  OBJECT IDENTIFIER ::= { lldpV2Xdot3Objects 2 }
lldpV2Xdot3RemoteData OBJECT IDENTIFIER ::= { lldpV2Xdot3Objects 3 }



------------------------------------------------------------------------------
-- IEEE 802.3 - Configuration
------------------------------------------------------------------------------


--
-- Version 2 of lldpV2Xdot3PortConfigTable
-- supports use of multiple destination MAC addresses
--


lldpV2Xdot3PortConfigTable OBJECT-TYPE
    SYNTAX      SEQUENCE OF LldpV2Xdot3PortConfigEntry
    MAX-ACCESS  not-accessible
    STATUS      current
    DESCRIPTION
            "A table that controls selection of LLDP TLVs to be transmitted
            on individual ports."
    ::= { lldpV2Xdot3Config 1 }

lldpV2Xdot3PortConfigEntry  OBJECT-TYPE
    SYNTAX      LldpV2Xdot3PortConfigEntry
    MAX-ACCESS  not-accessible
    STATUS      current
    DESCRIPTION
            "LLDP configuration information that controls the
            transmission of IEEE 802.3 organizationally defined TLVs on
            LLDP transmission capable ports.

            This configuration object augments the lldpV2PortConfigEntry of
            the LLDP-MIB, therefore it is only present along with the port
            configuration defined by the associated lldpV2PortConfigEntry
            entry.

            Each active lldpV2Xdot3PortConfigEntry is restored from non-volatile
            storage (along with the corresponding lldpV2PortConfigEntry)
            after a re-initialization of the management system."
    AUGMENTS { lldpV2PortConfigEntry }
    ::= { lldpV2Xdot3PortConfigTable 1 }

LldpV2Xdot3PortConfigEntry ::= SEQUENCE {
      lldpV2Xdot3PortConfigTLVsTxEnable  BITS
}

lldpV2Xdot3PortConfigTLVsTxEnable  OBJECT-TYPE
    SYNTAX      BITS {
            macPhyConfigStatus(0),
            powerViaMDI(1),
            unused(2), --avoids re-use of the old link agg bit number
            maxFrameSize(3)
    }
    MAX-ACCESS  read-write
    STATUS      current
    DESCRIPTION
            "The lldpV2Xdot3PortConfigTLVsTxEnable, defined as a bitmap,
            includes the IEEE 802.3 organizationally defined set of LLDP
            TLVs whose transmission is allowed by the local LLDP agent by
            the network management. Each bit in the bitmap corresponds
            to an IEEE 802.3 subtype associated with a specific IEEE
            802.3 optional TLV.

            The bit 'macPhyConfigStatus(0)' indicates that the LLDP agent
            should transmit 'MAC/PHY configuration/status TLV'.

            The bit 'powerViaMDI(1)' indicates that the LLDP agent should
            transmit 'Power via MDI TLV'.

            The bit 'unused(2)' is no longer used; this was used for
            the 'Link Aggregation TLV' in the previous version.

            The bit 'maxFrameSize(3)' indicates that the LLDP agent should
            transmit 'Maximum-frame-size TLV'.

            The default value for lldpV2Xdot3PortConfigTLVsTxEnable object
            is an empty set, which means no enumerated values are set.

            The value of this object is restored from non-volatile
            storage after a re-initialization of the management system."
    REFERENCE
            "IEEE Std 802.3 30.12.1.1.1"
    DEFVAL  { { } }
    ::= { lldpV2Xdot3PortConfigEntry  1 }



------------------------------------------------------------------------------
-- IEEE 802.3 - Local Device Information
------------------------------------------------------------------------------

---
--- lldpV2Xdot3LocPortTable: Ethernet Port AutoNeg/Speed/Duplex
---                        Information Table
--- V2 modified to be indexed by ifIndex.
---

lldpV2Xdot3LocPortTable OBJECT-TYPE
    SYNTAX      SEQUENCE OF LldpV2Xdot3LocPortEntry
    MAX-ACCESS  not-accessible
    STATUS      current
    DESCRIPTION
            "This table contains one row per port of Ethernet port
            information (as a part of the LLDP 802.3 organizational
            extension) on the local system known to this agent."
    ::= { lldpV2Xdot3LocalData 1 }

lldpV2Xdot3LocPortEntry OBJECT-TYPE
    SYNTAX      LldpV2Xdot3LocPortEntry
    MAX-ACCESS  not-accessible
    STATUS      current
    DESCRIPTION
            "Information about a particular port component."
    INDEX   { lldpV2LocPortIfIndex }
    ::= { lldpV2Xdot3LocPortTable 1 }

LldpV2Xdot3LocPortEntry ::= SEQUENCE {
         lldpV2Xdot3LocPortAutoNegSupported     TruthValue,
         lldpV2Xdot3LocPortAutoNegEnabled       TruthValue,
         lldpV2Xdot3LocPortAutoNegAdvertisedCap OCTET STRING,
         lldpV2Xdot3LocPortOperMauType          Unsigned32
}

lldpV2Xdot3LocPortAutoNegSupported OBJECT-TYPE
    SYNTAX      TruthValue
    MAX-ACCESS  read-only
    STATUS      current
    DESCRIPTION
            "The truth value used to indicate whether the given port
            (associated with the local system) supports Auto-negotiation."
    REFERENCE
            "IEEE Std 802.3 30.12.2.1.1"
    ::= { lldpV2Xdot3LocPortEntry 1 }

lldpV2Xdot3LocPortAutoNegEnabled  OBJECT-TYPE
    SYNTAX      TruthValue
    MAX-ACCESS  read-only
    STATUS      current
    DESCRIPTION
            "The truth value used to indicate whether port
            Auto-negotiation is enabled on the given port associated
            with the local system."
    REFERENCE
            "IEEE Std 802.3 30.12.2.1.2"
    ::= { lldpV2Xdot3LocPortEntry 2 }

lldpV2Xdot3LocPortAutoNegAdvertisedCap OBJECT-TYPE
    SYNTAX      OCTET STRING(SIZE(2))
    MAX-ACCESS  read-only
    STATUS      current
    DESCRIPTION
            "This object contains the value (bitmap) of the
            ifMauAutoNegCapAdvertisedBits object (defined in IETF RFC
            3636) which is associated with the given port on the
            local system."
    REFERENCE
            "IEEE Std 802.3 30.12.2.1.3"
    ::= { lldpV2Xdot3LocPortEntry 3 }

lldpV2Xdot3LocPortOperMauType  OBJECT-TYPE
    SYNTAX      Unsigned32(0..2147483647)
    MAX-ACCESS  read-only
    STATUS      current
    DESCRIPTION
            "An integer value that indicates the operational MAU type
            of the given port on the local system.

            This object contains the integer value derived from the
            list position of the corresponding dot3MauType as listed
            in Clause 13 and is equal to the last number in the
            respective dot3MauType OID.

            For example, if the ifMauType object is dot3MauType1000BaseTHD
            which corresponds to {dot3MauType 29}, the numerical value of
            this field is 29. For MAU types not listed in Clause 13,
            the value of this field shall be set to zero."
    REFERENCE
            "IEEE Std 802.3 30.12.2.1.4"
    ::= { lldpV2Xdot3LocPortEntry 4 }



---
---
--- lldpV2Xdot3LocPowerTable: Power Ethernet Information Table
--- V2 modified to be indexed by ifIndex.
---
---

lldpV2Xdot3LocPowerTable OBJECT-TYPE
    SYNTAX      SEQUENCE OF LldpV2Xdot3LocPowerEntry
    MAX-ACCESS  not-accessible
    STATUS      current
    DESCRIPTION
            "This table contains one row per port of power Ethernet
            information (as a part of the LLDP IEEE 802.3 organizational
            extension) on the local system known to this agent."
    ::= { lldpV2Xdot3LocalData 2 }

lldpV2Xdot3LocPowerEntry OBJECT-TYPE
    SYNTAX      LldpV2Xdot3LocPowerEntry
    MAX-ACCESS  not-accessible
    STATUS      current
    DESCRIPTION
            "Information about a particular port component."
    INDEX   { lldpV2LocPortIfIndex }
    ::= { lldpV2Xdot3LocPowerTable 1 }

LldpV2Xdot3LocPowerEntry ::= SEQUENCE {
         lldpV2Xdot3LocPowerPortClass           LldpV2PowerPortClass,
         lldpV2Xdot3LocPowerMDISupported        TruthValue,
         lldpV2Xdot3LocPowerMDIEnabled          TruthValue,
         lldpV2Xdot3LocPowerPairControlable     TruthValue,
         lldpV2Xdot3LocPowerPairs               Unsigned32,
         lldpV2Xdot3LocPowerClass               Unsigned32,
         lldpV2Xdot3LocPowerType                INTEGER,
         lldpV2Xdot3LocPowerSource              INTEGER,
         lldpV2Xdot3LocPowerPriority            INTEGER,
         lldpV2Xdot3LocPDRequestedPowerValue    Integer32,
         lldpV2Xdot3LocPSEAllocatedPowerValue   Integer32,
         lldpV2Xdot3LocResponseTime             Integer32,
         lldpV2Xdot3LocReady                    TruthValue,
         lldpV2Xdot3LocReducedOperationPowerValue  Integer32
}


lldpV2Xdot3LocPowerPortClass  OBJECT-TYPE
    SYNTAX      LldpV2PowerPortClass
    MAX-ACCESS  read-only
    STATUS      current
    DESCRIPTION
            "The value that identifies the port Class of the given port
            associated with the local system."
    REFERENCE
            "IEEE Std 802.3 30.12.2.1.5"
    ::= { lldpV2Xdot3LocPowerEntry 1 }

lldpV2Xdot3LocPowerMDISupported  OBJECT-TYPE
    SYNTAX      TruthValue
    MAX-ACCESS  read-only
    STATUS      current
    DESCRIPTION
            "The truth value used to indicate whether the MDI power is
            supported on the given port associated with the local system."
    REFERENCE
            "IEEE Std 802.3 30.12.2.1.6"
    ::= { lldpV2Xdot3LocPowerEntry 2 }

lldpV2Xdot3LocPowerMDIEnabled  OBJECT-TYPE
    SYNTAX      TruthValue
    MAX-ACCESS  read-only
    STATUS      current
    DESCRIPTION
            "The truth value used to identify whether MDI power is
            enabled on the given port associated with the local system."
    REFERENCE
            "IEEE Std 802.3 30.12.2.1.7"
    ::= { lldpV2Xdot3LocPowerEntry 3 }

lldpV2Xdot3LocPowerPairControlable  OBJECT-TYPE
    SYNTAX      TruthValue
    MAX-ACCESS  read-only
    STATUS      current
    DESCRIPTION
            "The truth value is derived from the value of
            pethPsePortPowerPairsControlAbility object (defined in
            Clause 8) and is used to indicate whether the pair selection
            can be controlled on the given port associated with the
            local system."
    REFERENCE
            "IEEE Std 802.3 30.12.2.1.8"
    ::= { lldpV2Xdot3LocPowerEntry 4 }

lldpV2Xdot3LocPowerPairs  OBJECT-TYPE
    SYNTAX      Unsigned32(1|2)
    MAX-ACCESS  read-only
    STATUS      current
    DESCRIPTION
            "This object contains the value of the pethPsePortPowerPairs
            object (defined in Clause 8) which is associated with
            the given port on the local system."
    REFERENCE
            "IEEE Std 802.3 30.12.2.1.9"
    ::= { lldpV2Xdot3LocPowerEntry 5 }

lldpV2Xdot3LocPowerClass  OBJECT-TYPE
    SYNTAX      Unsigned32(1|2|3|4|5)
    MAX-ACCESS  read-only
    STATUS      current
    DESCRIPTION
            "This object contains the value of the
            pethPsePortPowerClassifications object (defined in
            Clause 8) which is associated with the given port on the
            local system."
    REFERENCE
            "IEEE Std 802.3 30.12.2.1.10"
    ::= { lldpV2Xdot3LocPowerEntry 6 }

lldpV2Xdot3LocPowerType  OBJECT-TYPE
    SYNTAX      INTEGER {
                    psetype1(0),
                    psetype2(1),
                    pdtype(2),
                    pdtype2(3)
                }
    MAX-ACCESS  read-only
    STATUS      current
    DESCRIPTION
            "A GET returns an integer indicating whether the local
             system is a PSE or a PD and whether it is Type 1 or Type 2."
    REFERENCE
            "IEEE Std 802.3 30.12.2.1.14"
    ::= { lldpV2Xdot3LocPowerEntry 7 }

lldpV2Xdot3LocPowerSource  OBJECT-TYPE
    SYNTAX      INTEGER {
                    pseprimary(0),
                    psebackup(1),
                    pseunknown(2),
                    pdpseandlocal(3),
                    pdpseonly(4),
                    pdunknown(5)
                }
    MAX-ACCESS  read-only
    STATUS      current
    DESCRIPTION
            "A GET returns an integer indicating the power sources of the
            local system. A PSE indicates whether it is being powered by
            a primary power source; a backup power source; or unknown. A PD
            indicates whether it is being powered by a PSE and locally;
            by a PSE only; or unknown."
    REFERENCE
            "IEEE Std 802.3 30.12.2.1.15"
    ::= { lldpV2Xdot3LocPowerEntry 8 }

lldpV2Xdot3LocPowerPriority  OBJECT-TYPE
    SYNTAX      INTEGER {
                    low(0),
                    high(1),
                    critical(2),
                    unknown(3)
                }
    MAX-ACCESS  read-write
    STATUS      current
    DESCRIPTION
            "A GET returns the priority of a PD system. For a PSE, this
            is the priority that the PSE assigns to the PD. For a PD, this
            is the priority that the PD requests from the PSE. A SET
            operation changes the priority of the PD system to the indicated
            value."
    REFERENCE
            "IEEE Std 802.3 30.12.2.1.16"
    ::= { lldpV2Xdot3LocPowerEntry 9 }

lldpV2Xdot3LocPDRequestedPowerValue  OBJECT-TYPE
    SYNTAX      Integer32
    MAX-ACCESS  read-only
    STATUS      current
    DESCRIPTION
            "A GET returns the PD requested power value.
            For a PD, it is the power value that the PD has currently
            requested from the remote system. PD requested power value
            is the maximum input average power the PD ever draws under
            this power allocation if accepted. For a PSE, it is the power
            value that the PSE mirrors back to the remote system. This is
            the PD requested power value that was used by the PSE to compute
            the power it has currently allocated to the remote system.
            The PD requested power value is encoded according to
            IEEE Std 802.3 Equation (79?1), where X is the decimal value of
            aLldpXdot3LocPDRequestedPowerValue."
    REFERENCE
            "IEEE Std 802.3 30.12.2.1.17"
    ::= { lldpV2Xdot3LocPowerEntry 10 }

lldpV2Xdot3LocPSEAllocatedPowerValue  OBJECT-TYPE
    SYNTAX      Integer32
    MAX-ACCESS  read-only
    STATUS      current
    DESCRIPTION
            "A GET returns the PSE allocated power value.
            For a PSE, it is the power value that the PSE has currently
            allocated to the remote system. The PSE allocated power value
            is the maximum input average power that the PSE wants the PD
            to ever draw under this allocation if it is accepted. For a PD,
            it is the power value that the PD mirrors back to the remote
            system. This is the PSE allocated power value that was used by
            the PD to compute the power that it has currently requested from
            the remote system. The PSE allocated power value is encoded
            according to IEEE Std 802.3 Equation (79?2), where X is the
            decimal value of aLldpXdot3LocPSEAllocatedPowerValue."
    REFERENCE
            "IEEE Std 802.3 30.12.2.1.18"
    ::= { lldpV2Xdot3LocPowerEntry 11 }

lldpV2Xdot3LocResponseTime  OBJECT-TYPE
    SYNTAX      Integer32
    MAX-ACCESS  read-only
    STATUS      current
    DESCRIPTION
            "A GET returns the response time in seconds of the local system.
            For a PD, it is the maximum time required to update the value of
            lldpV2Xdot3LocPDRequestedPowerValue when the remote system
            requests the PD to change its max power draw. For a PSE, it is
            the maximum time required to update the value of
            lldpV2Xdot3LocPDRequestedPowerValue when the remote system
            requests of the PSE a new power value."
    REFERENCE
            "IEEE Std 802.3 30.12.2.1.19"
    ::= { lldpV2Xdot3LocPowerEntry 12 }

lldpV2Xdot3LocReady  OBJECT-TYPE
    SYNTAX      TruthValue
    MAX-ACCESS  read-only
    STATUS      current
    DESCRIPTION
            "The truth value used to identify whether the local Data Link Layer
            classification engine has completed initialization and is ready to
            receive and transmit LLDPDUs."
    REFERENCE
            "IEEE Std 802.3 30.12.2.1.20"
    ::= { lldpV2Xdot3LocPowerEntry 13 }

lldpV2Xdot3LocReducedOperationPowerValue  OBJECT-TYPE
    SYNTAX      Integer32
    MAX-ACCESS  read-only
    STATUS      current
    DESCRIPTION
            "A GET returns the reduced operation power value. For a PD, it
            is a power value that is lower than the currently requested
            power value. This reduced operation power value represents a
            power state in which the PD could continue to operate, but with
            less functionality than at the current PD requested power value.
            The PSE could optionally use this information in the event that
            the PSE subsequently requests a lower PD power value than the
            PD requested power value. For a PSE, it is a power value that the
            PSE could ask the PD to move to if the PSE wants the PD to move
            to a lower power state. The definition and encoding of PD
            requested power value is the same as described in
            lldpV2Xdot3LocPDRequestedPowerValue. The default value for this
            field is the hexadecimal value FFFF"
    REFERENCE
            "IEEE Std 802.3 30.12.2.1.21"
    ::= { lldpV2Xdot3LocPowerEntry 14 }

---
---
--- lldpV2Xdot3LocMaxFrameSizeTable: Maximum Frame Size information
--- V2 modified to be indexed by ifIndex.
---
---
lldpV2Xdot3LocMaxFrameSizeTable  OBJECT-TYPE
    SYNTAX      SEQUENCE OF LldpV2Xdot3LocMaxFrameSizeEntry
    MAX-ACCESS  not-accessible
    STATUS      current
    DESCRIPTION
            "This table contains one row per port of maximum frame
            size information (as a part of the LLDP IEEE 802.3 organizational
            extension) on the local system known to this agent."
    ::= { lldpV2Xdot3LocalData 3 }

lldpV2Xdot3LocMaxFrameSizeEntry OBJECT-TYPE
    SYNTAX      LldpV2Xdot3LocMaxFrameSizeEntry
    MAX-ACCESS  not-accessible
    STATUS      current
    DESCRIPTION
            "Maximum Frame Size information about a particular port
            component."
    INDEX   { lldpV2LocPortIfIndex }
    ::= { lldpV2Xdot3LocMaxFrameSizeTable 1 }

LldpV2Xdot3LocMaxFrameSizeEntry ::= SEQUENCE {
        lldpV2Xdot3LocMaxFrameSize             Unsigned32
}

lldpV2Xdot3LocMaxFrameSize OBJECT-TYPE
    SYNTAX      Unsigned32(0..65535)
    MAX-ACCESS  read-only
    STATUS      current
    DESCRIPTION
            "An integer value indicating the maximum supported frame
             size in octets on the given port of the local system."
    REFERENCE
            "IEEE Std 802.3 30.12.2.1.13"
    ::= { lldpV2Xdot3LocMaxFrameSizeEntry 1 }

---
---
--- lldpV2Xdot3LocEEETable: Energy Efficient Ethernet Information Table
--- V2 modified to be indexed by ifIndex.
---
---

lldpV2Xdot3LocEEETable OBJECT-TYPE
    SYNTAX      SEQUENCE OF LldpV2Xdot3LocEEEEntry
    MAX-ACCESS  not-accessible
    STATUS      current
    DESCRIPTION
            "This table contains one row per port of Energy Efficient Ethernet
            information (as a part of the LLDP IEEE 802.3 organizational
            extension) on the local system known to this agent."
    ::= { lldpV2Xdot3LocalData 4 }

lldpV2Xdot3LocEEEEntry OBJECT-TYPE
    SYNTAX      LldpV2Xdot3LocEEEEntry
    MAX-ACCESS  not-accessible
    STATUS      current
    DESCRIPTION
            "Information about a particular port component."
    INDEX   { lldpV2LocPortIfIndex }
    ::= { lldpV2Xdot3LocEEETable 1 }

LldpV2Xdot3LocEEEEntry ::= SEQUENCE {
         lldpV2Xdot3LocTxTwSys                  Integer32,
         lldpV2Xdot3LocTxTwSysEcho              Integer32,
         lldpV2Xdot3LocRxTwSys                  Integer32,
         lldpV2Xdot3LocRxTwSysEcho              Integer32,
         lldpV2Xdot3LocFbTwSys                  Integer32,
         lldpV2Xdot3TxDllReady                  TruthValue,
         lldpV2Xdot3RxDllReady                  TruthValue,
         lldpV2Xdot3LocDllEnabled               TruthValue
}

lldpV2Xdot3LocTxTwSys      OBJECT-TYPE
    SYNTAX      Integer32
    MAX-ACCESS  read-only
    STATUS      current
    DESCRIPTION
            "A GET returns the value of Tw_sys_tx that the local system
            can support in the transmit direction.
            This object maps to the variable LocTxSystemValue as defined
            in IEEE Std 802.3 78.4.2.3."
    REFERENCE
            "IEEE Std 802.3 30.12.2.1.22"
    ::= {lldpV2Xdot3LocEEEEntry 1 }

lldpV2Xdot3LocTxTwSysEcho      OBJECT-TYPE
    SYNTAX      Integer32
    MAX-ACCESS  read-only
    STATUS      current
    DESCRIPTION
            "A GET returns the value of Tw_sys_tx that the remote system is
            advertising that it can support in the transmit direction and is
            echoed by the local system under the control of the EEE DLL receiver
            state diagram. This object maps to the variable
            LocTxSystemValueEcho as defined in IEEE Std 802.3 78.4.2.3"
    REFERENCE
            "IEEE Std 802.3 30.12.2.1.23"
    ::= {lldpV2Xdot3LocEEEEntry 2 }

lldpV2Xdot3LocRxTwSys      OBJECT-TYPE
    SYNTAX      Integer32
    MAX-ACCESS  read-only
    STATUS      current
    DESCRIPTION
            "A GET returns the value of Tw_sys_tx that
            the local system is requesting in the receive direction.
            This object maps to the variable LocRxSystemValue as
            defined in IEEE Std 802.3 78.4.2.3."
    REFERENCE
            "IEEE Std 802.3 30.12.2.1.24"
    ::= {lldpV2Xdot3LocEEEEntry 3 }

lldpV2Xdot3LocRxTwSysEcho      OBJECT-TYPE
    SYNTAX      Integer32
    MAX-ACCESS  read-only
    STATUS      current
    DESCRIPTION
            "A GET returns the value of Tw_sys_tx that
            the remote system is advertising that it is requesting in the
            receive direction and is echoed by the local system under the
            control of the EEE DLL transmitter state diagram. This object
            maps to the variable LocRxSystemValueEcho as defined in
            IEEE Std 802.3 78.4.2.3."
    REFERENCE
            "IEEE Std 802.3 30.12.2.1.25"
    ::= {lldpV2Xdot3LocEEEEntry 4 }

lldpV2Xdot3LocFbTwSys      OBJECT-TYPE
    SYNTAX      Integer32
    MAX-ACCESS  read-only
    STATUS      current
    DESCRIPTION
            "A GET returns the value of the fallback Tw_sys_tx
            that the local system is advertising to the remote system.
            This object maps to the variable LocFbSystemValue as defined
            in IEEE Std 802.3 78.4.2.3."
    REFERENCE
            "IEEE Std 802.3 30.12.2.1.26"
    ::= {lldpV2Xdot3LocEEEEntry 5 }

lldpV2Xdot3TxDllReady      OBJECT-TYPE
    SYNTAX      TruthValue
    MAX-ACCESS  read-only
    STATUS      current
    DESCRIPTION
            "The truth value used to identify whether the local Data Link Layer
            EEE layer management function has completed initialization and
            is ready to receive and transmit LLDPDUs."
    REFERENCE
            "IEEE Std 802.3 30.12.2.1.27"
    ::= {lldpV2Xdot3LocEEEEntry 6 }

lldpV2Xdot3RxDllReady      OBJECT-TYPE
    SYNTAX      TruthValue
    MAX-ACCESS  read-only
    STATUS      current
    DESCRIPTION
            "The truth value used to identify whether the local Data Link Layer
            EEE layer management function has completed initialization and
            is ready to receive and transmit LLDPDUs."
    REFERENCE
            "IEEE Std 802.3 30.12.2.1.28"
    ::= {lldpV2Xdot3LocEEEEntry 7 }

lldpV2Xdot3LocDllEnabled      OBJECT-TYPE
    SYNTAX      TruthValue
    MAX-ACCESS  read-only
    STATUS      current
    DESCRIPTION
            "The truth value used to identify whether the local system has
            completed auto-negotiation with a link partner that has
            indicated at leat one EEE capability."
    REFERENCE
            "IEEE Std 802.3 30.12.2.1.29"
    ::= {lldpV2Xdot3LocEEEEntry 8 }



------------------------------------------------------------------------------
-- IEEE 802.3 - Remote Devices Information
------------------------------------------------------------------------------

---
---
--- lldpV2Xdot3RemPortTable: Ethernet Information Table
--- V2 modified to be indexed by ifIndex and destination MAC address.
---
---

lldpV2Xdot3RemPortTable OBJECT-TYPE
    SYNTAX      SEQUENCE OF LldpV2Xdot3RemPortEntry
    MAX-ACCESS  not-accessible
    STATUS      current
    DESCRIPTION
            "This table contains Ethernet port information (as a part
            of the LLDP IEEE 802.3 organizational extension) of the remote
            system."
    ::= { lldpV2Xdot3RemoteData 1 }

lldpV2Xdot3RemPortEntry OBJECT-TYPE
    SYNTAX      LldpV2Xdot3RemPortEntry
    MAX-ACCESS  not-accessible
    STATUS      current
    DESCRIPTION
            "Information about a particular physical network connection."
    INDEX   { lldpV2RemTimeMark,
              lldpV2RemLocalIfIndex,
              lldpV2RemLocalDestMACAddress,
              lldpV2RemIndex }
    ::= { lldpV2Xdot3RemPortTable 1 }

LldpV2Xdot3RemPortEntry ::= SEQUENCE {
              lldpV2Xdot3RemPortAutoNegSupported     TruthValue,
              lldpV2Xdot3RemPortAutoNegEnabled       TruthValue,
              lldpV2Xdot3RemPortAutoNegAdvertisedCap OCTET STRING,
              lldpV2Xdot3RemPortOperMauType          Unsigned32
}


lldpV2Xdot3RemPortAutoNegSupported OBJECT-TYPE
    SYNTAX      TruthValue
    MAX-ACCESS  read-only
    STATUS      current
    DESCRIPTION
            "The truth value used to indicate whether the given port
            (associated with remote system) supports Auto-negotiation."
    REFERENCE
            "IEEE Std 802.3 30.12.3.1.1"
    ::= { lldpV2Xdot3RemPortEntry 1 }

lldpV2Xdot3RemPortAutoNegEnabled  OBJECT-TYPE
    SYNTAX      TruthValue
    MAX-ACCESS  read-only
    STATUS      current
    DESCRIPTION
            "The truth value used to indicate whether port
            Auto-negotiation is enabled on the given port associated
            with the remote system."
    REFERENCE
            "IEEE Std 802.3 30.12.3.1.2"
    ::= { lldpV2Xdot3RemPortEntry 2 }

lldpV2Xdot3RemPortAutoNegAdvertisedCap  OBJECT-TYPE
    SYNTAX      OCTET STRING(SIZE(2))
    MAX-ACCESS  read-only
    STATUS      current
    DESCRIPTION
            "This object contains the value (bitmap) of the
            ifMauAutoNegCapAdvertisedBits object (defined in IETF RFC
            3636) which is associated with the given port on the
            remote system."
    REFERENCE
            "IEEE Std 802.3 30.12.3.1.3"
    ::= { lldpV2Xdot3RemPortEntry 3 }

lldpV2Xdot3RemPortOperMauType OBJECT-TYPE
    SYNTAX      Unsigned32(0..2147483647)
    MAX-ACCESS  read-only
    STATUS      current
    DESCRIPTION
            "An integer value that indicates the operational MAU type
            of the sending device.

            This object contains the integer value derived from the
            list position of the corresponding dot3MauType as listed in
            in Clause 13 and is equal to the last number in
            the respective dot3MauType OID.

            For example, if the ifMauType object is dot3MauType1000BaseTHD
            which corresponds to {dot3MauType 29}, the numerical value of
            this field is 29. For MAU types not listed in Clause 13,
            the value of this field shall be set to zero."
    REFERENCE
            "IEEE Std 802.3 30.12.3.1.4"
    ::= { lldpV2Xdot3RemPortEntry 4 }


---
---
--- lldpV2Xdot3RemPowerTable: Power Ethernet Information Table
--- V2 modified to be indexed by ifIndex and destination MAC address.
---
---

lldpV2Xdot3RemPowerTable OBJECT-TYPE
    SYNTAX      SEQUENCE OF LldpV2Xdot3RemPowerEntry
    MAX-ACCESS  not-accessible
    STATUS      current
    DESCRIPTION
            "This table contains Ethernet power information (as a part
            of the LLDP IEEE 802.3 organizational extension) of the remote
            system."
    ::= { lldpV2Xdot3RemoteData 2 }

lldpV2Xdot3RemPowerEntry OBJECT-TYPE
    SYNTAX      LldpV2Xdot3RemPowerEntry
    MAX-ACCESS  not-accessible
    STATUS      current
    DESCRIPTION
            "Information about a particular physical network connection."
    INDEX   { lldpV2RemTimeMark,
              lldpV2RemLocalIfIndex,
              lldpV2RemLocalDestMACAddress,
              lldpV2RemIndex }
    ::= { lldpV2Xdot3RemPowerTable 1 }

LldpV2Xdot3RemPowerEntry ::= SEQUENCE {
              lldpV2Xdot3RemPowerPortClass           LldpV2PowerPortClass,
              lldpV2Xdot3RemPowerMDISupported        TruthValue,
              lldpV2Xdot3RemPowerMDIEnabled          TruthValue,
              lldpV2Xdot3RemPowerPairControlable     TruthValue,
              lldpV2Xdot3RemPowerPairs               Unsigned32,
              lldpV2Xdot3RemPowerClass               Unsigned32,
              lldpV2Xdot3RemPowerType                INTEGER,
              lldpV2Xdot3RemPowerSource              INTEGER,
              lldpV2Xdot3RemPowerPriority            INTEGER,
              lldpV2Xdot3RemPDRequestedPowerValue    Integer32,
              lldpV2Xdot3RemPSEAllocatedPowerValue   Integer32
}


lldpV2Xdot3RemPowerPortClass  OBJECT-TYPE
    SYNTAX      LldpV2PowerPortClass
    MAX-ACCESS  read-only
    STATUS      current
    DESCRIPTION
            "The value that identifies the port Class of the given port
            associated with the remote system."
    REFERENCE
            "IEEE Std 802.3 30.12.3.1.5"
    ::= { lldpV2Xdot3RemPowerEntry 1 }

lldpV2Xdot3RemPowerMDISupported  OBJECT-TYPE
    SYNTAX      TruthValue
    MAX-ACCESS  read-only
    STATUS      current
    DESCRIPTION
            "The truth value used to indicate whether the MDI power
            is supported on the given port associated with the remote
            system."
    REFERENCE
            "IEEE Std 802.3 30.12.3.1.6"
    ::= { lldpV2Xdot3RemPowerEntry 2 }

lldpV2Xdot3RemPowerMDIEnabled  OBJECT-TYPE
    SYNTAX      TruthValue
    MAX-ACCESS  read-only
    STATUS      current
    DESCRIPTION
            "The truth value used to identify whether MDI power is
            enabled on the given port associated with the remote system."
    REFERENCE
            "IEEE Std 802.3 30.12.3.1.7"
    ::= { lldpV2Xdot3RemPowerEntry 3 }

lldpV2Xdot3RemPowerPairControlable  OBJECT-TYPE
    SYNTAX      TruthValue
    MAX-ACCESS  read-only
    STATUS      current
    DESCRIPTION
            "The truth value is derived from the value of
            pethPsePortPowerPairsControlAbility object (defined in
            Clause 8) and is used to indicate whether the pair selection
            can be controlled on the given port associated with the
            remote system."
    REFERENCE
            "IEEE Std 802.3 30.12.3.1.8"
    ::= { lldpV2Xdot3RemPowerEntry 4 }

lldpV2Xdot3RemPowerPairs  OBJECT-TYPE
    SYNTAX      Unsigned32(1|2)
    MAX-ACCESS  read-only
    STATUS      current
    DESCRIPTION
            "This object contains the value of the pethPsePortPowerPairs
            object (defined in Clause 8) which is associated with
            the given port on the remote system."
    REFERENCE
            "IEEE Std 802.3 30.12.3.1.9"
    ::= { lldpV2Xdot3RemPowerEntry 5 }

lldpV2Xdot3RemPowerClass  OBJECT-TYPE
    SYNTAX      Unsigned32(1|2|3|4|5)
    MAX-ACCESS  read-only
    STATUS      current
    DESCRIPTION
            "This object contains the value of the
            pethPsePortPowerClassifications object (defined in
            Clause 8) which is associated with the given port on the
            remote system."
    REFERENCE
            "IEEE Std 802.3 30.12.3.1.10"
    ::= { lldpV2Xdot3RemPowerEntry 6 }


lldpV2Xdot3RemPowerType  OBJECT-TYPE
    SYNTAX      INTEGER {
                    psetype1(0),
                    psetype2(1),
                    pdtype(2),
                    pdtype2(3)
                }
    MAX-ACCESS  read-only
    STATUS      current
    DESCRIPTION
            "A GET returns an integer indicating whether the remote
             system is a PSE or a PD and whether it is Type 1 or Type 2."
    REFERENCE
            "IEEE Std 802.3 30.12.3.1.14"
    ::= { lldpV2Xdot3RemPowerEntry 7 }

lldpV2Xdot3RemPowerSource  OBJECT-TYPE
    SYNTAX      INTEGER {
                    pseprimary(0),
                    psebackup(1),
                    pseunknown(2),
                    pdpseandlocal(3),
                    pdlocalonly(4),
                    pdpseonly(5),
                    pdunknown(6)
                }
    MAX-ACCESS  read-only
    STATUS      current
    DESCRIPTION
            "A GET returns an integer indicating the power sources of the
            remote system. When the remote system is a PSE, it indicates
            whether it is being powered by a primary power source; a backup
            power source; or unknown. When the remote system is a PD, it
            indicates whether it is being powered by a PSE and locally;
            locally only; by a PSE only; or unknown."
    REFERENCE
            "IEEE Std 802.3 30.12.3.1.15"
    ::= { lldpV2Xdot3RemPowerEntry 8 }

lldpV2Xdot3RemPowerPriority  OBJECT-TYPE
    SYNTAX      INTEGER {
                    low(0),
                    high(1),
                    critical(2),
                    unknown(3)
                }
    MAX-ACCESS  read-write
    STATUS      current
    DESCRIPTION
            "A GET returns the priority of a PD system. For a PSE, this
            is the priority that the remote system requests. For a PD, this
            is the priority that the remote system has assigned."
    REFERENCE
            "IEEE Std 802.3 30.12.3.1.16"
    ::= { lldpV2Xdot3RemPowerEntry 9 }

lldpV2Xdot3RemPDRequestedPowerValue  OBJECT-TYPE
    SYNTAX      Integer32
    MAX-ACCESS  read-only
    STATUS      current
    DESCRIPTION
            "A GET returns the PD requested power value that was used
            by the remote system to compute the power value that is has
            currently allocated to the PD. For a PSE, it is the PD requested
            power value received from the remote system. The definition and
            encoding of PD requested power value is the same as described in
            lldpV2Xdot3LocPDRequestedPowerValue."
    REFERENCE
            "IEEE Std 802.3 30.12.3.1.17"
    ::= { lldpV2Xdot3RemPowerEntry 10 }

lldpV2Xdot3RemPSEAllocatedPowerValue  OBJECT-TYPE
    SYNTAX      Integer32
    MAX-ACCESS  read-only
    STATUS      current
    DESCRIPTION
            "A GET returns the PSE allocated power value
            received from the remote system. For a PSE, it is the PSE allocated
            power value that was used by the remote system to compute the power
            value that it has currently requested from the PSE. For a PD, it
            is the PSE allocated power value received from the remote system.
            The definition and encoding of PSE allocated power value is
            the same as described in lldpV2Xdot3LocPSEAllocatedPowerValue."
    REFERENCE
            "IEEE Std 802.3 30.12.3.1.18"
    ::= { lldpV2Xdot3RemPowerEntry 11 }

---
--- lldpV2Xdot3RemMaxFrameSizeTable: Maximum Frame Size information
--- V2 modified to be indexed by ifIndex and destination MAC address.
---
---

lldpV2Xdot3RemMaxFrameSizeTable  OBJECT-TYPE
    SYNTAX      SEQUENCE OF LldpV2Xdot3RemMaxFrameSizeEntry
    MAX-ACCESS  not-accessible
    STATUS      current
    DESCRIPTION
            "This table contains one row per port/destination
            address pair of maximum frame
            size information (as a part of the LLDP IEEE 802.3
            organizational extension) of the remote system."
    ::= { lldpV2Xdot3RemoteData 3 }

lldpV2Xdot3RemMaxFrameSizeEntry OBJECT-TYPE
    SYNTAX      LldpV2Xdot3RemMaxFrameSizeEntry
    MAX-ACCESS  not-accessible
    STATUS      current
    DESCRIPTION
            "Maximum Frame Size information about a particular port
            component."
    INDEX   { lldpV2RemTimeMark,
              lldpV2RemLocalIfIndex,
              lldpV2RemLocalDestMACAddress,
              lldpV2RemIndex }
    ::= { lldpV2Xdot3RemMaxFrameSizeTable 1 }

LldpV2Xdot3RemMaxFrameSizeEntry ::= SEQUENCE {
              lldpV2Xdot3RemMaxFrameSize   Unsigned32
}

lldpV2Xdot3RemMaxFrameSize OBJECT-TYPE
    SYNTAX      Unsigned32(0..65535)
    MAX-ACCESS  read-only
    STATUS      current
    DESCRIPTION
            "An integer value indicating the maximum supported frame
             size in octets on the port component associated with the
             remote system."
    REFERENCE
            "IEEE Std 802.3 30.12.3.1.13"
    ::= { lldpV2Xdot3RemMaxFrameSizeEntry 1 }

---
---
--- lldpV2Xdot3RemEEETable: Energy Efficient Ethernet Information Table
--- V2 modified to be indexed by ifIndex.
---
---

lldpV2Xdot3RemEEETable OBJECT-TYPE
    SYNTAX      SEQUENCE OF LldpV2Xdot3RemEEEEntry
    MAX-ACCESS  not-accessible
    STATUS      current
    DESCRIPTION
            "This table contains one row per port of Energy Efficient Ethernet
            information (as a part of the LLDP IEEE 802.3 organizational
            extension) on the local system known to this agent."
    ::= { lldpV2Xdot3RemoteData 4 }

lldpV2Xdot3RemEEEEntry OBJECT-TYPE
    SYNTAX      LldpV2Xdot3RemEEEEntry
    MAX-ACCESS  not-accessible
    STATUS      current
    DESCRIPTION
            "Information about a particular port component."
    INDEX   { lldpV2RemLocalIfIndex }
    ::= { lldpV2Xdot3RemEEETable 1 }

LldpV2Xdot3RemEEEEntry ::= SEQUENCE {
         lldpV2Xdot3RemTxTwSys                  Integer32,
         lldpV2Xdot3RemTxTwSysEcho              Integer32,
         lldpV2Xdot3RemRxTwSys                  Integer32,
         lldpV2Xdot3RemRxTwSysEcho              Integer32,
         lldpV2Xdot3RemFbTwSys                  Integer32
}


lldpV2Xdot3RemTxTwSys      OBJECT-TYPE
    SYNTAX      Integer32
    MAX-ACCESS  read-only
    STATUS      current
    DESCRIPTION
            "A GET returns the value of Tw_sys_tx that the remote system
            can support in the transmit direction.
            This object maps to the variable RemTxSystemValue as defined
            in IEEE Std 802.3 78.4.2.3."
    REFERENCE
            "IEEE Std 802.3 30.12.3.1.19"
    ::= {lldpV2Xdot3RemEEEEntry 1 }

lldpV2Xdot3RemTxTwSysEcho      OBJECT-TYPE
    SYNTAX      Integer32
    MAX-ACCESS  read-only
    STATUS      current
    DESCRIPTION
            "A GET returns the value of Tw_sys_tx that the local system is
            advertising that it can support in the transmit direction as
             echoed by the remote system under the control of the EEE DLL receiver
            state diagram. This object maps to the variable
            RemTxSystemValueEcho as defined in IEEE Std 802.3 78.4.2.3"
    REFERENCE
            "IEEE Std 802.3 30.12.3.1.20"
    ::= {lldpV2Xdot3RemEEEEntry 2 }

lldpV2Xdot3RemRxTwSys      OBJECT-TYPE
    SYNTAX      Integer32
    MAX-ACCESS  read-only
    STATUS      current
    DESCRIPTION
            "A GET returns the value of Tw_sys_tx that
            the remote system is requesting in the receive direction.
            This object maps to the variable RemRxSystemValue as
            defined in IEEE Std 802.3 78.4.2.3."
    REFERENCE
            "IEEE Std 802.3 30.12.3.1.21"
    ::= {lldpV2Xdot3RemEEEEntry 3 }

lldpV2Xdot3RemRxTwSysEcho      OBJECT-TYPE
    SYNTAX      Integer32
    MAX-ACCESS  read-only
    STATUS      current
    DESCRIPTION
            "A GET returns the value of Tw_sys_tx that
            the local system is advertising that it is requesting in the
            receive direction and is echoed by the remote system under the
            control of the EEE DLL transmitter state diagram. This object
            maps to the variable RemRxSystemValueEcho as defined in
            IEEE Std 802.3 78.4.2.3."
    REFERENCE
            "IEEE Std 802.3 30.12.3.1.22"
    ::= {lldpV2Xdot3RemEEEEntry 4 }

lldpV2Xdot3RemFbTwSys      OBJECT-TYPE
    SYNTAX      Integer32
    MAX-ACCESS  read-only
    STATUS      current
    DESCRIPTION
            "A GET returns the value of the fallback Tw_sys_tx
            that the remote system is advertising.
            This object maps to the variable RemFbSystemValue as defined
            in IEEE Std 802.3 78.4.2.3."
    REFERENCE
            "IEEE Std 802.3 30.12.3.1.23"
    ::= {lldpV2Xdot3RemEEEEntry 5 }



------------------------------------------------------------------------------
-- Conformance statements
------------------------------------------------------------------------------
lldpV2Xdot3Conformance OBJECT IDENTIFIER ::= { ieee8023lldpV2Xdot3MIB 2 }
lldpV2Xdot3Compliances OBJECT IDENTIFIER ::= { lldpV2Xdot3Conformance 1 }
lldpV2Xdot3Groups      OBJECT IDENTIFIER ::= { lldpV2Xdot3Conformance 2 }

-- Compliance statements


lldpV2Xdot3TxRxCompliance MODULE-COMPLIANCE
    STATUS  current
    DESCRIPTION
            "A compliance statement for SNMP entities that implement
            the LLDP IEEE 802.3 organizational extension MIB.

            This group is mandatory for all agents that implement the
            LLDP IEEE 802.3 organizational extension in TX and/or RX mode.

            This version defines compliance requirements for
            V2 of the LLDP MIB."
    MODULE  -- this module
        MANDATORY-GROUPS { lldpV2Xdot3ConfigGroup,
                           ifGeneralInformationGroup
        }
    ::= { lldpV2Xdot3Compliances 1 }

lldpV2Xdot3TxCompliance MODULE-COMPLIANCE
    STATUS  current
    DESCRIPTION
            "The compliance statement for SNMP entities that implement
            the LLDP IEEE 802.3 organizational extension MIB.

            This group is mandatory for agents that implement the
            LLDP IEEE 802.3 organizational extension in the TX mode.

            This version defines compliance requirements for
            V2 of the LLDP MIB."
    MODULE  -- this module
        MANDATORY-GROUPS { lldpV2Xdot3LocSysGroup }
    ::= { lldpV2Xdot3Compliances 2 }

lldpV2Xdot3RxCompliance MODULE-COMPLIANCE
    STATUS  current
    DESCRIPTION
            "The compliance statement for SNMP entities that implement
            the LLDP IEEE 802.3 organizational extension MIB.

            This group is mandatory for agents that implement the
            LLDP IEEE 802.3 organizational extension in the RX mode.

            This version defines compliance requirements for
            V2 of the LLDP MIB."
    MODULE  -- this module
        MANDATORY-GROUPS { lldpV2Xdot3RemSysGroup }
    ::= { lldpV2Xdot3Compliances 3 }


-- MIB groupings


lldpV2Xdot3ConfigGroup    OBJECT-GROUP
    OBJECTS {
        lldpV2Xdot3PortConfigTLVsTxEnable
    }
    STATUS  current
    DESCRIPTION
            "The collection of objects that are used to configure the
            LLDP IEEE 802.3 organizational extension implementation behavior."
    ::= { lldpV2Xdot3Groups 1 }

lldpV2Xdot3LocSysGroup  OBJECT-GROUP
    OBJECTS {
        lldpV2Xdot3LocPortAutoNegSupported,
        lldpV2Xdot3LocPortAutoNegEnabled,
        lldpV2Xdot3LocPortAutoNegAdvertisedCap,
        lldpV2Xdot3LocPortOperMauType,
        lldpV2Xdot3LocPowerPortClass,
        lldpV2Xdot3LocPowerMDISupported,
        lldpV2Xdot3LocPowerMDIEnabled,
        lldpV2Xdot3LocPowerPairControlable,
        lldpV2Xdot3LocPowerPairs,
        lldpV2Xdot3LocPowerClass,
        lldpV2Xdot3LocMaxFrameSize,
        lldpV2Xdot3LocPowerType,
        lldpV2Xdot3LocPowerSource,
        lldpV2Xdot3LocPowerPriority,
        lldpV2Xdot3LocPDRequestedPowerValue,
        lldpV2Xdot3LocPSEAllocatedPowerValue,
        lldpV2Xdot3LocResponseTime,
        lldpV2Xdot3LocReady,
        lldpV2Xdot3LocReducedOperationPowerValue,
        lldpV2Xdot3LocTxTwSys,
        lldpV2Xdot3LocTxTwSysEcho,
        lldpV2Xdot3LocRxTwSys,
        lldpV2Xdot3LocRxTwSysEcho,
        lldpV2Xdot3LocFbTwSys,
        lldpV2Xdot3TxDllReady,
        lldpV2Xdot3RxDllReady,
        lldpV2Xdot3LocDllEnabled
    }
    STATUS  current
    DESCRIPTION
            "The collection of objects that are used to represent LLDP
            IEEE 802.3 organizational extension Local Device Information."
    ::= { lldpV2Xdot3Groups 2 }

lldpV2Xdot3RemSysGroup  OBJECT-GROUP
    OBJECTS {
        lldpV2Xdot3RemPortAutoNegSupported,
        lldpV2Xdot3RemPortAutoNegEnabled,
        lldpV2Xdot3RemPortAutoNegAdvertisedCap,
        lldpV2Xdot3RemPortOperMauType,
        lldpV2Xdot3RemPowerPortClass,
        lldpV2Xdot3RemPowerMDISupported,
        lldpV2Xdot3RemPowerMDIEnabled,
        lldpV2Xdot3RemPowerPairControlable,
        lldpV2Xdot3RemPowerPairs,
        lldpV2Xdot3RemPowerClass,
        lldpV2Xdot3RemMaxFrameSize,
        lldpV2Xdot3RemPowerType,
        lldpV2Xdot3RemPowerSource,
        lldpV2Xdot3RemPowerPriority,
        lldpV2Xdot3RemPDRequestedPowerValue,
        lldpV2Xdot3RemPSEAllocatedPowerValue,
        lldpV2Xdot3RemTxTwSys,
        lldpV2Xdot3RemTxTwSysEcho,
        lldpV2Xdot3RemRxTwSys,
        lldpV2Xdot3RemRxTwSysEcho,
        lldpV2Xdot3RemFbTwSys
    }
    STATUS  current
    DESCRIPTION
            "The collection of objects that are used to represent LLDP
            IEEE 802.3 organizational extension Local Device Information."
    ::= { lldpV2Xdot3Groups 3 }

END

RBT-PRODUCT-MIB DEFINITIONS ::= BEGIN
IMPORTS
    MODULE-IDENTITY FROM SNMPv2-SMI
    rbt, productFamilies FROM RBT-MIB;

rbtProductsMib MODULE-IDENTITY
    LAST-UPDATED        "201708010000Z"
    ORGANIZATION        "Riverbed Technology, Inc."
    CONTACT-INFO
    "   Riverbed Technical Support
           support@riverbed.com"
    DESCRIPTION         "Riverbed Technology Products Definition MIB"

    REVISION 		"201708010000Z"
    DESCRIPTION         "Initial Revision"
    ::= { rbt 4 }

steelCentral OBJECT IDENTIFIER
    ::= { productFamilies 100}

scAppResponse OBJECT IDENTIFIER
    ::= { steelCentral 1}

scInsights OBJECT IDENTIFIER
    ::= { steelCentral 2}
END

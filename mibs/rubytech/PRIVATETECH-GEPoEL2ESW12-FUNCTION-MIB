PRIVATETECH-GEPoEL2ESW12-FUNCTION-MIB DEFINITIONS ::= BEGIN

IMPORTS
    DisplayString,MacAddress FROM SNMPv2-TC
    MODULE-COMPLIANCE,OBJECT-GROUP, NOTIFICATION-GROUP       FROM SNMPv2-CONF
    ifIndex    FROM RFC1213-MIB
    enterprises,MODULE-IDENTITY,OBJECT-TYPE,NOTIFICATION-TYPE,Counter32,Counter64,IpAddress        FROM SNMPv2-SMI
    InetAddress                   FROM INET-ADDRESS-MIB
    MacAddress FROM BRIDGE-MIB;

privatetech MODULE-IDENTITY
        LAST-UPDATED "201112150000Z"
        ORGANIZATION "Corp."
        CONTACT-INFO
            ""
        DESCRIPTION
            ""
        ::= { enterprises 5205 }

switch                                                          OBJECT IDENTIFIER ::= { privatetech 1 }

gepoel2esw12ProductId                                             OBJECT IDENTIFIER ::= { switch 24 }

gepoel2esw12System                                                OBJECT IDENTIFIER ::= { gepoel2esw12ProductId 1 }

gepoel2esw12SystemInformation                                     OBJECT IDENTIFIER ::= { gepoel2esw12System 1 }

gepoel2esw12ModelName OBJECT-TYPE
   SYNTAX       DisplayString
   MAX-ACCESS   read-only
   STATUS       current
   DESCRIPTION
       ""
 ::= { gepoel2esw12SystemInformation 1 }

gepoel2esw12BIOSVersion OBJECT-TYPE
   SYNTAX       DisplayString
   MAX-ACCESS   read-only
   STATUS       current
   DESCRIPTION
       ""
   ::= { gepoel2esw12SystemInformation 2 }

gepoel2esw12FirmwareVersion OBJECT-TYPE
   SYNTAX       DisplayString
   MAX-ACCESS   read-only
   STATUS       current
   DESCRIPTION
       ""
   ::= { gepoel2esw12SystemInformation 3 }

gepoel2esw12HardwareMechanicalVersion OBJECT-TYPE
   SYNTAX       DisplayString
   MAX-ACCESS   read-only
   STATUS       current
   DESCRIPTION
       ""
   ::= { gepoel2esw12SystemInformation 4 }

gepoel2esw12SeriesNumber OBJECT-TYPE
   SYNTAX       DisplayString
   MAX-ACCESS   read-only
   STATUS       current
   DESCRIPTION
       ""
   ::= { gepoel2esw12SystemInformation 5 }

gepoel2esw12HostMACAddress OBJECT-TYPE
   SYNTAX       MacAddress
   MAX-ACCESS   read-only
   STATUS       current
   DESCRIPTION
       ""
   ::= { gepoel2esw12SystemInformation 6 }

gepoel2esw12ConsoleBaudrate OBJECT-TYPE
   SYNTAX       DisplayString
   MAX-ACCESS   read-only
   STATUS       current
   DESCRIPTION
       ""
   ::= { gepoel2esw12SystemInformation 7 }

gepoel2esw12RAMSize OBJECT-TYPE
   SYNTAX       DisplayString
   MAX-ACCESS   read-only
   STATUS       current
   DESCRIPTION
       ""
   ::= { gepoel2esw12SystemInformation 8 }

gepoel2esw12FlashSize OBJECT-TYPE
   SYNTAX       DisplayString
   MAX-ACCESS   read-only
   STATUS       current
   DESCRIPTION
       ""
   ::= { gepoel2esw12SystemInformation 9 }

gepoel2esw12BridgeFBDSize OBJECT-TYPE
   SYNTAX       DisplayString
   MAX-ACCESS   read-only
   STATUS       current
   DESCRIPTION
       ""
   ::= { gepoel2esw12SystemInformation 10 }

gepoel2esw12TransmitQueue OBJECT-TYPE
   SYNTAX       DisplayString
   MAX-ACCESS   read-only
   STATUS       current
   DESCRIPTION
       ""
   ::= { gepoel2esw12SystemInformation 11 }

gepoel2esw12MaximumFrameSize OBJECT-TYPE
   SYNTAX       DisplayString
   MAX-ACCESS   read-only
   STATUS       current
   DESCRIPTION
       ""
   ::= { gepoel2esw12SystemInformation 12 }

gepoel2esw12CPULoad OBJECT-TYPE
   SYNTAX       DisplayString
   MAX-ACCESS   read-only
   STATUS       current
   DESCRIPTION
       ""
   ::= { gepoel2esw12SystemInformation 13 }


gepoel2esw12SystemTime                                            OBJECT IDENTIFIER ::= { gepoel2esw12System 2 }

gepoel2esw12SystemTimeManual                                      OBJECT IDENTIFIER ::= { gepoel2esw12SystemTime 1 }

gepoel2esw12SystemTimeManualClockSource OBJECT-TYPE
   SYNTAX       INTEGER(0|1)
   MAX-ACCESS   read-write
   STATUS       current
   DESCRIPTION
       "default: 0,
        0 : Use Local Settings,
        1 : Use NTP Server."
   ::= { gepoel2esw12SystemTimeManual 1 }
   
gepoel2esw12SystemTimeManualLocaltime OBJECT-TYPE
   SYNTAX       DisplayString
   MAX-ACCESS   read-write
   STATUS       current
   DESCRIPTION
       "Get/Set the system time of the device.
        The input format is 'Year-Month-Day Hour:Minute:Second'.
        ex: 2011-01-01 05:43:05  means 2011/1/1 - 05:43:05 .
        The value range:
        Year    : 2010 - 2090,
        Mouth   : 1 - 12,
        Day     : 1 - 31,
        Hour    : 0 - 23,
        Minute  : 0 - 59,
        Sec     : 0 - 59."
   ::= { gepoel2esw12SystemTimeManual 2 }

gepoel2esw12SystemTimeManualTimeZoneOffset OBJECT-TYPE
   SYNTAX       INTEGER(-720..780)
   MAX-ACCESS   read-write
   STATUS       current
   DESCRIPTION
       "Get/Set the NTP Time Zone.
        The value range is between -720 and 780 (minutes)."
   ::= { gepoel2esw12SystemTimeManual 3 }
   
gepoel2esw12SystemTimeManualDaylightSavings OBJECT-TYPE
   SYNTAX       INTEGER(0|1)
   MAX-ACCESS   read-write
   STATUS       current
   DESCRIPTION
       "default: 0,
        0 : Disable,
        1 : Enable."
   ::= { gepoel2esw12SystemTimeManual 4 }
   
gepoel2esw12SystemTimeManualTimeSetOffset OBJECT-TYPE
   SYNTAX       INTEGER(1..1440)
   MAX-ACCESS   read-write
   STATUS       current
   DESCRIPTION
       "Get/Set the Daylight Saving Time.
        The value range is between 1 and 1440 (minutes),
        Default : 60 (minutes)."
   ::= { gepoel2esw12SystemTimeManual 5 }
   
gepoel2esw12SystemTimeManualDaylightSavingsType OBJECT-TYPE
   SYNTAX       INTEGER(0|1)
   MAX-ACCESS   read-write
   STATUS       current
   DESCRIPTION
       "default: 0,
        0 : By dates,
        1 : Recurring."
   ::= { gepoel2esw12SystemTimeManual 6 }
   
gepoel2esw12SystemTimeManualDaylightSavingsBydatesFrom OBJECT-TYPE
   SYNTAX       DisplayString
   MAX-ACCESS   read-write
   STATUS       current
   DESCRIPTION
       "Get/Set the Start time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gepoel2esw12SystemTimeManual 7 }
   
gepoel2esw12SystemTimeManualDaylightSavingsBydatesTo OBJECT-TYPE
   SYNTAX       DisplayString
   MAX-ACCESS   read-write
   STATUS       current
   DESCRIPTION
       "Get/Set the End time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gepoel2esw12SystemTimeManual 8 }

gepoel2esw12SystemTimeManualDaylightSavingsRecurringDayFrom OBJECT-TYPE
   SYNTAX       INTEGER(0..6)
   MAX-ACCESS   read-write
   STATUS       current
   DESCRIPTION
       "Get/Set the Daylight Saving Time Day From.
        0 : Sun, 1 : Mon, 2 : Tue, 3 : Wed, 4 : Thu, 5 : Fri, 6 : Sat."
   ::= { gepoel2esw12SystemTimeManual 9 }

gepoel2esw12SystemTimeManualDaylightSavingsRecurringWeekFrom OBJECT-TYPE
   SYNTAX       INTEGER(1..5)
   MAX-ACCESS   read-write
   STATUS       current
   DESCRIPTION
       "Get/Set the Daylight Saving Time Week From.
        1 : first week, 2, 3, 4, 5 : last week"
   ::= { gepoel2esw12SystemTimeManual 10 }
   
gepoel2esw12SystemTimeManualDaylightSavingsRecurringMonthFrom OBJECT-TYPE
   SYNTAX       INTEGER(0..11)
   MAX-ACCESS   read-write
   STATUS       current
   DESCRIPTION
       "Get/Set the Daylight Saving Time Month From.
        1 : Jan, 2 : Feb, 3 : Mar, 4 : Apr, 5 : May, 6 : Jun,
        7 : Jul, 8 : Aug, 9 : Sep, 10 : Oct, 11 : Nov, 12 : Dec."
   ::= { gepoel2esw12SystemTimeManual 11 }

gepoel2esw12SystemTimeManualDaylightSavingsRecurringTimeFrom OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gepoel2esw12SystemTimeManual 12 }
   
gepoel2esw12SystemTimeManualDaylightSavingsRecurringDayTo OBJECT-TYPE
   SYNTAX       INTEGER(0..6)
   MAX-ACCESS   read-write
   STATUS       current
   DESCRIPTION
       "Get/Set the Daylight Saving Time Day To.
        0 : Sun, 1 : Mon, 2 : Tue, 3 : Wed, 4 : Thu, 5 : Fri, 6 : Sat."
   ::= { gepoel2esw12SystemTimeManual 13 }

gepoel2esw12SystemTimeManualDaylightSavingsRecurringWeekTo OBJECT-TYPE
   SYNTAX       INTEGER(1..5)
   MAX-ACCESS   read-write
   STATUS       current
   DESCRIPTION
       "Get/Set the Daylight Saving Time Week To.
        1 : first week, 2, 3, 4, 5 : last week"
   ::= { gepoel2esw12SystemTimeManual 14 }
   
gepoel2esw12SystemTimeManualDaylightSavingsRecurringMonthTo OBJECT-TYPE
   SYNTAX       INTEGER(0..11)
   MAX-ACCESS   read-write
   STATUS       current
   DESCRIPTION
       "Get/Set the Daylight Saving Time Month To.
        1 : Jan, 2 : Feb, 3 : Mar, 4 : Apr, 5 : May, 6 : Jun,
        7 : Jul, 8 : Aug, 9 : Sep, 10 : Oct, 11 : Nov, 12 : Dec."
   ::= { gepoel2esw12SystemTimeManual 15 }

gepoel2esw12SystemTimeManualDaylightSavingsRecurringTimeTo OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gepoel2esw12SystemTimeManual 16 }

gepoel2esw12SystemTimeNTP                                     OBJECT IDENTIFIER ::= { gepoel2esw12SystemTime 2 }

gepoel2esw12SystemTimeNTPTable OBJECT-TYPE
   SYNTAX      SEQUENCE OF GEPoEL2ESW12SystemTimeNTPEntry
   MAX-ACCESS  not-accessible
   STATUS      current
   DESCRIPTION
       " "
   ::= { gepoel2esw12SystemTimeNTP 1 }

gepoel2esw12SystemTimeNTPEntry OBJECT-TYPE
   SYNTAX      GEPoEL2ESW12SystemTimeNTPEntry
   MAX-ACCESS  not-accessible
   STATUS      current
   DESCRIPTION
       ""
   INDEX    { gepoel2esw12SystemTimeNTPIndex  }
   ::= { gepoel2esw12SystemTimeNTPTable 1 }

GEPoEL2ESW12SystemTimeNTPEntry ::= SEQUENCE {
   gepoel2esw12SystemTimeNTPIndex             INTEGER,
   gepoel2esw12SystemTimeNTPServerIPType      INTEGER,
   gepoel2esw12SystemTimeNTPServer            DisplayString,
   gepoel2esw12SystemTimeNTPCurrentMode       INTEGER
}

gepoel2esw12SystemTimeNTPIndex OBJECT-TYPE
   SYNTAX      INTEGER (1..5)
   MAX-ACCESS  not-accessible
   STATUS      current
   DESCRIPTION
       " The index of the ntp entry. "
   ::= { gepoel2esw12SystemTimeNTPEntry 1 }

gepoel2esw12SystemTimeNTPServerIPType OBJECT-TYPE
   SYNTAX       INTEGER(0|1)
   MAX-ACCESS   read-write
   STATUS       current
   DESCRIPTION
       "Default: 0,
        0 : IPv4,
        1 : IPv6."
   ::= { gepoel2esw12SystemTimeNTPEntry 2 }

gepoel2esw12SystemTimeNTPServer OBJECT-TYPE
   SYNTAX       DisplayString
   MAX-ACCESS   read-write
   STATUS       current
   DESCRIPTION
       "Get/Set the NTP Time Server1. You can use the IP address or domain name."
   ::= { gepoel2esw12SystemTimeNTPEntry 3 }

gepoel2esw12SystemTimeNTPCurrentMode OBJECT-TYPE
   SYNTAX      INTEGER (0..3)
   MAX-ACCESS  read-write
   STATUS      current
   DESCRIPTION
       " 0: Empty
        1: Active
        2: Edit
        3: Delete"
   ::= { gepoel2esw12SystemTimeNTPEntry 4 }
    

gepoel2esw12SystemAccount                                         OBJECT IDENTIFIER ::= { gepoel2esw12System 3 }

gepoel2esw12SystemAccountUsers                                    OBJECT IDENTIFIER ::= { gepoel2esw12SystemAccount 1 }

gepoel2esw12SystemAccountUserCreate OBJECT-TYPE
   SYNTAX       INTEGER(0|1)
   MAX-ACCESS   read-write
   STATUS       current
   DESCRIPTION
       "default: 0
        0 : None  (read only)
        1 : Create a user account"
   ::= { gepoel2esw12SystemAccountUsers 1 }

gepoel2esw12SystemAccountUsersTable OBJECT-TYPE
   SYNTAX      SEQUENCE OF GEPoEL2ESW12SystemAccountUsersEntry
   MAX-ACCESS  not-accessible
   STATUS      current
   DESCRIPTION
       " "
   ::= { gepoel2esw12SystemAccountUsers 2 }

gepoel2esw12SystemAccountUsersEntry OBJECT-TYPE
   SYNTAX      GEPoEL2ESW12SystemAccountUsersEntry
   MAX-ACCESS  not-accessible
   STATUS      current
   DESCRIPTION
       ""
   INDEX    { gepoel2esw12UserIndex  }
   ::= { gepoel2esw12SystemAccountUsersTable 1 }


GEPoEL2ESW12SystemAccountUsersEntry ::= SEQUENCE {
   gepoel2esw12UserIndex              INTEGER,
   gepoel2esw12UserName               DisplayString,
   gepoel2esw12Password               DisplayString,
   gepoel2esw12UserPrivilegeLevel     INTEGER,
   gepoel2esw12AccountUserRowStatus   INTEGER
}


gepoel2esw12UserIndex OBJECT-TYPE
   SYNTAX      INTEGER (1..20)
   MAX-ACCESS  not-accessible
   STATUS      current
   DESCRIPTION
       " "
   ::= { gepoel2esw12SystemAccountUsersEntry 1 }

gepoel2esw12UserName OBJECT-TYPE
   SYNTAX      DisplayString (SIZE (1..32))
   MAX-ACCESS  read-write
   STATUS      current
   DESCRIPTION
       " "
   ::= { gepoel2esw12SystemAccountUsersEntry 2 }

gepoel2esw12Password OBJECT-TYPE
   SYNTAX      DisplayString (SIZE (1..32))
   MAX-ACCESS  read-write
   STATUS      current
   DESCRIPTION
       " "
   ::= { gepoel2esw12SystemAccountUsersEntry 3 }

gepoel2esw12UserPrivilegeLevel OBJECT-TYPE
   SYNTAX      INTEGER (1..15)
   MAX-ACCESS  read-write
   STATUS      current
   DESCRIPTION
       "default:1 
        User privilege level range : 1 - 15"
   ::= { gepoel2esw12SystemAccountUsersEntry 4 }

gepoel2esw12AccountUserRowStatus OBJECT-TYPE
   SYNTAX      INTEGER (1..5)
   MAX-ACCESS  read-write
   STATUS      current
   DESCRIPTION
       " 1: active
        2: notInservice
        3: edit
        4: destroy
        5: undo"
   ::= { gepoel2esw12SystemAccountUsersEntry 5 }

gepoel2esw12SystemAccountPrivilegeLevel                           OBJECT IDENTIFIER ::= { gepoel2esw12SystemAccount 2 }

gepoel2esw12PrivilegeLevelAccount OBJECT-TYPE
   SYNTAX      INTEGER (1..15)
   MAX-ACCESS  read-write
   STATUS      current
   DESCRIPTION
       "default:10 "
   ::= { gepoel2esw12SystemAccountPrivilegeLevel 1 }

gepoel2esw12PrivilegeLevelDiagnostics OBJECT-TYPE
   SYNTAX      INTEGER (1..15)
   MAX-ACCESS  read-write
   STATUS      current
   DESCRIPTION
       "default:10 "
   ::= { gepoel2esw12SystemAccountPrivilegeLevel 2 }

gepoel2esw12PrivilegeLevelIP OBJECT-TYPE
   SYNTAX      INTEGER (1..15)
   MAX-ACCESS  read-write
   STATUS      current
   DESCRIPTION
       "default:10 "
   ::= { gepoel2esw12SystemAccountPrivilegeLevel 3 }

gepoel2esw12PrivilegeLevelMaintenance OBJECT-TYPE
   SYNTAX      INTEGER (1..15)
   MAX-ACCESS  read-write
   STATUS      current
   DESCRIPTION
       "default:10 "
   ::= { gepoel2esw12SystemAccountPrivilegeLevel 4 }

gepoel2esw12PrivilegeLevelOLT OBJECT-TYPE
   SYNTAX      INTEGER (1..15)
   MAX-ACCESS  read-write
   STATUS      current
   DESCRIPTION
       "default:10 "
   ::= { gepoel2esw12SystemAccountPrivilegeLevel 5 }

gepoel2esw12PrivilegeLevelONU OBJECT-TYPE
   SYNTAX      INTEGER (1..15)
   MAX-ACCESS  read-write
   STATUS      current
   DESCRIPTION
       "default:10 "
   ::= { gepoel2esw12SystemAccountPrivilegeLevel 6 }

gepoel2esw12PrivilegeLevelSMTP OBJECT-TYPE
   SYNTAX      INTEGER (1..15)
   MAX-ACCESS  read-write
   STATUS      current
   DESCRIPTION
       "default:10 "
   ::= { gepoel2esw12SystemAccountPrivilegeLevel 7 }

gepoel2esw12PrivilegeLevelSNMP OBJECT-TYPE
   SYNTAX      INTEGER (1..15)
   MAX-ACCESS  read-write
   STATUS      current
   DESCRIPTION
       "default:10 "
   ::= { gepoel2esw12SystemAccountPrivilegeLevel 8 }

gepoel2esw12PrivilegeLevelSecurity OBJECT-TYPE
   SYNTAX      INTEGER (1..15)
   MAX-ACCESS  read-write
   STATUS      current
   DESCRIPTION
       "default:10 "
   ::= { gepoel2esw12SystemAccountPrivilegeLevel 9 }

gepoel2esw12PrivilegeLevelSystem OBJECT-TYPE
   SYNTAX      INTEGER (1..15)
   MAX-ACCESS  read-write
   STATUS      current
   DESCRIPTION
       "default:10 "
   ::= { gepoel2esw12SystemAccountPrivilegeLevel 10 }

gepoel2esw12PrivilegeLevelTrapEvent OBJECT-TYPE
   SYNTAX      INTEGER (1..15)
   MAX-ACCESS  read-write
   STATUS      current
   DESCRIPTION
       "default:10 "
   ::= { gepoel2esw12SystemAccountPrivilegeLevel 11 }


gepoel2esw12IP                                                    OBJECT IDENTIFIER ::= { gepoel2esw12System 4 }

gepoel2esw12IPv4                                                  OBJECT IDENTIFIER ::= { gepoel2esw12IP 1 }

gepoel2esw12IPv4Configured                                                  OBJECT IDENTIFIER ::= { gepoel2esw12IPv4 1 }

gepoel2esw12Ipv4DHCPClient OBJECT-TYPE
   SYNTAX      INTEGER (0|1)
   MAX-ACCESS  read-write
   STATUS      current
   DESCRIPTION
       "default:0
       0: disable
       1: enable"
   ::= { gepoel2esw12IPv4Configured 1 }

gepoel2esw12IPv4Address OBJECT-TYPE
   SYNTAX      IpAddress
   MAX-ACCESS  read-write
   STATUS      current
   DESCRIPTION
       ""
   ::= { gepoel2esw12IPv4Configured 2 }

gepoel2esw12IPv4Mask OBJECT-TYPE
   SYNTAX      IpAddress
   MAX-ACCESS  read-write
   STATUS      current
   DESCRIPTION
       ""
   ::= { gepoel2esw12IPv4Configured 3 }

gepoel2esw12IPv4Router OBJECT-TYPE
   SYNTAX      IpAddress
   MAX-ACCESS  read-write
   STATUS      current
   DESCRIPTION
       ""
   ::= { gepoel2esw12IPv4Configured 4 }

gepoel2esw12IPv4VLANId OBJECT-TYPE
   SYNTAX      INTEGER (1..4094)
   MAX-ACCESS  read-write
   STATUS      current
   DESCRIPTION
       "default:1"
   ::= { gepoel2esw12IPv4Configured 5 }

gepoel2esw12IPv4DNSServer OBJECT-TYPE
   SYNTAX      IpAddress
   MAX-ACCESS  read-write
   STATUS      current
   DESCRIPTION
       ""
   ::= { gepoel2esw12IPv4Configured 6 }

gepoel2esw12IPv4DNSProxy OBJECT-TYPE
   SYNTAX      INTEGER (0|1)
   MAX-ACCESS  read-write
   STATUS      current
   DESCRIPTION
       " "
   ::= { gepoel2esw12IPv4Configured 7 }

gepoel2esw12IPv4Current                                                  OBJECT IDENTIFIER ::= { gepoel2esw12IPv4 2 }

gepoel2esw12Ipv4CurrentDHCPClient OBJECT-TYPE
   SYNTAX      INTEGER (0|1)
   MAX-ACCESS  read-write
   STATUS      current
   DESCRIPTION
       "default:0
       0: none (for read)
       1: renew"
   ::= { gepoel2esw12IPv4Current 1 }

gepoel2esw12IPv4CurrentAddress OBJECT-TYPE
   SYNTAX      IpAddress
   MAX-ACCESS  read-only
   STATUS      current
   DESCRIPTION
       ""
   ::= { gepoel2esw12IPv4Current 2 }

gepoel2esw12IPv4CurrentMask OBJECT-TYPE
   SYNTAX      IpAddress
   MAX-ACCESS  read-only
   STATUS      current
   DESCRIPTION
       ""
   ::= { gepoel2esw12IPv4Current 3 }

gepoel2esw12IPv4CurrentRouter OBJECT-TYPE
   SYNTAX      IpAddress
   MAX-ACCESS  read-only
   STATUS      current
   DESCRIPTION
       ""
   ::= { gepoel2esw12IPv4Current 4 }

gepoel2esw12IPv4CurrentVLANId OBJECT-TYPE
   SYNTAX      INTEGER (1..4094)
   MAX-ACCESS  read-only
   STATUS      current
   DESCRIPTION
       "default:1"
   ::= { gepoel2esw12IPv4Current 5 }

gepoel2esw12IPv4CurrentDNSServer OBJECT-TYPE
   SYNTAX      IpAddress
   MAX-ACCESS  read-only
   STATUS      current
   DESCRIPTION
       ""
   ::= { gepoel2esw12IPv4Current 6 }


gepoel2esw12IPv6                                                  OBJECT IDENTIFIER ::= { gepoel2esw12IP 2 }

gepoel2esw12IPv6Configured                                                  OBJECT IDENTIFIER ::= { gepoel2esw12IPv6 1 }

gepoel2esw12Ipv6AutoConfiguration OBJECT-TYPE
   SYNTAX      INTEGER (0|1)
   MAX-ACCESS  read-write
   STATUS      current
   DESCRIPTION
       "default:0
       0: disable
       1: enable"
   ::= { gepoel2esw12IPv6Configured 1 }

gepoel2esw12Ipv6Address OBJECT-TYPE
   SYNTAX      DisplayString (SIZE (0..30))
   MAX-ACCESS  read-write
   STATUS      current
   DESCRIPTION
       ""
   ::= { gepoel2esw12IPv6Configured 2 }

gepoel2esw12Ipv6Prefix OBJECT-TYPE
   SYNTAX      INTEGER (1..128)
   MAX-ACCESS  read-write
   STATUS      current
   DESCRIPTION
       "default: 96"
   ::= { gepoel2esw12IPv6Configured 3 }

gepoel2esw12Ipv6Router OBJECT-TYPE
   SYNTAX      DisplayString (SIZE (0..30))
   MAX-ACCESS  read-write
   STATUS      current
   DESCRIPTION
       " "
   ::= { gepoel2esw12IPv6Configured 4 }

gepoel2esw12IPv6Current                                                  OBJECT IDENTIFIER ::= { gepoel2esw12IPv6 2 }

gepoel2esw12Ipv6CurrentAutoConfiguration OBJECT-TYPE
   SYNTAX      INTEGER (0|1)
   MAX-ACCESS  read-only
   STATUS      current
   DESCRIPTION
       "default:0
       0: disable
       1: enable"
   ::= { gepoel2esw12IPv6Current 1 }

gepoel2esw12Ipv6CurrentAddress OBJECT-TYPE
   SYNTAX      DisplayString (SIZE (0..30))
   MAX-ACCESS  read-only
   STATUS      current
   DESCRIPTION
       ""
   ::= { gepoel2esw12IPv6Current 2 }


gepoel2esw12Ipv6CurrentLinkLocalAddress OBJECT-TYPE
   SYNTAX      DisplayString(SIZE (0..30))
   MAX-ACCESS  read-only
   STATUS      current
   DESCRIPTION
       ""
   ::= { gepoel2esw12IPv6Current 3 }


gepoel2esw12Ipv6CurrentPrefix OBJECT-TYPE
   SYNTAX      INTEGER (1..128)
   MAX-ACCESS  read-only
   STATUS      current
   DESCRIPTION
       ""
   ::= { gepoel2esw12IPv6Current 4 }

gepoel2esw12Ipv6CurrentRouter OBJECT-TYPE
   SYNTAX      DisplayString (SIZE (0..30))
   MAX-ACCESS  read-only
   STATUS      current
   DESCRIPTION
       " "
   ::= { gepoel2esw12IPv6Current 5 }

gepoel2esw12Syslog                                                OBJECT IDENTIFIER ::= { gepoel2esw12System 5 }

gepoel2esw12SyslogConf                                            OBJECT IDENTIFIER ::= { gepoel2esw12Syslog 1 }

gepoel2esw12ServerMode OBJECT-TYPE
   SYNTAX      INTEGER (0|1)
   MAX-ACCESS  read-write
   STATUS      current
   DESCRIPTION
       "default: 0
       0: disable
       1: enable "
   ::= { gepoel2esw12SyslogConf 1 }

gepoel2esw12ServerAddress1 OBJECT-TYPE
   SYNTAX      IpAddress
   MAX-ACCESS  read-write
   STATUS      current
   DESCRIPTION
       " "
   ::= { gepoel2esw12SyslogConf 2 }



gepoel2esw12SyslogLevel OBJECT-TYPE
   SYNTAX      INTEGER(0..7)
   MAX-ACCESS  read-write
   STATUS      current
   DESCRIPTION
       "default: 6 (Info)
       0: Emergency
       1: Alert
       2: Critical
       3: Error
       4: Warning
       5: Notice
       6: Info
       7: Debug"
   ::= { gepoel2esw12SyslogConf 4 }

gepoel2esw12SyslogDetailedInfo                                    OBJECT IDENTIFIER ::= { gepoel2esw12Syslog 2 }

gepoel2esw12SyslogDetailedInfoClear OBJECT-TYPE
   SYNTAX      INTEGER(0|1)
   MAX-ACCESS  read-write
   STATUS      current
   DESCRIPTION
      "default: 0
       0 : None  (read only)
       1 : Clear Syslog"
   ::= { gepoel2esw12SyslogDetailedInfo 1 }

gepoel2esw12SyslogDetailedInfoTable OBJECT-TYPE
  SYNTAX      SEQUENCE OF GEPoEL2ESW12SyslogDetailedInfoEntry
  MAX-ACCESS  not-accessible
  STATUS      current
  DESCRIPTION
           " "
       ::= { gepoel2esw12SyslogDetailedInfo 2 }

gepoel2esw12SyslogDetailedInfoEntry OBJECT-TYPE
   SYNTAX      GEPoEL2ESW12SyslogDetailedInfoEntry
   MAX-ACCESS  not-accessible
   STATUS      current
   DESCRIPTION
           ""
   INDEX    { gepoel2esw12SyslogDetailedInfoIndex  }
   ::= { gepoel2esw12SyslogDetailedInfoTable 1 }

GEPoEL2ESW12SyslogDetailedInfoEntry ::= SEQUENCE {
   gepoel2esw12SyslogDetailedInfoIndex       INTEGER,
   gepoel2esw12SyslogDetailedInfoLevel       DisplayString,
   gepoel2esw12SyslogDetailedInfoTime        DisplayString,
   gepoel2esw12SyslogDetailedInfoMessage     DisplayString
}

gepoel2esw12SyslogDetailedInfoIndex OBJECT-TYPE
   SYNTAX      INTEGER (1..1024)
   MAX-ACCESS  not-accessible
   STATUS      current
   DESCRIPTION
       " "
   ::= { gepoel2esw12SyslogDetailedInfoEntry 1 }
   
gepoel2esw12SyslogDetailedInfoLevel OBJECT-TYPE
   SYNTAX      DisplayString
   MAX-ACCESS  read-only
   STATUS      current
   DESCRIPTION
       " "
   ::= { gepoel2esw12SyslogDetailedInfoEntry 2 }

gepoel2esw12SyslogDetailedInfoTime OBJECT-TYPE
   SYNTAX      DisplayString(SIZE (0..20))
   MAX-ACCESS  read-only
   STATUS      current
   DESCRIPTION
       " "
   ::= { gepoel2esw12SyslogDetailedInfoEntry 3 }

gepoel2esw12SyslogDetailedInfoMessage OBJECT-TYPE
   SYNTAX      DisplayString
   MAX-ACCESS  read-only
   STATUS      current
   DESCRIPTION
       " "
   ::= { gepoel2esw12SyslogDetailedInfoEntry 4 }


gepoel2esw12Snmp                                                OBJECT IDENTIFIER ::= { gepoel2esw12System 6 }

gepoel2esw12SnmpConf                                            OBJECT IDENTIFIER ::= { gepoel2esw12Snmp 1 }

gepoel2esw12TrapHostConfTable OBJECT-TYPE
   SYNTAX      SEQUENCE OF GEPoEL2ESW12TrapHostConfEntry
   MAX-ACCESS  not-accessible
   STATUS      current
   DESCRIPTION
       "A list of trap host entry. The numbers of entries are given by the value of gepoel2esw12TrapHostConfNumber."
   ::= { gepoel2esw12SnmpConf 4 }
   
gepoel2esw12TrapHostConfEntry OBJECT-TYPE
   SYNTAX      GEPoEL2ESW12TrapHostConfEntry
   MAX-ACCESS  not-accessible
   STATUS      current
   DESCRIPTION
       "This is the entry information for trap host."
   INDEX    { gepoel2esw12TrapHostConfIndex  }
   ::= { gepoel2esw12TrapHostConfTable 1 }

GEPoEL2ESW12TrapHostConfEntry ::= SEQUENCE {
    gepoel2esw12TrapHostConfIndex             INTEGER,
    gepoel2esw12TrapHostConfVersion           INTEGER,
    gepoel2esw12TrapHostConfIPType            INTEGER,
    gepoel2esw12TrapHostConfIP                DisplayString,
    gepoel2esw12TrapHostConfPort              INTEGER,
    gepoel2esw12TrapHostConfCommunity         DisplayString,
    gepoel2esw12TrapHostConfSeverityLevel     INTEGER,
    gepoel2esw12TrapHostConfSecurityLevel     INTEGER,
    gepoel2esw12TrapHostConfAuthPtc           INTEGER,
    gepoel2esw12TrapHostConfAuthPassword      DisplayString,
    gepoel2esw12TrapHostConfPrivPtc           INTEGER,
    gepoel2esw12TrapHostConfPrivPassword      DisplayString,
    gepoel2esw12TrapHostConfCurrentMode       INTEGER
}
   
gepoel2esw12TrapHostConfIndex OBJECT-TYPE
   SYNTAX      INTEGER (1..6)
   MAX-ACCESS  not-accessible
   STATUS      current
   DESCRIPTION
       " The index of the trap host entry. "
   ::= { gepoel2esw12TrapHostConfEntry 1 }

gepoel2esw12TrapHostConfVersion OBJECT-TYPE
   SYNTAX       INTEGER(2..3)
   MAX-ACCESS   read-write
   STATUS       current
   DESCRIPTION
       "The version of the Trap PDU. Version : 2(SNMPv2c), 3(SNMPv3)"
   ::= { gepoel2esw12TrapHostConfEntry 2 }

gepoel2esw12TrapHostConfIPType OBJECT-TYPE
   SYNTAX       INTEGER(4|6)
   MAX-ACCESS   read-write
   STATUS       current
   DESCRIPTION
       "Server IP Type. Default: 4,
        4 : IPv4,
        6 : IPv6."
   ::= { gepoel2esw12TrapHostConfEntry 3 }

gepoel2esw12TrapHostConfIP OBJECT-TYPE
   SYNTAX       DisplayString
   MAX-ACCESS   read-write
   STATUS       current
   DESCRIPTION
       "This is the IP of the trap host."
   ::= { gepoel2esw12TrapHostConfEntry 4 }

gepoel2esw12TrapHostConfPort OBJECT-TYPE
   SYNTAX       INTEGER(1..65535)
   MAX-ACCESS   read-write
   STATUS       current
   DESCRIPTION
       "This is the receiving-port number of the trap host.
        range : 1 - 65535."
   ::= { gepoel2esw12TrapHostConfEntry 5 }

gepoel2esw12TrapHostConfCommunity OBJECT-TYPE
   SYNTAX       DisplayString (SIZE (1..32))
   MAX-ACCESS   read-write
   STATUS       current
   DESCRIPTION
       "The community/security name for the trap PDU."
   ::= { gepoel2esw12TrapHostConfEntry 6 }

gepoel2esw12TrapHostConfSeverityLevel	OBJECT-TYPE
   SYNTAX       INTEGER(0..7)
   MAX-ACCESS   read-write
   STATUS       current
   DESCRIPTION
       "The Severity Level.
        0 : Emerg, 1 : Alert, 2 : Crit, 3 : Error, 4 : Warning, 5 : Notice, 6 : Info, 7 : Debug."
	::= { gepoel2esw12TrapHostConfEntry 7 }

gepoel2esw12TrapHostConfSecurityLevel	OBJECT-TYPE
   SYNTAX       INTEGER(1..3)
   MAX-ACCESS   read-write
   STATUS       current
   DESCRIPTION
       "The Security Level, NoAuthNoPriv, AuthNoPriv, and AuthPriv.
        1 : NoAuthNoPriv, 2 : AuthNoPriv, 3 : AuthPriv.
        Privacy protocol will be configured as 'DES' automatically if security level is 3(AuthPriv)."
	::= { gepoel2esw12TrapHostConfEntry 8 }

gepoel2esw12TrapHostConfAuthPtc	OBJECT-TYPE
   SYNTAX       INTEGER(1..2)
   MAX-ACCESS   read-write
   STATUS       current
   DESCRIPTION
       "Authentication Protocol, there are SHA and MD5 supported presently.
        1 : MD5, 2 : SHA."
	::= { gepoel2esw12TrapHostConfEntry 9 }

gepoel2esw12TrapHostConfAuthPassword	OBJECT-TYPE
   SYNTAX      DisplayString
   MAX-ACCESS  read-write
   STATUS		current
   DESCRIPTION
       "Authentication Password, is used for authenticating. The return value is always '********'.
        If the authentication protocol is MD5, the length of password should be 8 ~ 32 characters.
        If the authentication protocol is SHA, the length of password should be 8 ~ 40 characters."
   ::= { gepoel2esw12TrapHostConfEntry 10 }

gepoel2esw12TrapHostConfPrivPtc	OBJECT-TYPE
   SYNTAX       INTEGER(1)
   MAX-ACCESS   read-write
   STATUS       current
   DESCRIPTION
       "This is the Privacy Procol, which is used in AuthPriv. Only supports DES.
        An empty string will be returned if the security level is not 3(AuthPriv).
        1 : DES."
	::= { gepoel2esw12TrapHostConfEntry 11 }

gepoel2esw12TrapHostConfPrivPassword	OBJECT-TYPE
   SYNTAX       DisplayString
   MAX-ACCESS   read-write
   STATUS       current
   DESCRIPTION
       "The password is Privacy Key.  The return value is always '********'.  This Key
        must be more than 8 characters, and less than 32 characters."
   ::= { gepoel2esw12TrapHostConfEntry 12 }

gepoel2esw12TrapHostConfCurrentMode OBJECT-TYPE
   SYNTAX       INTEGER(0..2)
   MAX-ACCESS   read-write
   STATUS       current
   DESCRIPTION
       "0:Empty, 1:Active mode, 2:Edit mode, 3:Delete."
   ::= { gepoel2esw12TrapHostConfEntry 13 }


------------------------------------------------------------------------------------------------------------------------------------

gepoel2esw12OltManagement                                         OBJECT IDENTIFIER ::= { gepoel2esw12ProductId 2 }

gepoel2esw12OltPortTable OBJECT-TYPE
   SYNTAX      SEQUENCE OF GEPoEL2ESW12OltPortEntry
   MAX-ACCESS  not-accessible
   STATUS      current
   DESCRIPTION
       " Show Olt port configurations. "
   ::= { gepoel2esw12OltManagement 1 }

gepoel2esw12OltPortEntry OBJECT-TYPE
   SYNTAX      GEPoEL2ESW12OltPortEntry
   MAX-ACCESS  not-accessible
   STATUS      current
   DESCRIPTION
       ""
   INDEX    { gepoel2esw12OltPortStatusIndex  }
   ::= { gepoel2esw12OltPortTable 1 }

GEPoEL2ESW12OltPortEntry ::= SEQUENCE {
   gepoel2esw12OltPortStatusIndex   INTEGER,
   gepoel2esw12OltPortLinkStatus    DisplayString,
   gepoel2esw12OltPortState         INTEGER,
   gepoel2esw12OltPortSpdDpxConf    INTEGER,
   gepoel2esw12OltPortSpdDpx        DisplayString,
   gepoel2esw12OltPortFlwCtlConf    INTEGER,
   gepoel2esw12OltPortFlwCtl        DisplayString
}

gepoel2esw12OltPortStatusIndex OBJECT-TYPE
   SYNTAX      INTEGER (1..6)
   MAX-ACCESS  not-accessible
   STATUS      current
   DESCRIPTION
       " 1: Epon-0,
         2: Epon-1,
         3: NNI-0 TP,
         4: NNI-0 Fiber,
         5: NNI-1 TP,
         6: NNI-1 Fiber.
         range : 1 - 6. "
   ::= { gepoel2esw12OltPortEntry 1 }

gepoel2esw12OltPortLinkStatus OBJECT-TYPE
   SYNTAX      DisplayString
   MAX-ACCESS  read-only
   STATUS      current
   DESCRIPTION
       " dowm/up. "
   ::= { gepoel2esw12OltPortEntry 2 }

gepoel2esw12OltPortState OBJECT-TYPE
   SYNTAX      INTEGER (-1|0|1)
   MAX-ACCESS  read-write
   STATUS      current
   DESCRIPTION
       " 0:disable,
         1: enable.
         range : -1 - 1. "
   ::= { gepoel2esw12OltPortEntry 3 }

gepoel2esw12OltPortSpdDpxConf OBJECT-TYPE
   SYNTAX      INTEGER (-1|1|10|11|100|101|1000|1001)
   MAX-ACCESS  read-write
   STATUS      current
   DESCRIPTION
       " 1: auto nego,
         10: 10M Half,
         11: 10M Full,
         100: 100M Half,
         101: 100M Full,
         1000: 1000M Half,
         1001: 1000M Full,
         -1: not exist. "
   ::= { gepoel2esw12OltPortEntry 4 }

gepoel2esw12OltPortSpdDpx OBJECT-TYPE
   SYNTAX      DisplayString
   MAX-ACCESS  read-only
   STATUS      current
   DESCRIPTION
       " "
   ::= { gepoel2esw12OltPortEntry 5 }

gepoel2esw12OltPortFlwCtlConf OBJECT-TYPE
   SYNTAX      INTEGER (-1|0|1)
   MAX-ACCESS  read-write
   STATUS      current
   DESCRIPTION
       "0: disable
        1: enable "
   ::= { gepoel2esw12OltPortEntry 6 }

gepoel2esw12OltPortFlwCtl OBJECT-TYPE
   SYNTAX      DisplayString
   MAX-ACCESS  read-only
   STATUS      current
   DESCRIPTION
       " "
   ::= { gepoel2esw12OltPortEntry 7 }


gepoel2esw12OltStatisticsTable OBJECT-TYPE
   SYNTAX      SEQUENCE OF GEPoEL2ESW12OltStatisticsEntry
   MAX-ACCESS  not-accessible
   STATUS      current
   DESCRIPTION
       " Show Olt port configurations. "
   ::= { gepoel2esw12OltManagement 2 }

gepoel2esw12OltStatisticsEntry OBJECT-TYPE
   SYNTAX      GEPoEL2ESW12OltStatisticsEntry
   MAX-ACCESS  not-accessible
   STATUS      current
   DESCRIPTION
       ""
   INDEX    { gepoel2esw12OltStatisticsPortType, gepoel2esw12OltStatisticsQueryGroup  }
   ::= { gepoel2esw12OltStatisticsTable 1 }

GEPoEL2ESW12OltStatisticsEntry ::= SEQUENCE {
   gepoel2esw12OltStatisticsPortType                INTEGER,
   gepoel2esw12OltStatisticsQueryGroup              INTEGER,
   gepoel2esw12OltStatisticsOctet                   Counter64,
   gepoel2esw12OltStatisticsCRC8Errors              Counter64,
   gepoel2esw12OltStatisticsErrorFrameTransfer      Counter64,
   
   gepoel2esw12OltStatisticsLineCodeError           Counter64,
   gepoel2esw12OltStatisticsCorrectableFECBlock     Counter64,
   gepoel2esw12OltStatisticsUncorrectableFECBlock   Counter64,
   gepoel2esw12OltStatisticsUndersizeFrame          Counter64,
   gepoel2esw12OltStatisticsCorrectableFECBytes     Counter64,
   
   gepoel2esw12OltStatisticsPostFECGoodFrame        Counter64,
   gepoel2esw12OltStatisticsPostFECBadFrame         Counter64,
   gepoel2esw12OltStatisticsPreFECGoodFrame         Counter64,
   gepoel2esw12OltStatisticsPreFECBadFrame          Counter64,
   gepoel2esw12OltStatisticsLaserIdlePower          Counter64,
   
   gepoel2esw12OltStatisticsFECPacketTooLongEvent   Counter64,
   gepoel2esw12OltStatisticsFECBlock                Counter64,
   gepoel2esw12OltStatisticsLaserPower              Counter64,
   gepoel2esw12OltStatisticsLaserVCC                Counter64,
   gepoel2esw12OltStatisticsLaserBias               Counter64,
   
   gepoel2esw12OltStatisticsLaserTemp               Counter64,
   gepoel2esw12OltStatisticsUnicastFrame            Counter64,
   gepoel2esw12OltStatisticsMulticastFrame          Counter64,
   gepoel2esw12OltStatisticsBroadcastFrame          Counter64,
   gepoel2esw12OltStatisticsOversizetFrame          Counter64,
   
   gepoel2esw12OltStatisticsCRC32Frame              Counter64,
   gepoel2esw12OltStatisticsMPCPFrame               Counter64,
   gepoel2esw12OltStatisticsMPCPBytes               Counter64,
   gepoel2esw12OltStatisticsMPCPDiscoveryTimeout    Counter64,
   gepoel2esw12OltStatisticsMPCPDiscoveryWindow     Counter64,
   
   gepoel2esw12OltStatisticsReportFrame             Counter64,
   gepoel2esw12OltStatisticsReportFrameAbort        Counter64,
   gepoel2esw12OltStatisticsOAMFrames               Counter64,
   gepoel2esw12OltStatisticsOAMBytes                Counter64,
   gepoel2esw12OltStatisticsLlidMisMatch            Counter64,
   
   gepoel2esw12OltStatisticsUngrantedFrames         Counter64,
   gepoel2esw12OltStatisticsRegisterRequests        Counter64, 
   gepoel2esw12OltStatisticsRegisterAcks            Counter64,
   gepoel2esw12OltStatisticsGateFrame               Counter64,
   gepoel2esw12OltStatisticsReport                  Counter64,   
   
   gepoel2esw12OltStatisticsClear                   INTEGER
}

gepoel2esw12OltStatisticsPortType OBJECT-TYPE
   SYNTAX      INTEGER (1..4)
   MAX-ACCESS  not-accessible
   STATUS      current
   DESCRIPTION
       " 1: Epon-0 ,  2: Epon-1 , 3:NNI-0, 4:NNI-1.
         range : 1 - 4. "
   ::= { gepoel2esw12OltStatisticsEntry 1 }

gepoel2esw12OltStatisticsQueryGroup OBJECT-TYPE
   SYNTAX      INTEGER (1..4)
   MAX-ACCESS  not-accessible
   STATUS      current
   DESCRIPTION
       " 1: OLT Epon LIF Receive ,  2: OLT Epon LIF Transmit , 3:OLT Epon Mac Receive, 4:OLT Epon Mac Transmit.
         range : 1 - 4. "
   ::= { gepoel2esw12OltStatisticsEntry 2 }

gepoel2esw12OltStatisticsOctet OBJECT-TYPE
   SYNTAX      Counter64
   MAX-ACCESS  read-only
   STATUS      current
   DESCRIPTION
       "  "
   ::= { gepoel2esw12OltStatisticsEntry 3 }

gepoel2esw12OltStatisticsCRC8Errors OBJECT-TYPE
   SYNTAX      Counter64
   MAX-ACCESS  read-only
   STATUS      current
   DESCRIPTION
       "  "
   ::= { gepoel2esw12OltStatisticsEntry 4 }

gepoel2esw12OltStatisticsErrorFrameTransfer OBJECT-TYPE
   SYNTAX      Counter64
   MAX-ACCESS  read-only
   STATUS      current
   DESCRIPTION
       "  "
   ::= { gepoel2esw12OltStatisticsEntry 5 }

gepoel2esw12OltStatisticsLineCodeError OBJECT-TYPE
   SYNTAX      Counter64
   MAX-ACCESS  read-only
   STATUS      current
   DESCRIPTION
       "  "
   ::= { gepoel2esw12OltStatisticsEntry 6 }

gepoel2esw12OltStatisticsCorrectableFECBlock OBJECT-TYPE
   SYNTAX      Counter64
   MAX-ACCESS  read-only
   STATUS      current
   DESCRIPTION
       "  "
   ::= { gepoel2esw12OltStatisticsEntry 7 }

gepoel2esw12OltStatisticsUncorrectableFECBlock OBJECT-TYPE
   SYNTAX      Counter64
   MAX-ACCESS  read-only
   STATUS      current
   DESCRIPTION
       "  "
   ::= { gepoel2esw12OltStatisticsEntry 8 }

gepoel2esw12OltStatisticsUndersizeFrame OBJECT-TYPE
   SYNTAX      Counter64
   MAX-ACCESS  read-only
   STATUS      current
   DESCRIPTION
       "  "
   ::= { gepoel2esw12OltStatisticsEntry 9 }

gepoel2esw12OltStatisticsCorrectableFECBytes OBJECT-TYPE
   SYNTAX      Counter64
   MAX-ACCESS  read-only
   STATUS      current
   DESCRIPTION
       "  "
   ::= { gepoel2esw12OltStatisticsEntry 10 }

gepoel2esw12OltStatisticsPostFECGoodFrame OBJECT-TYPE
   SYNTAX      Counter64
   MAX-ACCESS  read-only
   STATUS      current
   DESCRIPTION
       "  "
   ::= { gepoel2esw12OltStatisticsEntry 11 }

gepoel2esw12OltStatisticsPostFECBadFrame OBJECT-TYPE
   SYNTAX      Counter64
   MAX-ACCESS  read-only
   STATUS      current
   DESCRIPTION
       "  "
   ::= { gepoel2esw12OltStatisticsEntry 12 }

gepoel2esw12OltStatisticsPreFECGoodFrame OBJECT-TYPE
   SYNTAX      Counter64
   MAX-ACCESS  read-only
   STATUS      current
   DESCRIPTION
       "  "
   ::= { gepoel2esw12OltStatisticsEntry 13 }

gepoel2esw12OltStatisticsPreFECBadFrame OBJECT-TYPE
   SYNTAX      Counter64
   MAX-ACCESS  read-only
   STATUS      current
   DESCRIPTION
       "  "
   ::= { gepoel2esw12OltStatisticsEntry 14 }

gepoel2esw12OltStatisticsLaserIdlePower OBJECT-TYPE
   SYNTAX      Counter64
   MAX-ACCESS  read-only
   STATUS      current
   DESCRIPTION
       "  "
   ::= { gepoel2esw12OltStatisticsEntry 15 }

gepoel2esw12OltStatisticsFECPacketTooLongEvent OBJECT-TYPE
   SYNTAX      Counter64
   MAX-ACCESS  read-only
   STATUS      current
   DESCRIPTION
       "  "
   ::= { gepoel2esw12OltStatisticsEntry 16 }

gepoel2esw12OltStatisticsFECBlock OBJECT-TYPE
   SYNTAX      Counter64
   MAX-ACCESS  read-only
   STATUS      current
   DESCRIPTION
       "  "
   ::= { gepoel2esw12OltStatisticsEntry 17 }

gepoel2esw12OltStatisticsLaserPower OBJECT-TYPE
   SYNTAX      Counter64
   MAX-ACCESS  read-only
   STATUS      current
   DESCRIPTION
       "  "
   ::= { gepoel2esw12OltStatisticsEntry 18 }

gepoel2esw12OltStatisticsLaserVCC OBJECT-TYPE
   SYNTAX      Counter64
   MAX-ACCESS  read-only
   STATUS      current
   DESCRIPTION
       "  "
   ::= { gepoel2esw12OltStatisticsEntry 19 }

gepoel2esw12OltStatisticsLaserBias OBJECT-TYPE
   SYNTAX      Counter64
   MAX-ACCESS  read-only
   STATUS      current
   DESCRIPTION
       "  "
   ::= { gepoel2esw12OltStatisticsEntry 20 }

gepoel2esw12OltStatisticsLaserTemp OBJECT-TYPE
   SYNTAX      Counter64
   MAX-ACCESS  read-only
   STATUS      current
   DESCRIPTION
       "  "
   ::= { gepoel2esw12OltStatisticsEntry 21 }

gepoel2esw12OltStatisticsUnicastFrame OBJECT-TYPE
   SYNTAX      Counter64
   MAX-ACCESS  read-only
   STATUS      current
   DESCRIPTION
       "  "
   ::= { gepoel2esw12OltStatisticsEntry 22 }

gepoel2esw12OltStatisticsMulticastFrame OBJECT-TYPE
   SYNTAX      Counter64
   MAX-ACCESS  read-only
   STATUS      current
   DESCRIPTION
       "  "
   ::= { gepoel2esw12OltStatisticsEntry 23 }

gepoel2esw12OltStatisticsBroadcastFrame OBJECT-TYPE
   SYNTAX      Counter64
   MAX-ACCESS  read-only
   STATUS      current
   DESCRIPTION
       "  "
   ::= { gepoel2esw12OltStatisticsEntry 24 }

gepoel2esw12OltStatisticsOversizetFrame OBJECT-TYPE
   SYNTAX      Counter64
   MAX-ACCESS  read-only
   STATUS      current
   DESCRIPTION
       "  "
   ::= { gepoel2esw12OltStatisticsEntry 25 }

gepoel2esw12OltStatisticsCRC32Frame OBJECT-TYPE
   SYNTAX      Counter64
   MAX-ACCESS  read-only
   STATUS      current
   DESCRIPTION
       "  "
   ::= { gepoel2esw12OltStatisticsEntry 26 }

gepoel2esw12OltStatisticsMPCPFrame OBJECT-TYPE
   SYNTAX      Counter64
   MAX-ACCESS  read-only
   STATUS      current
   DESCRIPTION
       "  "
   ::= { gepoel2esw12OltStatisticsEntry 27 }

gepoel2esw12OltStatisticsMPCPBytes OBJECT-TYPE
   SYNTAX      Counter64
   MAX-ACCESS  read-only
   STATUS      current
   DESCRIPTION
       "  "
   ::= { gepoel2esw12OltStatisticsEntry 28 }

gepoel2esw12OltStatisticsMPCPDiscoveryTimeout OBJECT-TYPE
   SYNTAX      Counter64
   MAX-ACCESS  read-only
   STATUS      current
   DESCRIPTION
       "  "
   ::= { gepoel2esw12OltStatisticsEntry 29 }

gepoel2esw12OltStatisticsMPCPDiscoveryWindow OBJECT-TYPE
   SYNTAX      Counter64
   MAX-ACCESS  read-only
   STATUS      current
   DESCRIPTION
       "  "
   ::= { gepoel2esw12OltStatisticsEntry 30 }

gepoel2esw12OltStatisticsReportFrame OBJECT-TYPE
   SYNTAX      Counter64
   MAX-ACCESS  read-only
   STATUS      current
   DESCRIPTION
       "  "
   ::= { gepoel2esw12OltStatisticsEntry 31 }

gepoel2esw12OltStatisticsReportFrameAbort OBJECT-TYPE
   SYNTAX      Counter64
   MAX-ACCESS  read-only
   STATUS      current
   DESCRIPTION
       "  "
   ::= { gepoel2esw12OltStatisticsEntry 32 }

gepoel2esw12OltStatisticsOAMFrames OBJECT-TYPE
   SYNTAX      Counter64
   MAX-ACCESS  read-only
   STATUS      current
   DESCRIPTION
       "  "
   ::= { gepoel2esw12OltStatisticsEntry 33 }

gepoel2esw12OltStatisticsOAMBytes OBJECT-TYPE
   SYNTAX      Counter64
   MAX-ACCESS  read-only
   STATUS      current
   DESCRIPTION
       "  "
   ::= { gepoel2esw12OltStatisticsEntry 34 }

gepoel2esw12OltStatisticsLlidMisMatch OBJECT-TYPE
   SYNTAX      Counter64
   MAX-ACCESS  read-only
   STATUS      current
   DESCRIPTION
       "  "
   ::= { gepoel2esw12OltStatisticsEntry 35 }

gepoel2esw12OltStatisticsUngrantedFrames OBJECT-TYPE
   SYNTAX      Counter64
   MAX-ACCESS  read-only
   STATUS      current
   DESCRIPTION
       "  "
   ::= { gepoel2esw12OltStatisticsEntry 36 }

gepoel2esw12OltStatisticsRegisterRequests OBJECT-TYPE
   SYNTAX      Counter64
   MAX-ACCESS  read-only
   STATUS      current
   DESCRIPTION
       "  "
   ::= { gepoel2esw12OltStatisticsEntry 37 }   

gepoel2esw12OltStatisticsRegisterAcks OBJECT-TYPE
   SYNTAX      Counter64
   MAX-ACCESS  read-only
   STATUS      current
   DESCRIPTION
       "  "
   ::= { gepoel2esw12OltStatisticsEntry 38 }

gepoel2esw12OltStatisticsGateFrame OBJECT-TYPE
   SYNTAX      Counter64
   MAX-ACCESS  read-only
   STATUS      current
   DESCRIPTION
       "  "
   ::= { gepoel2esw12OltStatisticsEntry 39 }

gepoel2esw12OltStatisticsReport OBJECT-TYPE
   SYNTAX      Counter64
   MAX-ACCESS  read-only
   STATUS      current
   DESCRIPTION
       "  "
   ::= { gepoel2esw12OltStatisticsEntry 40 }

gepoel2esw12OltStatisticsClear OBJECT-TYPE
   SYNTAX      INTEGER (0|1)
   MAX-ACCESS  read-write
   STATUS      current
   DESCRIPTION
       "0: no action
        1: clear "
   ::= { gepoel2esw12OltStatisticsEntry 41 }


gepoel2esw12OltInformation                                                  OBJECT IDENTIFIER ::= { gepoel2esw12OltManagement 3 }

gepoel2esw12OltChipID OBJECT-TYPE
   SYNTAX       DisplayString
   MAX-ACCESS   read-only
   STATUS       current
   DESCRIPTION
       ""
 ::= { gepoel2esw12OltInformation 1 }

gepoel2esw12OltFirmwareVersion OBJECT-TYPE
   SYNTAX       DisplayString
   MAX-ACCESS   read-only
   STATUS       current
   DESCRIPTION
       ""
 ::= { gepoel2esw12OltInformation 2 }

gepoel2esw12OltPersonalityVersion OBJECT-TYPE
   SYNTAX       DisplayString
   MAX-ACCESS   read-only
   STATUS       current
   DESCRIPTION
       ""
 ::= { gepoel2esw12OltInformation 3 }

gepoel2esw12OltOltApp0Version OBJECT-TYPE
   SYNTAX       DisplayString
   MAX-ACCESS   read-only
   STATUS       current
   DESCRIPTION
       ""
 ::= { gepoel2esw12OltInformation 4 }

gepoel2esw12OltOltApp1Version OBJECT-TYPE
   SYNTAX       DisplayString
   MAX-ACCESS   read-only
   STATUS       current
   DESCRIPTION
       ""
 ::= { gepoel2esw12OltInformation 5 }


gepoel2esw12OltGreenPonConf                                                  OBJECT IDENTIFIER ::= { gepoel2esw12OltManagement 4 }

gepoel2esw12OltGreenPonTable OBJECT-TYPE
   SYNTAX      SEQUENCE OF GEPoEL2ESW12OltGreenPonEntry
   MAX-ACCESS  not-accessible
   STATUS      current
   DESCRIPTION
       " Show Olt Green Pon. "
   ::= { gepoel2esw12OltGreenPonConf 1 }

gepoel2esw12OltGreenPonEntry OBJECT-TYPE
   SYNTAX      GEPoEL2ESW12OltGreenPonEntry
   MAX-ACCESS  not-accessible
   STATUS      current
   DESCRIPTION
       ""
   INDEX    { gepoel2esw12OltGreenPonIndex }
   ::= { gepoel2esw12OltGreenPonTable 1 }

GEPoEL2ESW12OltGreenPonEntry ::= SEQUENCE {
   gepoel2esw12OltGreenPonIndex                         INTEGER,
   gepoel2esw12OltGreenPonstate                         INTEGER,
   gepoel2esw12OltGreenPonSleepAfterNoTraffic           INTEGER,
   gepoel2esw12OltGreenPonOffTime                       INTEGER,
   gepoel2esw12OltGreenPonMinOnTime                     INTEGER,
   gepoel2esw12OltGreenPonMinOnuOffTime                 INTEGER,
   gepoel2esw12OltGreenPonSleepCheckTime                INTEGER,
   gepoel2esw12OltGreenPonTimeForOnuToBeginToSleep      INTEGER,
   gepoel2esw12OltGreenPonSleepGraceTimeAfterWakeup     INTEGER,
   gepoel2esw12OltGreenPonProvisionOnu                  INTEGER,
   gepoel2esw12OltGreenPonUnprovisionOnu                INTEGER
}

gepoel2esw12OltGreenPonIndex OBJECT-TYPE
   SYNTAX      INTEGER (1..2)
   MAX-ACCESS  not-accessible
   STATUS      current
   DESCRIPTION
       " 1: Epon-0,
         2: Epon-1.
         range : 1 - 2. "
   ::= { gepoel2esw12OltGreenPonEntry 1 }

gepoel2esw12OltGreenPonstate OBJECT-TYPE
   SYNTAX      INTEGER (0|1)
   MAX-ACCESS  read-write
   STATUS      current
   DESCRIPTION
       " 0:disable,
         1:enable. "
   ::= { gepoel2esw12OltGreenPonEntry 2 }

gepoel2esw12OltGreenPonSleepAfterNoTraffic OBJECT-TYPE
   SYNTAX      INTEGER (9999)
   MAX-ACCESS  read-write
   STATUS      current
   DESCRIPTION
       " "
   ::= { gepoel2esw12OltGreenPonEntry 3 }

gepoel2esw12OltGreenPonOffTime OBJECT-TYPE
   SYNTAX      INTEGER (9999)
   MAX-ACCESS  read-write
   STATUS      current
   DESCRIPTION
       "  "
   ::= { gepoel2esw12OltGreenPonEntry 4 }
   
gepoel2esw12OltGreenPonMinOnTime OBJECT-TYPE
   SYNTAX      INTEGER (9999)
   MAX-ACCESS  read-write
   STATUS      current
   DESCRIPTION
       "  "
   ::= { gepoel2esw12OltGreenPonEntry 5 }

gepoel2esw12OltGreenPonMinOnuOffTime OBJECT-TYPE
   SYNTAX      INTEGER (9999)
   MAX-ACCESS  read-write
   STATUS      current
   DESCRIPTION
       "  "
   ::= { gepoel2esw12OltGreenPonEntry 6 }   
   
gepoel2esw12OltGreenPonSleepCheckTime OBJECT-TYPE
   SYNTAX      INTEGER (9999)
   MAX-ACCESS  read-write
   STATUS      current
   DESCRIPTION
       "  "
   ::= { gepoel2esw12OltGreenPonEntry 7 }   

gepoel2esw12OltGreenPonTimeForOnuToBeginToSleep OBJECT-TYPE
   SYNTAX      INTEGER (9999)
   MAX-ACCESS  read-write
   STATUS      current
   DESCRIPTION
       "  "
   ::= { gepoel2esw12OltGreenPonEntry 8 }

gepoel2esw12OltGreenPonSleepGraceTimeAfterWakeup OBJECT-TYPE
   SYNTAX      INTEGER (9999)
   MAX-ACCESS  read-write
   STATUS      current
   DESCRIPTION
       "  "
   ::= { gepoel2esw12OltGreenPonEntry 9 }

gepoel2esw12OltGreenPonProvisionOnu OBJECT-TYPE
   SYNTAX      INTEGER (0|1)
   MAX-ACCESS  read-write
   STATUS      current
   DESCRIPTION
       " "
   ::= { gepoel2esw12OltGreenPonEntry 10 }
   
gepoel2esw12OltGreenPonUnprovisionOnu OBJECT-TYPE
   SYNTAX      INTEGER (0|1)
   MAX-ACCESS  read-write
   STATUS      current
   DESCRIPTION
       "  "
   ::= { gepoel2esw12OltGreenPonEntry 11 }




gepoel2esw12OltPowerSavingReportTable OBJECT-TYPE
   SYNTAX      SEQUENCE OF GEPoEL2ESW12OltPowerSavingReportEntry
   MAX-ACCESS  not-accessible
   STATUS      current
   DESCRIPTION
       " Show Olt port configurations. "
   ::= { gepoel2esw12OltGreenPonConf 2 }

gepoel2esw12OltPowerSavingReportEntry OBJECT-TYPE
   SYNTAX      GEPoEL2ESW12OltPowerSavingReportEntry
   MAX-ACCESS  not-accessible
   STATUS      current
   DESCRIPTION
       ""
   INDEX    { gepoel2esw12OltPowerSavingReportIndex  }
   ::= { gepoel2esw12OltPowerSavingReportTable 1 }

GEPoEL2ESW12OltPowerSavingReportEntry ::= SEQUENCE {
   gepoel2esw12OltPowerSavingReportIndex      INTEGER,
   gepoel2esw12OltPowerSavingReportOnuMac     MacAddress,
   gepoel2esw12OltPowerSavingReportCandidate  INTEGER,
   gepoel2esw12OltPowerSavingReportTimeAsleep INTEGER,
   gepoel2esw12OltPowerSavingReportTimeActive INTEGER
}

gepoel2esw12OltPowerSavingReportIndex OBJECT-TYPE
   SYNTAX       INTEGER
   MAX-ACCESS   not-accessible
   STATUS       current
   DESCRIPTION
       " "
 ::= { gepoel2esw12OltPowerSavingReportEntry 1 }
 
gepoel2esw12OltPowerSavingReportOnuMac OBJECT-TYPE
   SYNTAX       DisplayString
   MAX-ACCESS   read-only
   STATUS       current
   DESCRIPTION
       " "
 ::= { gepoel2esw12OltPowerSavingReportEntry 2 }

gepoel2esw12OltPowerSavingReportCandidate OBJECT-TYPE
   SYNTAX       INTEGER (0|1)
   MAX-ACCESS   read-only
   STATUS       current
   DESCRIPTION
       "  "
 ::= { gepoel2esw12OltPowerSavingReportEntry 3 }

gepoel2esw12OltPowerSavingReportAsleep OBJECT-TYPE
   SYNTAX       INTEGER (0|1)
   MAX-ACCESS   read-only
   STATUS       current
   DESCRIPTION
       "  "
 ::= { gepoel2esw12OltPowerSavingReportEntry 4 }
 
gepoel2esw12OltPowerSavingReportTimeAsleep OBJECT-TYPE
   SYNTAX       Counter
   MAX-ACCESS   read-only
   STATUS       current
   DESCRIPTION
       "  "
 ::= { gepoel2esw12OltPowerSavingReportEntry 5 }

gepoel2esw12OltPowerSavingReportTimeActive OBJECT-TYPE
   SYNTAX       Counter
   MAX-ACCESS   read-only
   STATUS       current
   DESCRIPTION
       "  "
 ::= { gepoel2esw12OltPowerSavingReportEntry 6 }

gepoel2esw12OltBridgeConfig                                         OBJECT IDENTIFIER ::= { gepoel2esw12OltManagement 5 }

gepoel2esw12OltBridgingConfAgeLimit OBJECT-TYPE
   SYNTAX      INTEGER
   MAX-ACCESS  read-write
   STATUS      current
   DESCRIPTION
       " 0:disable (Units 9.375ms),Age Limit: 0~2,000,000,000(default:0 disable aging). "
   ::= { gepoel2esw12OltBridgeConfig 1 } 

gepoel2esw12OltBridgingConfAllowVlanOnSimple OBJECT-TYPE
   SYNTAX      INTEGER
   MAX-ACCESS  read-write
   STATUS      current
   DESCRIPTION
       "0: disable, 1: enable"
   ::= { gepoel2esw12OltBridgeConfig 2 } 

gepoel2esw12OltDBA                                                  OBJECT IDENTIFIER ::= { gepoel2esw12OltManagement 6 }

gepoel2esw12OltAggregateShaperTable OBJECT-TYPE
   SYNTAX      SEQUENCE OF GEPoEL2ESW12OltAggregateShaperEntry
   MAX-ACCESS  not-accessible
   STATUS      current
   DESCRIPTION
       " Show Olt Aggregate Shaper Table. "
   ::= { gepoel2esw12OltDBA 1 }

gepoel2esw12OltAggregateShaperEntry OBJECT-TYPE
   SYNTAX      GEPoEL2ESW12OltAggregateShaperEntry
   MAX-ACCESS  not-accessible
   STATUS      current
   DESCRIPTION
       ""
   INDEX    { gepoel2esw12OltAggregateShaperIndex }
   ::= { gepoel2esw12OltAggregateShaperTable 1 }

GEPoEL2ESW12OltAggregateShaperEntry ::= SEQUENCE {
   gepoel2esw12OltAggregateShaperIndex          INTEGER,
   gepoel2esw12OltAggregateShaperBwEnable       INTEGER,
   gepoel2esw12OltAggregateShaperMaxBw          INTEGER,
   gepoel2esw12OltAggregateShaperMaxBurst       INTEGER
}

gepoel2esw12OltAggregateShaperIndex OBJECT-TYPE
   SYNTAX      INTEGER (1..6)
   MAX-ACCESS  not-accessible
   STATUS      current
   DESCRIPTION
       " 1: Epon-0: Ingress/DBA,
         2: Epon-1: Ingress/DBA,
         3: Epon-0: Egress,
         4: Epon-1: Egress,
         5: NNI-0: Egress,
         6: NNI-1: Egress.
         range : 1 - 6. "
   ::= { gepoel2esw12OltAggregateShaperEntry 1 }

gepoel2esw12OltAggregateShaperBwEnable OBJECT-TYPE
   SYNTAX      INTEGER (0|1)
   MAX-ACCESS  read-write
   STATUS      current
   DESCRIPTION
       " 0:disable,
         1:enable. "
   ::= { gepoel2esw12OltAggregateShaperEntry 2 }

gepoel2esw12OltAggregateShaperMaxBw OBJECT-TYPE
   SYNTAX      INTEGER (0|256..1000000)
   MAX-ACCESS  read-write
   STATUS      current
   DESCRIPTION
       "  "
   ::= { gepoel2esw12OltAggregateShaperEntry 3 }
   
gepoel2esw12OltAggregateShaperMaxBurst OBJECT-TYPE
   SYNTAX      INTEGER (0..256)
   MAX-ACCESS  read-write
   STATUS      current
   DESCRIPTION
       "  "
   ::= { gepoel2esw12OltAggregateShaperEntry 4 }   


gepoel2esw12OltDropDownWeightsTable OBJECT-TYPE
   SYNTAX      SEQUENCE OF GEPoEL2ESW12OltDropDownWeightsEntry
   MAX-ACCESS  not-accessible
   STATUS      current
   DESCRIPTION
       " Show Olt Drop Down Weights Table. "
   ::= { gepoel2esw12OltDBA 2 }

gepoel2esw12OltDropDownWeightsEntry OBJECT-TYPE
   SYNTAX      GEPoEL2ESW12OltDropDownWeightsEntry
   MAX-ACCESS  not-accessible
   STATUS      current
   DESCRIPTION
       ""
   INDEX    { gepoel2esw12OltDropDownWeightsIndex }
   ::= { gepoel2esw12OltDropDownWeightsTable 1 }

GEPoEL2ESW12OltDropDownWeightsEntry ::= SEQUENCE {
   gepoel2esw12OltDropDownWeightsIndex      INTEGER,
   gepoel2esw12OltDropDownLevel0            INTEGER,
   gepoel2esw12OltDropDownLevel1            INTEGER
}

gepoel2esw12OltDropDownWeightsIndex OBJECT-TYPE
   SYNTAX      INTEGER (1..6)
   MAX-ACCESS  not-accessible
   STATUS      current
   DESCRIPTION
       " 1: Epon-0: Ingress/DBA,
         2: Epon-1: Ingress/DBA,
         3: Epon-0: Egress,
         4: Epon-1: Egress,
         5: NNI-0: Egress,
         6: NNI-1: Egress.
         range : 1 - 6. "
   ::= { gepoel2esw12OltDropDownWeightsEntry 1 }

gepoel2esw12OltDropDownLevel1 OBJECT-TYPE
   SYNTAX      INTEGER (0..256)
   MAX-ACCESS  read-write
   STATUS      current
   DESCRIPTION
       " Ingress/DBA -> Level 0, Level 1 : 0~256(default:16) .
         Egress -> Level 0, Level 1 : 0~256(default:0) . "
   ::= { gepoel2esw12OltDropDownWeightsEntry 2 }

gepoel2esw12OltDropDownLevel2 OBJECT-TYPE
   SYNTAX      INTEGER (0..256)
   MAX-ACCESS  read-write
   STATUS      current
   DESCRIPTION
       " 0:defaultIngress/DBA -> Level 0, Level 1 : 0~256(default:16) 
         Egress -> Level 0, Level 1 : 0~256(default:0)  . "
   ::= { gepoel2esw12OltDropDownWeightsEntry 3 }

gepoel2esw12OltDropDownLevel3 OBJECT-TYPE
   SYNTAX      INTEGER (0..256)
   MAX-ACCESS  read-write
   STATUS      current
   DESCRIPTION
       " 0:defaultIngress/DBA -> Level 0, Level 1 : 0~256(default:16) 
         Egress -> Level 0, Level 1 : 0~256(default:0)  . "
   ::= { gepoel2esw12OltDropDownWeightsEntry 4 }
   
gepoel2esw12OltDropDownLevel4 OBJECT-TYPE
   SYNTAX      INTEGER (0..256)
   MAX-ACCESS  read-write
   STATUS      current
   DESCRIPTION
       " 0:defaultIngress/DBA -> Level 0, Level 1 : 0~256(default:16) 
         Egress -> Level 0, Level 1 : 0~256(default:0)  . "
   ::= { gepoel2esw12OltDropDownWeightsEntry 5 }   
   
gepoel2esw12OltDropDownLevel5 OBJECT-TYPE
   SYNTAX      INTEGER (0..256)
   MAX-ACCESS  read-write
   STATUS      current
   DESCRIPTION
       " 0:defaultIngress/DBA -> Level 0, Level 1 : 0~256(default:16) 
         Egress -> Level 0, Level 1 : 0~256(default:0)  . "
   ::= { gepoel2esw12OltDropDownWeightsEntry 6 }   
   
gepoel2esw12OltDropDownLevel6 OBJECT-TYPE
   SYNTAX      INTEGER (0..256)
   MAX-ACCESS  read-write
   STATUS      current
   DESCRIPTION
       " 0:defaultIngress/DBA -> Level 0, Level 1 : 0~256(default:16) 
         Egress -> Level 0, Level 1 : 0~256(default:0)  . "
   ::= { gepoel2esw12OltDropDownWeightsEntry 7 }   

gepoel2esw12OltDropDownLevel7 OBJECT-TYPE
   SYNTAX      INTEGER (0..256)
   MAX-ACCESS  read-write
   STATUS      current
   DESCRIPTION
       " 0:defaultIngress/DBA -> Level 0, Level 1 : 0~256(default:16) 
         Egress -> Level 0, Level 1 : 0~256(default:0)  . "
   ::= { gepoel2esw12OltDropDownWeightsEntry 8 }   
  

gepoel2esw12OltPollingRateTable OBJECT-TYPE
   SYNTAX      SEQUENCE OF GEPoEL2ESW12OltPollingRateEntry
   MAX-ACCESS  not-accessible
   STATUS      current
   DESCRIPTION
       " Show Olt Polling Rate Table. "
   ::= { gepoel2esw12OltDBA 3 }

gepoel2esw12OltPollingRateEntry OBJECT-TYPE
   SYNTAX      GEPoEL2ESW12OltPollingRateEntry
   MAX-ACCESS  not-accessible
   STATUS      current
   DESCRIPTION
       ""
   INDEX    { gepoel2esw12OltPollingRateIndex }
   ::= { gepoel2esw12OltPollingRateTable 1 }

GEPoEL2ESW12OltPollingRateEntry ::= SEQUENCE {
   gepoel2esw12OltPollingRateIndex      INTEGER,
   gepoel2esw12OltPollingRateLevel0     INTEGER,
   gepoel2esw12OltPollingRateLevel1     INTEGER,
   gepoel2esw12OltPollingRateLevel2     INTEGER,
   gepoel2esw12OltPollingRateLevel3     INTEGER,
   gepoel2esw12OltPollingRateLevel4     INTEGER,
   gepoel2esw12OltPollingRateLevel5     INTEGER,
   gepoel2esw12OltPollingRateLevel6     INTEGER,
   gepoel2esw12OltPollingRateLevel7     INTEGER
}

gepoel2esw12OltPollingRateIndex OBJECT-TYPE
   SYNTAX      INTEGER (1..2)
   MAX-ACCESS  not-accessible
   STATUS      current
   DESCRIPTION
       " 1: Epon-0,
         2: Epon-1. "
   ::= { gepoel2esw12OltPollingRateEntry 1 }

gepoel2esw12OltPollingRateLevel0 OBJECT-TYPE
   SYNTAX      INTEGER (0..256)
   MAX-ACCESS  read-only
   STATUS      current
   DESCRIPTION
       " range : 0~256. "
   ::= { gepoel2esw12OltPollingRateEntry 2 }

gepoel2esw12OltPollingRateLevel1 OBJECT-TYPE
   SYNTAX      INTEGER (0..256)
   MAX-ACCESS  read-write
   STATUS      current
   DESCRIPTION
       " range : 0~256. "
   ::= { gepoel2esw12OltPollingRateEntry 3 }

gepoel2esw12OltPollingRateLevel2 OBJECT-TYPE
   SYNTAX      INTEGER (0..256)
   MAX-ACCESS  read-write
   STATUS      current
   DESCRIPTION
       " range : 0~256. "
   ::= { gepoel2esw12OltPollingRateEntry 4 }

gepoel2esw12OltPollingRateLevel3 OBJECT-TYPE
   SYNTAX      INTEGER (0..256)
   MAX-ACCESS  read-write
   STATUS      current
   DESCRIPTION
       " range : 0~256. "
   ::= { gepoel2esw12OltPollingRateEntry 5 }
   
gepoel2esw12OltPollingRateLevel4 OBJECT-TYPE
   SYNTAX      INTEGER (0..256)
   MAX-ACCESS  read-write
   STATUS      current
   DESCRIPTION
       " range : 0~256. "
   ::= { gepoel2esw12OltPollingRateEntry 6 }   
   
gepoel2esw12OltPollingRateLevel5 OBJECT-TYPE
   SYNTAX      INTEGER (0..256)
   MAX-ACCESS  read-write
   STATUS      current
   DESCRIPTION
       " range : 0~256. "
   ::= { gepoel2esw12OltPollingRateEntry 7 }   
   
gepoel2esw12OltPollingRateLevel6 OBJECT-TYPE
   SYNTAX      INTEGER (0..256)
   MAX-ACCESS  read-write
   STATUS      current
   DESCRIPTION
       " range : 0~256. "
   ::= { gepoel2esw12OltPollingRateEntry 8 }

gepoel2esw12OltPollingRateLevel7 OBJECT-TYPE
   SYNTAX      INTEGER (0..256)
   MAX-ACCESS  read-write
   STATUS      current
   DESCRIPTION
       " range : 0~256. "
   ::= { gepoel2esw12OltPollingRateEntry 9 }


gepoel2esw12OltIgmpProxy                                                  OBJECT IDENTIFIER ::= { gepoel2esw12OltManagement 7 }

gepoel2esw12OltMaxIGMPGroup OBJECT-TYPE
   SYNTAX      INTEGER (0..4096)
   MAX-ACCESS  read-write
   STATUS      current
   DESCRIPTION
       "  "
   ::= { gepoel2esw12OltIgmpProxy 1 } 
   
gepoel2esw12OltGlobalBwPollSize OBJECT-TYPE
   SYNTAX      INTEGER (0..2000000)
   MAX-ACCESS  read-write
   STATUS      current
   DESCRIPTION
       "  "
   ::= { gepoel2esw12OltIgmpProxy 2 } 
   
gepoel2esw12OltIgmpCaptureAllMode OBJECT-TYPE
   SYNTAX      INTEGER (0..1)
   MAX-ACCESS  read-write
   STATUS      current
   DESCRIPTION
       "  "
   ::= { gepoel2esw12OltIgmpProxy 3 }  
   
gepoel2esw12OltIgmpDAForwarding OBJECT-TYPE
   SYNTAX      INTEGER (0..1)
   MAX-ACCESS  read-write
   STATUS      current
   DESCRIPTION
       "  "
   ::= { gepoel2esw12OltIgmpProxy 4 } 
   
gepoel2esw12OltIgmpSAForwarding OBJECT-TYPE
   SYNTAX      INTEGER (0..1)
   MAX-ACCESS  read-write
   STATUS      current
   DESCRIPTION
       "  "
   ::= { gepoel2esw12OltIgmpProxy 5 }         


gepoel2esw12OltNetworkParameters                                    OBJECT IDENTIFIER ::= { gepoel2esw12OltManagement 8 }

gepoel2esw12OltOamParameters                                        OBJECT IDENTIFIER ::= { gepoel2esw12OltNetworkParameters 1 }

gepoel2esw12OltMaxOamRate OBJECT-TYPE
   SYNTAX      INTEGER (-1..255)
   MAX-ACCESS  read-write
   STATUS      current
   DESCRIPTION
       "  "
   ::= { gepoel2esw12OltOamParameters 1 } 
   
gepoel2esw12OltMinOamRate OBJECT-TYPE
   SYNTAX      INTEGER (-1..255)
   MAX-ACCESS  read-write
   STATUS      current
   DESCRIPTION
       "  "
   ::= { gepoel2esw12OltOamParameters 2 } 
   
gepoel2esw12OltLoopbackTimeout OBJECT-TYPE
   SYNTAX      INTEGER (-1|10..65535)
   MAX-ACCESS  read-write
   STATUS      current
   DESCRIPTION
       "  "
   ::= { gepoel2esw12OltOamParameters 3 }    
   
gepoel2esw12OltVlanParameters                                        OBJECT IDENTIFIER ::= { gepoel2esw12OltNetworkParameters 2 }

gepoel2esw12OltVlanEtherType OBJECT-TYPE
   SYNTAX      DisplayString
   MAX-ACCESS  read-write
   STATUS      current
   DESCRIPTION
       " default: 0x8100-unsigned short(2 bytes). "
   ::= { gepoel2esw12OltVlanParameters 1 }   

gepoel2esw12OltTagUp OBJECT-TYPE
   SYNTAX      INTEGER (0|1)
   MAX-ACCESS  read-write
   STATUS      current
   DESCRIPTION
       "  "
   ::= { gepoel2esw12OltVlanParameters 2 } 

gepoel2esw12OltTagDown OBJECT-TYPE
   SYNTAX      INTEGER (0|1)
   MAX-ACCESS  read-write
   STATUS      current
   DESCRIPTION
       "  "
   ::= { gepoel2esw12OltVlanParameters 3 }

gepoel2esw12OltMpcpParametersTable OBJECT-TYPE
   SYNTAX      SEQUENCE OF GEPoEL2ESW12OltMpcpParametersEntry
   MAX-ACCESS  not-accessible
   STATUS      current
   DESCRIPTION
       " Show Olt Mpcp Parameters Table. "
   ::= { gepoel2esw12OltNetworkParameters 3 }

gepoel2esw12OltMpcpParametersEntry OBJECT-TYPE
   SYNTAX      GEPoEL2ESW12OltMpcpParametersEntry
   MAX-ACCESS  not-accessible
   STATUS      current
   DESCRIPTION
       ""
   INDEX    { gepoel2esw12OltMpcpParametersIndex }
   ::= { gepoel2esw12OltMpcpParametersTable 1 }

GEPoEL2ESW12OltMpcpParametersEntry ::= SEQUENCE {
   gepoel2esw12OltMpcpParametersIndex       INTEGER,
   gepoel2esw12OltMpcpDiscoveryPeriod       INTEGER,
   gepoel2esw12OltMpcpDiscoveryWindow       INTEGER
}

gepoel2esw12OltMpcpParametersIndex OBJECT-TYPE
   SYNTAX      INTEGER (1..2)
   MAX-ACCESS  not-accessible
   STATUS      current
   DESCRIPTION
       " 1: Epon-0,
         2: Epon-1. "
   ::= { gepoel2esw12OltMpcpParametersEntry 1 }

gepoel2esw12OltMpcpDiscoveryPeriod OBJECT-TYPE
   SYNTAX      INTEGER (1..65535)
   MAX-ACCESS  read-only
   STATUS      current
   DESCRIPTION
       " range : 1~65535. "
   ::= { gepoel2esw12OltMpcpParametersEntry 2 }

gepoel2esw12OltMpcpDiscoveryWindow OBJECT-TYPE
   SYNTAX      INTEGER (84..131070)
   MAX-ACCESS  read-write
   STATUS      current
   DESCRIPTION
       " range : 84~131070. "
   ::= { gepoel2esw12OltMpcpParametersEntry 3 } 


gepoel2esw12OltOperation                                    OBJECT IDENTIFIER ::= { gepoel2esw12OltManagement 9 }

gepoel2esw12OltEnable OBJECT-TYPE
   SYNTAX      INTEGER (0|1)
   MAX-ACCESS  read-write
   STATUS      current
   DESCRIPTION
       " 0: do nothing, 1: enable olt traffic. "
   ::= { gepoel2esw12OltOperation 1 } 
   
gepoel2esw12OltDisable OBJECT-TYPE
   SYNTAX      INTEGER (0|1)
   MAX-ACCESS  read-write
   STATUS      current
   DESCRIPTION
       " 0: do nothing, 1: disable olt traffic. "
   ::= { gepoel2esw12OltOperation 2 } 


gepoel2esw12OltBlockLinkListTable OBJECT-TYPE
   SYNTAX      SEQUENCE OF GEPoEL2ESW12OltBlockLinkListEntry
   MAX-ACCESS  not-accessible
   STATUS      current
   DESCRIPTION
       " Show Olt Block Link List Table. "
   ::= { gepoel2esw12OltManagement 10 }

gepoel2esw12OltBlockLinkListEntry OBJECT-TYPE
   SYNTAX      GEPoEL2ESW12OltBlockLinkListEntry
   MAX-ACCESS  not-accessible
   STATUS      current
   DESCRIPTION
       ""
   INDEX    { gepoel2esw12OltBlockLinkIndex }
   ::= { gepoel2esw12OltBlockLinkListTable 1 }

GEPoEL2ESW12OltBlockLinkListEntry ::= SEQUENCE {
   gepoel2esw12OltBlockLinkIndex        INTEGER,
   gepoel2esw12OltBlockLinkLabel        MacAddress,
   gepoel2esw12OltBlockLinkUnblock      INTEGER
}

gepoel2esw12OltBlockLinkIndex OBJECT-TYPE
   SYNTAX      INTEGER (1..240)
   MAX-ACCESS  not-accessible
   STATUS      current
   DESCRIPTION
       " index. "
   ::= { gepoel2esw12OltBlockLinkListEntry 1 }

gepoel2esw12OltBlockLinkLabel OBJECT-TYPE
   SYNTAX      MacAddress
   MAX-ACCESS  read-only
   STATUS      current
   DESCRIPTION
       "  "
   ::= { gepoel2esw12OltBlockLinkListEntry 2 }

gepoel2esw12OltBlockLinkUnblock OBJECT-TYPE
   SYNTAX      INTEGER (0|1)
   MAX-ACCESS  read-write
   STATUS      current
   DESCRIPTION
       " 0: do nothing, 1:unblock. "
   ::= { gepoel2esw12OltBlockLinkListEntry 3 }   


gepoel2esw12OltAllKnownLinkProvision                                                  OBJECT IDENTIFIER ::= { gepoel2esw12OltManagement 11 }

gepoel2esw12OltProvisionInOltTable OBJECT-TYPE
   SYNTAX      SEQUENCE OF GEPoEL2ESW12OltProvisionInOltEntry
   MAX-ACCESS  not-accessible
   STATUS      current
   DESCRIPTION
       "  "
   ::= { gepoel2esw12OltAllKnownLinkProvision 1 }

gepoel2esw12OltProvisionInOltEntry OBJECT-TYPE
   SYNTAX      GEPoEL2ESW12OltProvisionInOltEntry
   MAX-ACCESS  not-accessible
   STATUS      current
   DESCRIPTION
       ""
   INDEX    { gepoel2esw12ProvInOltIndex  }
   ::= { gepoel2esw12OltProvisionInOltTable 1 }

GEPoEL2ESW12OltProvisionInOltEntry ::= SEQUENCE {
   gepoel2esw12ProvInOltIndex           INTEGER,
   gepoel2esw12ProvInOltLinkLabel       MacAddress,
   gepoel2esw12ProvInOltBridge          INTEGER,
   gepoel2esw12ProvInOltSourceEpon      INTEGER,
   gepoel2esw12ProvInOltDestNNI         INTEGER,
   gepoel2esw12ProvInOltVlan            DisplayString,
   gepoel2esw12DelProvInOlt             INTEGER
}

gepoel2esw12ProvInOltIndex OBJECT-TYPE
   SYNTAX      INTEGER (1..480)
   MAX-ACCESS  not-accessible
   STATUS      current
   DESCRIPTION
       "  "
   ::= { gepoel2esw12OltProvisionInOltEntry 1 }

gepoel2esw12ProvInOltLinkLabel OBJECT-TYPE
   SYNTAX      MacAddress
   MAX-ACCESS  read-only
   STATUS      current
   DESCRIPTION
       " "
   ::= { gepoel2esw12OltProvisionInOltEntry 2 }

gepoel2esw12ProvInOltBridge OBJECT-TYPE
   SYNTAX      INTEGER
   MAX-ACCESS  read-only
   STATUS      current
   DESCRIPTION
       "  "
   ::= { gepoel2esw12OltProvisionInOltEntry 3 }

gepoel2esw12ProvInOltSourceEpon OBJECT-TYPE
   SYNTAX      INTEGER (-1..15)
   MAX-ACCESS  read-only
   STATUS      current
   DESCRIPTION
       "  "
   ::= { gepoel2esw12OltProvisionInOltEntry 4 }

gepoel2esw12ProvInOltDestNNI OBJECT-TYPE
   SYNTAX      INTEGER (1..2)
   MAX-ACCESS  read-only
   STATUS      current
   DESCRIPTION
       "  "
   ::= { gepoel2esw12OltProvisionInOltEntry 5 }

gepoel2esw12ProvInOltVlan OBJECT-TYPE
   SYNTAX      DisplayString
   MAX-ACCESS  read-only
   STATUS      current
   DESCRIPTION
       " (1..4094) "
   ::= { gepoel2esw12OltProvisionInOltEntry 6 }

gepoel2esw12DelProvInOlt OBJECT-TYPE
   SYNTAX      INTEGER (0|1)
   MAX-ACCESS  read-only
   STATUS      current
   DESCRIPTION
       " 0: do nothing, 1:clear provsion in olt. "
   ::= { gepoel2esw12OltProvisionInOltEntry 7 }


gepoel2esw12OltProvisionInHostTable OBJECT-TYPE
   SYNTAX      SEQUENCE OF GEPoEL2ESW12OltProvisionInHostEntry
   MAX-ACCESS  not-accessible
   STATUS      current
   DESCRIPTION
       "  "
   ::= { gepoel2esw12OltAllKnownLinkProvision 2 }

gepoel2esw12OltProvisionInHostEntry OBJECT-TYPE
   SYNTAX      GEPoEL2ESW12OltProvisionInHostEntry
   MAX-ACCESS  not-accessible
   STATUS      current
   DESCRIPTION
       ""
   INDEX    { gepoel2esw12ProvInHostEponPort, gepoel2esw12ProvInHostIndex }
   ::= { gepoel2esw12OltProvisionInHostTable 1 }

GEPoEL2ESW12OltProvisionInHostEntry ::= SEQUENCE {
   gepoel2esw12ProvInHostEponPort       INTEGER,
   gepoel2esw12ProvInHostIndex          INTEGER,
   gepoel2esw12ProvInHostLinkLabel      MacAddress,
   gepoel2esw12ProvInHostBridge         INTEGER,
   gepoel2esw12ProvInHostBridgeDestNNI  INTEGER,
   gepoel2esw12ProvInHostVlan           DisplayString,
   gepoel2esw12DelProvInHost            INTEGER
}

gepoel2esw12ProvInHostEponPort OBJECT-TYPE
   SYNTAX      INTEGER (1..2)
   MAX-ACCESS  not-accessible
   STATUS      current
   DESCRIPTION
       "  "
   ::= { gepoel2esw12OltProvisionInHostEntry 1 }

gepoel2esw12ProvInHostIndex OBJECT-TYPE
   SYNTAX      INTEGER
   MAX-ACCESS  not-accessible
   STATUS      current
   DESCRIPTION
       "  "
   ::= { gepoel2esw12OltProvisionInHostEntry 2 }

gepoel2esw12ProvInHostLinkLabel OBJECT-TYPE
   SYNTAX      MacAddress
   MAX-ACCESS  read-only
   STATUS      current
   DESCRIPTION
       "  "
   ::= { gepoel2esw12OltProvisionInHostEntry 3 }

gepoel2esw12ProvInHostBridge OBJECT-TYPE
   SYNTAX      INTEGER (-1..15)
   MAX-ACCESS  read-only
   STATUS      current
   DESCRIPTION
       " 1: NNI-0, 2: NNI-1. "
   ::= { gepoel2esw12OltProvisionInHostEntry 4 }
   
gepoel2esw12ProvInHostBridgeDestNNI OBJECT-TYPE
   SYNTAX      INTEGER (1..2)
   MAX-ACCESS  read-only
   STATUS      current
   DESCRIPTION
       " 1: NNI-0, 2: NNI-1. "
   ::= { gepoel2esw12OltProvisionInHostEntry 5 }   

gepoel2esw12ProvInHostVlan OBJECT-TYPE
   SYNTAX      DisplayString
   MAX-ACCESS  read-only
   STATUS      current
   DESCRIPTION
       "  "
   ::= { gepoel2esw12OltProvisionInHostEntry 6 }

gepoel2esw12DelProvInHost OBJECT-TYPE
   SYNTAX      INTEGER (0|1)
   MAX-ACCESS  read-write
   STATUS      current
   DESCRIPTION
       " 0: do nothing, 1:clear provsion in host. "
   ::= { gepoel2esw12OltProvisionInHostEntry 7 }   




---------------------------------------------------------------------------------------------------------------------------------------

gepoel2esw12OnuManagement                                         OBJECT IDENTIFIER ::= { gepoel2esw12ProductId 3 }

gepoel2esw12OnuStatisticsTable OBJECT-TYPE
   SYNTAX      SEQUENCE OF GEPoEL2ESW12OnuStatisticsEntry
   MAX-ACCESS  not-accessible
   STATUS      current
   DESCRIPTION
       ""
   ::= { gepoel2esw12OnuManagement 1 }

gepoel2esw12OnuStatisticsEntry OBJECT-TYPE
   SYNTAX      GEPoEL2ESW12OnuStatisticsEntry
   MAX-ACCESS  not-accessible
   STATUS      current
   DESCRIPTION
       ""
   INDEX    { gepoel2esw12OnuPortStatisticsMacAddress, gepoel2esw12OnuPortStatisticsIndex}
   ::= { gepoel2esw12OnuStatisticsTable 1 }

GEPoEL2ESW12OnuStatisticsEntry ::= SEQUENCE {
    gepoel2esw12OnuPortStatisticsMacAddress   MacAddress,
    gepoel2esw12OnuPortStatisticsIndex   INTEGER,
    gepoel2esw12OnuPortStatisticsOctetTransfer   Counter64,
    gepoel2esw12OnuPortStatisticsTotalFrame   Counter64,
    gepoel2esw12OnuPortStatisticsUnicastFrame   Counter64,
    gepoel2esw12OnuPortStatisticsMulticastFrame   Counter64,
    gepoel2esw12OnuPortStatisticsBroadcastFrame   Counter64,
    gepoel2esw12OnuPortStatistics64OctetFrame   Counter64,
    gepoel2esw12OnuPortStatistics65to127OctetFrame   Counter64,
    gepoel2esw12OnuPortStatistics128to255OctetFrame   Counter64,
    gepoel2esw12OnuPortStatistics256to511OctetFrame   Counter64,
    gepoel2esw12OnuPortStatistics512to1023OctetFrame   Counter64,
    gepoel2esw12OnuPortStatistics1024to1518OctetFrame   Counter64,
    gepoel2esw12OnuPortStatistics1519upOctetFrame   Counter64,
    gepoel2esw12OnuPortStatisticsUndersizeFrame   Counter64,
    gepoel2esw12OnuPortStatisticsFCSError   Counter64,
    gepoel2esw12OnuPortStatisticsCRC8Error   Counter64,
    gepoel2esw12OnuPortStatisticsLineCodeError   Counter64,
    gepoel2esw12OnuPortStatisticsBytesDropped   Counter64,
    gepoel2esw12OnuPortStatisticsFramesDropped   Counter64,
    gepoel2esw12OnuPortStatisticsBytesDelayed   Counter64,
    gepoel2esw12OnuPortStatisticsMaxDelay   Counter64,
    gepoel2esw12OnuPortStatisticsDelayThreshold   Counter64,
    gepoel2esw12OnuPortStatisticsErroredFrame   Counter64,
    gepoel2esw12OnuPortStatisticsUnusedBytes   Counter64,
    gepoel2esw12OnuPortStatisticsOversizedFrame   Counter64,
    gepoel2esw12OnuPortStatisticsPauseFrames   Counter64,
    gepoel2esw12OnuPortStatisticsLengthErrors   Counter64,
    gepoel2esw12OnuPortStatisticsAligmentErrors   Counter64,
    gepoel2esw12OnuPortStatisticsCRC32Error   Counter64,
    gepoel2esw12OnuPortStatisticsSingleCollision   Counter64,
    gepoel2esw12OnuPortStatisticsMultipleCollision   Counter64,
    gepoel2esw12OnuPortStatisticsLateCollision   Counter64,
    gepoel2esw12OnuPortStatisticsExcessiveCollision   Counter64,
    gepoel2esw12OnuStatisticsClear   INTEGER
}

gepoel2esw12OnuPortStatisticsMacAddress OBJECT-TYPE
   SYNTAX      MacAddress
   MAX-ACCESS  not-accessible
   STATUS      current
   DESCRIPTION
       " "
   ::= { gepoel2esw12OnuStatisticsEntry 1 }

gepoel2esw12OnuPortStatisticsIndex OBJECT-TYPE
   SYNTAX      INTEGER(1..6)
   MAX-ACCESS  not-accessible
   STATUS      current
   DESCRIPTION
       " "
   ::= { gepoel2esw12OnuStatisticsEntry 2 }

gepoel2esw12OnuPortStatisticsOctetTransfer	OBJECT-TYPE
   SYNTAX       Counter64
   MAX-ACCESS   read-only
   STATUS       current
   DESCRIPTION
       " "
   ::= { gepoel2esw12OnuStatisticsEntry 3 }

gepoel2esw12OnuPortStatisticsTotalFrame	OBJECT-TYPE
   SYNTAX       Counter64
   MAX-ACCESS   read-only
   STATUS       current
   DESCRIPTION
       " "
   ::= { gepoel2esw12OnuStatisticsEntry 4 }

gepoel2esw12OnuPortStatisticsUnicastFrame	OBJECT-TYPE
   SYNTAX       Counter64
   MAX-ACCESS   read-only
   STATUS       current
   DESCRIPTION
       " "
   ::= { gepoel2esw12OnuStatisticsEntry 5 }

gepoel2esw12OnuPortStatisticsMulticastFrame	OBJECT-TYPE
   SYNTAX       Counter64
   MAX-ACCESS   read-only
   STATUS       current
   DESCRIPTION
       " "
   ::= { gepoel2esw12OnuStatisticsEntry 6 }

gepoel2esw12OnuPortStatisticsBroadcastFrame	OBJECT-TYPE
   SYNTAX       Counter64
   MAX-ACCESS   read-only
   STATUS       current
   DESCRIPTION
       " "
   ::= { gepoel2esw12OnuStatisticsEntry 7 }

gepoel2esw12OnuPortStatistics64OctetFrame	OBJECT-TYPE
   SYNTAX       Counter64
   MAX-ACCESS   read-only
   STATUS       current
   DESCRIPTION
       " "
   ::= { gepoel2esw12OnuStatisticsEntry 8 }

gepoel2esw12OnuPortStatistics65to127OctetFrame	OBJECT-TYPE
   SYNTAX       Counter64
   MAX-ACCESS   read-only
   STATUS       current
   DESCRIPTION
       " "
   ::= { gepoel2esw12OnuStatisticsEntry 9 }

gepoel2esw12OnuPortStatistics128to255OctetFrame	OBJECT-TYPE
   SYNTAX       Counter64
   MAX-ACCESS   read-only
   STATUS       current
   DESCRIPTION
       " "
   ::= { gepoel2esw12OnuStatisticsEntry 10 }

gepoel2esw12OnuPortStatistics256to511OctetFrame	OBJECT-TYPE
   SYNTAX       Counter64
   MAX-ACCESS   read-only
   STATUS       current
   DESCRIPTION
       " "
   ::= { gepoel2esw12OnuStatisticsEntry 11 }

gepoel2esw12OnuPortStatistics512to1023OctetFrame	OBJECT-TYPE
   SYNTAX       Counter64
   MAX-ACCESS   read-only
   STATUS       current
   DESCRIPTION
       " "
   ::= { gepoel2esw12OnuStatisticsEntry 12 }

gepoel2esw12OnuPortStatistics1024to1518OctetFrame	OBJECT-TYPE
   SYNTAX       Counter64
   MAX-ACCESS   read-only
   STATUS       current
   DESCRIPTION
       " "
   ::= { gepoel2esw12OnuStatisticsEntry 13 }

gepoel2esw12OnuPortStatistics1519upOctetFrame	OBJECT-TYPE
   SYNTAX       Counter64
   MAX-ACCESS   read-only
   STATUS       current
   DESCRIPTION
       " "
   ::= { gepoel2esw12OnuStatisticsEntry 14 }

gepoel2esw12OnuPortStatisticsUndersizeFrame	OBJECT-TYPE
   SYNTAX       Counter64
   MAX-ACCESS   read-only
   STATUS       current
   DESCRIPTION
       " "
   ::= { gepoel2esw12OnuStatisticsEntry 15 }

gepoel2esw12OnuPortStatisticsFCSError	OBJECT-TYPE
   SYNTAX       Counter64
   MAX-ACCESS   read-only
   STATUS       current
   DESCRIPTION
       " "
   ::= { gepoel2esw12OnuStatisticsEntry 16 }

gepoel2esw12OnuPortStatisticsCRC8Error	OBJECT-TYPE
   SYNTAX       Counter64
   MAX-ACCESS   read-only
   STATUS       current
   DESCRIPTION
       " "
   ::= { gepoel2esw12OnuStatisticsEntry 17 }

gepoel2esw12OnuPortStatisticsLineCodeError	OBJECT-TYPE
   SYNTAX       Counter64
   MAX-ACCESS   read-only
   STATUS       current
   DESCRIPTION
       " "
   ::= { gepoel2esw12OnuStatisticsEntry 18 }

gepoel2esw12OnuPortStatisticsBytesDropped	OBJECT-TYPE
   SYNTAX       Counter64
   MAX-ACCESS   read-only
   STATUS       current
   DESCRIPTION
       " "
   ::= { gepoel2esw12OnuStatisticsEntry 19 }

gepoel2esw12OnuPortStatisticsFramesDropped	OBJECT-TYPE
   SYNTAX       Counter64
   MAX-ACCESS   read-only
   STATUS       current
   DESCRIPTION
       " "
   ::= { gepoel2esw12OnuStatisticsEntry 20 }

gepoel2esw12OnuPortStatisticsBytesDelayed	OBJECT-TYPE
   SYNTAX       Counter64
   MAX-ACCESS   read-only
   STATUS       current
   DESCRIPTION
       " "
   ::= { gepoel2esw12OnuStatisticsEntry 21 }

gepoel2esw12OnuPortStatisticsMaxDelay	OBJECT-TYPE
   SYNTAX       Counter64
   MAX-ACCESS   read-only
   STATUS       current
   DESCRIPTION
       " "
   ::= { gepoel2esw12OnuStatisticsEntry 22 }

gepoel2esw12OnuPortStatisticsDelayThreshold	OBJECT-TYPE
   SYNTAX       Counter64
   MAX-ACCESS   read-only
   STATUS       current
   DESCRIPTION
       " "
   ::= { gepoel2esw12OnuStatisticsEntry 23 }

gepoel2esw12OnuPortStatisticsErroredFrame	OBJECT-TYPE
   SYNTAX       Counter64
   MAX-ACCESS   read-only
   STATUS       current
   DESCRIPTION
       " "
   ::= { gepoel2esw12OnuStatisticsEntry 24 }

gepoel2esw12OnuPortStatisticsUnusedBytes	OBJECT-TYPE
   SYNTAX       Counter64
   MAX-ACCESS   read-only
   STATUS       current
   DESCRIPTION
       " "
   ::= { gepoel2esw12OnuStatisticsEntry 25 }

gepoel2esw12OnuPortStatisticsOversizedFrame	OBJECT-TYPE
   SYNTAX       Counter64
   MAX-ACCESS   read-only
   STATUS       current
   DESCRIPTION
       " "
   ::= { gepoel2esw12OnuStatisticsEntry 26 }

gepoel2esw12OnuPortStatisticsPauseFrames	OBJECT-TYPE
   SYNTAX       Counter64
   MAX-ACCESS   read-only
   STATUS       current
   DESCRIPTION
       " "
   ::= { gepoel2esw12OnuStatisticsEntry 27 }

gepoel2esw12OnuPortStatisticsLengthErrors	OBJECT-TYPE
   SYNTAX       Counter64
   MAX-ACCESS   read-only
   STATUS       current
   DESCRIPTION
       " "
   ::= { gepoel2esw12OnuStatisticsEntry 28 }

gepoel2esw12OnuPortStatisticsAligmentErrors	OBJECT-TYPE
   SYNTAX       Counter64
   MAX-ACCESS   read-only
   STATUS       current
   DESCRIPTION
       " "
   ::= { gepoel2esw12OnuStatisticsEntry 29 }

gepoel2esw12OnuPortStatisticsCRC32Error	OBJECT-TYPE
   SYNTAX       Counter64
   MAX-ACCESS   read-only
   STATUS       current
   DESCRIPTION
       " "
   ::= { gepoel2esw12OnuStatisticsEntry 30 }

gepoel2esw12OnuPortStatisticsSingleCollision	OBJECT-TYPE
   SYNTAX       Counter64
   MAX-ACCESS   read-only
   STATUS       current
   DESCRIPTION
       " "
   ::= { gepoel2esw12OnuStatisticsEntry 31 }

gepoel2esw12OnuPortStatisticsMultipleCollision	OBJECT-TYPE
   SYNTAX       Counter64
   MAX-ACCESS   read-only
   STATUS       current
   DESCRIPTION
       " "
   ::= { gepoel2esw12OnuStatisticsEntry 32 }

gepoel2esw12OnuPortStatisticsLateCollision	OBJECT-TYPE
   SYNTAX       Counter64
   MAX-ACCESS   read-only
   STATUS       current
   DESCRIPTION
       " "
   ::= { gepoel2esw12OnuStatisticsEntry 33 }

gepoel2esw12OnuPortStatisticsExcessiveCollision	OBJECT-TYPE
   SYNTAX       Counter64
   MAX-ACCESS   read-only
   STATUS       current
   DESCRIPTION
       " "
   ::= { gepoel2esw12OnuStatisticsEntry 34 }

gepoel2esw12OnuStatisticsClear	OBJECT-TYPE
   SYNTAX       INTEGER(0|1)
   MAX-ACCESS   read-write
   STATUS       current
   DESCRIPTION
       " "
   ::= { gepoel2esw12OnuStatisticsEntry 35 }

gepoel2esw12OnuInformationTable OBJECT-TYPE
   SYNTAX      SEQUENCE OF GEPoEL2ESW12OnuInformationEntry
   MAX-ACCESS  not-accessible
   STATUS      current
   DESCRIPTION
       ""
   ::= { gepoel2esw12OnuManagement 2 }
   
gepoel2esw12OnuInformationEntry OBJECT-TYPE
   SYNTAX      GEPoEL2ESW12OnuInformationEntry
   MAX-ACCESS  not-accessible
   STATUS      current
   DESCRIPTION
       ""
   INDEX    { gepoel2esw12OnuInfoOltPort, gepoel2esw12OnuInfoMacAddress}
   ::= { gepoel2esw12OnuInformationTable 1 }

GEPoEL2ESW12OnuInformationEntry ::= SEQUENCE {
    gepoel2esw12OnuInfoOltPort   INTEGER,
    gepoel2esw12OnuInfoMacAddress   MacAddress,
    gepoel2esw12OnuModelName   DisplayString,
    gepoel2esw12OnuSerialNumber   DisplayString,
    gepoel2esw12OnuOutputOpticalWavelength   DisplayString,
    gepoel2esw12OnuFirmwaveVersion   DisplayString,
    gepoel2esw12OnuBootCodeVersion   DisplayString,
    gepoel2esw12OnuPersonalityVersion   DisplayString,
    gepoel2esw12OnuApp0Version   DisplayString,
    gepoel2esw12OnuApp1Version   DisplayString
}

gepoel2esw12OnuInfoOltPort OBJECT-TYPE
   SYNTAX      INTEGER(1|2)
   MAX-ACCESS  not-accessible
   STATUS      current
   DESCRIPTION
       " "
   ::= { gepoel2esw12OnuInformationEntry 1 }
   
gepoel2esw12OnuInfoMacAddress OBJECT-TYPE
   SYNTAX      MacAddress
   MAX-ACCESS  not-accessible
   STATUS      current
   DESCRIPTION
       " "
   ::= { gepoel2esw12OnuInformationEntry 2 }
   
gepoel2esw12OnuModelName	OBJECT-TYPE
   SYNTAX       DisplayString
   MAX-ACCESS   read-only
   STATUS       current
   DESCRIPTION
       " "
   ::= { gepoel2esw12OnuInformationEntry 3 }

gepoel2esw12OnuSerialNumber	OBJECT-TYPE
   SYNTAX       DisplayString
   MAX-ACCESS   read-only
   STATUS       current
   DESCRIPTION
       " "
   ::= { gepoel2esw12OnuInformationEntry 4 }

gepoel2esw12OnuOutputOpticalWavelength	OBJECT-TYPE
   SYNTAX       DisplayString
   MAX-ACCESS   read-only
   STATUS       current
   DESCRIPTION
       " "
   ::= { gepoel2esw12OnuInformationEntry 5 }

gepoel2esw12OnuFirmwaveVersion	OBJECT-TYPE
   SYNTAX       DisplayString
   MAX-ACCESS   read-only
   STATUS       current
   DESCRIPTION
       " "
   ::= { gepoel2esw12OnuInformationEntry 6 }

gepoel2esw12OnuBootCodeVersion	OBJECT-TYPE
   SYNTAX       DisplayString
   MAX-ACCESS   read-only
   STATUS       current
   DESCRIPTION
       " "
   ::= { gepoel2esw12OnuInformationEntry 7 }

gepoel2esw12OnuPersonalityVersion	OBJECT-TYPE
   SYNTAX       DisplayString
   MAX-ACCESS   read-only
   STATUS       current
   DESCRIPTION
       " "
   ::= { gepoel2esw12OnuInformationEntry 8 }

gepoel2esw12OnuApp0Version	OBJECT-TYPE
   SYNTAX       DisplayString
   MAX-ACCESS   read-only
   STATUS       current
   DESCRIPTION
       " "
   ::= { gepoel2esw12OnuInformationEntry 9 }

gepoel2esw12OnuApp1Version	OBJECT-TYPE
   SYNTAX       DisplayString
   MAX-ACCESS   read-only
   STATUS       current
   DESCRIPTION
       " "
   ::= { gepoel2esw12OnuInformationEntry 10 }


gepoel2esw12OnuTrafficManagement                                         OBJECT IDENTIFIER ::= { gepoel2esw12OnuManagement 3 }

gepoel2esw12OnuQueueConfig                                         OBJECT IDENTIFIER ::= { gepoel2esw12OnuTrafficManagement 1 }

gepoel2esw12OnuUpstreamQueueConfigTable OBJECT-TYPE
   SYNTAX      SEQUENCE OF GEPoEL2ESW12OnuUpstreamQueueConfigEntry
   MAX-ACCESS  not-accessible
   STATUS      current
   DESCRIPTION
       " Show Onu Upstream Queue Config Table. "
   ::= { gepoel2esw12OnuQueueConfig 1 }

gepoel2esw12OnuUpstreamQueueConfigEntry OBJECT-TYPE
   SYNTAX      GEPoEL2ESW12OnuUpstreamQueueConfigEntry
   MAX-ACCESS  not-accessible
   STATUS      current
   DESCRIPTION
       ""
   INDEX    { gepoel2esw12OnuUpstreamQueueOltPort, gepoel2esw12OnuUpstreamMacAddress, gepoel2esw12OnuUpstreamConfigIndex }
   ::= { gepoel2esw12OnuUpstreamQueueConfigTable 1 }

GEPoEL2ESW12OnuUpstreamQueueConfigEntry ::= SEQUENCE {
   gepoel2esw12OnuUpstreamQueueOltPort          INTEGER,
   gepoel2esw12OnuUpstreamMacAddress            MacAddress,
   gepoel2esw12OnuUpstreamConfigIndex           INTEGER,
   gepoel2esw12OnuUpstreamQueueSize             DisplayString,
   gepoel2esw12OnuUpstreamQueueSizeDoModify     DisplayString
}

gepoel2esw12OnuUpstreamQueueOltPort OBJECT-TYPE
   SYNTAX      INTEGER (1..2)
   MAX-ACCESS  not-accessible
   STATUS      current
   DESCRIPTION
       " index 1: Epon-0, 2: Epon-1. "
   ::= { gepoel2esw12OnuUpstreamQueueConfigEntry 1 }

gepoel2esw12OnuUpstreamMacAddress OBJECT-TYPE
   SYNTAX      MacAddress
   MAX-ACCESS  not-accessible
   STATUS      current
   DESCRIPTION
       "  "
   ::= { gepoel2esw12OnuUpstreamQueueConfigEntry 2 }

gepoel2esw12OnuUpstreamConfigIndex OBJECT-TYPE
   SYNTAX      INTEGER (1..8)
   MAX-ACCESS  not-accessible
   STATUS      current
   DESCRIPTION
       " range : 1 - 8. "
   ::= { gepoel2esw12OnuUpstreamQueueConfigEntry 3 }
                                   
gepoel2esw12OnuUpstreamQueueSize OBJECT-TYPE
   SYNTAX      DisplayString
   MAX-ACCESS  read-only
   STATUS      current
   DESCRIPTION
       " (2..100) Upstream Queue Size Total is 236. "
   ::= { gepoel2esw12OnuUpstreamQueueConfigEntry 4 }  
                 
gepoel2esw12OnuUpstreamQueueSizeDoModify OBJECT-TYPE
   SYNTAX      DisplayString
   MAX-ACCESS  read-write
   STATUS      current
   DESCRIPTION
       " (2..100) Upstream Queue Size Total is 236. "
   ::= { gepoel2esw12OnuUpstreamQueueConfigEntry 5 }


gepoel2esw12OnuDownstreamQueueConfigTable OBJECT-TYPE
   SYNTAX      SEQUENCE OF GEPoEL2ESW12OnuDownstreamQueueConfigEntry
   MAX-ACCESS  not-accessible
   STATUS      current
   DESCRIPTION
       " Show Onu Downstream Queue Config Table. "
   ::= { gepoel2esw12OnuQueueConfig 2 }

gepoel2esw12OnuDownstreamQueueConfigEntry OBJECT-TYPE
   SYNTAX      GEPoEL2ESW12OnuDownstreamQueueConfigEntry
   MAX-ACCESS  not-accessible
   STATUS      current
   DESCRIPTION
       ""
   INDEX    { gepoel2esw12OnuDownstreamQueueConfigOltPort, gepoel2esw12OnuDownstreamMacAddress, gepoel2esw12OnuDownstreamPort }
   ::= { gepoel2esw12OnuDownstreamQueueConfigTable 1 }

GEPoEL2ESW12OnuDownstreamQueueConfigEntry ::= SEQUENCE {
   gepoel2esw12OnuDownstreamQueueConfigOltPort  INTEGER,
   gepoel2esw12OnuDownstreamMacAddress          MacAddress,
   gepoel2esw12OnuDownstreamPort                INTEGER,
   gepoel2esw12OnuDownstreamQueueSize           DisplayString,
   gepoel2esw12OnuDownstreamQueueSizeDoModify   DisplayString
}

gepoel2esw12OnuDownstreamQueueConfigOltPort OBJECT-TYPE
   SYNTAX      INTEGER (1..2)
   MAX-ACCESS  not-accessible
   STATUS      current
   DESCRIPTION
       " index 1: Epon-0, 2: Epon-1. "
   ::= { gepoel2esw12OnuDownstreamQueueConfigEntry 1 }

gepoel2esw12OnuDownstreamMacAddress OBJECT-TYPE
   SYNTAX      MacAddress
   MAX-ACCESS  not-accessible
   STATUS      current
   DESCRIPTION
       "  "
   ::= { gepoel2esw12OnuDownstreamQueueConfigEntry 2 }

gepoel2esw12OnuDownstreamPort OBJECT-TYPE
   SYNTAX      INTEGER (1|2)
   MAX-ACCESS  not-accessible
   STATUS      current
   DESCRIPTION
       " index, 1: port 1, 2: port 2. "
   ::= { gepoel2esw12OnuDownstreamQueueConfigEntry 3 }
                                   
gepoel2esw12OnuDownstreamQueueSize OBJECT-TYPE
   SYNTAX      DisplayString
   MAX-ACCESS  read-only
   STATUS      current
   DESCRIPTION
       " (2..100) Downstream Queue Size Total is 55. "
   ::= { gepoel2esw12OnuDownstreamQueueConfigEntry 4 }  
                 
gepoel2esw12OnuDownstreamQueueSizeDoModify OBJECT-TYPE
   SYNTAX      DisplayString
   MAX-ACCESS  read-write
   STATUS      current
   DESCRIPTION
       " (2..100) Upstream Queue Size Total is 55. "
   ::= { gepoel2esw12OnuDownstreamQueueConfigEntry 5 }


gepoel2esw12OnuUpstreamQueueConfigAdd                                    OBJECT IDENTIFIER ::= { gepoel2esw12OnuQueueConfig 3 }

gepoel2esw12OnuUpstreamQueueAddOltPort OBJECT-TYPE
   SYNTAX      INTEGER (1..2)
   MAX-ACCESS  read-write
   STATUS      current
   DESCRIPTION
       " index 1:Epon-0, 2: Epon-1. "
   ::= { gepoel2esw12OnuUpstreamQueueConfigAdd 1 } 
   
gepoel2esw12OnuUpstreamQueueAddMacAddress OBJECT-TYPE
   SYNTAX      MacAddress
   MAX-ACCESS  read-write
   STATUS      current
   DESCRIPTION
       " "
   ::= { gepoel2esw12OnuUpstreamQueueConfigAdd 2 } 
   
gepoel2esw12OnuUpstreamQueueAddSize OBJECT-TYPE
   SYNTAX      DisplayString
   MAX-ACCESS  read-write
   STATUS      current
   DESCRIPTION
       " (2..100) Upstream Queue Size Total is 236. "
   ::= { gepoel2esw12OnuUpstreamQueueConfigAdd 3 } 
   
gepoel2esw12OnuUpstreamQueueAdd OBJECT-TYPE
   SYNTAX      INTEGER (0|1)
   MAX-ACCESS  read-write
   STATUS      current
   DESCRIPTION
       " 0: do nothing, 1:add upstream queue size. "
   ::= { gepoel2esw12OnuUpstreamQueueConfigAdd 4 }
   

gepoel2esw12OnuUpstreamQueueConfigDel                                    OBJECT IDENTIFIER ::= { gepoel2esw12OnuQueueConfig 4 }

gepoel2esw12OnuUpstreamQueueDelConfigOltPort OBJECT-TYPE
   SYNTAX      INTEGER (1..2)
   MAX-ACCESS  read-write
   STATUS      current
   DESCRIPTION
       " index 1:Epon-0, 2: Epon-1. "
   ::= { gepoel2esw12OnuUpstreamQueueConfigDel 1 } 
   
gepoel2esw12OnuUpstreamQueueDelMacAddress OBJECT-TYPE
   SYNTAX      MacAddress
   MAX-ACCESS  read-write
   STATUS      current
   DESCRIPTION
       " "
   ::= { gepoel2esw12OnuUpstreamQueueConfigDel 2 } 
   
gepoel2esw12OnuUpstreamQueueDel OBJECT-TYPE
   SYNTAX      INTEGER (0|1)
   MAX-ACCESS  read-write
   STATUS      current
   DESCRIPTION
       " delete upstream queue entry(只能刪除最後一筆entry). "
   ::= { gepoel2esw12OnuUpstreamQueueConfigDel 3 }


gepoel2esw12OnuFieldSelectTable OBJECT-TYPE
   SYNTAX      SEQUENCE OF GEPoEL2ESW12OnuFieldSelectEntry
   MAX-ACCESS  not-accessible
   STATUS      current
   DESCRIPTION
       ""
   ::= { gepoel2esw12OnuTrafficManagement 2 }

gepoel2esw12OnuFieldSelectEntry OBJECT-TYPE
   SYNTAX      GEPoEL2ESW12OnuFieldSelectEntry
   MAX-ACCESS  not-accessible
   STATUS      current
   DESCRIPTION
       ""
   INDEX    { gepoel2esw12OnuFieldSelectOltPort, gepoel2esw12OnuMacAddress, gepoel2esw12OnuPort, gepoel2esw12OnuFieldIndex }
   ::= { gepoel2esw12OnuFieldSelectTable 1 }

GEPoEL2ESW12OnuFieldSelectEntry ::= SEQUENCE {
    gepoel2esw12OnuFieldSelectOltPort   INTEGER,
    gepoel2esw12OnuMacAddress           MacAddress,
    gepoel2esw12OnuPort                 INTEGER,
    gepoel2esw12OnuFieldIndex           INTEGER,
    gepoel2esw12OnuFieldName            DisplayString,
    gepoel2esw12OnuRefCount             INTEGER,
    gepoel2esw12OnuLayerSel             INTEGER,
    gepoel2esw12OnuDWord                INTEGER,
    gepoel2esw12OnuBitOffset            INTEGER,
    gepoel2esw12OnuFieldWidth           INTEGER,
    gepoel2esw12OnuFieldModify          INTEGER,
    gepoel2esw12OnuFieldDoModify        INTEGER
}

gepoel2esw12OnuFieldSelectOltPort OBJECT-TYPE
   SYNTAX      INTEGER (1|2)
   MAX-ACCESS  not-accessible
   STATUS      current
   DESCRIPTION
       " "
   ::= { gepoel2esw12OnuFieldSelectEntry 1 }

gepoel2esw12OnuMacAddress OBJECT-TYPE
   SYNTAX       MacAddress
   MAX-ACCESS   not-accessible
   STATUS       current
   DESCRIPTION
       " "
   ::= { gepoel2esw12OnuFieldSelectEntry 2 }

gepoel2esw12OnuPort OBJECT-TYPE
   SYNTAX      INTEGER (1..3)
   MAX-ACCESS  not-accessible
   STATUS      current
   DESCRIPTION
       " "
   ::= { gepoel2esw12OnuFieldSelectEntry 3 }

gepoel2esw12OnuFieldIndex OBJECT-TYPE
   SYNTAX      INTEGER (1..11)
   MAX-ACCESS  not-accessible
   STATUS      current
   DESCRIPTION
       " "
   ::= { gepoel2esw12OnuFieldSelectEntry 4 }

gepoel2esw12OnuFieldName	OBJECT-TYPE
   SYNTAX       DisplayString
   MAX-ACCESS   read-only
   STATUS       current
   DESCRIPTION
       " "
   ::= { gepoel2esw12OnuFieldSelectEntry 5 }

gepoel2esw12OnuRefCount	OBJECT-TYPE
   SYNTAX       INTEGER(0..255)
   MAX-ACCESS   read-only
   STATUS       current
   DESCRIPTION
       " "
   ::= { gepoel2esw12OnuFieldSelectEntry 6 }

gepoel2esw12OnuLayerSel	OBJECT-TYPE
   SYNTAX       INTEGER(0..7)
   MAX-ACCESS   read-only
   STATUS       current
   DESCRIPTION
       " "
   ::= { gepoel2esw12OnuFieldSelectEntry 7 }

gepoel2esw12OnuDWord	OBJECT-TYPE
   SYNTAX       INTEGER(0..8)
   MAX-ACCESS   read-only
   STATUS       current
   DESCRIPTION
       " "
   ::= { gepoel2esw12OnuFieldSelectEntry 8 }

gepoel2esw12OnuBitOffset	OBJECT-TYPE
   SYNTAX       INTEGER(0..31)
   MAX-ACCESS   read-only
   STATUS       current
   DESCRIPTION
       " "
   ::= { gepoel2esw12OnuFieldSelectEntry 9 }

gepoel2esw12OnuFieldWidth	OBJECT-TYPE
   SYNTAX       INTEGER(1..32)
   MAX-ACCESS   read-only
   STATUS       current
   DESCRIPTION
       " "
   ::= { gepoel2esw12OnuFieldSelectEntry 10 }

gepoel2esw12OnuFieldModify	OBJECT-TYPE
   SYNTAX       INTEGER(-1..37)
   MAX-ACCESS   read-write
   STATUS       current
   DESCRIPTION
       "0:L2 Dest Addr, 1:L2 Source Addr, 2:L2 Link Index, 3:L2 Length/Type, 4:Eth VID, 5:Eth First-Ether Type,
       6:IPv4 Protocol, 7:Eth CoS, 8:L2 LLID Value, 9:Eth DA 1, 10:Eth DA 2, 11:Eth SA 1,
       12:Eth SA 2, 13:L3 Version, 14:IPv4 DA, 15:IPv6 DA, 16:IPv4 SA, 17:IPv6 SA,
       18:IPv4 IHL, 19:IPv4 ToS, 20:IPv4 Ident., 21:IPv4 Flags, 22:IPv4 Offset, 23:IPv4 TTL,
       24:IPv4 Checksum, 25:IPv4 Option, 26:TCP Src. Port, 27:TCP Dst. Port, 28:TCP Seq No., 29:TCP Ack No.
       30:TCP Offset, 31:TCP Reserved, 32:TCP ECN, 33:TCP Control, 34:TCP Window, 35:TCP Checksum,
       36:TCP Urgent Ptr., 37:TCP Option -1:none "
   ::= { gepoel2esw12OnuFieldSelectEntry 11 }

gepoel2esw12OnuFieldClear	OBJECT-TYPE
   SYNTAX       INTEGER(0|1)
   MAX-ACCESS   read-write
   STATUS       current
   DESCRIPTION
       "0 - do nothing , 1 - clear onu field table entry and change field name to Unused. When OnuRefCount is 0, the field can be changed."
   ::= { gepoel2esw12OnuFieldSelectEntry 12 }

gepoel2esw12OnuRule                                         OBJECT IDENTIFIER ::= { gepoel2esw12OnuTrafficManagement 3 }

gepoel2esw12OnuRuleNumberTable OBJECT-TYPE
   SYNTAX      SEQUENCE OF GEPoEL2ESW12OnuRuleNumberEntry
   MAX-ACCESS  not-accessible
   STATUS      current
   DESCRIPTION
       ""
   ::= { gepoel2esw12OnuRule 1 }

gepoel2esw12OnuRuleNumberEntry OBJECT-TYPE
   SYNTAX      GEPoEL2ESW12OnuRuleNumberEntry
   MAX-ACCESS  not-accessible
   STATUS      current
   DESCRIPTION
       ""
   INDEX    { gepoel2esw12OnuRuleNumberOltPort, gepoel2esw12OnuRuleNumberMacAddress, gepoel2esw12OnuRuleNumberPort }
   ::= { gepoel2esw12OnuRuleNumberTable 1 }

GEPoEL2ESW12OnuRuleNumberEntry ::= SEQUENCE {
    gepoel2esw12OnuRuleNumberOltPort        INTEGER,
    gepoel2esw12OnuRuleNumberMacAddress     MacAddress,
    gepoel2esw12OnuRuleNumberPort           INTEGER,
    gepoel2esw12OnuRuleNumber               INTEGER
}

gepoel2esw12OnuRuleNumberOltPort OBJECT-TYPE
   SYNTAX      INTEGER (1|2)
   MAX-ACCESS  not-accessible
   STATUS      current
   DESCRIPTION
       " index 1: Epon-0, 2: Epon-1. "
   ::= { gepoel2esw12OnuRuleNumberEntry 1 }

gepoel2esw12OnuRuleNumberMacAddress OBJECT-TYPE
   SYNTAX       MacAddress
   MAX-ACCESS   not-accessible
   STATUS       current
   DESCRIPTION
       " "
   ::= { gepoel2esw12OnuRuleNumberEntry 2 }

gepoel2esw12OnuRuleNumberPort OBJECT-TYPE
   SYNTAX      INTEGER (1..3)
   MAX-ACCESS  not-accessible
   STATUS      current
   DESCRIPTION
       " "
   ::= { gepoel2esw12OnuRuleNumberEntry 3 }

gepoel2esw12OnuRuleNumber OBJECT-TYPE
   SYNTAX       INTEGER (0..19)
   MAX-ACCESS   read-only
   STATUS       current
   DESCRIPTION
       " "
   ::= { gepoel2esw12OnuRuleNumberEntry 4 }


gepoel2esw12OnuRuleClauseNumberTable OBJECT-TYPE
   SYNTAX      SEQUENCE OF GEPoEL2ESW12OnuRuleClauseNumberEntry
   MAX-ACCESS  not-accessible
   STATUS      current
   DESCRIPTION
       ""
   ::= { gepoel2esw12OnuRule 2 }

gepoel2esw12OnuRuleClauseNumberEntry OBJECT-TYPE
   SYNTAX      GEPoEL2ESW12OnuRuleClauseNumberEntry
   MAX-ACCESS  not-accessible
   STATUS      current
   DESCRIPTION
       ""
   INDEX    { gepoel2esw12OnuRuleClauseNumberOltPort, gepoel2esw12OnuRuleClauseMacAddress, gepoel2esw12OnuRuleClausePort, gepoel2esw12OnuRuleClauseNumberIndex }
   ::= { gepoel2esw12OnuRuleClauseNumberTable 1 }

GEPoEL2ESW12OnuRuleClauseNumberEntry ::= SEQUENCE {
    gepoel2esw12OnuRuleClauseNumberOltPort   INTEGER,
    gepoel2esw12OnuRuleClauseMacAddress            MacAddress,
    gepoel2esw12OnuRuleClausePort                  INTEGER,
    gepoel2esw12OnuRuleClauseNumberIndex           INTEGER,
    gepoel2esw12OnuRuleClauseNumber          INTEGER
}

gepoel2esw12OnuRuleClauseNumberOltPort OBJECT-TYPE
   SYNTAX      INTEGER (1|2)
   MAX-ACCESS  not-accessible
   STATUS      current
   DESCRIPTION
       " "
   ::= { gepoel2esw12OnuRuleClauseNumberEntry 1 }

gepoel2esw12OnuRuleClauseMacAddress OBJECT-TYPE
   SYNTAX       MacAddress
   MAX-ACCESS   not-accessible
   STATUS       current
   DESCRIPTION
       " "
   ::= { gepoel2esw12OnuRuleClauseNumberEntry 2 }

gepoel2esw12OnuRuleClausePort OBJECT-TYPE
   SYNTAX      INTEGER (1..3)
   MAX-ACCESS  not-accessible
   STATUS      current
   DESCRIPTION
       " "
   ::= { gepoel2esw12OnuRuleClauseNumberEntry 3 }

gepoel2esw12OnuRuleClauseNumberIndex OBJECT-TYPE
   SYNTAX      INTEGER (1..19)
   MAX-ACCESS  not-accessible
   STATUS      current
   DESCRIPTION
       " "
   ::= { gepoel2esw12OnuRuleClauseNumberEntry 4 }

gepoel2esw12OnuRuleClauseNumber	OBJECT-TYPE
   SYNTAX       INTEGER(1..8)
   MAX-ACCESS   read-only
   STATUS       current
   DESCRIPTION
       " "
   ::= { gepoel2esw12OnuRuleClauseNumberEntry 5 }

gepoel2esw12OnuRuleTable OBJECT-TYPE
   SYNTAX      SEQUENCE OF GEPoEL2ESW12OnuRuleEntry
   MAX-ACCESS  not-accessible
   STATUS      current
   DESCRIPTION
       ""
   ::= { gepoel2esw12OnuRule 3 }

gepoel2esw12OnuRuleEntry OBJECT-TYPE
   SYNTAX      GEPoEL2ESW12OnuRuleEntry
   MAX-ACCESS  not-accessible
   STATUS      current
   DESCRIPTION
       ""
   INDEX    { gepoel2esw12OnuRuleOltPort, gepoel2esw12OnuRuleMacAddress, gepoel2esw12OnuRulePort, gepoel2esw12OnuPortRuleIndex }
   ::= { gepoel2esw12OnuRuleTable 1 }

GEPoEL2ESW12OnuRuleEntry ::= SEQUENCE {
    gepoel2esw12OnuRuleOltPort   INTEGER,
    gepoel2esw12OnuRuleMacAddress            MacAddress,
    gepoel2esw12OnuRulePort                  INTEGER,
    gepoel2esw12OnuPortRuleIndex           INTEGER,
    gepoel2esw12OnuPortRuleDelete          INTEGER,
    gepoel2esw12OnuPortRuleAction          DisplayString,
    gepoel2esw12OnuPortRuleClauses          DisplayString,
    gepoel2esw12OnuPortRuleNextClauses          DisplayString
}

gepoel2esw12OnuRuleOltPort OBJECT-TYPE
   SYNTAX      INTEGER (1|2)
   MAX-ACCESS  not-accessible
   STATUS      current
   DESCRIPTION
       " "
   ::= { gepoel2esw12OnuRuleEntry 1 }

gepoel2esw12OnuRuleMacAddress OBJECT-TYPE
   SYNTAX       MacAddress
   MAX-ACCESS   not-accessible
   STATUS       current
   DESCRIPTION
       " "
   ::= { gepoel2esw12OnuRuleEntry 2 }

gepoel2esw12OnuRulePort OBJECT-TYPE
   SYNTAX      INTEGER (1..3)
   MAX-ACCESS  not-accessible
   STATUS      current
   DESCRIPTION
       " "
   ::= { gepoel2esw12OnuRuleEntry 3 }

gepoel2esw12OnuPortRuleIndex OBJECT-TYPE
   SYNTAX      INTEGER (1..19)
   MAX-ACCESS  not-accessible
   STATUS      current
   DESCRIPTION
       " "
   ::= { gepoel2esw12OnuRuleEntry 4 }

gepoel2esw12OnuPortRuleDelete	OBJECT-TYPE
   SYNTAX       INTEGER(0|1)
   MAX-ACCESS   read-write
   STATUS       current
   DESCRIPTION
       " "
   ::= { gepoel2esw12OnuRuleEntry 5 }

gepoel2esw12OnuPortRuleAction	OBJECT-TYPE
   SYNTAX       DisplayString
   MAX-ACCESS   read-only
   STATUS       current
   DESCRIPTION
       " "
   ::= { gepoel2esw12OnuRuleEntry 6 }

gepoel2esw12OnuPortRuleClauses	OBJECT-TYPE
   SYNTAX       DisplayString
   MAX-ACCESS   read-only
   STATUS       current
   DESCRIPTION
       " "
   ::= { gepoel2esw12OnuRuleEntry 7 }

gepoel2esw12OnuPortRuleNextClauses	OBJECT-TYPE
   SYNTAX       DisplayString
   MAX-ACCESS   read-only
   STATUS       current
   DESCRIPTION
       " "
   ::= { gepoel2esw12OnuRuleEntry 8 }


gepoel2esw12OnuRuleAdd                                    OBJECT IDENTIFIER ::= { gepoel2esw12OnuRule 4 }

gepoel2esw12OnuRuleAddOltPort OBJECT-TYPE
   SYNTAX      INTEGER (1..2)
   MAX-ACCESS  read-write
   STATUS      current
   DESCRIPTION
       "  "
   ::= { gepoel2esw12OnuRuleAdd 1 } 
   
gepoel2esw12OnuRuleAddMacAddress OBJECT-TYPE
   SYNTAX      MacAddress
   MAX-ACCESS  read-write
   STATUS      current
   DESCRIPTION
       " "
   ::= { gepoel2esw12OnuRuleAdd 2 } 
   
gepoel2esw12OnuRuleAddPort OBJECT-TYPE
   SYNTAX      INTEGER (1..3)
   MAX-ACCESS  read-write
   STATUS      current
   DESCRIPTION
       "  "
   ::= { gepoel2esw12OnuRuleAdd 3 } 
   
gepoel2esw12OnuPortRuleAddPriority OBJECT-TYPE
   SYNTAX      INTEGER (8..13)
   MAX-ACCESS  read-write
   STATUS      current
   DESCRIPTION
       "  "
   ::= { gepoel2esw12OnuRuleAdd 4 } 
   
gepoel2esw12OnuPortRuleAddAction OBJECT-TYPE
   SYNTAX      INTEGER (0..29)
   MAX-ACCESS  read-write
   STATUS      current
   DESCRIPTION
       "  "
   ::= { gepoel2esw12OnuRuleAdd 5 } 
   
gepoel2esw12OnuPortRuleAddActionPort OBJECT-TYPE
   SYNTAX      INTEGER (0..8)
   MAX-ACCESS  read-write
   STATUS      current
   DESCRIPTION
       "  "
   ::= { gepoel2esw12OnuRuleAdd 6 } 
   
gepoel2esw12OnuPortRuleAddActionQueue OBJECT-TYPE
   SYNTAX      INTEGER (0..19)
   MAX-ACCESS  read-write
   STATUS      current
   DESCRIPTION
       "  "
   ::= { gepoel2esw12OnuRuleAdd 7 } 
   
gepoel2esw12OnuPortRuleAddClauseNum OBJECT-TYPE
   SYNTAX      INTEGER (0..8)
   MAX-ACCESS  read-write
   STATUS      current
   DESCRIPTION
       "  "
   ::= { gepoel2esw12OnuRuleAdd 8 } 
   

gepoel2esw12OnuPortRuleAddClauseTable OBJECT-TYPE
   SYNTAX      SEQUENCE OF GEPoEL2ESW12OnuPortRuleAddClauseEntry
   MAX-ACCESS  not-accessible
   STATUS      current
   DESCRIPTION
       ""
   ::= { gepoel2esw12OnuRuleAdd 9 }

gepoel2esw12OnuPortRuleAddClauseEntry OBJECT-TYPE
   SYNTAX      GEPoEL2ESW12OnuPortRuleAddClauseEntry
   MAX-ACCESS  not-accessible
   STATUS      current
   DESCRIPTION
       ""
   INDEX    { gepoel2esw12OnuPortRuleAddClauseIndex }
   ::= { gepoel2esw12OnuPortRuleAddClauseTable 1 }

GEPoEL2ESW12OnuPortRuleAddClauseEntry ::= SEQUENCE {
    gepoel2esw12OnuPortRuleAddClauseIndex   INTEGER,
    gepoel2esw12OnuPortRuleAddField         INTEGER,
    gepoel2esw12OnuPortRuleAddOperation     INTEGER,
    gepoel2esw12OnuPortRuleAddValueType     INTEGER,
    gepoel2esw12OnuPortRuleAddValue         DisplayString
}

gepoel2esw12OnuPortRuleAddClauseIndex OBJECT-TYPE
   SYNTAX      INTEGER (1..8)
   MAX-ACCESS  not-accessible
   STATUS      current
   DESCRIPTION
       " "
   ::= { gepoel2esw12OnuPortRuleAddClauseEntry 1 }

gepoel2esw12OnuPortRuleAddField OBJECT-TYPE
   SYNTAX       INTEGER (0..11)
   MAX-ACCESS   read-write
   STATUS       current
   DESCRIPTION
       " 0..11代表值的意義請參考此台ONU的OnuFieldEntry/OnuFieldName. "
   ::= { gepoel2esw12OnuPortRuleAddClauseEntry 2 }

gepoel2esw12OnuPortRuleAddOperation OBJECT-TYPE
   SYNTAX      INTEGER (0..7)
   MAX-ACCESS  read-write
   STATUS      current
   DESCRIPTION
       " 0: F, 1:==, 2:!=, 3: <=, 4: >=, 5: exists, 6: !exist, 7: T. "
   ::= { gepoel2esw12OnuPortRuleAddClauseEntry 3 }

gepoel2esw12OnuPortRuleAddValueType OBJECT-TYPE
   SYNTAX       INTEGER (0|1|2)
   MAX-ACCESS   read-write
   STATUS       current
   DESCRIPTION
       " 0 : Hex , 1 : Decimal , 2 : IP Format. "
   ::= { gepoel2esw12OnuPortRuleAddClauseEntry 4 }
   
gepoel2esw12OnuPortRuleAddValue OBJECT-TYPE
   SYNTAX       DisplayString
   MAX-ACCESS   read-write
   STATUS       current
   DESCRIPTION
       " 8 bytes(String), depend on value type. "
   ::= { gepoel2esw12OnuPortRuleAddClauseEntry 5 }


gepoel2esw12DoOnuRulerAdd OBJECT-TYPE
   SYNTAX      INTEGER (0|1)
   MAX-ACCESS  read-write
   STATUS      current
   DESCRIPTION
       " 0:do nothing, 1:port rule add. "
   ::= { gepoel2esw12OnuRuleAdd 10 } 


gepoel2esw12OnuIGMP                                         OBJECT IDENTIFIER ::= { gepoel2esw12OnuManagement 4 }

gepoel2esw12OnuIGMPSnoopingTable OBJECT-TYPE
   SYNTAX      SEQUENCE OF GEPoEL2ESW12OnuIGMPSnoopingEntry
   MAX-ACCESS  not-accessible
   STATUS      current
   DESCRIPTION
       ""
   ::= { gepoel2esw12OnuIGMP 1 }

gepoel2esw12OnuIGMPSnoopingEntry OBJECT-TYPE
   SYNTAX      GEPoEL2ESW12OnuIGMPSnoopingEntry
   MAX-ACCESS  not-accessible
   STATUS      current
   DESCRIPTION
       ""
   INDEX    { gepoel2esw12OnuIGMPSnoopingOltPort, gepoel2esw12OnuIGMPSnoopingMacAddress}
   ::= { gepoel2esw12OnuIGMPSnoopingTable 1 }

GEPoEL2ESW12OnuIGMPSnoopingEntry ::= SEQUENCE {
    gepoel2esw12OnuIGMPSnoopingOltPort             INTEGER,
    gepoel2esw12OnuIGMPSnoopingMacAddress          MacAddress,
    gepoel2esw12OnuRobustnessCount                 INTEGER,
    gepoel2esw12OnuLastMemberQuery                 INTEGER,
    gepoel2esw12OnuPort1IGMPGroupNumber            INTEGER,
    gepoel2esw12OnuPort1QueueForClassification     INTEGER,
    gepoel2esw12OnuPort2IGMPGroupNumber            INTEGER,
    gepoel2esw12OnuPort2QueueForClassification     INTEGER,
    gepoel2esw12OnuIGMPForwardGroupByL2DA          INTEGER,
    gepoel2esw12OnuIGMPForwardGroupByVID           INTEGER,
    gepoel2esw12OnuIGMPForwardGroupByIPDA          INTEGER
}

gepoel2esw12OnuIGMPSnoopingOltPort OBJECT-TYPE
   SYNTAX      INTEGER (1|2)
   MAX-ACCESS  not-accessible
   STATUS      current
   DESCRIPTION
       " "
   ::= { gepoel2esw12OnuIGMPSnoopingEntry 1 }

gepoel2esw12OnuIGMPSnoopingMacAddress OBJECT-TYPE
   SYNTAX       MacAddress
   MAX-ACCESS   not-accessible
   STATUS       current
   DESCRIPTION
       " "
   ::= { gepoel2esw12OnuIGMPSnoopingEntry 2 }

gepoel2esw12OnuRobustnessCount	OBJECT-TYPE
   SYNTAX       INTEGER(0..12)
   MAX-ACCESS   read-write
   STATUS       current
   DESCRIPTION
       " "
   ::= { gepoel2esw12OnuIGMPSnoopingEntry 3 }

gepoel2esw12OnuLastMemberQuery	OBJECT-TYPE
   SYNTAX       INTEGER(0..12)
   MAX-ACCESS   read-write
   STATUS       current
   DESCRIPTION
       " "
   ::= { gepoel2esw12OnuIGMPSnoopingEntry 4 }

gepoel2esw12OnuPort1IGMPGroupNumber	OBJECT-TYPE
   SYNTAX       INTEGER(0..90)
   MAX-ACCESS   read-write
   STATUS       current
   DESCRIPTION
       " "
   ::= { gepoel2esw12OnuIGMPSnoopingEntry 5 }

gepoel2esw12OnuPort1QueueForClassification	OBJECT-TYPE
   SYNTAX       INTEGER(0..6)
   MAX-ACCESS   read-write
   STATUS       current
   DESCRIPTION
       " "
   ::= { gepoel2esw12OnuIGMPSnoopingEntry 6 }

gepoel2esw12OnuPort2IGMPGroupNumber	OBJECT-TYPE
   SYNTAX       INTEGER(0..90)
   MAX-ACCESS   read-write
   STATUS       current
   DESCRIPTION
       " "
   ::= { gepoel2esw12OnuIGMPSnoopingEntry 7 }

gepoel2esw12OnuPort2QueueForClassification	OBJECT-TYPE
   SYNTAX       INTEGER(0..6)
   MAX-ACCESS   read-write
   STATUS       current
   DESCRIPTION
       " "
   ::= { gepoel2esw12OnuIGMPSnoopingEntry 8 }

gepoel2esw12OnuIGMPForwardGroupByL2DA	OBJECT-TYPE
   SYNTAX       INTEGER(0|1)
   MAX-ACCESS   read-write
   STATUS       current
   DESCRIPTION
       " "
   ::= { gepoel2esw12OnuIGMPSnoopingEntry 9 }

gepoel2esw12OnuIGMPForwardGroupByVID	OBJECT-TYPE
   SYNTAX       INTEGER(0|1)
   MAX-ACCESS   read-write
   STATUS       current
   DESCRIPTION
       " "
   ::= { gepoel2esw12OnuIGMPSnoopingEntry 10 }

gepoel2esw12OnuIGMPForwardGroupByIPDA	OBJECT-TYPE
   SYNTAX       INTEGER(0|1)
   MAX-ACCESS   read-write
   STATUS       current
   DESCRIPTION
       " "
   ::= { gepoel2esw12OnuIGMPSnoopingEntry 11 }


gepoel2esw12OnuIGMPVlanProvision                                         OBJECT IDENTIFIER ::= { gepoel2esw12OnuIGMP 2 }

gepoel2esw12OnuIGMPVlanProvisionTable OBJECT-TYPE
   SYNTAX      SEQUENCE OF GEPoEL2ESW12OnuIGMPVlanProvisionEntry
   MAX-ACCESS  not-accessible
   STATUS      current
   DESCRIPTION
       ""
   ::= { gepoel2esw12OnuIGMPVlanProvision 1 }

gepoel2esw12OnuIGMPVlanProvisionEntry OBJECT-TYPE
   SYNTAX      GEPoEL2ESW12OnuIGMPVlanProvisionEntry
   MAX-ACCESS  not-accessible
   STATUS      current
   DESCRIPTION
       ""
   INDEX    { gepoel2esw12OnuIGMPVlanProvisionOltPort, gepoel2esw12OnuIGMPVlanProvisionMacAddress}
   ::= { gepoel2esw12OnuIGMPVlanProvisionTable 1 }

GEPoEL2ESW12OnuIGMPVlanProvisionEntry ::= SEQUENCE {
    gepoel2esw12OnuIGMPVlanProvisionOltPort                     INTEGER,
    gepoel2esw12OnuIGMPVlanProvisionMacAddress                  MacAddress,
    gepoel2esw12OnuIGMPVlanProvisionActionforUnmanagedGroup     INTEGER,
    gepoel2esw12OnuIGMPVlanProvisionNumberofIGMPVlan            INTEGER
}

gepoel2esw12OnuIGMPVlanProvisionOltPort OBJECT-TYPE
   SYNTAX      INTEGER (1|2)
   MAX-ACCESS  not-accessible
   STATUS      current
   DESCRIPTION
       " index 1: Epon-0, 2: Epon-1. "
   ::= { gepoel2esw12OnuIGMPVlanProvisionEntry 1 }

gepoel2esw12OnuIGMPVlanProvisionMacAddress OBJECT-TYPE
   SYNTAX       MacAddress
   MAX-ACCESS   not-accessible
   STATUS       current
   DESCRIPTION
       " "
   ::= { gepoel2esw12OnuIGMPVlanProvisionEntry 2 }

gepoel2esw12OnuIGMPVlanProvisionActionforUnmanagedGroup OBJECT-TYPE
   SYNTAX       INTEGER(0|1)
   MAX-ACCESS   read-write
   STATUS       current
   DESCRIPTION
       " 0: discard(block IPMC, IGMP), 1: ignore(forward unchanged). "
   ::= { gepoel2esw12OnuIGMPVlanProvisionEntry 3 }

gepoel2esw12OnuIGMPVlanProvisionNumberofIGMPVlan OBJECT-TYPE
   SYNTAX       INTEGER(0..16)
   MAX-ACCESS   read-only
   STATUS       current
   DESCRIPTION
       " "
   ::= { gepoel2esw12OnuIGMPVlanProvisionEntry 4 }


gepoel2esw12OnuIGMPVlanTable OBJECT-TYPE
   SYNTAX      SEQUENCE OF GEPoEL2ESW12OnuIGMPVlanEntry
   MAX-ACCESS  not-accessible
   STATUS      current
   DESCRIPTION
       "  "
   ::= { gepoel2esw12OnuIGMPVlanProvision 2 }

gepoel2esw12OnuIGMPVlanEntry OBJECT-TYPE
   SYNTAX      GEPoEL2ESW12OnuIGMPVlanEntry
   MAX-ACCESS  not-accessible
   STATUS      current
   DESCRIPTION
       ""
   INDEX    { gepoel2esw12OnuIGMPVlanOltPort, gepoel2esw12OnuIGMPVlanMacAddress, gepoel2esw12OnuIGMPVlanIndex }
   ::= { gepoel2esw12OnuIGMPVlanTable 1 }

GEPoEL2ESW12OnuIGMPVlanEntry ::= SEQUENCE {
   gepoel2esw12OnuIGMPVlanOltPort           INTEGER,
   gepoel2esw12OnuIGMPVlanMacAddress        MacAddress,
   gepoel2esw12OnuIGMPVlanIndex             INTEGER,
   gepoel2esw12OnuIGMPVlanEponVlanID        INTEGER,
   gepoel2esw12OnuIGMPVlanUserVlanID        INTEGER,
   gepoel2esw12OnuIGMPVlanMaxAllowedGroup   INTEGER,
   gepoel2esw12OnuIGMPVlanDel               INTEGER
}

gepoel2esw12OnuIGMPVlanOltPort OBJECT-TYPE
   SYNTAX      INTEGER (1..2)
   MAX-ACCESS  not-accessible
   STATUS      current
   DESCRIPTION
       " index 1: Epon-0, 2: Epon-1. "
   ::= { gepoel2esw12OnuIGMPVlanEntry 1 }

gepoel2esw12OnuIGMPVlanMacAddress OBJECT-TYPE
   SYNTAX      MacAddress
   MAX-ACCESS  not-accessible
   STATUS      current
   DESCRIPTION
       "  "
   ::= { gepoel2esw12OnuIGMPVlanEntry 2 }

gepoel2esw12OnuIGMPVlanIndex OBJECT-TYPE
   SYNTAX      INTEGER (1..16)
   MAX-ACCESS  not-accessible
   STATUS      current
   DESCRIPTION
       " "
   ::= { gepoel2esw12OnuIGMPVlanEntry 3 }
                                   
gepoel2esw12OnuIGMPVlanEponVlanID OBJECT-TYPE
   SYNTAX      INTEGER (0..4095)
   MAX-ACCESS  read-only
   STATUS      current
   DESCRIPTION
       " "
   ::= { gepoel2esw12OnuIGMPVlanEntry 4 }  
                 
gepoel2esw12OnuIGMPVlanUserVlanID OBJECT-TYPE
   SYNTAX      INTEGER (0..4095)
   MAX-ACCESS  read-only
   STATUS      current
   DESCRIPTION
       "  "
   ::= { gepoel2esw12OnuIGMPVlanEntry 5 }     
   
gepoel2esw12OnuIGMPVlanMaxAllowedGroup OBJECT-TYPE
   SYNTAX      INTEGER (0..255)
   MAX-ACCESS  read-only
   STATUS      current
   DESCRIPTION
       "  "
   ::= { gepoel2esw12OnuIGMPVlanEntry 6 } 
   
gepoel2esw12OnuIGMPVlanDel OBJECT-TYPE
   SYNTAX      INTEGER (0|1)
   MAX-ACCESS  read-write
   STATUS      current
   DESCRIPTION
       " delete index entry. "
   ::= { gepoel2esw12OnuIGMPVlanEntry 7 }


gepoel2esw12OnuIGMPVlanAdd                                    OBJECT IDENTIFIER ::= { gepoel2esw12OnuIGMPVlanProvision 3 }

gepoel2esw12OnuIGMPVlanAddOltPort OBJECT-TYPE
   SYNTAX      INTEGER (1..2)
   MAX-ACCESS  read-write
   STATUS      current
   DESCRIPTION
       "  "
   ::= { gepoel2esw12OnuIGMPVlanAdd 1 } 
   
gepoel2esw12OnuIGMPVlanAddMacAddress OBJECT-TYPE
   SYNTAX      MacAddress
   MAX-ACCESS  read-write
   STATUS      current
   DESCRIPTION
       " "
   ::= { gepoel2esw12OnuIGMPVlanAdd 2 } 
   
gepoel2esw12OnuIGMPVlanAddEponVlanID OBJECT-TYPE
   SYNTAX      INTEGER (0..4095)
   MAX-ACCESS  read-write
   STATUS      current
   DESCRIPTION
       "  "
   ::= { gepoel2esw12OnuIGMPVlanAdd 3 } 
   
gepoel2esw12OnuIGMPVlanAddUserVlanID OBJECT-TYPE
   SYNTAX      INTEGER (0..4095)
   MAX-ACCESS  read-write
   STATUS      current
   DESCRIPTION
       "  "
   ::= { gepoel2esw12OnuIGMPVlanAdd 4 } 
   
gepoel2esw12OnuIGMPVlanAddMaxAllowedGroup OBJECT-TYPE
   SYNTAX      INTEGER (0..255)
   MAX-ACCESS  read-write
   STATUS      current
   DESCRIPTION
       "  "
   ::= { gepoel2esw12OnuIGMPVlanAdd 5 } 
   
gepoel2esw12OnuIGMPVlanAddDo OBJECT-TYPE
   SYNTAX      INTEGER (0|1)
   MAX-ACCESS  read-write
   STATUS      current
   DESCRIPTION
       "  "
   ::= { gepoel2esw12OnuIGMPVlanAdd 6 } 
   

gepoel2esw12OnuIGMPGroup                                         OBJECT IDENTIFIER ::= { gepoel2esw12OnuIGMP 3 }

gepoel2esw12OnuIGMPGroupTable OBJECT-TYPE
   SYNTAX      SEQUENCE OF GEPoEL2ESW12OnuIGMPGroupEntry
   MAX-ACCESS  not-accessible
   STATUS      current
   DESCRIPTION
       "  "
   ::= { gepoel2esw12OnuIGMPGroup 1 }

gepoel2esw12OnuIGMPGroupEntry OBJECT-TYPE
   SYNTAX      GEPoEL2ESW12OnuIGMPGroupEntry
   MAX-ACCESS  not-accessible
   STATUS      current
   DESCRIPTION
       ""
   INDEX    { gepoel2esw12OnuIGMPGroupOltPort, gepoel2esw12OnuIGMPGroupMacAddress, gepoel2esw12OnuIGMPGroupJoinedIndex }
   ::= { gepoel2esw12OnuIGMPGroupTable 1 }

GEPoEL2ESW12OnuIGMPGroupEntry ::= SEQUENCE {
   gepoel2esw12OnuIGMPGroupOltPort          INTEGER,
   gepoel2esw12OnuIGMPGroupMacAddress       MacAddress,
   gepoel2esw12OnuIGMPGroupJoinedIndex      INTEGER,
   gepoel2esw12OnuIGMPGroupJoinedID         IpAddress,
   gepoel2esw12OnuIGMPGroupJoinedPort       DisplayString
}

gepoel2esw12OnuIGMPGroupOltPort OBJECT-TYPE
   SYNTAX      INTEGER (1..2)
   MAX-ACCESS  not-accessible
   STATUS      current
   DESCRIPTION
       " index 1: Epon-0, 2: Epon-1. "
   ::= { gepoel2esw12OnuIGMPGroupEntry 1 }

gepoel2esw12OnuIGMPGroupMacAddress OBJECT-TYPE
   SYNTAX      MacAddress
   MAX-ACCESS  not-accessible
   STATUS      current
   DESCRIPTION
       "  "
   ::= { gepoel2esw12OnuIGMPGroupEntry 2 }

gepoel2esw12OnuIGMPGroupJoinedIndex OBJECT-TYPE
   SYNTAX      INTEGER (1..80)
   MAX-ACCESS  not-accessible
   STATUS      current
   DESCRIPTION
       " "
   ::= { gepoel2esw12OnuIGMPGroupEntry 3 }
                                   
gepoel2esw12OnuIGMPGroupJoinedID OBJECT-TYPE
   SYNTAX      IpAddress
   MAX-ACCESS  read-only
   STATUS      current
   DESCRIPTION
       " "
   ::= { gepoel2esw12OnuIGMPGroupEntry 4 }  
                 
gepoel2esw12OnuIGMPGroupJoinedPort OBJECT-TYPE
   SYNTAX      DisplayString
   MAX-ACCESS  read-only
   STATUS      current
   DESCRIPTION
       " 1:port 1, 2:port 2, 1&2: prot 1 and port 2. "
   ::= { gepoel2esw12OnuIGMPGroupEntry 5 }  


gepoel2esw12OnuBridgeConfig                                         OBJECT IDENTIFIER ::= { gepoel2esw12OnuManagement 5 }


gepoel2esw12OnuBridgeConfigTable OBJECT-TYPE
   SYNTAX      SEQUENCE OF GEPoEL2ESW12OnuBridgeConfigEntry
   MAX-ACCESS  not-accessible
   STATUS      current
   DESCRIPTION
       "  "
   ::= { gepoel2esw12OnuBridgeConfig 1 }

gepoel2esw12OnuBridgeConfigEntry OBJECT-TYPE
   SYNTAX      GEPoEL2ESW12OnuBridgeConfigEntry
   MAX-ACCESS  not-accessible
   STATUS      current
   DESCRIPTION
       ""
   INDEX    { gepoel2esw12OnuBridgeConfigOltPort, gepoel2esw12OnuBridgeConfigMacAddress, gepoel2esw12OnuBridgeConfigPort }
   ::= { gepoel2esw12OnuBridgeConfigTable 1 }

GEPoEL2ESW12OnuBridgeConfigEntry ::= SEQUENCE {
   gepoel2esw12OnuBridgeConfigOltPort           INTEGER,
   gepoel2esw12OnuBridgeConfigMacAddress        MacAddress,
   gepoel2esw12OnuBridgeConfigPort              INTEGER,
   gepoel2esw12OnuBridgeConfigAgeLimit          INTEGER,
   gepoel2esw12OnuBridgeConfigEntryLimit        INTEGER,
   gepoel2esw12OnuBridgeConfigLearningMode      INTEGER
}

gepoel2esw12OnuBridgeConfigOltPort OBJECT-TYPE
   SYNTAX      INTEGER (1..2)
   MAX-ACCESS  not-accessible
   STATUS      current
   DESCRIPTION
       " index 1: Epon-0, 2: Epon-1. "
   ::= { gepoel2esw12OnuBridgeConfigEntry 1 }

gepoel2esw12OnuBridgeConfigMacAddress OBJECT-TYPE
   SYNTAX      MacAddress
   MAX-ACCESS  not-accessible
   STATUS      current
   DESCRIPTION
       "  "
   ::= { gepoel2esw12OnuBridgeConfigEntry 2 }

gepoel2esw12OnuBridgeConfigPort OBJECT-TYPE
   SYNTAX      INTEGER (1|2)
   MAX-ACCESS  not-accessible
   STATUS      current
   DESCRIPTION
       " 1:port 1, 2:port 2. "
   ::= { gepoel2esw12OnuBridgeConfigEntry 3 }
                                   
gepoel2esw12OnuBridgeConfigAgeLimit OBJECT-TYPE
   SYNTAX      INTEGER (0..32768)
   MAX-ACCESS  read-write
   STATUS      current
   DESCRIPTION
       " unit: 8.75 msec. 0:disable. "
   ::= { gepoel2esw12OnuBridgeConfigEntry 4 }  
                 
gepoel2esw12OnuBridgeConfigEntryLimit OBJECT-TYPE
   SYNTAX      INTEGER (0..64)
   MAX-ACCESS  read-write
   STATUS      current
   DESCRIPTION
       " 當Learning Mode為Forward(802.1d Learning)時,Entry Limit:0~64
         當Learning Mode為Drop Until Learned(Mac Access Control)時,Entry Limit:0~32. "
   ::= { gepoel2esw12OnuBridgeConfigEntry 5 }     
   
gepoel2esw12OnuBridgeConfigLearningMode OBJECT-TYPE
   SYNTAX      INTEGER (0|1)
   MAX-ACCESS  read-write
   STATUS      current
   DESCRIPTION
       " 0:Forward, 1:Drop Until Learned. "
   ::= { gepoel2esw12OnuBridgeConfigEntry 6 }


gepoel2esw12OnuDynamicMac                                         OBJECT IDENTIFIER ::= { gepoel2esw12OnuBridgeConfig 2 }

gepoel2esw12OnuDynamicMacTable OBJECT-TYPE
   SYNTAX      SEQUENCE OF GEPoEL2ESW12OnuDynamicMacEntry
   MAX-ACCESS  not-accessible
   STATUS      current
   DESCRIPTION
       ""
   ::= { gepoel2esw12OnuDynamicMac 1 }

gepoel2esw12OnuDynamicMacEntry OBJECT-TYPE
   SYNTAX      GEPoEL2ESW12OnuDynamicMacEntry
   MAX-ACCESS  not-accessible
   STATUS      current
   DESCRIPTION
       ""
   INDEX    { gepoel2esw12OnuDynamicOltPort, gepoel2esw12OnuDynamicLink, gepoel2esw12OnuDynamicPort, gepoel2esw12OnuDynamicMacIndex }
   ::= { gepoel2esw12OnuDynamicMacTable 1 }

GEPoEL2ESW12OnuDynamicMacEntry ::= SEQUENCE {
    gepoel2esw12OnuDynamicOltPort   INTEGER,
    gepoel2esw12OnuDynamicLink      MacAddress,
    gepoel2esw12OnuDynamicPort      INTEGER,
    gepoel2esw12OnuDynamicMacIndex  INTEGER,
    gepoel2esw12OnuDynamicMacLink       MacAddress
}

gepoel2esw12OnuDynamicOltPort OBJECT-TYPE
   SYNTAX      INTEGER (1|2)
   MAX-ACCESS  not-accessible
   STATUS      current
   DESCRIPTION
       " "
   ::= { gepoel2esw12OnuDynamicMacEntry 1 }

gepoel2esw12OnuDynamicLink OBJECT-TYPE
   SYNTAX       MacAddress
   MAX-ACCESS   not-accessible
   STATUS       current
   DESCRIPTION
       " "
   ::= { gepoel2esw12OnuDynamicMacEntry 2 }

gepoel2esw12OnuDynamicPort OBJECT-TYPE
   SYNTAX      INTEGER (1|2)
   MAX-ACCESS  not-accessible
   STATUS      current
   DESCRIPTION
       " "
   ::= { gepoel2esw12OnuDynamicMacEntry 3 }

gepoel2esw12OnuDynamicMacIndex OBJECT-TYPE
   SYNTAX      INTEGER (1..4095)
   MAX-ACCESS  not-accessible
   STATUS      current
   DESCRIPTION
       " "
   ::= { gepoel2esw12OnuDynamicMacEntry 4 }

gepoel2esw12OnuDynamicMacLink	OBJECT-TYPE
   SYNTAX       MacAddress
   MAX-ACCESS   read-only
   STATUS       current
   DESCRIPTION
       " "
   ::= { gepoel2esw12OnuDynamicMacEntry 5 }


gepoel2esw12OnuClearDynamicMacTable OBJECT-TYPE
   SYNTAX      SEQUENCE OF GEPoEL2ESW12OnuClearDynamicMacEntry
   MAX-ACCESS  not-accessible
   STATUS      current
   DESCRIPTION
       "  "
   ::= { gepoel2esw12OnuDynamicMac 2 }

gepoel2esw12OnuClearDynamicMacEntry OBJECT-TYPE
   SYNTAX      GEPoEL2ESW12OnuClearDynamicMacEntry
   MAX-ACCESS  not-accessible
   STATUS      current
   DESCRIPTION
       ""
   INDEX    { gepoel2esw12OnuClearDynamicMacOltPort, gepoel2esw12OnuClearDynamicMacLink, gepoel2esw12OnuClearDynamicMacPort }
   ::= { gepoel2esw12OnuClearDynamicMacTable 1 }

GEPoEL2ESW12OnuClearDynamicMacEntry ::= SEQUENCE {
   gepoel2esw12OnuClearDynamicMacOltPort           INTEGER,
   gepoel2esw12OnuClearDynamicMacLink        MacAddress,
   gepoel2esw12OnuClearDynamicMacPort              INTEGER,
   gepoel2esw12OnuClearDynamicMacClear      INTEGER
}

gepoel2esw12OnuClearDynamicMacOltPort OBJECT-TYPE
   SYNTAX      INTEGER (1..2)
   MAX-ACCESS  not-accessible
   STATUS      current
   DESCRIPTION
       " index 1: Epon-0, 2: Epon-1. "
   ::= { gepoel2esw12OnuClearDynamicMacEntry 1 }

gepoel2esw12OnuClearDynamicMacLink OBJECT-TYPE
   SYNTAX      MacAddress
   MAX-ACCESS  not-accessible
   STATUS      current
   DESCRIPTION
       "  "
   ::= { gepoel2esw12OnuClearDynamicMacEntry 2 }

gepoel2esw12OnuClearDynamicMacPort OBJECT-TYPE
   SYNTAX      INTEGER (1|2)
   MAX-ACCESS  not-accessible
   STATUS      current
   DESCRIPTION
       " 1:port 1, 2:port 2. "
   ::= { gepoel2esw12OnuClearDynamicMacEntry 3 }
                                   
gepoel2esw12OnuClearDynamicMacClear OBJECT-TYPE
   SYNTAX      INTEGER (0|1)
   MAX-ACCESS  read-write
   STATUS      current
   DESCRIPTION
       " 0:do nothing, 1-clear mac address. "
   ::= { gepoel2esw12OnuClearDynamicMacEntry 4 }  


gepoel2esw12OnuVlanOption                                         OBJECT IDENTIFIER ::= { gepoel2esw12OnuBridgeConfig 3 }

gepoel2esw12OnuVlanOptionTable OBJECT-TYPE
   SYNTAX      SEQUENCE OF GEPoEL2ESW12OnuVlanOptionEntry
   MAX-ACCESS  not-accessible
   STATUS      current
   DESCRIPTION
       "  "
   ::= { gepoel2esw12OnuVlanOption 1 }

gepoel2esw12OnuVlanOptionEntry OBJECT-TYPE
   SYNTAX      GEPoEL2ESW12OnuVlanOptionEntry
   MAX-ACCESS  not-accessible
   STATUS      current
   DESCRIPTION
       ""
   INDEX    { gepoel2esw12OnuVlanOptionOltPort, gepoel2esw12OnuVlanOptionMac }
   ::= { gepoel2esw12OnuVlanOptionTable 1 }

GEPoEL2ESW12OnuVlanOptionEntry ::= SEQUENCE {
   gepoel2esw12OnuVlanOptionOltPort     INTEGER,
   gepoel2esw12OnuVlanOptionMac         MacAddress,
   gepoel2esw12OnuVlanOptionEtherType   DisplayString,
   gepoel2esw12OnuVlanOptionTagUp       INTEGER,
   gepoel2esw12OnuVlanOptionTagDown     INTEGER
}

gepoel2esw12OnuVlanOptionOltPort OBJECT-TYPE
   SYNTAX      INTEGER (1..2)
   MAX-ACCESS  not-accessible
   STATUS      current
   DESCRIPTION
       " index 1: Epon-0, 2: Epon-1. "
   ::= { gepoel2esw12OnuVlanOptionEntry 1 }

gepoel2esw12OnuVlanOptionMac OBJECT-TYPE
   SYNTAX      MacAddress
   MAX-ACCESS  not-accessible
   STATUS      current
   DESCRIPTION
       "  "
   ::= { gepoel2esw12OnuVlanOptionEntry 2 }

gepoel2esw12OnuVlanOptionEtherType OBJECT-TYPE
   SYNTAX      DisplayString
   MAX-ACCESS  read-write
   STATUS      current
   DESCRIPTION
       " default: 0x8100-unsigned short(2 bytes). "
   ::= { gepoel2esw12OnuVlanOptionEntry 3 }
                                   
gepoel2esw12OnuVlanOptionTagUp OBJECT-TYPE
   SYNTAX      INTEGER (0|1)
   MAX-ACCESS  read-write
   STATUS      current
   DESCRIPTION
       " "
   ::= { gepoel2esw12OnuVlanOptionEntry 4 } 
   
gepoel2esw12OnuVlanOptionTagDown OBJECT-TYPE
   SYNTAX      INTEGER (0|1)
   MAX-ACCESS  read-write
   STATUS      current
   DESCRIPTION
       " "
   ::= { gepoel2esw12OnuVlanOptionEntry 5 } 


gepoel2esw12OnuBroadcastQueue                                         OBJECT IDENTIFIER ::= { gepoel2esw12OnuBridgeConfig 4 }

gepoel2esw12OnuBroadcastQueueTable OBJECT-TYPE
   SYNTAX      SEQUENCE OF GEPoEL2ESW12OnuBroadcastQueueEntry
   MAX-ACCESS  not-accessible
   STATUS      current
   DESCRIPTION
       "  "
   ::= { gepoel2esw12OnuBroadcastQueue 1 }

gepoel2esw12OnuBroadcastQueueEntry OBJECT-TYPE
   SYNTAX      GEPoEL2ESW12OnuBroadcastQueueEntry
   MAX-ACCESS  not-accessible
   STATUS      current
   DESCRIPTION
       ""
   INDEX    { gepoel2esw12OnuBroadcastQueueOltPort, gepoel2esw12OnuBroadcastQueueMacAddress, gepoel2esw12OnuBroadcastQueuePort }
   ::= { gepoel2esw12OnuBroadcastQueueTable 1 }

GEPoEL2ESW12OnuBroadcastQueueEntry ::= SEQUENCE {
   gepoel2esw12OnuBroadcastQueueOltPort         INTEGER,
   gepoel2esw12OnuBroadcastQueueMacAddress      MacAddress,
   gepoel2esw12OnuBroadcastQueuePort            INTEGER,
   gepoel2esw12OnuBroadcastQueueIndex           INTEGER
}

gepoel2esw12OnuBroadcastQueueOltPort OBJECT-TYPE
   SYNTAX      INTEGER (1..2)
   MAX-ACCESS  not-accessible
   STATUS      current
   DESCRIPTION
       " index 1: Epon-0, 2: Epon-1. "
   ::= { gepoel2esw12OnuBroadcastQueueEntry 1 }

gepoel2esw12OnuBroadcastQueueMacAddress OBJECT-TYPE
   SYNTAX      MacAddress
   MAX-ACCESS  not-accessible
   STATUS      current
   DESCRIPTION
       "  "
   ::= { gepoel2esw12OnuBroadcastQueueEntry 2 }

gepoel2esw12OnuBroadcastQueuePort OBJECT-TYPE
   SYNTAX      INTEGER (1..2)
   MAX-ACCESS  not-accessible
   STATUS      current
   DESCRIPTION
       " 1:port 1, 2:port 2. "
   ::= { gepoel2esw12OnuBroadcastQueueEntry 3 }
                                   
gepoel2esw12OnuBroadcastQueueIndex OBJECT-TYPE
   SYNTAX      INTEGER (0..255)
   MAX-ACCESS  read-write
   STATUS      current
   DESCRIPTION
       " 255:disable forward broadcast/multicast traffic. "
   ::= { gepoel2esw12OnuBroadcastQueueEntry 4 } 
   

gepoel2esw12OnuMiscOperationTable OBJECT-TYPE
   SYNTAX      SEQUENCE OF GEPoEL2ESW12OnuMiscOperationEntry
   MAX-ACCESS  not-accessible
   STATUS      current
   DESCRIPTION
       "  "
   ::= { gepoel2esw12OnuManagement 6 }

gepoel2esw12OnuMiscOperationEntry OBJECT-TYPE
   SYNTAX      GEPoEL2ESW12OnuMiscOperationEntry
   MAX-ACCESS  not-accessible
   STATUS      current
   DESCRIPTION
       ""
   INDEX    { gepoel2esw12OnuMiscOperationOltPort, gepoel2esw12OnuMiscOperationMacAddress }
   ::= { gepoel2esw12OnuMiscOperationTable 1 }

GEPoEL2ESW12OnuMiscOperationEntry ::= SEQUENCE {
   gepoel2esw12OnuMiscOperationOltPort          INTEGER,
   gepoel2esw12OnuMiscOperationMacAddress       MacAddress,
   gepoel2esw12OnuMiscOperationEnable           INTEGER,
   gepoel2esw12OnuMiscOperationDisable          INTEGER,
   gepoel2esw12OnuMiscOperationReset            INTEGER,
   
   gepoel2esw12OnuMiscOperationRestore          INTEGER,
   gepoel2esw12OnuMiscOperationExportFilePath   DisplayString,
   gepoel2esw12OnuMiscOperationDoExport         INTEGER,
   gepoel2esw12OnuMiscOperationImportFilePath   DisplayString,
   gepoel2esw12OnuMiscOperationDoImport         INTEGER,
   
   gepoel2esw12OnuMiscOperationRFModule         INTEGER
}

gepoel2esw12OnuMiscOperationOltPort OBJECT-TYPE
   SYNTAX      INTEGER (1..2)
   MAX-ACCESS  not-accessible
   STATUS      current
   DESCRIPTION
       " index 1: Epon-0, 2: Epon-1. "
   ::= { gepoel2esw12OnuMiscOperationEntry 1 }

gepoel2esw12OnuMiscOperationMacAddress OBJECT-TYPE
   SYNTAX      MacAddress
   MAX-ACCESS  not-accessible
   STATUS      current
   DESCRIPTION
       "  "
   ::= { gepoel2esw12OnuMiscOperationEntry 2 }

gepoel2esw12OnuMiscOperationEnable OBJECT-TYPE
   SYNTAX      INTEGER (0|1)
   MAX-ACCESS  read-write
   STATUS      current
   DESCRIPTION
       " 0: do nothing, 1: enable. "
   ::= { gepoel2esw12OnuMiscOperationEntry 3 }
                                   
gepoel2esw12OnuMiscOperationDisable OBJECT-TYPE
   SYNTAX      INTEGER (0|1)
   MAX-ACCESS  read-write
   STATUS      current
   DESCRIPTION
       " 0: do nothing, 1: disable. "
   ::= { gepoel2esw12OnuMiscOperationEntry 4 } 
   
gepoel2esw12OnuMiscOperationReset OBJECT-TYPE
   SYNTAX      INTEGER (0|1)
   MAX-ACCESS  read-write
   STATUS      current
   DESCRIPTION
       " 0: do nothing, 1: reset. "
   ::= { gepoel2esw12OnuMiscOperationEntry 5 } 

gepoel2esw12OnuMiscOperationRestore OBJECT-TYPE
   SYNTAX      INTEGER (0|1)
   MAX-ACCESS  read-write
   STATUS      current
   DESCRIPTION
       " 0: do nothing, 1: restore. "
   ::= { gepoel2esw12OnuMiscOperationEntry 6 } 

gepoel2esw12OnuMiscOperationExportFilePath OBJECT-TYPE
   SYNTAX      DisplayString
   MAX-ACCESS  read-write
   STATUS      current
   DESCRIPTION
       "  "
   ::= { gepoel2esw12OnuMiscOperationEntry 7 } 

gepoel2esw12OnuMiscOperationDoExport OBJECT-TYPE
   SYNTAX      INTEGER (0|1)
   MAX-ACCESS  read-write
   STATUS      current
   DESCRIPTION
       " 0: do nothing, 1: export onu config file. "
   ::= { gepoel2esw12OnuMiscOperationEntry 8 } 

gepoel2esw12OnuMiscOperationImportFilePath OBJECT-TYPE
   SYNTAX      DisplayString
   MAX-ACCESS  read-write
   STATUS      current
   DESCRIPTION
       " "
   ::= { gepoel2esw12OnuMiscOperationEntry 9 } 

gepoel2esw12OnuMiscOperationDoImport OBJECT-TYPE
   SYNTAX      INTEGER (0|1)
   MAX-ACCESS  read-write
   STATUS      current
   DESCRIPTION
       " 0: do nothing, 1: import onu config file. "
   ::= { gepoel2esw12OnuMiscOperationEntry 10 } 

gepoel2esw12OnuMiscOperationRFModule OBJECT-TYPE
   SYNTAX      INTEGER (-1|0|1)
   MAX-ACCESS  read-write
   STATUS      current
   DESCRIPTION
       " "
   ::= { gepoel2esw12OnuMiscOperationEntry 11 } 


gepoel2esw12OnuGreenPonTable OBJECT-TYPE
   SYNTAX      SEQUENCE OF GEPoEL2ESW12OnuGreenPonEntry
   MAX-ACCESS  not-accessible
   STATUS      current
   DESCRIPTION
       "  "
   ::= { gepoel2esw12OnuManagement 7 }

gepoel2esw12OnuGreenPonEntry OBJECT-TYPE
   SYNTAX      GEPoEL2ESW12OnuGreenPonEntry
   MAX-ACCESS  not-accessible
   STATUS      current
   DESCRIPTION
       ""
   INDEX    { gepoel2esw12OnuGreenPonOltPort, gepoel2esw12OnuGreenPonMacAddress }
   ::= { gepoel2esw12OnuGreenPonTable 1 }

GEPoEL2ESW12OnuGreenPonEntry ::= SEQUENCE {
   gepoel2esw12OnuGreenPonOltPort               INTEGER,
   gepoel2esw12OnuGreenPonMacAddress            MacAddress,
   gepoel2esw12OnuGreenPonEnable                INTEGER,
   gepoel2esw12OnuPowerSaveEnable               INTEGER,
   gepoel2esw12OnuGreenPonPDnLaserTransmit      INTEGER,
   
   gepoel2esw12OnuGreenPonPDnLaserRecv          INTEGER,
   gepoel2esw12OnuGreenPonPDnSerdes             INTEGER
}

gepoel2esw12OnuGreenPonOltPort OBJECT-TYPE
   SYNTAX      INTEGER (1..2)
   MAX-ACCESS  not-accessible
   STATUS      current
   DESCRIPTION
       " index 1: Epon-0, 2: Epon-1. "
   ::= { gepoel2esw12OnuGreenPonEntry 1 }

gepoel2esw12OnuGreenPonMacAddress OBJECT-TYPE
   SYNTAX      MacAddress
   MAX-ACCESS  not-accessible
   STATUS      current
   DESCRIPTION
       "  "
   ::= { gepoel2esw12OnuGreenPonEntry 2 }

gepoel2esw12OnuGreenPonEnable OBJECT-TYPE
   SYNTAX      INTEGER (0|1)
   MAX-ACCESS  read-write
   STATUS      current
   DESCRIPTION
       " "
   ::= { gepoel2esw12OnuGreenPonEntry 3 }
                                   
gepoel2esw12OnuPowerSaveEnable OBJECT-TYPE
   SYNTAX      INTEGER (9999)
   MAX-ACCESS  read-only
   STATUS      current
   DESCRIPTION
       " "
   ::= { gepoel2esw12OnuGreenPonEntry 4 } 
   
gepoel2esw12OnuGreenPonPDnLaserTransmit OBJECT-TYPE
   SYNTAX      INTEGER (9999)
   MAX-ACCESS  read-only
   STATUS      current
   DESCRIPTION
       " "
   ::= { gepoel2esw12OnuGreenPonEntry 5 } 

gepoel2esw12OnuGreenPonPDnLaserRecv OBJECT-TYPE
   SYNTAX      INTEGER (9999)
   MAX-ACCESS  read-only
   STATUS      current
   DESCRIPTION
       " "
   ::= { gepoel2esw12OnuGreenPonEntry 6 } 

gepoel2esw12OnuGreenPonPDnSerdes OBJECT-TYPE
   SYNTAX      INTEGER (9999)
   MAX-ACCESS  read-only
   STATUS      current
   DESCRIPTION
       "  "
   ::= { gepoel2esw12OnuGreenPonEntry 7 } 


gepoel2esw12OnuAuthorization                                         OBJECT IDENTIFIER ::= { gepoel2esw12OnuManagement 8 }

gepoel2esw12OnuAuthorizationTable OBJECT-TYPE
   SYNTAX      SEQUENCE OF GEPoEL2ESW12OnuAuthorizationEntry
   MAX-ACCESS  not-accessible
   STATUS      current
   DESCRIPTION
       "  "
   ::= { gepoel2esw12OnuAuthorization 1 }

gepoel2esw12OnuAuthorizationEntry OBJECT-TYPE
   SYNTAX      GEPoEL2ESW12OnuAuthorizationEntry
   MAX-ACCESS  not-accessible
   STATUS      current
   DESCRIPTION
       ""
   INDEX    { gepoel2esw12OnuAuthorizationOltPort, gepoel2esw12OnuAuthorizationMacAddress }
   ::= { gepoel2esw12OnuAuthorizationTable 1 }

GEPoEL2ESW12OnuAuthorizationEntry ::= SEQUENCE {
   gepoel2esw12OnuAuthorizationOltPort      INTEGER,
   gepoel2esw12OnuAuthorizationMacAddress   MacAddress,
   gepoel2esw12OnuAuthorizationAllLinks     INTEGER,
   gepoel2esw12OnuAuthorizationStatus       DisplayString,
   gepoel2esw12OnuAuthorizations            DisplayString,
   gepoel2esw12OnuAuthorize                 INTEGER
}

gepoel2esw12OnuAuthorizationOltPort OBJECT-TYPE
   SYNTAX      INTEGER (1..2)
   MAX-ACCESS  not-accessible
   STATUS      current
   DESCRIPTION
       " index 1: Epon-0, 2: Epon-1. "
   ::= { gepoel2esw12OnuAuthorizationEntry 1 }

gepoel2esw12OnuAuthorizationMacAddress OBJECT-TYPE
   SYNTAX      MacAddress
   MAX-ACCESS  not-accessible
   STATUS      current
   DESCRIPTION
       "  "
   ::= { gepoel2esw12OnuAuthorizationEntry 2 }

gepoel2esw12OnuAuthorizationAllLinks OBJECT-TYPE
   SYNTAX      INTEGER (1..8)
   MAX-ACCESS  read-only
   STATUS      current
   DESCRIPTION
       " "
   ::= { gepoel2esw12OnuAuthorizationEntry 3 }
                                   
gepoel2esw12OnuAuthorizationStatus OBJECT-TYPE
   SYNTAX      DisplayString
   MAX-ACCESS  read-only
   STATUS      current
   DESCRIPTION
       " "
   ::= { gepoel2esw12OnuAuthorizationEntry 4 } 
   
gepoel2esw12OnuAuthorizations OBJECT-TYPE
   SYNTAX      DisplayString
   MAX-ACCESS  read-only
   STATUS      current
   DESCRIPTION
       " "
   ::= { gepoel2esw12OnuAuthorizationEntry 5 } 

gepoel2esw12OnuAuthorize OBJECT-TYPE
   SYNTAX      INTEGER (-1|0|1)
   MAX-ACCESS  read-write
   STATUS      current
   DESCRIPTION
       " 0: UnAuthorize Onu, 1: Authorize Onu, -1:do nothing. "
   ::= { gepoel2esw12OnuAuthorizationEntry 6 } 


gepoel2esw12OnuAuthorizationAdd                                    OBJECT IDENTIFIER ::= { gepoel2esw12OnuAuthorization 2 }

gepoel2esw12OnuAuthorizationAddOltPort OBJECT-TYPE
   SYNTAX      INTEGER (1..2)
   MAX-ACCESS  read-write
   STATUS      current
   DESCRIPTION
       " 1: Epon-0, 2: Epon-1. "
   ::= { gepoel2esw12OnuAuthorizationAdd 1 } 
   
gepoel2esw12OnuAuthorizationAddOnuMac OBJECT-TYPE
   SYNTAX      MacAddress
   MAX-ACCESS  read-write
   STATUS      current
   DESCRIPTION
       " "
   ::= { gepoel2esw12OnuAuthorizationAdd 2 } 
   
gepoel2esw12OnuAuthorizationAddLinkNumber OBJECT-TYPE
   SYNTAX      INTEGER (1..8)
   MAX-ACCESS  read-write
   STATUS      current
   DESCRIPTION
       "  "
   ::= { gepoel2esw12OnuAuthorizationAdd 3 } 
   
gepoel2esw12OnuAuthorizationAddDo OBJECT-TYPE
   SYNTAX      INTEGER (0|1)
   MAX-ACCESS  read-write
   STATUS      current
   DESCRIPTION
       " 0:do nothing , 1: add one authorization. "
   ::= { gepoel2esw12OnuAuthorizationAdd 4 } 
   




----------------------------------------------------------------------------------------------------------------------------------------

gepoel2esw12LlidManagement                                         OBJECT IDENTIFIER ::= { gepoel2esw12ProductId 4 }

gepoel2esw12LinkQue                                                  OBJECT IDENTIFIER ::= { gepoel2esw12LlidManagement 1 }

gepoel2esw12LinkSLATable OBJECT-TYPE
   SYNTAX      SEQUENCE OF GEPoEL2ESW12LinkSLAEntry
   MAX-ACCESS  not-accessible
   STATUS      current
   DESCRIPTION
       " Show Link SLA Table. "
   ::= { gepoel2esw12LinkQue 1 }

gepoel2esw12LinkSLAEntry OBJECT-TYPE
   SYNTAX      GEPoEL2ESW12LinkSLAEntry
   MAX-ACCESS  not-accessible
   STATUS      current
   DESCRIPTION
       ""
   INDEX    { gepoel2esw12LinkOltPort, gepoel2esw12LinkMacAddress }
   ::= { gepoel2esw12LinkSLATable 1 }

GEPoEL2ESW12LinkSLAEntry ::= SEQUENCE {
   gepoel2esw12LinkOltPort                          INTEGER,
   gepoel2esw12LinkMacAddress                       MacAddress,
   gepoel2esw12LinkSLAMinShaperEnable               INTEGER,
   gepoel2esw12LinkSLAMaxShaperMaxBw                INTEGER,
   gepoel2esw12LinkSLAMaxShaperMaxBurst             INTEGER,
   gepoel2esw12LinkSLAMaxShaperSchedulerLevel       INTEGER,
   gepoel2esw12LinkSLAMaxShaperSchedulerWeight      INTEGER,
   gepoel2esw12LinkSLAMinShaperMinBw                INTEGER,
   gepoel2esw12LinkSLAMinShaperMaxBurst             INTEGER,
   gepoel2esw12LinkSLAMinShaperSchedulerLevel       INTEGER,
   gepoel2esw12LinkSLAMinShaperSchedulerWeight      INTEGER
}

gepoel2esw12LinkOltPort OBJECT-TYPE
   SYNTAX      INTEGER (1..2)
   MAX-ACCESS  not-accessible
   STATUS      current
   DESCRIPTION
       " index 1: Epon-0, 2: Epon-1. "
   ::= { gepoel2esw12LinkSLAEntry 1 }

gepoel2esw12LinkMacAddress OBJECT-TYPE
   SYNTAX      MacAddress
   MAX-ACCESS  not-accessible
   STATUS      current
   DESCRIPTION
       "  "
   ::= { gepoel2esw12LinkSLAEntry 2 }

gepoel2esw12LinkSLAMinShaperEnable OBJECT-TYPE
   SYNTAX      INTEGER (0|1)
   MAX-ACCESS  read-write
   STATUS      current
   DESCRIPTION
       " 0:disable, 1:enable. "
   ::= { gepoel2esw12LinkSLAEntry 3 }

gepoel2esw12LinkSLAMaxShaperMaxBw OBJECT-TYPE
   SYNTAX      INTEGER (256..1000000)
   MAX-ACCESS  read-write
   STATUS      current
   DESCRIPTION
       " range : 256 - 1000000. "
   ::= { gepoel2esw12LinkSLAEntry 4 }

gepoel2esw12LinkSLAMaxShaperMaxBurst OBJECT-TYPE
   SYNTAX      INTEGER (1..256)
   MAX-ACCESS  read-write
   STATUS      current
   DESCRIPTION
       " range : 1 - 256. "
   ::= { gepoel2esw12LinkSLAEntry 5 }

gepoel2esw12LinkSLAMaxShaperSchedulerLevel OBJECT-TYPE
   SYNTAX      INTEGER (0..7)
   MAX-ACCESS  read-write
   STATUS      current
   DESCRIPTION
       " range : 0 - 7. "
   ::= { gepoel2esw12LinkSLAEntry 6 }

gepoel2esw12LinkSLAMaxShaperSchedulerWeight OBJECT-TYPE
   SYNTAX      INTEGER (2..32)
   MAX-ACCESS  read-write
   STATUS      current
   DESCRIPTION
       " range : 2 - 32. "
   ::= { gepoel2esw12LinkSLAEntry 7 }

gepoel2esw12LinkSLAMinShaperMinBw OBJECT-TYPE
   SYNTAX      INTEGER (0|256..1000000)
   MAX-ACCESS  read-write
   STATUS      current
   DESCRIPTION
       " range : 256 - 1000000 or 0. "
   ::= { gepoel2esw12LinkSLAEntry 8 }
   
gepoel2esw12LinkSLAMinShaperMaxBurst OBJECT-TYPE
   SYNTAX      INTEGER (1..256)
   MAX-ACCESS  read-write
   STATUS      current
   DESCRIPTION
       " range : 1 - 256. "
   ::= { gepoel2esw12LinkSLAEntry 9 }
   
gepoel2esw12LinkSLAMinShaperSchedulerLevel OBJECT-TYPE
   SYNTAX      INTEGER (0..7)
   MAX-ACCESS  read-write
   STATUS      current
   DESCRIPTION
       " range : 0 - 7. "
   ::= { gepoel2esw12LinkSLAEntry 10 }
   
gepoel2esw12LinkSLAMinShaperSchedulerWeight OBJECT-TYPE
   SYNTAX      INTEGER (2..32)
   MAX-ACCESS  read-write
   STATUS      current
   DESCRIPTION
       " range : 2 - 32. "
   ::= { gepoel2esw12LinkSLAEntry 11 }


gepoel2esw12LinkUpQSLATable OBJECT-TYPE
   SYNTAX      SEQUENCE OF GEPoEL2ESW12LinkUpQSLAEntry
   MAX-ACCESS  not-accessible
   STATUS      current
   DESCRIPTION
       " Show Link Up QSLA Table. "
   ::= { gepoel2esw12LinkQue 2 }

gepoel2esw12LinkUpQSLAEntry OBJECT-TYPE
   SYNTAX      GEPoEL2ESW12LinkUpQSLAEntry
   MAX-ACCESS  not-accessible
   STATUS      current
   DESCRIPTION
       ""
   INDEX    { gepoel2esw12LinkUpQOltPort, gepoel2esw12LinkUpQMacAddress }
   ::= { gepoel2esw12LinkUpQSLATable 1 }

GEPoEL2ESW12LinkUpQSLAEntry ::= SEQUENCE {
   gepoel2esw12LinkUpQOltPort                          INTEGER,
   gepoel2esw12LinkUpQMacAddress                       MacAddress,
   gepoel2esw12LinkUpQSLAMinShaperEnable               INTEGER,
   gepoel2esw12LinkUpQSLAMaxShaperMaxBw                INTEGER,
   gepoel2esw12LinkUpQSLAMaxShaperMaxBurst             INTEGER,
   gepoel2esw12LinkUpQSLAMaxShaperSchedulerLevel       INTEGER,
   gepoel2esw12LinkUpQSLAMaxShaperSchedulerWeight      INTEGER,
   gepoel2esw12LinkUpQSLAMinShaperMinBw                INTEGER,
   gepoel2esw12LinkUpQSLAMinShaperMaxBurst             INTEGER,
   gepoel2esw12LinkUpQSLAMinShaperSchedulerLevel       INTEGER,
   gepoel2esw12LinkUpQSLAMinShaperSchedulerWeight      INTEGER
}

gepoel2esw12LinkUpQOltPort OBJECT-TYPE
   SYNTAX      INTEGER (1..2)
   MAX-ACCESS  not-accessible
   STATUS      current
   DESCRIPTION
       " index 1: Epon-0, 2: Epon-1. "
   ::= { gepoel2esw12LinkUpQSLAEntry 1 }

gepoel2esw12LinkUpQMacAddress OBJECT-TYPE
   SYNTAX      MacAddress
   MAX-ACCESS  not-accessible
   STATUS      current
   DESCRIPTION
       "  "
   ::= { gepoel2esw12LinkUpQSLAEntry 2 }

gepoel2esw12LinkUpQSLAMinShaperEnable OBJECT-TYPE
   SYNTAX      INTEGER (256..1000000)
   MAX-ACCESS  read-write
   STATUS      current
   DESCRIPTION
       " range : 256 - 1000000. "
   ::= { gepoel2esw12LinkUpQSLAEntry 3 }
   
gepoel2esw12LinkUpQSLAMaxShaperMaxBw OBJECT-TYPE
   SYNTAX      INTEGER (256..1000000)
   MAX-ACCESS  read-write
   STATUS      current
   DESCRIPTION
       " range : 256 - 1000000. "
   ::= { gepoel2esw12LinkUpQSLAEntry 4 }

gepoel2esw12LinkUpQSLAMaxShaperMaxBurst OBJECT-TYPE
   SYNTAX      INTEGER (1..256)
   MAX-ACCESS  read-write
   STATUS      current
   DESCRIPTION
       " range : 1 - 256. "
   ::= { gepoel2esw12LinkUpQSLAEntry 5 }

gepoel2esw12LinkUpQSLAMaxShaperSchedulerLevel OBJECT-TYPE
   SYNTAX      INTEGER (0..7)
   MAX-ACCESS  read-write
   STATUS      current
   DESCRIPTION
       " range : 0 - 7. "
   ::= { gepoel2esw12LinkUpQSLAEntry 6 }

gepoel2esw12LinkUpQSLAMaxShaperSchedulerWeight OBJECT-TYPE
   SYNTAX      INTEGER (2..32)
   MAX-ACCESS  read-write
   STATUS      current
   DESCRIPTION
       " range : 2 - 32. "
   ::= { gepoel2esw12LinkUpQSLAEntry 7 }

gepoel2esw12LinkUpQSLAMinShaperMinBw OBJECT-TYPE
   SYNTAX      INTEGER (0|256..1000000)
   MAX-ACCESS  read-write
   STATUS      current
   DESCRIPTION
       " range : 256 - 1000000 or 0. "
   ::= { gepoel2esw12LinkUpQSLAEntry 8 }
   
gepoel2esw12LinkUpQSLAMinShaperMaxBurst OBJECT-TYPE
   SYNTAX      INTEGER (1..256)
   MAX-ACCESS  read-write
   STATUS      current
   DESCRIPTION
       " range : 1 - 256. "
   ::= { gepoel2esw12LinkUpQSLAEntry 9 }
   
gepoel2esw12LinkUpQSLAMinShaperSchedulerLevel OBJECT-TYPE
   SYNTAX      INTEGER (0..7)
   MAX-ACCESS  read-write
   STATUS      current
   DESCRIPTION
       " range : 0 - 7. "
   ::= { gepoel2esw12LinkUpQSLAEntry 10 }
   
gepoel2esw12LinkUpQSLAMinShaperSchedulerWeight OBJECT-TYPE
   SYNTAX      INTEGER (2..32)
   MAX-ACCESS  read-write
   STATUS      current
   DESCRIPTION
       " range : 2 - 32. "
   ::= { gepoel2esw12LinkUpQSLAEntry 11 }


gepoel2esw12LinkDnQSLATable OBJECT-TYPE
   SYNTAX      SEQUENCE OF GEPoEL2ESW12LinkDnQSLAEntry
   MAX-ACCESS  not-accessible
   STATUS      current
   DESCRIPTION
       " Show Link Down QSLA Table. "
   ::= { gepoel2esw12LinkQue 3 }

gepoel2esw12LinkDnQSLAEntry OBJECT-TYPE
   SYNTAX      GEPoEL2ESW12LinkDnQSLAEntry
   MAX-ACCESS  not-accessible
   STATUS      current
   DESCRIPTION
       ""
   INDEX    { gepoel2esw12LinkDnQOltPort, gepoel2esw12LinkDnQMacAddress }
   ::= { gepoel2esw12LinkDnQSLATable 1 }

GEPoEL2ESW12LinkDnQSLAEntry ::= SEQUENCE {
   gepoel2esw12LinkDnQOltPort                          INTEGER,
   gepoel2esw12LinkDnQMacAddress                       MacAddress,
   gepoel2esw12LinkDnQSLAMinShaperEnable               INTEGER,   
   gepoel2esw12LinkDnQSLAMaxShaperMaxBw                INTEGER,
   gepoel2esw12LinkDnQSLAMaxShaperMaxBurst             INTEGER,
   gepoel2esw12LinkDnQSLAMaxShaperSchedulerLevel       INTEGER,
   gepoel2esw12LinkDnQSLAMaxShaperSchedulerWeight      INTEGER,
   gepoel2esw12LinkDnQSLAMinShaperMinBw                INTEGER,
   gepoel2esw12LinkDnQSLAMinShaperMaxBurst             INTEGER,
   gepoel2esw12LinkDnQSLAMinShaperSchedulerLevel       INTEGER,
   gepoel2esw12LinkDnQSLAMinShaperSchedulerWeight      INTEGER
}

gepoel2esw12LinkDnQOltPort OBJECT-TYPE
   SYNTAX      INTEGER (1..2)
   MAX-ACCESS  not-accessible
   STATUS      current
   DESCRIPTION
       " index 1: Epon-0, 2: Epon-1. "
   ::= { gepoel2esw12LinkDnQSLAEntry 1 }

gepoel2esw12LinkDnQMacAddress OBJECT-TYPE
   SYNTAX      MacAddress
   MAX-ACCESS  not-accessible
   STATUS      current
   DESCRIPTION
       "  "
   ::= { gepoel2esw12LinkDnQSLAEntry 2 }

gepoel2esw12LinkDnQSLAMinShaperEnable OBJECT-TYPE
   SYNTAX      INTEGER (256..1000000)
   MAX-ACCESS  read-write
   STATUS      current
   DESCRIPTION
       " range : 256 - 1000000. "
   ::= { gepoel2esw12LinkDnQSLAEntry 3 }

gepoel2esw12LinkDnQSLAMaxShaperMaxBw OBJECT-TYPE
   SYNTAX      INTEGER (256..1000000)
   MAX-ACCESS  read-write
   STATUS      current
   DESCRIPTION
       " range : 256 - 1000000. "
   ::= { gepoel2esw12LinkDnQSLAEntry 4 }

gepoel2esw12LinkDnQSLAMaxShaperMaxBurst OBJECT-TYPE
   SYNTAX      INTEGER (1..256)
   MAX-ACCESS  read-write
   STATUS      current
   DESCRIPTION
       " range : 1 - 256. "
   ::= { gepoel2esw12LinkDnQSLAEntry 5 }

gepoel2esw12LinkDnQSLAMaxShaperSchedulerLevel OBJECT-TYPE
   SYNTAX      INTEGER (0..7)
   MAX-ACCESS  read-write
   STATUS      current
   DESCRIPTION
       " range : 0 - 7. "
   ::= { gepoel2esw12LinkDnQSLAEntry 6 }

gepoel2esw12LinkDnQSLAMaxShaperSchedulerWeight OBJECT-TYPE
   SYNTAX      INTEGER (2..32)
   MAX-ACCESS  read-write
   STATUS      current
   DESCRIPTION
       " range : 2 - 32. "
   ::= { gepoel2esw12LinkDnQSLAEntry 7 }

gepoel2esw12LinkDnQSLAMinShaperMinBw OBJECT-TYPE
   SYNTAX      INTEGER (0|256..1000000)
   MAX-ACCESS  read-write
   STATUS      current
   DESCRIPTION
       " range : 256 - 1000000 or 0. "
   ::= { gepoel2esw12LinkDnQSLAEntry 8 }
   
gepoel2esw12LinkDnQSLAMinShaperMaxBurst OBJECT-TYPE
   SYNTAX      INTEGER (1..256)
   MAX-ACCESS  read-write
   STATUS      current
   DESCRIPTION
       " range : 1 - 256. "
   ::= { gepoel2esw12LinkDnQSLAEntry 9 }
   
gepoel2esw12LinkDnQSLAMinShaperSchedulerLevel OBJECT-TYPE
   SYNTAX      INTEGER (0..7)
   MAX-ACCESS  read-write
   STATUS      current
   DESCRIPTION
       " range : 0 - 7. "
   ::= { gepoel2esw12LinkDnQSLAEntry 10 }
   
gepoel2esw12LinkDnQSLAMinShaperSchedulerWeight OBJECT-TYPE
   SYNTAX      INTEGER (2..32)
   MAX-ACCESS  read-write
   STATUS      current
   DESCRIPTION
       " range : 2 - 32. "
   ::= { gepoel2esw12LinkDnQSLAEntry 11 }


gepoel2esw12LinkMulticastSLATable OBJECT-TYPE
   SYNTAX      SEQUENCE OF GEPoEL2ESW12LinkMulticastSLAEntry
   MAX-ACCESS  not-accessible
   STATUS      current
   DESCRIPTION
       " Show Link Multicast SLA Table. "
   ::= { gepoel2esw12LlidManagement 2 }

gepoel2esw12LinkMulticastSLAEntry OBJECT-TYPE
   SYNTAX      GEPoEL2ESW12LinkMulticastSLAEntry
   MAX-ACCESS  not-accessible
   STATUS      current
   DESCRIPTION
       ""
   INDEX    { gepoel2esw12LinkMulticastOltPort, gepoel2esw12LinkMulticastMacAddress }
   ::= { gepoel2esw12LinkMulticastSLATable 1 }

GEPoEL2ESW12LinkMulticastSLAEntry ::= SEQUENCE {
   gepoel2esw12LinkMulticastOltPort                          INTEGER,
   gepoel2esw12LinkMulticastMacAddress                       MacAddress,
   gepoel2esw12LinkMulticastSLAMinShaperEnable               INTEGER,   
   gepoel2esw12LinkMulticastSLAMaxShaperMaxBw                INTEGER,
   gepoel2esw12LinkMulticastSLAMaxShaperMaxBurst             INTEGER,
   gepoel2esw12LinkMulticastSLAMaxShaperSchedulerLevel       INTEGER,
   gepoel2esw12LinkMulticastSLAMaxShaperSchedulerWeight      INTEGER,
   gepoel2esw12LinkMulticastSLAMinShaperMinBw                INTEGER,
   gepoel2esw12LinkMulticastSLAMinShaperMaxBurst             INTEGER,
   gepoel2esw12LinkMulticastSLAMinShaperSchedulerLevel       INTEGER,
   gepoel2esw12LinkMulticastSLAMinShaperSchedulerWeight      INTEGER
}

gepoel2esw12LinkMulticastOltPort OBJECT-TYPE
   SYNTAX      INTEGER (1..2)
   MAX-ACCESS  not-accessible
   STATUS      current
   DESCRIPTION
       " index 1: Epon-0, 2: Epon-1. "
   ::= { gepoel2esw12LinkMulticastSLAEntry 1 }

gepoel2esw12LinkMulticastMacAddress OBJECT-TYPE
   SYNTAX      MacAddress
   MAX-ACCESS  not-accessible
   STATUS      current
   DESCRIPTION
       "  "
   ::= { gepoel2esw12LinkMulticastSLAEntry 2 }

gepoel2esw12LinkMulticastSLAMinShaperEnable OBJECT-TYPE
   SYNTAX      INTEGER (0|1)
   MAX-ACCESS  read-write
   STATUS      current
   DESCRIPTION
       ""
   ::= { gepoel2esw12LinkMulticastSLAEntry 3 }

gepoel2esw12LinkMulticastSLAMaxShaperMaxBw OBJECT-TYPE
   SYNTAX      INTEGER (256..1000000)
   MAX-ACCESS  read-write
   STATUS      current
   DESCRIPTION
       " range : 256 - 1000000. "
   ::= { gepoel2esw12LinkMulticastSLAEntry 4 }

gepoel2esw12LinkMulticastSLAMaxShaperMaxBurst OBJECT-TYPE
   SYNTAX      INTEGER (1..256)
   MAX-ACCESS  read-write
   STATUS      current
   DESCRIPTION
       " range : 1 - 256. "
   ::= { gepoel2esw12LinkMulticastSLAEntry 5 }

gepoel2esw12LinkMulticastSLAMaxShaperSchedulerLevel OBJECT-TYPE
   SYNTAX      INTEGER (0..7)
   MAX-ACCESS  read-write
   STATUS      current
   DESCRIPTION
       " range : 0 - 7. "
   ::= { gepoel2esw12LinkMulticastSLAEntry 6 }

gepoel2esw12LinkMulticastSLAMaxShaperSchedulerWeight OBJECT-TYPE
   SYNTAX      INTEGER (2..32)
   MAX-ACCESS  read-write
   STATUS      current
   DESCRIPTION
       " range : 2 - 32. "
   ::= { gepoel2esw12LinkMulticastSLAEntry 7 }

gepoel2esw12LinkMulticastSLAMinShaperMinBw OBJECT-TYPE
   SYNTAX      INTEGER (0|256..1000000)
   MAX-ACCESS  read-write
   STATUS      current
   DESCRIPTION
       " range : 256 - 1000000 or 0. "
   ::= { gepoel2esw12LinkMulticastSLAEntry 8 }
   
gepoel2esw12LinkMulticastSLAMinShaperMaxBurst OBJECT-TYPE
   SYNTAX      INTEGER (1..256)
   MAX-ACCESS  read-write
   STATUS      current
   DESCRIPTION
       " range : 1 - 256. "
   ::= { gepoel2esw12LinkMulticastSLAEntry 9 }
   
gepoel2esw12LinkMulticastSLAMinShaperSchedulerLevel OBJECT-TYPE
   SYNTAX      INTEGER (0..7)
   MAX-ACCESS  read-write
   STATUS      current
   DESCRIPTION
       " range : 0 - 7. "
   ::= { gepoel2esw12LinkMulticastSLAEntry 10 }
   
gepoel2esw12LinkMulticastSLAMinShaperSchedulerWeight OBJECT-TYPE
   SYNTAX      INTEGER (2..32)
   MAX-ACCESS  read-write
   STATUS      current
   DESCRIPTION
       " range : 2 - 32. "
   ::= { gepoel2esw12LinkMulticastSLAEntry 11 }


gepoel2esw12LinkBridge                                                  OBJECT IDENTIFIER ::= { gepoel2esw12LlidManagement 3 }

gepoel2esw12LinkBridgeModeTable OBJECT-TYPE
   SYNTAX      SEQUENCE OF GEPoEL2ESW12LinkBridgeModeEntry
   MAX-ACCESS  not-accessible
   STATUS      current
   DESCRIPTION
       " Show Link Bridge Mode Table. "
   ::= { gepoel2esw12LinkBridge 1 }

gepoel2esw12LinkBridgeModeEntry OBJECT-TYPE
   SYNTAX      GEPoEL2ESW12LinkBridgeModeEntry
   MAX-ACCESS  not-accessible
   STATUS      current
   DESCRIPTION
       ""
   INDEX    { gepoel2esw12LinkBridgeOltPort, gepoel2esw12LinkBridgeLinkMacAddress }
   ::= { gepoel2esw12LinkBridgeModeTable 1 }

GEPoEL2ESW12LinkBridgeModeEntry ::= SEQUENCE {
   gepoel2esw12LinkBridgeOltPort            INTEGER,
   gepoel2esw12LinkBridgeLinkMacAddress     MacAddress,
   gepoel2esw12LinkBridgeMode               INTEGER,
   gepoel2esw12LinkBridgeDestNNI            INTEGER,
   gepoel2esw12LinkEntryLimit               INTEGER,
   gepoel2esw12LinkVlan                     DisplayString,
   gepoel2esw12LinkUpstreamCoS              INTEGER,
   gepoel2esw12LinkMaxToSCoS                INTEGER,
   gepoel2esw12LinkMinToSCoS                INTEGER,
   gepoel2esw12LinkUsingCosTos              INTEGER,
   gepoel2esw12LinkNonIP                    INTEGER
}

gepoel2esw12LinkBridgeOltPort OBJECT-TYPE
   SYNTAX      INTEGER (1..2)
   MAX-ACCESS  not-accessible
   STATUS      current
   DESCRIPTION
       " index 1: Epon-0, 2: Epon-1. "
   ::= { gepoel2esw12LinkBridgeModeEntry 1 }

gepoel2esw12LinkBridgeLinkMacAddress OBJECT-TYPE
   SYNTAX      MacAddress
   MAX-ACCESS  not-accessible
   STATUS      current
   DESCRIPTION
       "  "
   ::= { gepoel2esw12LinkBridgeModeEntry 2 }

gepoel2esw12LinkBridgeMode OBJECT-TYPE
   SYNTAX      INTEGER (-1..15)
   MAX-ACCESS  read-only
   STATUS      current
   DESCRIPTION
       " range : -1 ~ 15. "
   ::= { gepoel2esw12LinkBridgeModeEntry 3 }

gepoel2esw12LinkBridgeDestNNI OBJECT-TYPE
   SYNTAX      INTEGER (1..2)
   MAX-ACCESS  read-only
   STATUS      current
   DESCRIPTION
       " 1: NNI-0, 2: NNI-1. "
   ::= { gepoel2esw12LinkBridgeModeEntry 4 }

gepoel2esw12LinkEntryLimit OBJECT-TYPE
   SYNTAX      INTEGER (0..999)
   MAX-ACCESS  read-only
   STATUS      current
   DESCRIPTION
       " range : 0 - 999. "
   ::= { gepoel2esw12LinkBridgeModeEntry 5 }

gepoel2esw12LinkVlan OBJECT-TYPE
   SYNTAX      DisplayString
   MAX-ACCESS  read-only
   STATUS      current
   DESCRIPTION
       " range : 1 - 4094. "
   ::= { gepoel2esw12LinkBridgeModeEntry 6 }

gepoel2esw12LinkUpstreamCoS OBJECT-TYPE
   SYNTAX      INTEGER (0..7)
   MAX-ACCESS  read-only
   STATUS      current
   DESCRIPTION
       " range : 0 - 7. "
   ::= { gepoel2esw12LinkBridgeModeEntry 7 }
   
gepoel2esw12LinkMaxToSCoS OBJECT-TYPE
   SYNTAX      INTEGER (-1..7)
   MAX-ACCESS  read-only
   STATUS      current
   DESCRIPTION
       " range : -1 - 7. -1:not exist"
   ::= { gepoel2esw12LinkBridgeModeEntry 8 }
   
gepoel2esw12LinkMinToSCoS OBJECT-TYPE
   SYNTAX      INTEGER (-1..7)
   MAX-ACCESS  read-only
   STATUS      current
   DESCRIPTION
       " range : -1 - 7. -1:not exist"
   ::= { gepoel2esw12LinkBridgeModeEntry 9 }
   
gepoel2esw12LinkUsingCosTos OBJECT-TYPE
   SYNTAX      INTEGER (-1|0|1)
   MAX-ACCESS  read-only
   STATUS      current
   DESCRIPTION
       " 0:CoS, 1:ToS. -1:not exist"
   ::= { gepoel2esw12LinkBridgeModeEntry 10 }  
   
gepoel2esw12LinkNonIP OBJECT-TYPE
   SYNTAX      INTEGER (-1|0|1)
   MAX-ACCESS  read-only
   STATUS      current
   DESCRIPTION
       "-1:not exist"
   ::= { gepoel2esw12LinkBridgeModeEntry 11 }


gepoel2esw12LinkBridgeModeDel                                    OBJECT IDENTIFIER ::= { gepoel2esw12LinkBridge 2 }

gepoel2esw12LinkDelBridgeOltPort OBJECT-TYPE
   SYNTAX      INTEGER (1..2)
   MAX-ACCESS  read-write
   STATUS      current
   DESCRIPTION
       " index 1:Epon-0, 2: Epon-1. "
   ::= { gepoel2esw12LinkBridgeModeDel 1 } 
   
gepoel2esw12LinkDelBridgeLinkMacAddress OBJECT-TYPE
   SYNTAX      MacAddress
   MAX-ACCESS  read-write
   STATUS      current
   DESCRIPTION
       " "
   ::= { gepoel2esw12LinkBridgeModeDel 2 } 
   
gepoel2esw12LinkDelBridgeMode OBJECT-TYPE
   SYNTAX      INTEGER (0..15)
   MAX-ACCESS  read-write
   STATUS      current
   DESCRIPTION
       " "
   ::= { gepoel2esw12LinkBridgeModeDel 3 } 
   
gepoel2esw12D0DelLinkBridgeMode OBJECT-TYPE
   SYNTAX      INTEGER (0|1)
   MAX-ACCESS  read-write
   STATUS      current
   DESCRIPTION
       " 0:do nothing, 1: del. "
   ::= { gepoel2esw12LinkBridgeModeDel 4 }


gepoel2esw12LinkBridgeModeAdd                                    OBJECT IDENTIFIER ::= { gepoel2esw12LinkBridge 3 }

gepoel2esw12LinkAddBridgeOltPort OBJECT-TYPE
   SYNTAX      INTEGER (1..2)
   MAX-ACCESS  read-write
   STATUS      current
   DESCRIPTION
       " index 1:Epon-0, 2: Epon-1. "
   ::= { gepoel2esw12LinkBridgeModeAdd 1 } 
   
gepoel2esw12LinkAddBridgeLinkMacAddress OBJECT-TYPE
   SYNTAX      MacAddress
   MAX-ACCESS  read-write
   STATUS      current
   DESCRIPTION
       " "
   ::= { gepoel2esw12LinkBridgeModeAdd 2 } 
   
gepoel2esw12LinkAddBridgeMode OBJECT-TYPE
   SYNTAX      INTEGER (0..15)
   MAX-ACCESS  read-write
   STATUS      current
   DESCRIPTION
       " range : 0 - 15. "
   ::= { gepoel2esw12LinkBridgeModeAdd 3 } 
   
gepoel2esw12LinkAddBridgeDestNNI OBJECT-TYPE
   SYNTAX      INTEGER (1..2)
   MAX-ACCESS  read-write
   STATUS      current
   DESCRIPTION
       " 1: NNI-0, 2: NNI-1. "
   ::= { gepoel2esw12LinkBridgeModeAdd 4 }
   
gepoel2esw12LinkAddEntryLimit OBJECT-TYPE
   SYNTAX      INTEGER (0..999)
   MAX-ACCESS  read-write
   STATUS      current
   DESCRIPTION
       " range : 0 - 999. "
   ::= { gepoel2esw12LinkBridgeModeAdd 5 }
   
gepoel2esw12LinkAddVlan OBJECT-TYPE
   SYNTAX      INTEGER (1..4094)
   MAX-ACCESS  read-write
   STATUS      current
   DESCRIPTION
       " range : 1 - 4094. "
   ::= { gepoel2esw12LinkBridgeModeAdd 6 }

gepoel2esw12LinkAddMaxVlan OBJECT-TYPE
   SYNTAX      INTEGER (1..4094)
   MAX-ACCESS  read-write
   STATUS      current
   DESCRIPTION
       " range : 1 - 4094. "
   ::= { gepoel2esw12LinkBridgeModeAdd 7 }
   
gepoel2esw12LinkAddUpstreamCoS OBJECT-TYPE
   SYNTAX      INTEGER (0..7)
   MAX-ACCESS  read-write
   STATUS      current
   DESCRIPTION
       " range : 0 - 7. "
   ::= { gepoel2esw12LinkBridgeModeAdd 8 }

gepoel2esw12LinkAddMaxToSCoS OBJECT-TYPE
   SYNTAX      INTEGER (0..7)
   MAX-ACCESS  read-write
   STATUS      current
   DESCRIPTION
       " range : 0 - 7. "
   ::= { gepoel2esw12LinkBridgeModeAdd 9 }
   
gepoel2esw12LinkAddMinToSCoS OBJECT-TYPE
   SYNTAX      INTEGER (0..7)
   MAX-ACCESS  read-write
   STATUS      current
   DESCRIPTION
       " range : 0 - 7. "
   ::= { gepoel2esw12LinkBridgeModeAdd 10 }
   
gepoel2esw12LinkAddUsingCosTos OBJECT-TYPE
   SYNTAX      INTEGER (0|1)
   MAX-ACCESS  read-write
   STATUS      current
   DESCRIPTION
       " 0:CoS, 1:ToS. "
   ::= { gepoel2esw12LinkBridgeModeAdd 11 }
   
gepoel2esw12LinkAddNonIP OBJECT-TYPE
   SYNTAX      INTEGER (0|1)
   MAX-ACCESS  read-write
   STATUS      current
   DESCRIPTION
       "  "
   ::= { gepoel2esw12LinkBridgeModeAdd 12 }
   
gepoel2esw12DoLinkAddBridgeMode OBJECT-TYPE
   SYNTAX      INTEGER (0|1)
   MAX-ACCESS  read-write
   STATUS      current
   DESCRIPTION
       "  "
   ::= { gepoel2esw12LinkBridgeModeAdd 13 }


gepoel2esw12LinkVlanTagDel                                    OBJECT IDENTIFIER ::= { gepoel2esw12LinkBridge 4 }

gepoel2esw12LinkDelVlanOltPort OBJECT-TYPE
   SYNTAX      INTEGER (1..2)
   MAX-ACCESS  read-write
   STATUS      current
   DESCRIPTION
       " index 1:Epon-0, 2: Epon-1. "
   ::= { gepoel2esw12LinkVlanTagDel 1 } 
   
gepoel2esw12LinkDelVlanMacAddress OBJECT-TYPE
   SYNTAX      MacAddress
   MAX-ACCESS  read-write
   STATUS      current
   DESCRIPTION
       " "
   ::= { gepoel2esw12LinkVlanTagDel 2 } 
   
gepoel2esw12LinkDelVlan OBJECT-TYPE
   SYNTAX      INTEGER (1..4094)
   MAX-ACCESS  read-write
   STATUS      current
   DESCRIPTION
       " range : 1 - 4094. "
   ::= { gepoel2esw12LinkVlanTagDel 3 } 
   
gepoel2esw12LinkDelMaxVlan OBJECT-TYPE
   SYNTAX      INTEGER (1..4094)
   MAX-ACCESS  read-write
   STATUS      current
   DESCRIPTION
       " range : 1 - 4094. "
   ::= { gepoel2esw12LinkVlanTagDel 4 }
   
gepoel2esw12LinkDelUpstreamCos OBJECT-TYPE
   SYNTAX      INTEGER (0..7)
   MAX-ACCESS  read-write
   STATUS      current
   DESCRIPTION
       " range : 0 - 7. "
   ::= { gepoel2esw12LinkVlanTagDel 5 }
   
gepoel2esw12DoLinkDelVlan OBJECT-TYPE
   SYNTAX      INTEGER (0|1)
   MAX-ACCESS  read-write
   STATUS      current
   DESCRIPTION
       " 0: do nothing, 1: add. "
   ::= { gepoel2esw12LinkVlanTagDel 6 }


gepoel2esw12LinkStatistics                                                  OBJECT IDENTIFIER ::= { gepoel2esw12LlidManagement 4 }

gepoel2esw12LinkStatisticsOltSideTable OBJECT-TYPE
   SYNTAX      SEQUENCE OF GEPoEL2ESW12LinkStatisticsOltSideEntry
   MAX-ACCESS  not-accessible
   STATUS      current
   DESCRIPTION
       " Show Link Statistics Olt Side Table. "
   ::= { gepoel2esw12LinkStatistics 1 }

gepoel2esw12LinkStatisticsOltSideEntry OBJECT-TYPE
   SYNTAX      GEPoEL2ESW12LinkStatisticsOltSideEntry
   MAX-ACCESS  not-accessible
   STATUS      current
   DESCRIPTION
       ""
   INDEX    { gepoel2esw12LinkStaticOltSideOltPort, gepoel2esw12LinkStaticOltSideLinkMacAddress, gepoel2esw12LinkStatisticsOltSideIndex }
   ::= { gepoel2esw12LinkStatisticsOltSideTable 1 }

GEPoEL2ESW12LinkStatisticsOltSideEntry ::= SEQUENCE {
   gepoel2esw12LinkStaticOltSideOltPort                     INTEGER,
   gepoel2esw12LinkStaticOltSideLinkMacAddress              MacAddress,
   gepoel2esw12LinkStatisticsOltSideIndex                   INTEGER,
   gepoel2esw12LinkStatisticsOltSideBytes                   Counter64,
   gepoel2esw12LinkStatisticsOltSideTotalFrame              Counter64,
   
   gepoel2esw12LinkStatisticsOltSideUnicastFrame            Counter64,
   gepoel2esw12LinkStatisticsOltSideBroadcastFrame          Counter64,
   gepoel2esw12LinkStatisticsOltSideMulticastFrame          Counter64,
   gepoel2esw12LinkStatisticsOltSideUndersizeFrame          Counter64,
   gepoel2esw12LinkStatisticsOltSideOversizedFrame          Counter64,
   
   gepoel2esw12LinkStatisticsOltSideFCSErrors               Counter64,
   gepoel2esw12LinkStatisticsOltSide64OctetFrame            Counter64,
   gepoel2esw12LinkStatisticsOltSide65to127OctetFrame       Counter64,
   gepoel2esw12LinkStatisticsOltSide128to255OctetFrame      Counter64,
   gepoel2esw12LinkStatisticsOltSide256to511OctetFrame      Counter64,
   
   gepoel2esw12LinkStatisticsOltSide512to1023OctetFrame     Counter64,
   gepoel2esw12LinkStatisticsOltSide1024to1518OctetFrame    Counter64,
   gepoel2esw12LinkStatisticsOltSide1519upOctetFrame        Counter64,
   gepoel2esw12LinkStatisticsOltSideFramesDropped           Counter64,
   gepoel2esw12LinkStatisticsOltSideMPCPFrames              Counter64,
   
   gepoel2esw12LinkStatisticsOltSideMPCPBytes               Counter64,
   gepoel2esw12LinkStatisticsOltSideReportFrames            Counter64,
   gepoel2esw12LinkStatisticsOltSideReportBytes             Counter64,
   gepoel2esw12LinkStatisticsOltSideOAMFrame                Counter64,
   gepoel2esw12LinkStatisticsOltSideOAMBytes                Counter64,
   
   gepoel2esw12LinkStatisticsOltSideMPCPRegisterRequest     Counter64,
   gepoel2esw12LinkStatisticsOltSideMPCPRegisterAck         Counter64,
   gepoel2esw12LinkStatisticsOltSideMPCPRegisterFrame       Counter64,
   gepoel2esw12LinkStatisticsOltSideMPCPGatesFrame          Counter64,
   gepoel2esw12LinkStatisticsOltSideLineCodeError           Counter64,
   
   gepoel2esw12LinkStatisticsOltSideLineCodeErrorMax        Counter64,
   gepoel2esw12LinkStatisticsOltSideLaserPower              Counter64,
   gepoel2esw12LinkStatisticsOltSideMPCPFrames20            Counter64,
   gepoel2esw12LinkStatisticsOltSideMPCPBytes21             Counter64,
   gepoel2esw12LinkStatisticsOltSideGateFrames              Counter64,
   
   gepoel2esw12LinkStatisticsOltSideGateBytes               Counter64,
   gepoel2esw12LinkStatisticsOltSideClear                   INTEGER
}

gepoel2esw12LinkStaticOltSideOltPort OBJECT-TYPE
   SYNTAX      INTEGER (1..2)
   MAX-ACCESS  not-accessible
   STATUS      current
   DESCRIPTION
       " index 1: Epon-0, 2: Epon-1. "
   ::= { gepoel2esw12LinkStatisticsOltSideEntry 1 }

gepoel2esw12LinkStaticOltSideLinkMacAddress OBJECT-TYPE
   SYNTAX      MacAddress
   MAX-ACCESS  not-accessible
   STATUS      current
   DESCRIPTION
       "  "
   ::= { gepoel2esw12LinkStatisticsOltSideEntry 2 }

gepoel2esw12LinkStatisticsOltSideIndex OBJECT-TYPE
   SYNTAX      INTEGER (1|2)
   MAX-ACCESS  not-accessible
   STATUS      current
   DESCRIPTION
       " 1:Receive, 2:Transmit(index). "
   ::= { gepoel2esw12LinkStatisticsOltSideEntry 3 }

gepoel2esw12LinkStatisticsOltSideBytes OBJECT-TYPE
   SYNTAX      Counter64
   MAX-ACCESS  read-only
   STATUS      current
   DESCRIPTION
       " "
   ::= { gepoel2esw12LinkStatisticsOltSideEntry 4 }

gepoel2esw12LinkStatisticsOltSideTotalFrame OBJECT-TYPE
   SYNTAX      Counter64
   MAX-ACCESS  read-only
   STATUS      current
   DESCRIPTION
       "  "
   ::= { gepoel2esw12LinkStatisticsOltSideEntry 5 }

gepoel2esw12LinkStatisticsOltSideUnicastFrame OBJECT-TYPE
   SYNTAX      Counter64
   MAX-ACCESS  read-only
   STATUS      current
   DESCRIPTION
       "  "
   ::= { gepoel2esw12LinkStatisticsOltSideEntry 6 }

gepoel2esw12LinkStatisticsOltSideBroadcastFrame OBJECT-TYPE
   SYNTAX      Counter64
   MAX-ACCESS  read-only
   STATUS      current
   DESCRIPTION
       "  "
   ::= { gepoel2esw12LinkStatisticsOltSideEntry 7 }
   
gepoel2esw12LinkStatisticsOltSideMulticastFrame OBJECT-TYPE
   SYNTAX      Counter64
   MAX-ACCESS  read-only
   STATUS      current
   DESCRIPTION
       "  "
   ::= { gepoel2esw12LinkStatisticsOltSideEntry 8 }
   
gepoel2esw12LinkStatisticsOltSideUndersizeFrame OBJECT-TYPE
   SYNTAX      Counter64
   MAX-ACCESS  read-only
   STATUS      current
   DESCRIPTION
       "  "
   ::= { gepoel2esw12LinkStatisticsOltSideEntry 9 }
   
gepoel2esw12LinkStatisticsOltSideOversizedFrame OBJECT-TYPE
   SYNTAX      Counter64
   MAX-ACCESS  read-only
   STATUS      current
   DESCRIPTION
       "  "
   ::= { gepoel2esw12LinkStatisticsOltSideEntry 10 }  

gepoel2esw12LinkStatisticsOltSideFCSErrors OBJECT-TYPE
   SYNTAX      Counter64
   MAX-ACCESS  read-only
   STATUS      current
   DESCRIPTION
       "  "
   ::= { gepoel2esw12LinkStatisticsOltSideEntry 11 }
   
gepoel2esw12LinkStatisticsOltSide64OctetFrame OBJECT-TYPE
   SYNTAX      Counter64
   MAX-ACCESS  read-only
   STATUS      current
   DESCRIPTION
       "  "
   ::= { gepoel2esw12LinkStatisticsOltSideEntry 12 } 
   
gepoel2esw12LinkStatisticsOltSide65to127OctetFrame OBJECT-TYPE
   SYNTAX      Counter64
   MAX-ACCESS  read-only
   STATUS      current
   DESCRIPTION
       "  "
   ::= { gepoel2esw12LinkStatisticsOltSideEntry 13 }
   
gepoel2esw12LinkStatisticsOltSide128to255OctetFrame OBJECT-TYPE
   SYNTAX      Counter64
   MAX-ACCESS  read-only
   STATUS      current
   DESCRIPTION
       "  "
   ::= { gepoel2esw12LinkStatisticsOltSideEntry 14 }
   
gepoel2esw12LinkStatisticsOltSide256to511OctetFrame OBJECT-TYPE
   SYNTAX      Counter64
   MAX-ACCESS  read-only
   STATUS      current
   DESCRIPTION
       "  "
   ::= { gepoel2esw12LinkStatisticsOltSideEntry 15 }  
   
gepoel2esw12LinkStatisticsOltSide512to1023OctetFrame OBJECT-TYPE
   SYNTAX      Counter64
   MAX-ACCESS  read-only
   STATUS      current
   DESCRIPTION
       "  "
   ::= { gepoel2esw12LinkStatisticsOltSideEntry 16 }  
  
gepoel2esw12LinkStatisticsOltSide1024to1518OctetFrame OBJECT-TYPE
   SYNTAX      Counter64
   MAX-ACCESS  read-only
   STATUS      current
   DESCRIPTION
       "  "
   ::= { gepoel2esw12LinkStatisticsOltSideEntry 17 }  
  
gepoel2esw12LinkStatisticsOltSide1519upOctetFrame OBJECT-TYPE
   SYNTAX      Counter64
   MAX-ACCESS  read-only
   STATUS      current
   DESCRIPTION
       "  "
   ::= { gepoel2esw12LinkStatisticsOltSideEntry 18 }  
  
gepoel2esw12LinkStatisticsOltSideFramesDropped OBJECT-TYPE
   SYNTAX      Counter64
   MAX-ACCESS  read-only
   STATUS      current
   DESCRIPTION
       "  "
   ::= { gepoel2esw12LinkStatisticsOltSideEntry 19 }  
  
gepoel2esw12LinkStatisticsOltSideMPCPFrames OBJECT-TYPE
   SYNTAX      Counter64
   MAX-ACCESS  read-only
   STATUS      current
   DESCRIPTION
       "  "
   ::= { gepoel2esw12LinkStatisticsOltSideEntry 20 }  

gepoel2esw12LinkStatisticsOltSideMPCPBytes OBJECT-TYPE
   SYNTAX      Counter64
   MAX-ACCESS  read-only
   STATUS      current
   DESCRIPTION
       "  "
   ::= { gepoel2esw12LinkStatisticsOltSideEntry 21 }  
 
gepoel2esw12LinkStatisticsOltSideReportFrames OBJECT-TYPE
   SYNTAX      Counter64
   MAX-ACCESS  read-only
   STATUS      current
   DESCRIPTION
       "  "
   ::= { gepoel2esw12LinkStatisticsOltSideEntry 22 }  
 
gepoel2esw12LinkStatisticsOltSideReportBytes OBJECT-TYPE
   SYNTAX      Counter64
   MAX-ACCESS  read-only
   STATUS      current
   DESCRIPTION
       "  "
   ::= { gepoel2esw12LinkStatisticsOltSideEntry 23 }  
 
gepoel2esw12LinkStatisticsOltSideOAMFrame OBJECT-TYPE
   SYNTAX      Counter64
   MAX-ACCESS  read-only
   STATUS      current
   DESCRIPTION
       "  "
   ::= { gepoel2esw12LinkStatisticsOltSideEntry 24 }  
 
gepoel2esw12LinkStatisticsOltSideOAMBytes OBJECT-TYPE
   SYNTAX      Counter64
   MAX-ACCESS  read-only
   STATUS      current
   DESCRIPTION
       "  "
   ::= { gepoel2esw12LinkStatisticsOltSideEntry 25 }  
                 
gepoel2esw12LinkStatisticsOltSideMPCPRegisterRequest OBJECT-TYPE
   SYNTAX      Counter64
   MAX-ACCESS  read-only
   STATUS      current
   DESCRIPTION
       "  "
   ::= { gepoel2esw12LinkStatisticsOltSideEntry 26 }  
                 
gepoel2esw12LinkStatisticsOltSideMPCPRegisterAck OBJECT-TYPE
   SYNTAX      Counter64
   MAX-ACCESS  read-only
   STATUS      current
   DESCRIPTION
       "  "
   ::= { gepoel2esw12LinkStatisticsOltSideEntry 27 }  
                 
gepoel2esw12LinkStatisticsOltSideMPCPRegisterFrame OBJECT-TYPE
   SYNTAX      Counter64
   MAX-ACCESS  read-only
   STATUS      current
   DESCRIPTION
       "  "
   ::= { gepoel2esw12LinkStatisticsOltSideEntry 28 }  
                 
gepoel2esw12LinkStatisticsOltSideMPCPGatesFrame OBJECT-TYPE
   SYNTAX      Counter64
   MAX-ACCESS  read-only
   STATUS      current
   DESCRIPTION
       "  "
   ::= { gepoel2esw12LinkStatisticsOltSideEntry 29 }  
                 
gepoel2esw12LinkStatisticsOltSideLineCodeError OBJECT-TYPE
   SYNTAX      Counter64
   MAX-ACCESS  read-only
   STATUS      current
   DESCRIPTION
       "  "
   ::= { gepoel2esw12LinkStatisticsOltSideEntry 30 }  
                 
gepoel2esw12LinkStatisticsOltSideLineCodeErrorMax OBJECT-TYPE
   SYNTAX      Counter64
   MAX-ACCESS  read-only
   STATUS      current
   DESCRIPTION
       "  "
   ::= { gepoel2esw12LinkStatisticsOltSideEntry 31 }  
                 
gepoel2esw12LinkStatisticsOltSideLaserPower OBJECT-TYPE
   SYNTAX      Counter64
   MAX-ACCESS  read-only
   STATUS      current
   DESCRIPTION
       "  "
   ::= { gepoel2esw12LinkStatisticsOltSideEntry 32 }                  
                 
gepoel2esw12LinkStatisticsOltSideGateFrames OBJECT-TYPE
   SYNTAX      Counter64
   MAX-ACCESS  read-only
   STATUS      current
   DESCRIPTION
       "  "
   ::= { gepoel2esw12LinkStatisticsOltSideEntry 33 }  
                 
gepoel2esw12LinkStatisticsOltSideGateBytes OBJECT-TYPE
   SYNTAX      Counter64
   MAX-ACCESS  read-only
   STATUS      current
   DESCRIPTION
       "  "
   ::= { gepoel2esw12LinkStatisticsOltSideEntry 34 }  
                 
gepoel2esw12LinkStatisticsOltSideClear OBJECT-TYPE
   SYNTAX      INTEGER (0|1)
   MAX-ACCESS  read-write
   STATUS      current
   DESCRIPTION
       " 0:do nothing, 1:clear statistics. "
   ::= { gepoel2esw12LinkStatisticsOltSideEntry 35 }  


gepoel2esw12LinkStatisticsOnuSideTable OBJECT-TYPE
   SYNTAX      SEQUENCE OF GEPoEL2ESW12LinkStatisticsOnuSideEntry
   MAX-ACCESS  not-accessible
   STATUS      current
   DESCRIPTION
       " Show Link Statistics Onu Side Table. "
   ::= { gepoel2esw12LinkStatistics 2 }

gepoel2esw12LinkStatisticsOnuSideEntry OBJECT-TYPE
   SYNTAX      GEPoEL2ESW12LinkStatisticsOnuSideEntry
   MAX-ACCESS  not-accessible
   STATUS      current
   DESCRIPTION
       ""
   INDEX    { gepoel2esw12LinkStaticOnuSideOltPort, gepoel2esw12LinkStaticOnuSideLinkMacAddress, gepoel2esw12LinkStatisticsOnuSideIndex }
   ::= { gepoel2esw12LinkStatisticsOnuSideTable 1 }

GEPoEL2ESW12LinkStatisticsOnuSideEntry ::= SEQUENCE {
   gepoel2esw12LinkStaticOnuSideOltPort                     INTEGER,
   gepoel2esw12LinkStaticOnuSideLinkMacAddress              MacAddress,
   gepoel2esw12LinkStatisticsOnuSideIndex                   INTEGER,
   gepoel2esw12LinkStatisticsOnuSideBytes                   Counter64,
   gepoel2esw12LinkStatisticsOnuSideTotalFrame              Counter64,
   
   gepoel2esw12LinkStatisticsOnuSideUnicastFrame            Counter64,
   gepoel2esw12LinkStatisticsOnuSideBroadcastFrame          Counter64,
   gepoel2esw12LinkStatisticsOnuSideMulticastFrame          Counter64,
   gepoel2esw12LinkStatisticsOnuSide64OctetFrame            Counter64,
   gepoel2esw12LinkStatisticsOnuSide65to127OctetFrame       Counter64,
   
   gepoel2esw12LinkStatisticsOnuSide128to255OctetFrame      Counter64,
   gepoel2esw12LinkStatisticsOnuSide256to511OctetFrame      Counter64,
   gepoel2esw12LinkStatisticsOnuSide512to1023OctetFrame     Counter64,
   gepoel2esw12LinkStatisticsOnuSide1024to1518OctetFrame    Counter64,
   gepoel2esw12LinkStatisticsOnuSide1519upOctetFrame        Counter64,
   
   gepoel2esw12LinkStatisticsOnuSideUndersizeFrame          Counter64,
   gepoel2esw12LinkStatisticsOnuSideFCSErrors               Counter64,
   gepoel2esw12LinkStatisticsOnuSideBytesDropped            Counter64,
   gepoel2esw12LinkStatisticsOnuSideFramesDropped           Counter64,
   gepoel2esw12LinkStatisticsOnuSideBytesDelayed            Counter64,
   
   gepoel2esw12LinkStatisticsOnuSideMaximumDelayed          Counter64,
   gepoel2esw12LinkStatisticsOnuSideDelayThreshold          Counter64,
   gepoel2esw12LinkStatisticsOnuSideOAMFrames               Counter64,
   gepoel2esw12LinkStatisticsOnuSideErroredFrames           Counter64,
   gepoel2esw12LinkStatisticsOnuSideErroredFramePeriods     Counter64,
   
   gepoel2esw12LinkStatisticsOnuSideMPCPGates               Counter64,
   gepoel2esw12LinkStatisticsOnuSideMPCPRegister            Counter64,
   gepoel2esw12LinkStatisticsOnuSideMPCPReport              Counter64,
   gepoel2esw12LinkStatisticsOnuSideMPCPRequest             Counter64,
   gepoel2esw12LinkStatisticsOnuSideMPCPRegisterAck         Counter64,
   
   gepoel2esw12LinkStatisticsOnuSideUnused                  Counter64,
   gepoel2esw12LinkStatisticsOnuSideClear                   INTEGER
}

gepoel2esw12LinkStaticOnuSideOltPort OBJECT-TYPE
   SYNTAX      INTEGER (1..2)
   MAX-ACCESS  not-accessible
   STATUS      current
   DESCRIPTION
       " index 1: Epon-0, 2: Epon-1. "
   ::= { gepoel2esw12LinkStatisticsOnuSideEntry 1 }

gepoel2esw12LinkStaticOnuSideLinkMacAddress OBJECT-TYPE
   SYNTAX      MacAddress
   MAX-ACCESS  not-accessible
   STATUS      current
   DESCRIPTION
       "  "
   ::= { gepoel2esw12LinkStatisticsOnuSideEntry 2 }

gepoel2esw12LinkStatisticsOnuSideIndex OBJECT-TYPE
   SYNTAX      INTEGER (1|2)
   MAX-ACCESS  not-accessible
   STATUS      current
   DESCRIPTION
       " 1:Receive, 2:Transmit(index). "
   ::= { gepoel2esw12LinkStatisticsOnuSideEntry 3 }

gepoel2esw12LinkStatisticsOnuSideBytes OBJECT-TYPE
   SYNTAX      Counter64
   MAX-ACCESS  read-only
   STATUS      current
   DESCRIPTION
       " "
   ::= { gepoel2esw12LinkStatisticsOnuSideEntry 4 }

gepoel2esw12LinkStatisticsOnuSideTotalFrame OBJECT-TYPE
   SYNTAX      Counter64
   MAX-ACCESS  read-only
   STATUS      current
   DESCRIPTION
       "  "
   ::= { gepoel2esw12LinkStatisticsOnuSideEntry 5 }

gepoel2esw12LinkStatisticsOnuSideUnicastFrame OBJECT-TYPE
   SYNTAX      Counter64
   MAX-ACCESS  read-only
   STATUS      current
   DESCRIPTION
       "  "
   ::= { gepoel2esw12LinkStatisticsOnuSideEntry 6 }

gepoel2esw12LinkStatisticsOnuSideBroadcastFrame OBJECT-TYPE
   SYNTAX      Counter64
   MAX-ACCESS  read-only
   STATUS      current
   DESCRIPTION
       "  "
   ::= { gepoel2esw12LinkStatisticsOnuSideEntry 7 }
   
gepoel2esw12LinkStatisticsOnuSideMulticastFrame OBJECT-TYPE
   SYNTAX      Counter64
   MAX-ACCESS  read-only
   STATUS      current
   DESCRIPTION
       "  "
   ::= { gepoel2esw12LinkStatisticsOnuSideEntry 8 }
   
gepoel2esw12LinkStatisticsOnuSide64OctetFrame OBJECT-TYPE
   SYNTAX      Counter64
   MAX-ACCESS  read-only
   STATUS      current
   DESCRIPTION
       "  "
   ::= { gepoel2esw12LinkStatisticsOnuSideEntry 9 }
   
gepoel2esw12LinkStatisticsOnuSide65to127OctetFrame OBJECT-TYPE
   SYNTAX      Counter64
   MAX-ACCESS  read-only
   STATUS      current
   DESCRIPTION
       "  "
   ::= { gepoel2esw12LinkStatisticsOnuSideEntry 10 }  

gepoel2esw12LinkStatisticsOnuSide128to255OctetFrame OBJECT-TYPE
   SYNTAX      Counter64
   MAX-ACCESS  read-only
   STATUS      current
   DESCRIPTION
       "  "
   ::= { gepoel2esw12LinkStatisticsOnuSideEntry 11 }
   
gepoel2esw12LinkStatisticsOnuSide256to511OctetFrame OBJECT-TYPE
   SYNTAX      Counter64
   MAX-ACCESS  read-only
   STATUS      current
   DESCRIPTION
       "  "
   ::= { gepoel2esw12LinkStatisticsOnuSideEntry 12 } 
   
gepoel2esw12LinkStatisticsOnuSide512to1023OctetFrame OBJECT-TYPE
   SYNTAX      Counter64
   MAX-ACCESS  read-only
   STATUS      current
   DESCRIPTION
       "  "
   ::= { gepoel2esw12LinkStatisticsOnuSideEntry 13 }
   
gepoel2esw12LinkStatisticsOnuSide1024to1518OctetFrame OBJECT-TYPE
   SYNTAX      Counter64
   MAX-ACCESS  read-only
   STATUS      current
   DESCRIPTION
       "  "
   ::= { gepoel2esw12LinkStatisticsOnuSideEntry 14 }
   
gepoel2esw12LinkStatisticsOnuSide1519upOctetFrame OBJECT-TYPE
   SYNTAX      Counter64
   MAX-ACCESS  read-only
   STATUS      current
   DESCRIPTION
       "  "
   ::= { gepoel2esw12LinkStatisticsOnuSideEntry 15 }  
   
gepoel2esw12LinkStatisticsOnuSideUndersizeFrame OBJECT-TYPE
   SYNTAX      Counter64
   MAX-ACCESS  read-only
   STATUS      current
   DESCRIPTION
       "  "
   ::= { gepoel2esw12LinkStatisticsOnuSideEntry 16 }  
  
gepoel2esw12LinkStatisticsOnuSideFCSErrors OBJECT-TYPE
   SYNTAX      Counter64
   MAX-ACCESS  read-only
   STATUS      current
   DESCRIPTION
       "  "
   ::= { gepoel2esw12LinkStatisticsOnuSideEntry 17 }  
  
gepoel2esw12LinkStatisticsOnuSideBytesDropped OBJECT-TYPE
   SYNTAX      Counter64
   MAX-ACCESS  read-only
   STATUS      current
   DESCRIPTION
       "  "
   ::= { gepoel2esw12LinkStatisticsOnuSideEntry 18 }  
  
gepoel2esw12LinkStatisticsOnuSideFramesDropped OBJECT-TYPE
   SYNTAX      Counter64
   MAX-ACCESS  read-only
   STATUS      current
   DESCRIPTION
       "  "
   ::= { gepoel2esw12LinkStatisticsOnuSideEntry 19 }  
  
gepoel2esw12LinkStatisticsOnuSideBytesDelayed OBJECT-TYPE
   SYNTAX      Counter64
   MAX-ACCESS  read-only
   STATUS      current
   DESCRIPTION
       "  "
   ::= { gepoel2esw12LinkStatisticsOnuSideEntry 20 }  

gepoel2esw12LinkStatisticsOnuSideMaximumDelayed OBJECT-TYPE
   SYNTAX      Counter64
   MAX-ACCESS  read-only
   STATUS      current
   DESCRIPTION
       "  "
   ::= { gepoel2esw12LinkStatisticsOnuSideEntry 21 }  
 
gepoel2esw12LinkStatisticsOnuSideDelayThreshold OBJECT-TYPE
   SYNTAX      Counter64
   MAX-ACCESS  read-only
   STATUS      current
   DESCRIPTION
       "  "
   ::= { gepoel2esw12LinkStatisticsOnuSideEntry 22 }  
 
gepoel2esw12LinkStatisticsOnuSideOAMFrames OBJECT-TYPE
   SYNTAX      Counter64
   MAX-ACCESS  read-only
   STATUS      current
   DESCRIPTION
       "  "
   ::= { gepoel2esw12LinkStatisticsOnuSideEntry 23 }  
 
gepoel2esw12LinkStatisticsOnuSideErroredFrames OBJECT-TYPE
   SYNTAX      Counter64
   MAX-ACCESS  read-only
   STATUS      current
   DESCRIPTION
       "  "
   ::= { gepoel2esw12LinkStatisticsOnuSideEntry 24 }  
 
gepoel2esw12LinkStatisticsOnuSideErroredFramePeriods OBJECT-TYPE
   SYNTAX      Counter64
   MAX-ACCESS  read-only
   STATUS      current
   DESCRIPTION
       "  "
   ::= { gepoel2esw12LinkStatisticsOnuSideEntry 25 }  
                 
gepoel2esw12LinkStatisticsOnuSideMPCPGates OBJECT-TYPE
   SYNTAX      Counter64
   MAX-ACCESS  read-only
   STATUS      current
   DESCRIPTION
       "  "
   ::= { gepoel2esw12LinkStatisticsOnuSideEntry 26 }  
                 
gepoel2esw12LinkStatisticsOnuSideMPCPRegister OBJECT-TYPE
   SYNTAX      Counter64
   MAX-ACCESS  read-only
   STATUS      current
   DESCRIPTION
       "  "
   ::= { gepoel2esw12LinkStatisticsOnuSideEntry 27 }  
                 
gepoel2esw12LinkStatisticsOnuSideMPCPReport OBJECT-TYPE
   SYNTAX      Counter64
   MAX-ACCESS  read-only
   STATUS      current
   DESCRIPTION
       "  "
   ::= { gepoel2esw12LinkStatisticsOnuSideEntry 28 }  
                 
gepoel2esw12LinkStatisticsOnuSideMPCPRequest OBJECT-TYPE
   SYNTAX      Counter64
   MAX-ACCESS  read-only
   STATUS      current
   DESCRIPTION
       "  "
   ::= { gepoel2esw12LinkStatisticsOnuSideEntry 29 }  
                 
gepoel2esw12LinkStatisticsOnuSideMPCPRegisterAck OBJECT-TYPE
   SYNTAX      Counter64
   MAX-ACCESS  read-only
   STATUS      current
   DESCRIPTION
       "  "
   ::= { gepoel2esw12LinkStatisticsOnuSideEntry 30 }  
                 
gepoel2esw12LinkStatisticsOnuSideUnused OBJECT-TYPE
   SYNTAX      Counter64
   MAX-ACCESS  read-only
   STATUS      current
   DESCRIPTION
       "  "
   ::= { gepoel2esw12LinkStatisticsOnuSideEntry 31 }  
                                   
gepoel2esw12LinkStatisticsOnuSideClear OBJECT-TYPE
   SYNTAX      INTEGER (0|1)
   MAX-ACCESS  read-write
   STATUS      current
   DESCRIPTION
       " 0:do nothing, 1:clear statistics. "
   ::= { gepoel2esw12LinkStatisticsOnuSideEntry 32 }  
                 
   
gepoel2esw12LinkMiscOperationTable OBJECT-TYPE
   SYNTAX      SEQUENCE OF GEPoEL2ESW12LinkMiscOperationEntry
   MAX-ACCESS  not-accessible
   STATUS      current
   DESCRIPTION
       " Show Link Misc Operation Table. "
   ::= { gepoel2esw12LlidManagement 5 }

gepoel2esw12LinkMiscOperationEntry OBJECT-TYPE
   SYNTAX      GEPoEL2ESW12LinkMiscOperationEntry
   MAX-ACCESS  not-accessible
   STATUS      current
   DESCRIPTION
       ""
   INDEX    { gepoel2esw12LinkMiscOptOltPort, gepoel2esw12LinkMiscOptLinkMacAddress }
   ::= { gepoel2esw12LinkMiscOperationTable 1 }

GEPoEL2ESW12LinkMiscOperationEntry ::= SEQUENCE {
   gepoel2esw12LinkMiscOptOltPort           INTEGER,
   gepoel2esw12LinkMiscOptLinkMacAddress    MacAddress,
   gepoel2esw12LinkBlockState               INTEGER
}

gepoel2esw12LinkMiscOptOltPort OBJECT-TYPE
   SYNTAX      INTEGER (1..2)
   MAX-ACCESS  not-accessible
   STATUS      current
   DESCRIPTION
       " "
   ::= { gepoel2esw12LinkMiscOperationEntry 1 }

gepoel2esw12LinkMiscOptLinkMacAddress OBJECT-TYPE
   SYNTAX      MacAddress
   MAX-ACCESS  not-accessible
   STATUS      current
   DESCRIPTION
       "  "
   ::= { gepoel2esw12LinkMiscOperationEntry 2 }
                                   
gepoel2esw12LinkBlockState OBJECT-TYPE
   SYNTAX      INTEGER (0|1)
   MAX-ACCESS  read-write
   STATUS      current
   DESCRIPTION
       " 0: do nothing, 1: block. "
   ::= { gepoel2esw12LinkMiscOperationEntry 3 }  
                 
               
----------------------------------------------------------------------------------------------------------------------------------------
gepoel2esw12Configuration                                         OBJECT IDENTIFIER ::= { gepoel2esw12ProductId 5 }


gepoel2esw12TrapEventSeverity                                             OBJECT IDENTIFIER ::= { gepoel2esw12Configuration 1 }

gepoel2esw12TrapEventSeverityAccessMgmt OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gepoel2esw12TrapEventSeverity 1 }

gepoel2esw12TrapEventSeverityAuthFailed OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { gepoel2esw12TrapEventSeverity 2 }

gepoel2esw12TrapEventSeverityColdStart OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { gepoel2esw12TrapEventSeverity 3 }

gepoel2esw12TrapEventSeverityConfigInfo OBJECT-TYPE
   SYNTAX      INTEGER (0..7)
   MAX-ACCESS  read-write
   STATUS      current
   DESCRIPTION
       " default:  5(Notice)
        0: Emergency
        1: Alert
        2: Critical
        3: Error
        4: Warning
        5: Notice
        6: Info
        7: Debug"
   ::= { gepoel2esw12TrapEventSeverity 4 }

gepoel2esw12TrapEventSeverityDyingGaspPowerFailure OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gepoel2esw12TrapEventSeverity 5 }

gepoel2esw12TrapEventSeverityEPONLinkDown OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gepoel2esw12TrapEventSeverity 6 }

gepoel2esw12TrapEventSeverityEPONLinkUp OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gepoel2esw12TrapEventSeverity 7 }

gepoel2esw12TrapEventSeverityFirmwareUpgrade OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gepoel2esw12TrapEventSeverity 8 }

gepoel2esw12TrapEventSeverityJumboFrameReceivedError OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gepoel2esw12TrapEventSeverity 9 }

gepoel2esw12TrapEventSeverityKeyExchangeFailure OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gepoel2esw12TrapEventSeverity 10 }

gepoel2esw12TrapEventSeverityLogin OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { gepoel2esw12TrapEventSeverity 11 }

gepoel2esw12TrapEventSeverityLogout OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gepoel2esw12TrapEventSeverity 12 }

gepoel2esw12TrapEventSeverityLoopback OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gepoel2esw12TrapEventSeverity 13 }

gepoel2esw12TrapEventSeverityMACLearningTableOverflow OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gepoel2esw12TrapEventSeverity 14 }

gepoel2esw12TrapEventSeverityMgmtIPChange OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gepoel2esw12TrapEventSeverity 15 }

gepoel2esw12TrapEventSeverityNumberOfLinksExceeded OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gepoel2esw12TrapEventSeverity 16 }

gepoel2esw12TrapEventSeverityOLTBad OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gepoel2esw12TrapEventSeverity 17 }

gepoel2esw12TrapEventSeverityONUPowerAbnormal OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gepoel2esw12TrapEventSeverity 18 }

gepoel2esw12TrapEventSeverityPasswdChange OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gepoel2esw12TrapEventSeverity 19 }

gepoel2esw12TrapEventSeverityQueueOverflow OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gepoel2esw12TrapEventSeverity 20 }

gepoel2esw12TrapEventSeverityStandardDyingGasp OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gepoel2esw12TrapEventSeverity 21 }

gepoel2esw12TrapEventSeverityStandardLinkFault OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gepoel2esw12TrapEventSeverity 22 }

gepoel2esw12TrapEventSeverityStatisticsAlarm OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gepoel2esw12TrapEventSeverity 23 }

gepoel2esw12TrapEventSeverityUNILinkDown OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gepoel2esw12TrapEventSeverity 24 }

gepoel2esw12TrapEventSeverityUNILinkUp OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { gepoel2esw12TrapEventSeverity 25 }

gepoel2esw12TrapEventSeverityWarmStart OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { gepoel2esw12TrapEventSeverity 26 }


gepoel2esw12SMTP                                             OBJECT IDENTIFIER ::= { gepoel2esw12Configuration 2 }

gepoel2esw12SMTPMailServer OBJECT-TYPE
   SYNTAX      DisplayString
   MAX-ACCESS  read-write
   STATUS      current
   DESCRIPTION
       " Up to 47 characters describing email server. "
   ::= { gepoel2esw12SMTP 1 }

gepoel2esw12SMTPUserName OBJECT-TYPE
   SYNTAX      DisplayString
   MAX-ACCESS  read-write
   STATUS      current
   DESCRIPTION
       " Up to 47 characters describing user name. "
   ::= { gepoel2esw12SMTP 2 }

gepoel2esw12SMTPPassword OBJECT-TYPE
   SYNTAX      DisplayString
   MAX-ACCESS  read-write
   STATUS      current
   DESCRIPTION
       " Up to 47 characters describing password. "
   ::= { gepoel2esw12SMTP 3 }

gepoel2esw12SMTPServeriryLevel OBJECT-TYPE
   SYNTAX      INTEGER(0..7)
   MAX-ACCESS  read-write
   STATUS      current
   DESCRIPTION
       "default: 6
       0: Emergency
       1: Alert
       2: Critical
       3: Error
       4: Warning
       5: Notice
       6: Info
       7: Debug"
   ::= { gepoel2esw12SMTP 4 }

gepoel2esw12SMTPSender OBJECT-TYPE
   SYNTAX      DisplayString
   MAX-ACCESS  read-write
   STATUS      current
   DESCRIPTION
       " Up to 47 characters describing sender. "
   ::= { gepoel2esw12SMTP 5 }

gepoel2esw12SMTPReturnPath OBJECT-TYPE
   SYNTAX      DisplayString
   MAX-ACCESS  read-write
   STATUS      current
   DESCRIPTION
       " Up to 47 characters describing return path. "
   ::= { gepoel2esw12SMTP 6 }

gepoel2esw12SMTPEmailAddress1 OBJECT-TYPE
   SYNTAX      DisplayString
   MAX-ACCESS  read-write
   STATUS      current
   DESCRIPTION
       " Up to 47 characters describing mail address. "
   ::= { gepoel2esw12SMTP 7 }

gepoel2esw12SMTPEmailAddress2 OBJECT-TYPE
   SYNTAX      DisplayString
   MAX-ACCESS  read-write
   STATUS      current
   DESCRIPTION
       " Up to 47 characters describing mail address. "
   ::= { gepoel2esw12SMTP 8 }

gepoel2esw12SMTPEmailAddress3 OBJECT-TYPE
   SYNTAX      DisplayString
   MAX-ACCESS  read-write
   STATUS      current
   DESCRIPTION
       " Up to 47 characters describing mail address. "
   ::= { gepoel2esw12SMTP 9 }

gepoel2esw12SMTPEmailAddress4 OBJECT-TYPE
   SYNTAX      DisplayString
   MAX-ACCESS  read-write
   STATUS      current
   DESCRIPTION
       " Up to 47 characters describing mail address. "
   ::= { gepoel2esw12SMTP 10 }

gepoel2esw12SMTPEmailAddress5 OBJECT-TYPE
   SYNTAX      DisplayString
   MAX-ACCESS  read-write
   STATUS      current
   DESCRIPTION
       " Up to 47 characters describing mail address. "
   ::= { gepoel2esw12SMTP 11 }

gepoel2esw12SMTPEmailAddress6 OBJECT-TYPE
   SYNTAX      DisplayString
   MAX-ACCESS  read-write
   STATUS      current
   DESCRIPTION
       " Up to 47 characters describing mail address. "
   ::= { gepoel2esw12SMTP 12 }


----------------------------------------------------------------------------------------------------------------------------
gepoel2esw12Security                                              OBJECT IDENTIFIER ::= { gepoel2esw12ProductId 6 }

gepoel2esw12AccessManagement                                      OBJECT IDENTIFIER ::= { gepoel2esw12Security 1 }

gepoel2esw12AccessMgtConf                                         OBJECT IDENTIFIER ::= { gepoel2esw12AccessManagement 1 }

gepoel2esw12AccessMgtConfMode OBJECT-TYPE
   SYNTAX      INTEGER(0|1)
   MAX-ACCESS  read-write
   STATUS      current
   DESCRIPTION
       "default: 0
       0: disable
       1: enable "
   ::= { gepoel2esw12AccessMgtConf 1 }

gepoel2esw12AccessMgtConfCreate OBJECT-TYPE
   SYNTAX      INTEGER(0|1)
   MAX-ACCESS  read-write
   STATUS      current
   DESCRIPTION
       "default: 0
       0: none
       1: create "
   ::= { gepoel2esw12AccessMgtConf 2 }

gepoel2esw12AccessMgtConfTable OBJECT-TYPE
   SYNTAX      SEQUENCE OF GEPoEL2ESW12AccessMgtConfEntry
   MAX-ACCESS  not-accessible
   STATUS      current
   DESCRIPTION
       " "
   ::= { gepoel2esw12AccessMgtConf 3 }

gepoel2esw12AccessMgtConfEntry OBJECT-TYPE
   SYNTAX      GEPoEL2ESW12AccessMgtConfEntry
   MAX-ACCESS  not-accessible
   STATUS      current
   DESCRIPTION
       ""
   INDEX    { gepoel2esw12AccessMgtIndex  }
   ::= { gepoel2esw12AccessMgtConfTable 1 }
   
GEPoEL2ESW12AccessMgtConfEntry ::= SEQUENCE {
   gepoel2esw12AccessMgtIndex             INTEGER,
   gepoel2esw12AccessMgtAddresstype       INTEGER,
   gepoel2esw12AccessMgtStartIpAddress    DisplayString,
   gepoel2esw12AccessMgtEndIpAddress      DisplayString,
   gepoel2esw12AccessMgtHttpHttps         INTEGER,
   gepoel2esw12AccessMgtSNMP              INTEGER,
   gepoel2esw12AccessMgtTelnetSSH         INTEGER,
   gepoel2esw12AccessMgtRowStatus         INTEGER
}

gepoel2esw12AccessMgtIndex OBJECT-TYPE
   SYNTAX      INTEGER(1..16)
   MAX-ACCESS  read-write
   STATUS      current
   DESCRIPTION
       "Access Management config index"
   ::= { gepoel2esw12AccessMgtConfEntry 1 }

gepoel2esw12AccessMgtAddresstype OBJECT-TYPE
   SYNTAX      INTEGER(0|1)
   MAX-ACCESS  read-write
   STATUS      current
   DESCRIPTION
       "0: ipv4
       1: ipv6 "
   ::= { gepoel2esw12AccessMgtConfEntry 2 }
   
gepoel2esw12AccessMgtStartIpAddress OBJECT-TYPE
   SYNTAX      DisplayString
   MAX-ACCESS  read-write
   STATUS      current
   DESCRIPTION
       " "
   ::= { gepoel2esw12AccessMgtConfEntry 3 }
   
gepoel2esw12AccessMgtEndIpAddress OBJECT-TYPE
   SYNTAX      DisplayString
   MAX-ACCESS  read-write
   STATUS      current
   DESCRIPTION
       " "
   ::= { gepoel2esw12AccessMgtConfEntry 4 }

gepoel2esw12AccessMgtHttpHttps OBJECT-TYPE
   SYNTAX      INTEGER(0|1)
   MAX-ACCESS  read-write
   STATUS      current
   DESCRIPTION
       "default: 0
       0: disable
       1: enable "
   ::= { gepoel2esw12AccessMgtConfEntry 5 }

gepoel2esw12AccessMgtSNMP OBJECT-TYPE
   SYNTAX      INTEGER(0|1)
   MAX-ACCESS  read-write
   STATUS      current
   DESCRIPTION
       "default: 0
       0: disable
       1: enable "
   ::= { gepoel2esw12AccessMgtConfEntry 6 }

gepoel2esw12AccessMgtTelnetSSH OBJECT-TYPE
   SYNTAX      INTEGER(0|1)
   MAX-ACCESS  read-write
   STATUS      current
   DESCRIPTION
       "default: 0
       0: disable
       1: enable "
   ::= { gepoel2esw12AccessMgtConfEntry 7 }

gepoel2esw12AccessMgtRowStatus OBJECT-TYPE
   SYNTAX      INTEGER(1..5)
   MAX-ACCESS  read-write
   STATUS      current
   DESCRIPTION
       "1: active
        2: notInservice
        3: edit
        4: destroy
        5: undo"
   ::= { gepoel2esw12AccessMgtConfEntry 8 }

gepoel2esw12AccessMgtStatistics                                   OBJECT IDENTIFIER ::= { gepoel2esw12AccessManagement 2 }

gepoel2esw12HttpReceivedPkts OBJECT-TYPE
   SYNTAX      Counter32
   MAX-ACCESS  read-only
   STATUS      current
   DESCRIPTION
       " "
   ::= { gepoel2esw12AccessMgtStatistics 1 }

gepoel2esw12HttpAllowedPkts OBJECT-TYPE
   SYNTAX      Counter32
   MAX-ACCESS  read-only
   STATUS      current
   DESCRIPTION
       " "
   ::= { gepoel2esw12AccessMgtStatistics 2 }

gepoel2esw12HttpDiscardedPkts OBJECT-TYPE
   SYNTAX      Counter32
   MAX-ACCESS  read-only
   STATUS      current
   DESCRIPTION
       " "
   ::= { gepoel2esw12AccessMgtStatistics 3 }

gepoel2esw12HttpsReceivedPkts OBJECT-TYPE
   SYNTAX      Counter32
   MAX-ACCESS  read-only
   STATUS      current
   DESCRIPTION
       " "
   ::= { gepoel2esw12AccessMgtStatistics 4 }

gepoel2esw12HttpsAllowedPkts OBJECT-TYPE
   SYNTAX      Counter32
   MAX-ACCESS  read-only
   STATUS      current
   DESCRIPTION
       " "
   ::= { gepoel2esw12AccessMgtStatistics 5 }

gepoel2esw12HttpsDiscardedPkts OBJECT-TYPE
   SYNTAX      Counter32
   MAX-ACCESS  read-only
   STATUS      current
   DESCRIPTION
       " "
   ::= { gepoel2esw12AccessMgtStatistics 6 }

gepoel2esw12SnmpReceivedPkts OBJECT-TYPE
   SYNTAX      Counter32
   MAX-ACCESS  read-only
   STATUS      current
   DESCRIPTION
       " "
   ::= { gepoel2esw12AccessMgtStatistics 7 }

gepoel2esw12SnmpAllowedPkts OBJECT-TYPE
   SYNTAX      Counter32
   MAX-ACCESS  read-only
   STATUS      current
   DESCRIPTION
       " "
   ::= { gepoel2esw12AccessMgtStatistics 8 }

gepoel2esw12SnmpDiscardedPkts OBJECT-TYPE
   SYNTAX      Counter32
   MAX-ACCESS  read-only
   STATUS      current
   DESCRIPTION
       " "
   ::= { gepoel2esw12AccessMgtStatistics 9 }

gepoel2esw12TelnetReceivedPkts OBJECT-TYPE
   SYNTAX      Counter32
   MAX-ACCESS  read-only
   STATUS      current
   DESCRIPTION
       " "
   ::= { gepoel2esw12AccessMgtStatistics 10 }

gepoel2esw12TelnetAllowedPkts OBJECT-TYPE
   SYNTAX      Counter32
   MAX-ACCESS  read-only
   STATUS      current
   DESCRIPTION
       " "
   ::= { gepoel2esw12AccessMgtStatistics 11 }

gepoel2esw12TelnetDiscardedPkts OBJECT-TYPE
   SYNTAX      Counter32
   MAX-ACCESS  read-only
   STATUS      current
   DESCRIPTION
       " "
   ::= { gepoel2esw12AccessMgtStatistics 12 }

gepoel2esw12SSHReceivedPkts OBJECT-TYPE
   SYNTAX      Counter32
   MAX-ACCESS  read-only
   STATUS      current
   DESCRIPTION
       " "
   ::= { gepoel2esw12AccessMgtStatistics 13 }

gepoel2esw12SSHAllowedPkts OBJECT-TYPE
   SYNTAX      Counter32
   MAX-ACCESS  read-only
   STATUS      current
   DESCRIPTION
       " "
   ::= { gepoel2esw12AccessMgtStatistics 14 }

gepoel2esw12SSHDiscardedPkts OBJECT-TYPE
   SYNTAX      Counter32
   MAX-ACCESS  read-only
   STATUS      current
   DESCRIPTION
       " "
   ::= { gepoel2esw12AccessMgtStatistics 15 }

gepoel2esw12AccessMgtStatisticsClearAll OBJECT-TYPE
   SYNTAX      INTEGER(0|1)
   MAX-ACCESS  read-write
   STATUS      current
   DESCRIPTION
       "0: none
        1: clear"
   ::= { gepoel2esw12AccessMgtStatistics 16 }

gepoel2esw12SSH                                                   OBJECT IDENTIFIER ::= { gepoel2esw12Security 7 }

gepoel2esw12SSHMode OBJECT-TYPE
   SYNTAX      INTEGER(0|1)
   MAX-ACCESS  read-write
   STATUS      current
   DESCRIPTION
       "default: 1
        0: disable
        1: enable"
   ::= { gepoel2esw12SSH 1 }

gepoel2esw12HTTPS                                                 OBJECT IDENTIFIER ::= { gepoel2esw12Security 8 }

gepoel2esw12HTTPSMode OBJECT-TYPE
   SYNTAX      INTEGER(0|1)
   MAX-ACCESS  read-write
   STATUS      current
   DESCRIPTION
       "default: 1
        0: disable
        1: enable"
   ::= { gepoel2esw12HTTPS 1 }

gepoel2esw12HTTPSAutoRedirect OBJECT-TYPE
   SYNTAX      INTEGER(0|1)
   MAX-ACCESS  read-write
   STATUS      current
   DESCRIPTION
       "default: 0
        0: disable
        1: enable"
   ::= { gepoel2esw12HTTPS 2 }

gepoel2esw12AuthMethod                                            OBJECT IDENTIFIER ::= { gepoel2esw12Security 9 }

gepoel2esw12ConsoleAuthMethod OBJECT-TYPE
   SYNTAX      INTEGER(0..3)
   MAX-ACCESS  read-write
   STATUS      current
   DESCRIPTION
       "default: 1
        0: none
        1: local
        2: RADIUS
        3: TACACS+"
   ::= { gepoel2esw12AuthMethod 1 }

gepoel2esw12ConsoleFallback OBJECT-TYPE
   SYNTAX      INTEGER(0|1)
   MAX-ACCESS  read-write
   STATUS      current
   DESCRIPTION
       "default: 0
        0:disable
        1:enable"
   ::= { gepoel2esw12AuthMethod 2 }

gepoel2esw12TelnetAuthMethod OBJECT-TYPE
   SYNTAX      INTEGER(0..3)
   MAX-ACCESS  read-write
   STATUS      current
   DESCRIPTION
       "default: 1
        0: none
        1: local
        2: RADIUS
        3: TACACS+"
   ::= { gepoel2esw12AuthMethod 3 }

gepoel2esw12TelnetFallback OBJECT-TYPE
   SYNTAX      INTEGER(0|1)
   MAX-ACCESS  read-write
   STATUS      current
   DESCRIPTION
       "default: 0
        0:disable
        1:enable"
   ::= { gepoel2esw12AuthMethod 4 }

gepoel2esw12SshAuthMethod OBJECT-TYPE
   SYNTAX      INTEGER(0..3)
   MAX-ACCESS  read-write
   STATUS      current
   DESCRIPTION
       "default: 1
        0: none
        1: local
        2: RADIUS
        3: TACACS+"
   ::= { gepoel2esw12AuthMethod 5 }

gepoel2esw12SshFallback OBJECT-TYPE
   SYNTAX      INTEGER(0|1)
   MAX-ACCESS  read-write
   STATUS      current
   DESCRIPTION
       "default: 0
        0:disable
        1:enable"
   ::= { gepoel2esw12AuthMethod 6 }

gepoel2esw12WebAuthMethod OBJECT-TYPE
   SYNTAX      INTEGER(0..3)
   MAX-ACCESS  read-write
   STATUS      current
   DESCRIPTION
       "default: 1
        0: none
        1: local
        2: RADIUS
        3: TACACS+"
   ::= { gepoel2esw12AuthMethod 7 }

gepoel2esw12WebFallback OBJECT-TYPE
   SYNTAX      INTEGER(0|1)
   MAX-ACCESS  read-write
   STATUS      current
   DESCRIPTION
       "default: 0
        0:disable
        1:enable"
   ::= { gepoel2esw12AuthMethod 8 }

gepoel2esw12Maintenance                                           OBJECT IDENTIFIER ::= { gepoel2esw12ProductId 7 }

gepoel2esw12RestartDevice OBJECT-TYPE
   SYNTAX      INTEGER(0|1)
   MAX-ACCESS  read-write
   STATUS      current
   DESCRIPTION
       "default: 0
        0:none
        1:yes"
   ::= { gepoel2esw12Maintenance 1 }

gepoel2esw12Firmware                                         OBJECT IDENTIFIER ::= { gepoel2esw12Maintenance 2 }

gepoel2esw12FirmwareIpAddress OBJECT-TYPE
   SYNTAX       IpAddress
   MAX-ACCESS   read-write
   STATUS       current
   DESCRIPTION
        "Get/Set the firmware tftp server."
   ::= { gepoel2esw12Firmware 1 }

gepoel2esw12FirmwareFileName OBJECT-TYPE
   SYNTAX       DisplayString
   MAX-ACCESS   read-write
   STATUS       current
   DESCRIPTION
        "Get/Set the path and filename for firmware upgrading."
   ::= { gepoel2esw12Firmware 2 }

gepoel2esw12DoFirmwareUpgrade OBJECT-TYPE
   SYNTAX       INTEGER(0|1)
   MAX-ACCESS   read-write
   STATUS       current
   DESCRIPTION
        "Do firmware upgrade. Get this OID always return zero.
              1 - do firmware upgrade.
              0 - do nothing."
   ::= { gepoel2esw12Firmware 3 }

gepoel2esw12SaveOrRestore                                         OBJECT IDENTIFIER ::= { gepoel2esw12Maintenance 3 }

gepoel2esw12FactoryDefaults OBJECT-TYPE
   SYNTAX      INTEGER(0|1)
   MAX-ACCESS  read-write
   STATUS      current
   DESCRIPTION
       "default: 0
        0:none
        1:yes"
   ::= { gepoel2esw12SaveOrRestore 1 }

gepoel2esw12SaveStart OBJECT-TYPE
   SYNTAX      INTEGER(0|1)
   MAX-ACCESS  read-write
   STATUS      current
   DESCRIPTION
       "default: 0
        0:none
        1:yes"
   ::= { gepoel2esw12SaveOrRestore 2 }

gepoel2esw12SaveUser OBJECT-TYPE
   SYNTAX      INTEGER(0|1)
   MAX-ACCESS  read-write
   STATUS      current
   DESCRIPTION
       "default: 0
        0:none
        1:yes"
   ::= { gepoel2esw12SaveOrRestore 3 }

gepoel2esw12RestoreUser OBJECT-TYPE
   SYNTAX      INTEGER(0|1)
   MAX-ACCESS  read-write
   STATUS      current
   DESCRIPTION
       "default: 0
        0:none
        1:yes"
   ::= { gepoel2esw12SaveOrRestore 4 }


gepoel2esw12Diagnostics                                           OBJECT IDENTIFIER ::= { gepoel2esw12Maintenance 5 }

gepoel2esw12PingIpAddress OBJECT-TYPE
   SYNTAX      IpAddress
   MAX-ACCESS  read-write
   STATUS      current
   DESCRIPTION
       " The destination IP Address. "
   ::= { gepoel2esw12Diagnostics 1 }
   
gepoel2esw12PingSize OBJECT-TYPE
   SYNTAX      INTEGER(60..1400)
   MAX-ACCESS  read-write
   STATUS      current
   DESCRIPTION
       " Size of ICMP echo packet.
         range : 60-1400, default : 64. "
   ::= { gepoel2esw12Diagnostics 2 }   

gepoel2esw12DoPingConfig OBJECT-TYPE
   SYNTAX      INTEGER(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gepoel2esw12Diagnostics 3 }

gepoel2esw12PingResult OBJECT-TYPE
   SYNTAX      DisplayString
   MAX-ACCESS  read-only
   STATUS      current
   DESCRIPTION
       " Show ping result. "
   ::= { gepoel2esw12Diagnostics 4 }

gepoel2esw12Ping6IpAddress OBJECT-TYPE
   SYNTAX      DisplayString
   MAX-ACCESS  read-write
   STATUS      current
   DESCRIPTION
       " The destination IPv6 Address. "
   ::= { gepoel2esw12Diagnostics 5 }
   
gepoel2esw12Ping6Size OBJECT-TYPE
   SYNTAX      INTEGER(60..1400)
   MAX-ACCESS  read-write
   STATUS      current
   DESCRIPTION
       " Size of ICMP echo packet.
         range : 60-1400. "
   ::= { gepoel2esw12Diagnostics 6 }   

gepoel2esw12DoPing6Config OBJECT-TYPE
   SYNTAX      INTEGER(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gepoel2esw12Diagnostics 7 }

gepoel2esw12Ping6Result OBJECT-TYPE
   SYNTAX      DisplayString
   MAX-ACCESS  read-only
   STATUS      current
   DESCRIPTION
       " Show ping result. "
   ::= { gepoel2esw12Diagnostics 8 }


------------------------------------------------------------------------------------------------------------------
gepoel2esw12Trap                                                  OBJECT IDENTIFIER ::= { gepoel2esw12ProductId 8 }

gepoel2esw12TrapEvent                                             OBJECT IDENTIFIER ::= { gepoel2esw12Trap 1 }

gepoel2esw12Emergency NOTIFICATION-TYPE
  OBJECTS   { gepoel2esw12Information }
  STATUS        current
    DESCRIPTION
        "The severity level is Emergency. The system is unusable."
    ::= { gepoel2esw12TrapEvent 1 }

gepoel2esw12Alert NOTIFICATION-TYPE
  OBJECTS   { gepoel2esw12Information }
  STATUS        current
    DESCRIPTION
        "The severity level is Alert. The action must be taken immediately."
    ::= { gepoel2esw12TrapEvent 2 }

gepoel2esw12Critical NOTIFICATION-TYPE
  OBJECTS   { gepoel2esw12Information }
  STATUS        current
    DESCRIPTION
        "The severity level is Critical. Critical conditions."
    ::= { gepoel2esw12TrapEvent 3 }

gepoel2esw12Error NOTIFICATION-TYPE
  OBJECTS   { gepoel2esw12Information }
  STATUS        current
    DESCRIPTION
        "The severity level is Error. Error conditions."
    ::= { gepoel2esw12TrapEvent 4 }

gepoel2esw12Warning NOTIFICATION-TYPE
  OBJECTS   { gepoel2esw12Information }
  STATUS        current
    DESCRIPTION
        "The severity level is Warning. Warning conditions."
    ::= { gepoel2esw12TrapEvent 5 }

gepoel2esw12Notice NOTIFICATION-TYPE
  OBJECTS   { gepoel2esw12Information }
  STATUS        current
    DESCRIPTION
        "The severity level is Notice. Normal but significant condition."
    ::= { gepoel2esw12TrapEvent 6 }

gepoel2esw12Informational NOTIFICATION-TYPE
  OBJECTS   { gepoel2esw12Information }
  STATUS        current
    DESCRIPTION
        "The severity level is Informational. Informational messages."
    ::= { gepoel2esw12TrapEvent 7 }

gepoel2esw12Debug NOTIFICATION-TYPE
  OBJECTS   { gepoel2esw12Information }
  STATUS        current
    DESCRIPTION
        "The severity level is Debug. debug-level messages."
    ::= { gepoel2esw12TrapEvent 8 }

gepoel2esw12TrapVariable                                          OBJECT IDENTIFIER ::= { gepoel2esw12Trap 2 }

gepoel2esw12Information OBJECT-TYPE
    SYNTAX      DisplayString
    MAX-ACCESS  read-only
    STATUS      current
    DESCRIPTION
        "Trap information."
    ::= { gepoel2esw12TrapVariable 1 }


END

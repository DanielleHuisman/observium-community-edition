RUBYTECH-ES2126-MIB DEFINITIONS ::= BEGIN

IMPORTS
    DisplayString FROM SNMPv2-TC
    MODULE-COMPLIANCE,OBJECT-GROUP, NOTIFICATION-GROUP       FROM SNMPv2-CONF
    enterprises,MODULE-IDENTITY,OBJECT-TYPE,NOTIFICATION-TYPE,Counter32,IpAddress        FROM SNMPv2-SMI
    ifIndex    FROM RFC1213-MIB;

-- @ENTERPRISE-SECTION-START
rubytech MODULE-IDENTITY
    LAST-UPDATED "200904010000Z"
        ORGANIZATION "Ruby Tech Corp."
        CONTACT-INFO
            "2F, No.7, Lane 50, Nan Kang Road, Sec.3, Taipei, Taiwan
                 Email: rubytech@mail.rubytech.com.tw
                 TEL: 886-2-2785-3961
                 FAX: 886-2-2786-3012"
        DESCRIPTION
                "The MIB module for Ruby Tech."
        ::= { enterprises 5205 }

switch               OBJECT IDENTIFIER ::= { rubytech 2 }

es2126ProductID         OBJECT IDENTIFIER ::= { switch 16 }

-- @ENTERPRISE-SECTION-END
es2126Produces            OBJECT IDENTIFIER ::= { es2126ProductID 1 }

es2126System            OBJECT IDENTIFIER ::= { es2126Produces 1 }

es2126CommonSys             OBJECT IDENTIFIER ::= { es2126System 1 }

es2126Reboot OBJECT-TYPE
    SYNTAX      INTEGER(0|1|2)
    MAX-ACCESS      read-write
    STATUS      current
    DESCRIPTION
        "Reboot the system. Get this OID always return zero.
            0 - do nothing
            1 - Reboot without saving start
            2 - Reboot with saving start"
    ::= { es2126CommonSys 1 }

es2126BiosVsersion  OBJECT-TYPE
    SYNTAX      DisplayString
    MAX-ACCESS      read-only
    STATUS      current
    DESCRIPTION
        "Get the BIOS version of the system."
    ::= { es2126CommonSys 2 }

es2126FirmwareVersion   OBJECT-TYPE
    SYNTAX      DisplayString
    MAX-ACCESS      read-only
    STATUS      current
    DESCRIPTION
        "Get the firmware version of the system."
    ::= { es2126CommonSys 3 }

es2126HardwareVersion   OBJECT-TYPE
    SYNTAX      DisplayString
    MAX-ACCESS      read-only
    STATUS      current
    DESCRIPTION
        "Get the hardware version of the system."
    ::= { es2126CommonSys 4 }

es2126MechanicalVersion OBJECT-TYPE
    SYNTAX      DisplayString
    MAX-ACCESS      read-only
    STATUS      current
    DESCRIPTION
        "Get the mechanical version of the system."
    ::= { es2126CommonSys 5 }

es2126SerialNumber  OBJECT-TYPE
    SYNTAX      DisplayString
    MAX-ACCESS      read-only
    STATUS      current
    DESCRIPTION
        "Get the Serial number of the system."
    ::= { es2126CommonSys 6 }

es2126HostMacAddress    OBJECT-TYPE
    SYNTAX      DisplayString
    MAX-ACCESS      read-only
    STATUS      current
    DESCRIPTION
        "Get the MAC address of the system."
    ::= { es2126CommonSys 7 }

es2126DevicePort    OBJECT-TYPE
    SYNTAX      DisplayString
    MAX-ACCESS      read-only
    STATUS      current
    DESCRIPTION
        "Get the quantity of ports that this system owns now."
    ::= { es2126CommonSys 8 }

es2126RamSize  OBJECT-TYPE
    SYNTAX      DisplayString
    MAX-ACCESS      read-only
    STATUS      current
    DESCRIPTION
        "Get the RAM size of the system."
    ::= { es2126CommonSys 9 }

es2126FlashSize  OBJECT-TYPE
    SYNTAX      DisplayString
    MAX-ACCESS      read-only
    STATUS      current
    DESCRIPTION
        "Get the flash size of the system."
    ::= { es2126CommonSys 10 }

es2126IP            OBJECT IDENTIFIER ::= { es2126System 2 }

es2126DhcpSetting OBJECT-TYPE
    SYNTAX          INTEGER(0|1)
    MAX-ACCESS          read-write
    STATUS          current
    DESCRIPTION
        "Get/Set DHCP status of the system.
            0 - DHCP disable
            1 - DHCP enable"
    ::= { es2126IP 1 }

es2126IPAddress OBJECT-TYPE
    SYNTAX      IpAddress
    MAX-ACCESS      read-write
    STATUS      current
    DESCRIPTION
        "Get/Set the IP address of the system.
         You can't set this OID if DHCP status is enabled."
    ::= { es2126IP 2 }

es2126NetMask OBJECT-TYPE
    SYNTAX      IpAddress
    MAX-ACCESS      read-write
    STATUS      current
    DESCRIPTION
        "Get/Set the subnet mask of the system.
         You can't set this OID if DHCP status is enabled."
    ::= { es2126IP 3 }

es2126DefaultGateway OBJECT-TYPE
    SYNTAX      IpAddress
    MAX-ACCESS      read-write
    STATUS      current
    DESCRIPTION
        "Get/Set the default gateway of the system.
         You can't set this OID if DHCP status is enabled."
    ::= { es2126IP 4 }

es2126DnsSetting OBJECT-TYPE
    SYNTAX      INTEGER(0|1)
    MAX-ACCESS      read-write
    STATUS      current
    DESCRIPTION
        "Get/Set the source of DNS server.
         You can't set this OID if DHCP status is disabled.
            0 - manual, the DNS server is from manual setting
            1 - Auto, the DNS server is assigned by DHCP server."
    ::= { es2126IP 5 }

es2126DnsServer OBJECT-TYPE
    SYNTAX      IpAddress
    MAX-ACCESS      read-write
    STATUS      current
    DESCRIPTION
        "Get/Set the DNS server of the system."
    ::= { es2126IP 6 }

es2126Time              OBJECT IDENTIFIER ::= { es2126System 3 }

es2126SystemCurrentTime OBJECT-TYPE
    SYNTAX      DisplayString
    MAX-ACCESS      read-only
    STATUS      current
    DESCRIPTION
        "Get the current time of the system."
    ::= { es2126Time 1 }

es2126ManualTimeSetting OBJECT-TYPE
    SYNTAX      DisplayString
    MAX-ACCESS      read-write
    STATUS      current
    DESCRIPTION
        "Get/Set the system time of the device.
        The input format is 'Year/Month/Day/Hour/Minute/Second'.
        Ex: 2004/1/1/12/34/25 means 2004/1/1 - 12:24:25.
        Value range:
        Year    : 2000 - 2036,
        Mouth   : 1 - 12,
        Day     : 1 - 31,
        Hour    : 0 - 23,
        Minute  : 0 - 59,
        Sec     : 0 - 59."
    ::= { es2126Time 2 }

es2126NTPServer OBJECT-TYPE
    SYNTAX      DisplayString
    MAX-ACCESS      read-write
    STATUS      current
    DESCRIPTION
        "Get/Set the NTP Time Server. You can use the IP address or domain name."
    ::= { es2126Time 3 }

es2126NTPTimeZone OBJECT-TYPE
    SYNTAX      INTEGER(-12..13)
    MAX-ACCESS      read-write
    STATUS      current
    DESCRIPTION
        "Get/Set the NTP Time Zone.
        Value range is between -12 and 13
        -12 - GMT -12:00,
        -11 - GMT -11:00,
        -10 - GMT -10:00,
         -9 - GMT -09:00,
         -8 - GMT -08:00,
         -7 - GMT -07:00,
         -6 - GMT -06:00,
         -5 - GMT -05:00,
         -4 - GMT -04:00,
         -3 - GMT -03:00,
         -2 - GMT -02:00,
         -1 - GMT -01:00,
          0 - GMT +00:00,
          1 - GMT +01:00,
          2 - GMT +02:00,
          3 - GMT +03:00,
          4 - GMT +04:00,
          5 - GMT +05:00,
          6 - GMT +06:00,
          7 - GMT +07:00,
          8 - GMT +08:00,
          9 - GMT +09:00,
         10 - GMT +10:00,
         11 - GMT +11:00,
         12 - GMT +12:00,
         13 - GMT +13:00. "
    ::= { es2126Time 4 }

es2126NTPTimeSync OBJECT-TYPE
    SYNTAX      INTEGER(0|1)
    MAX-ACCESS      read-write
    STATUS      current
    DESCRIPTION
        "Sync time from NTP Server. Get this OID always return zero.
        Set the Time Server and Time Zone before doing time sync.
        Notice that time server must be correct!
        Value range (1|0):
        1 - Sync.
        0 - do nothing."
    ::= { es2126Time 5 }

es2126DaylightSavingTime OBJECT-TYPE
    SYNTAX      INTEGER(-5..5)
    MAX-ACCESS      read-write
    STATUS      current
    DESCRIPTION
        "Get/Set the daylight saving time.
        Value range is between -5 and 5. Unit: hour. "
    ::= { es2126Time 6 }

es2126DaylightStartTime OBJECT-TYPE
    SYNTAX      DisplayString
    MAX-ACCESS      read-write
    STATUS      current
    DESCRIPTION
        "Get/Set the Start time of Daylight Saving.
        The input format is 'MM/DD/HH',
        and daylight saving start month can't equal end month.
        Example: month/day/hour   10/01/00
        Month: 01~12, day: 01~31, hour: 00~23."
    ::= { es2126Time 7 }

es2126DaylightEndTime OBJECT-TYPE
    SYNTAX      DisplayString
    MAX-ACCESS      read-write
    STATUS      current
    DESCRIPTION
        "Get/Set the End time of Daylight Saving.
        The input format is 'MM/DD/HH',
        and daylight saving start month can't equal end month.
        Example: month/day/hour   04/01/00
        Month: 01~12, day: 01~31, hour: 00~23."
    ::= { es2126Time 8 }


es2126Account               OBJECT IDENTIFIER ::= { es2126System 4 }

es2126AccountNumber OBJECT-TYPE
    SYNTAX      INTEGER(1..5)
    MAX-ACCESS      read-only
    STATUS      current
    DESCRIPTION
        "Get the current account number(s) of the system."
    ::= { es2126Account 1 }

es2126AccountTable  OBJECT-TYPE
    SYNTAX      SEQUENCE OF ES2126AccountEntry
    MAX-ACCESS  not-accessible
    STATUS      current
    DESCRIPTION
        "This is a list of es2126AccountEntry. The numbers of entries are given by
        the value of es2126AccountNumber."
    ::= { es2126Account 2 }

ES2126AccountEntry ::=
SEQUENCE {
    es2126AccountIndex          INTEGER,
    es2126AccountAuthorization  DisplayString,
    es2126AccountName             DisplayString,
    es2126AccountPassword         DisplayString
}

es2126AccountEntry  OBJECT-TYPE
    SYNTAX      ES2126AccountEntry
    MAX-ACCESS      not-accessible
    STATUS      current
    DESCRIPTION
        "This is the Entry(s) for account information."
    INDEX {es2126AccountIndex}
    ::= { es2126AccountTable 1 }

es2126AccountIndex  OBJECT-TYPE
    SYNTAX      INTEGER(1..5)
    MAX-ACCESS      read-only
    STATUS      current
    DESCRIPTION
        "This is the index of the account entry."
    ::= { es2126AccountEntry 1 }

es2126AccountAuthorization  OBJECT-TYPE
    SYNTAX      DisplayString
    MAX-ACCESS      read-only
    STATUS      current
    DESCRIPTION
        "This is the authorization of the account entry."
    ::= { es2126AccountEntry 2 }

es2126AccountName   OBJECT-TYPE
    SYNTAX      DisplayString
    MAX-ACCESS      read-write
    STATUS      current
    DESCRIPTION
        "This is the username of the account entry."
    ::= { es2126AccountEntry 3 }

es2126AccountPassword   OBJECT-TYPE
    SYNTAX      DisplayString
    MAX-ACCESS      read-write
    STATUS      current
    DESCRIPTION
        "This is the password of the account entry. The return value is always '********'."
    ::= { es2126AccountEntry 4 }

es2126AccountAddName OBJECT-TYPE
    SYNTAX      DisplayString
    MAX-ACCESS      read-write
    STATUS      current
    DESCRIPTION
        "This is the account name for adding operation."
    ::= { es2126Account 3 }

es2126AccountAddPassword OBJECT-TYPE
    SYNTAX      DisplayString
    MAX-ACCESS      read-write
    STATUS      current
    DESCRIPTION
        "This is the account password for adding operation. The return value is always '********'."
    ::= { es2126Account 4 }

es2126DoAccountAdd OBJECT-TYPE
    SYNTAX      INTEGER(0|1)
    MAX-ACCESS      read-write
    STATUS      current
    DESCRIPTION
        "Add account name. OID es2126AccountAddName and es2126AccountAddPassword must be
        filled first. Get this OID always return zero.
            1 - Add account.
            0 - do nothing."
    ::= { es2126Account 5 }

es2126AccountDel    OBJECT-TYPE
    SYNTAX      INTEGER(2..5)
    MAX-ACCESS      read-write
    STATUS      current
    DESCRIPTION
        "Delete account. The value is valid es2126AccountIndex(Can't delete administrator)."
    ::= { es2126Account 6 }


es2126Snmp              OBJECT IDENTIFIER ::= { es2126Produces 2 }

es2126GetCommunity OBJECT-TYPE
    SYNTAX      DisplayString
    MAX-ACCESS      read-write
    STATUS      current
    DESCRIPTION
        "Get/Set the get-community of the SNMP."
    ::= { es2126Snmp 1 }

es2126SetCommunity OBJECT-TYPE
    SYNTAX      DisplayString
    MAX-ACCESS      read-write
    STATUS      current
    DESCRIPTION
        "Get/Set the set-community of the SNMP."
    ::= { es2126Snmp 2 }

es2126TrapHostNumber OBJECT-TYPE
    SYNTAX      INTEGER(1..6)
    MAX-ACCESS      read-only
    STATUS      current
    DESCRIPTION
        "Get the number of trap hosts."
    ::= { es2126Snmp 3 }

es2126TrapHostTable OBJECT-TYPE
    SYNTAX      SEQUENCE OF ES2126TrapHostEntry
    MAX-ACCESS  not-accessible
    STATUS      current
    DESCRIPTION
        "This is a list of trap host entry. The numbers of entries are given by the value of es2126TrapHostNumber."
    ::= { es2126Snmp 4 }

ES2126TrapHostEntry ::=
SEQUENCE {
    es2126TrapHostIndex         INTEGER,
    es2126TrapHostIP            IpAddress,
    es2126TrapHostPort            INTEGER,
    es2126TrapHostCommunity       DisplayString
}

es2126TrapHostEntry OBJECT-TYPE
    SYNTAX      ES2126TrapHostEntry
    MAX-ACCESS      not-accessible
    STATUS      current
    DESCRIPTION
        "This is the Entry Information for trap host."
    INDEX {es2126TrapHostIndex}
    ::= { es2126TrapHostTable 1 }

es2126TrapHostIndex OBJECT-TYPE
    SYNTAX      INTEGER(1..6)
    MAX-ACCESS      read-only
    STATUS      current
    DESCRIPTION
        "The index of the trap host entry."
    ::= { es2126TrapHostEntry 1 }

es2126TrapHostIP    OBJECT-TYPE
    SYNTAX      IpAddress
    MAX-ACCESS      read-write
    STATUS      current
    DESCRIPTION
        "This is the IP of the trap host."
    ::= { es2126TrapHostEntry 2 }


es2126TrapHostPort  OBJECT-TYPE
    SYNTAX      INTEGER(1..65535)
    MAX-ACCESS      read-write
    STATUS      current
    DESCRIPTION
        "This is the receiving-port number of the trap host."
    ::= { es2126TrapHostEntry 3 }


es2126TrapHostCommunity OBJECT-TYPE
    SYNTAX      DisplayString
    MAX-ACCESS      read-write
    STATUS      current
    DESCRIPTION
        "The community name for the trap PDU."
    ::= { es2126TrapHostEntry 4 }

es2126TrapBootDelayTime OBJECT-TYPE
    SYNTAX      INTEGER(0..120)
    MAX-ACCESS      read-write
    STATUS      current
    DESCRIPTION
        "Get/Set trap boot delay time in second. Default: 0"
    ::= { es2126Snmp 8 }

es2126Alarm             OBJECT IDENTIFIER ::= { es2126Produces 3 }

es2126Event             OBJECT IDENTIFIER ::= { es2126Alarm 1 }

es2126EventNumber OBJECT-TYPE
    SYNTAX      INTEGER(1..2147483647)
    MAX-ACCESS      read-only
    STATUS      current
    DESCRIPTION
        "Get the total number of alarm events."
    ::= { es2126Event 1 }

es2126EventTable    OBJECT-TYPE
    SYNTAX      SEQUENCE OF ES2126EventEntry
    MAX-ACCESS  not-accessible
    STATUS      current
    DESCRIPTION
        "This is a list of alarm event entry. The numbers of entries are given by the value of es2126EventNumber."
    ::= { es2126Event 2 }

ES2126EventEntry ::=
SEQUENCE {
    es2126EventIndex            INTEGER,
    es2126EventName             DisplayString,
    es2126EventSendEmail      INTEGER,
    es2126EventSendTrap       INTEGER
}

es2126EventEntry    OBJECT-TYPE
    SYNTAX      ES2126EventEntry
    MAX-ACCESS      not-accessible
    STATUS      current
    DESCRIPTION
        "This is the entry information for alarm event."
    INDEX {es2126EventIndex}
    ::= { es2126EventTable 1 }

es2126EventIndex    OBJECT-TYPE
    SYNTAX      INTEGER(1..2147483647)
    MAX-ACCESS      read-only
    STATUS      current
    DESCRIPTION
        "This is the index of the alarm event entry."
    ::= { es2126EventEntry 1 }

es2126EventName OBJECT-TYPE
    SYNTAX      DisplayString
    MAX-ACCESS      read-only
    STATUS      current
    DESCRIPTION
        "This is the alarm event name."
    ::= { es2126EventEntry 2 }

es2126EventSendEmail    OBJECT-TYPE
    SYNTAX      INTEGER(0|1)
    MAX-ACCESS      read-write
    STATUS      current
    DESCRIPTION
        "Send email when alarm event is triggered."
    ::= { es2126EventEntry 3 }

es2126EventSendTrap OBJECT-TYPE
    SYNTAX      INTEGER(0|1)
    MAX-ACCESS      read-write
    STATUS      current
    DESCRIPTION
        "Send trap when alarm event is triggered."
    ::= { es2126EventEntry 4 }


es2126Email             OBJECT IDENTIFIER ::= { es2126Alarm 2 }

es2126EmailServer OBJECT-TYPE
    SYNTAX      DisplayString
    MAX-ACCESS      read-write
    STATUS      current
    DESCRIPTION
        "This is the SMTP server for alarm event."
    ::= { es2126Email 1 }

es2126EmailUsername OBJECT-TYPE
    SYNTAX      DisplayString
    MAX-ACCESS      read-write
    STATUS      current
    DESCRIPTION
        "This is the Username of SMTP server."
    ::= { es2126Email 2 }

es2126EmailPassword OBJECT-TYPE
    SYNTAX      DisplayString
    MAX-ACCESS      read-write
    STATUS      current
    DESCRIPTION
        "This is the User Password of SMTP server."
    ::= { es2126Email 3 }

es2126EmailSender OBJECT-TYPE
	SYNTAX      DisplayString
	MAX-ACCESS	    read-write
	STATUS		current
	DESCRIPTION
		"This is the Sender of SMTP server."
	::= { es2126Email 4 }

es2126EmailReturnPath OBJECT-TYPE
	SYNTAX      DisplayString
	MAX-ACCESS	    read-write
	STATUS		current
	DESCRIPTION
		"This is the return path of mail."
	::= { es2126Email 5 }

es2126EmailUserNumber OBJECT-TYPE
    SYNTAX      INTEGER(1..6)
    MAX-ACCESS      read-only
    STATUS      current
    DESCRIPTION
        "The number of the email users that you want to send the alarm notification."
    ::= { es2126Email 6 }

es2126EmailUserTable    OBJECT-TYPE
    SYNTAX      SEQUENCE OF ES2126EmailUserEntry
    MAX-ACCESS  not-accessible
    STATUS      current
    DESCRIPTION
        "This is a list of email user entry. The numbers of entries are given by the value of es2126EmailUserNumber."
    ::= { es2126Email 7 }

ES2126EmailUserEntry ::=
SEQUENCE {
    es2126EmailUserIndex            INTEGER,
    es2126EmailUserAddress          DisplayString
}

es2126EmailUserEntry    OBJECT-TYPE
    SYNTAX      ES2126EmailUserEntry
    MAX-ACCESS      not-accessible
    STATUS      current
    DESCRIPTION
        "This is the Entry information for email user entry."
    INDEX {es2126EmailUserIndex}
    ::= { es2126EmailUserTable 1 }

es2126EmailUserIndex    OBJECT-TYPE
    SYNTAX      INTEGER(1..6)
    MAX-ACCESS      read-only
    STATUS      current
    DESCRIPTION
        "This is the index of the email user entry."
    ::= { es2126EmailUserEntry 1 }

es2126EmailUserAddress  OBJECT-TYPE
    SYNTAX      DisplayString
    MAX-ACCESS      read-write
    STATUS      current
    DESCRIPTION
        "This is the email address of the email user entry."
    ::= { es2126EmailUserEntry 2 }

es2126Tftp              OBJECT IDENTIFIER ::= { es2126Produces 4 }

es2126TftpServer OBJECT-TYPE
    SYNTAX      IpAddress
    MAX-ACCESS      read-write
    STATUS      current
    DESCRIPTION
        "Get/Set the tftp server."
    ::= { es2126Tftp 1 }

es2126Configuration             OBJECT IDENTIFIER ::= { es2126Produces 5 }

es2126SaveRestore               OBJECT IDENTIFIER ::= { es2126Configuration 1 }

es2126SaveStart OBJECT-TYPE
    SYNTAX      INTEGER(0|1)
    MAX-ACCESS      read-write
    STATUS      current
    DESCRIPTION
        "Save current configuration into flash memory (Save as Start Configuration).
        Get this OID always return zero.
            1 - Save.
            0 - do nothing. "
    ::= { es2126SaveRestore 1 }

es2126SaveUser OBJECT-TYPE
    SYNTAX      INTEGER(0|1)
    MAX-ACCESS      read-write
    STATUS      current
    DESCRIPTION
        "Save current configuration into flash memory (Save as User Configuration).
        Get this OID always return zero.
            1 - Save.
            0 - do nothing. "
    ::= { es2126SaveRestore 2 }

es2126RestoreDefault OBJECT-TYPE
    SYNTAX      INTEGER(0|1|2)
    MAX-ACCESS      read-write
    STATUS      current
    DESCRIPTION
        "Restore factory default configuration.
        Get this OID always return zero.
            2 - Restore default included default ip address.
        1 - Restore default without changing current ip address.
            0 - do nothing. "
    ::= { es2126SaveRestore 3 }

es2126RestoreUser OBJECT-TYPE
    SYNTAX      INTEGER(0|1)
    MAX-ACCESS      read-write
    STATUS      current
    DESCRIPTION
        "Restore user configuration.
        Get this OID always return zero.
            1 - Restore.
            0 - do nothing. "
    ::= { es2126SaveRestore 4 }


es2126ConfigFile            OBJECT IDENTIFIER ::= { es2126Configuration 2 }

es2126ExportConfigName OBJECT-TYPE
    SYNTAX      DisplayString
    MAX-ACCESS      read-write
    STATUS      current
    DESCRIPTION
        "Get/Set the export file path and name."
    ::= { es2126ConfigFile 1 }

es2126DoExportConfig OBJECT-TYPE
    SYNTAX      INTEGER(1|2)
    MAX-ACCESS      read-write
    STATUS      current
    DESCRIPTION
        "Do export-config.
        Get this OID always return zero.
            1   -   Export start section.
            2   -   Export user-conf section."
    ::= { es2126ConfigFile 2 }

es2126ImportConfigName OBJECT-TYPE
    SYNTAX      DisplayString
    MAX-ACCESS      read-write
    STATUS      current
    DESCRIPTION
        "Get/Set the import file path and name."
    ::= { es2126ConfigFile 3 }

es2126DoImportConfig OBJECT-TYPE
    SYNTAX      INTEGER(1|2)
    MAX-ACCESS      read-write
    STATUS      current
    DESCRIPTION
        "Do import-config.
        Get this OID always return zero.
            1   -   Import start section.
            2   -   Import user-conf section."
    ::= { es2126ConfigFile 4 }

es2126Diagnostic            OBJECT IDENTIFIER ::= { es2126Produces 6 }

es2126InternalLoopbackTest OBJECT-TYPE
    SYNTAX      DisplayString
    MAX-ACCESS      read-only
    STATUS      current
    DESCRIPTION
        "Internal loop back test."
    ::= { es2126Diagnostic 1 }

es2126ExternalLoopbackTest OBJECT-TYPE
    SYNTAX      DisplayString
    MAX-ACCESS      read-only
    STATUS      current
    DESCRIPTION
        "External loop back test."
    ::= { es2126Diagnostic 2 }

es2126PingTest OBJECT-TYPE
    SYNTAX      DisplayString
    MAX-ACCESS      read-write
    STATUS      current
    DESCRIPTION
        "Set the host address that you want to ping and the system will return the test result."
    ::= { es2126Diagnostic 3 }

es2126Watchdog               OBJECT IDENTIFIER ::= { es2126Diagnostic 4 }

es2126WatchdogState OBJECT-TYPE
    SYNTAX      INTEGER(0|1)
    MAX-ACCESS      read-write
    STATUS      current
    DESCRIPTION
        "Set the watchdog state.
            1 - Enable.
            0 - Disable."
    ::= { es2126Watchdog 1 }

es2126WatchdogTimeGap OBJECT-TYPE
    SYNTAX      INTEGER(0..100)
    MAX-ACCESS      read-write
    STATUS      current
    DESCRIPTION
        "Set the watchdog time gap, from 1 to 100."
    ::= { es2126Watchdog 2 }

es2126WatchdogHost OBJECT-TYPE
    SYNTAX      DisplayString
    MAX-ACCESS      read-write
    STATUS      current
    DESCRIPTION
        "Set the watchdog host"
    ::= { es2126Watchdog 3 }

es2126WatchdogResetMgtInf OBJECT-TYPE
    SYNTAX      INTEGER(0|1)
    MAX-ACCESS      read-write
    STATUS      current
    DESCRIPTION
        "Set the state of resetting the management cpu interface.
            1 - Enable.
            0 - Disable."
    ::= { es2126Watchdog 4 }

es2126WatchdogResetMgtInfCount OBJECT-TYPE
    SYNTAX      INTEGER(1..20)
    MAX-ACCESS      read-write
    STATUS      current
    DESCRIPTION
        "Set the count of resetting the management cpu interface."
    ::= { es2126Watchdog 5 }

es2126WatchdogResetSystem OBJECT-TYPE
    SYNTAX      INTEGER(0|1)
    MAX-ACCESS      read-write
    STATUS      current
    DESCRIPTION
        "Set the state of rebooting the system.
            1 - Enable.
            0 - Disable."
    ::= { es2126Watchdog 6 }

es2126WatchdogResetSystemCount OBJECT-TYPE
    SYNTAX      INTEGER(1..1000)
    MAX-ACCESS      read-write
    STATUS      current
    DESCRIPTION
        "Set the count of rebooting the system"
    ::= { es2126Watchdog 7 }

es2126Log               OBJECT IDENTIFIER ::= { es2126Produces 7 }

es2126ClearLog OBJECT-TYPE
    SYNTAX      INTEGER(0|1)
    MAX-ACCESS      read-write
    STATUS      current
    DESCRIPTION
        "Clear system log.
        Get this OID always return zero.
            1 - Clear log.
            0 - do nothing. "
    ::= { es2126Log 1 }

es2126UploadLog OBJECT-TYPE
    SYNTAX      INTEGER(0|1)
    MAX-ACCESS      read-write
    STATUS      current
    DESCRIPTION
        "Upload current system log. Set the correct tftp server first.
        The format of log file is 'ModelName_SerialNumbuer_YYMMDD_HHMM'.
        Get this OID always return zero.
            1 - Upload log
            0 - do nothing. "
    ::= { es2126Log 2 }

es2126AutoUploadLogState OBJECT-TYPE
    SYNTAX      INTEGER(0|1)
    MAX-ACCESS      read-write
    STATUS      current
    DESCRIPTION
        "Enable auto-upload log function. Set the correct tftp server first.
        The format of log file is 'ModelName_SerialNumbuer_YYMMDD_HHMM'.
        Get this OID always return zero.
            1 - Enable auto-upload
            0 - do nothing. "
    ::= { es2126Log 3 }

es2126LogNumber OBJECT-TYPE
    SYNTAX      INTEGER(0..120)
    MAX-ACCESS      read-only
    STATUS      current
    DESCRIPTION
        "Get the number of current system log. "
    ::= { es2126Log 4 }

es2126LogTable  OBJECT-TYPE
    SYNTAX      SEQUENCE OF ES2126LogEntry
    MAX-ACCESS  not-accessible
    STATUS      current
    DESCRIPTION
        "This is a list of log entry. The numbers of entries are given by the value of es2126LogNumber."
    ::= { es2126Log 5 }

ES2126LogEntry ::=
SEQUENCE {
    es2126LogIndex          INTEGER,
    es2126LogEvent              DisplayString
}

es2126LogEntry  OBJECT-TYPE
    SYNTAX      ES2126LogEntry
    MAX-ACCESS      not-accessible
    STATUS      current
    DESCRIPTION
        "This is the Entry information for system log."
    INDEX {es2126LogIndex}
    ::= { es2126LogTable 1 }

es2126LogIndex  OBJECT-TYPE
    SYNTAX      INTEGER(1..120)
    MAX-ACCESS      read-only
    STATUS      current
    DESCRIPTION
        "This is the index of the log entry."
    ::= { es2126LogEntry 1 }

es2126LogEvent  OBJECT-TYPE
    SYNTAX      DisplayString
    MAX-ACCESS      read-only
    STATUS      current
    DESCRIPTION
        "This is the detail information of the log entry."
    ::= { es2126LogEntry 2 }

es2126Firmware              OBJECT IDENTIFIER ::= { es2126Produces 8 }

es2126FirmwareFileName OBJECT-TYPE
    SYNTAX      DisplayString
    MAX-ACCESS      read-write
    STATUS      current
    DESCRIPTION
        "Get/Set the path and filename for firmware upgrading."
    ::= { es2126Firmware 1 }

es2126DoFirmwareUpgrade OBJECT-TYPE
    SYNTAX      INTEGER(0|1)
    MAX-ACCESS      read-write
    STATUS      current
    DESCRIPTION
        "Do firmware upgrade. Get this OID always return zero.
            1 - Do firmware upgrade.
            0 - do nothing."
    ::= { es2126Firmware 2 }


es2126Port              OBJECT IDENTIFIER ::= { es2126Produces 9 }

es2126PortStatus            OBJECT IDENTIFIER ::= { es2126Port 1 }

es2126PortStatusNumber OBJECT-TYPE
    SYNTAX      INTEGER(1..2147483647)
    MAX-ACCESS      read-only
    STATUS      current
    DESCRIPTION
        "Get the number of port."
    ::= { es2126PortStatus 1 }

es2126PortStatusTable   OBJECT-TYPE
    SYNTAX      SEQUENCE OF ES2126PortStatusEntry
    MAX-ACCESS  not-accessible
    STATUS      current
    DESCRIPTION
        "This is a list of port status entry. The numbers of entries are given by the value of es2126PortStatusNumber."
    ::= { es2126PortStatus 2 }

ES2126PortStatusEntry ::=
SEQUENCE {
    es2126PortStatusIndex           INTEGER,
    es2126PortStatusMedia          DisplayString,
    es2126PortStatusLink           DisplayString,
    es2126PortStatusPortState      DisplayString,
    es2126PortStatusAutoNego       DisplayString,
    es2126PortStatusSpdDpx         DisplayString,
    es2126PortStatusRxPause        DisplayString,
    es2126PortStatusTxPause        DisplayString,
    es2126PortStatusDescription     DisplayString
}

es2126PortStatusEntry   OBJECT-TYPE
    SYNTAX      ES2126PortStatusEntry
    MAX-ACCESS      not-accessible
    STATUS      current
    DESCRIPTION
        "This is the entry(s) for port status information."
    INDEX {es2126PortStatusIndex}
    ::= { es2126PortStatusTable 1 }

es2126PortStatusIndex   OBJECT-TYPE
    SYNTAX      INTEGER(1..2147483647)
    MAX-ACCESS      read-only
    STATUS      current
    DESCRIPTION
        "This is the index of the port status entry."
    ::= { es2126PortStatusEntry 1 }

es2126PortStatusMedia   OBJECT-TYPE
    SYNTAX      DisplayString
    MAX-ACCESS      read-only
    STATUS      current
    DESCRIPTION
        "The port media type of the port status entry."
    ::= { es2126PortStatusEntry 2 }

es2126PortStatusLink    OBJECT-TYPE
    SYNTAX      DisplayString
    MAX-ACCESS      read-only
    STATUS      current
    DESCRIPTION
        "This is the port link of the port status entry."
    ::= { es2126PortStatusEntry 3 }

es2126PortStatusPortState   OBJECT-TYPE
    SYNTAX      DisplayString
    MAX-ACCESS      read-only
    STATUS      current
    DESCRIPTION
        "This is the port state of the port status entry."
    ::= { es2126PortStatusEntry 4 }

es2126PortStatusAutoNego    OBJECT-TYPE
    SYNTAX      DisplayString
    MAX-ACCESS      read-only
    STATUS      current
    DESCRIPTION
        "This is the auto negotiation of the port status entry."
    ::= { es2126PortStatusEntry 5 }

es2126PortStatusSpdDpx  OBJECT-TYPE
    SYNTAX      DisplayString
    MAX-ACCESS      read-only
    STATUS      current
    DESCRIPTION
        "This is the speed/duplex of the port status entry."
    ::= { es2126PortStatusEntry 6 }

es2126PortStatusRxPause     OBJECT-TYPE
    SYNTAX      DisplayString
    MAX-ACCESS      read-only
    STATUS      current
    DESCRIPTION
        "The Rx Pause of the port status entry."
    ::= { es2126PortStatusEntry 7 }

es2126PortStatusTxPause     OBJECT-TYPE
    SYNTAX      DisplayString
    MAX-ACCESS      read-only
    STATUS      current
    DESCRIPTION
        "The Tx Pause of the port status entry."
    ::= { es2126PortStatusEntry 8 }

es2126PortStatusDescription OBJECT-TYPE
    SYNTAX      DisplayString
    MAX-ACCESS      read-only
    STATUS      current
    DESCRIPTION
        "This is the description of port."
    ::= { es2126PortStatusEntry 9 }

es2126PortConf              OBJECT IDENTIFIER ::= { es2126Port 2 }

es2126PortConfNumber OBJECT-TYPE
    SYNTAX      INTEGER(1..2147483647)
    MAX-ACCESS      read-only
    STATUS      current
    DESCRIPTION
        "Get the number of port configuration."
    ::= { es2126PortConf 1 }

es2126PortConfTable OBJECT-TYPE
    SYNTAX      SEQUENCE OF ES2126PortConfEntry
    MAX-ACCESS  not-accessible
    STATUS      current
    DESCRIPTION
        "This is a list of port configuration entry. The numbers of entries are given by the value of es2126PortConfNumber."
    ::= { es2126PortConf 2 }

ES2126PortConfEntry ::=
SEQUENCE {
    es2126PortConfIndex        INTEGER,
    es2126PortConfPortState        INTEGER,
    es2126PortConfSpdDpx           INTEGER,
    es2126PortConfFlwCtrl          INTEGER,
    es2126PortConfDescription      DisplayString
}

es2126PortConfEntry OBJECT-TYPE
    SYNTAX      ES2126PortConfEntry
    MAX-ACCESS      not-accessible
    STATUS      current
    DESCRIPTION
        "This is the Entry(s) for port configuration information."
    INDEX {es2126PortConfIndex}
    ::= { es2126PortConfTable 1 }

es2126PortConfIndex OBJECT-TYPE
    SYNTAX      INTEGER(1..2147483647)
    MAX-ACCESS      read-only
    STATUS      current
    DESCRIPTION
        "This is the index of the port configuration entry."
    ::= { es2126PortConfEntry 1 }

es2126PortConfPortState OBJECT-TYPE
    SYNTAX      INTEGER(0|1)
    MAX-ACCESS      read-write
    STATUS      current
    DESCRIPTION
        "This is the port state of the port configuration entry.
         0 - disabled.
         1 - enabled. "
    ::= { es2126PortConfEntry 2 }

es2126PortConfSpdDpx    OBJECT-TYPE
    SYNTAX      INTEGER(0..5)
    MAX-ACCESS      read-write
    STATUS      current
    DESCRIPTION
        "This is the speed/duplex of the port configuration entry.
         0 - auto.
         1 - 10M/Half.
         2 - 10M/Full.
         3 - 100M/Half.
         4 - 100M/Full.
         5 - 1G/Full.  "
    ::= { es2126PortConfEntry 3 }

es2126PortConfFlwCtrl   OBJECT-TYPE
    SYNTAX      INTEGER(0|1)
    MAX-ACCESS      read-write
    STATUS      current
    DESCRIPTION
        "This is the flow control of the port configuration entry.
         0 - asymmetric.
         1 - symmetric.  "
    ::= { es2126PortConfEntry 4 }

es2126PortConfDescription   OBJECT-TYPE
    SYNTAX      DisplayString
    MAX-ACCESS      read-write
    STATUS      current
    DESCRIPTION
        "This is the description of port."
    ::= { es2126PortConfEntry 5 }

es2126PortBandwidth             OBJECT IDENTIFIER ::= { es2126Port 3 }

es2126PortBandwidthTable    OBJECT-TYPE
    SYNTAX      SEQUENCE OF ES2126PortBandwidthEntry
    MAX-ACCESS  not-accessible
    STATUS      current
    DESCRIPTION
        "This is a list of port bandwidth entry."
    ::= { es2126PortBandwidth 1 }

ES2126PortBandwidthEntry ::=
SEQUENCE {
    es2126PortBandwidthIndex                  INTEGER,
    es2126PortBandwidthIngressRate        INTEGER,
    es2126PortBandwidthEgressRate         INTEGER
}

es2126PortBandwidthEntry    OBJECT-TYPE
    SYNTAX      ES2126PortBandwidthEntry
    MAX-ACCESS      not-accessible
    STATUS      current
    DESCRIPTION
        "This is the Entry(s) for port bandwidth configuration."
    INDEX {es2126PortBandwidthIndex}
    ::= { es2126PortBandwidthTable 1 }

es2126PortBandwidthIndex    OBJECT-TYPE
    SYNTAX      INTEGER(1..26)
    MAX-ACCESS      read-only
    STATUS      current
    DESCRIPTION
        "This is the index of the port bandwidth entry."
    ::= { es2126PortBandwidthEntry 1 }

es2126PortBandwidthIngressRate  OBJECT-TYPE
    SYNTAX      INTEGER(66..1024000)
    MAX-ACCESS      read-write
    STATUS      current
    DESCRIPTION
        "Get/Set the port bandwidth ingress rate.
         Fast Ethernet port range: 66~102400(Kb)
         Gigabit Ethernet port range: 66~1024000(Kb)"
    ::= { es2126PortBandwidthEntry 2 }

es2126PortBandwidthEgressRate   OBJECT-TYPE
    SYNTAX      INTEGER(66..1024000)
    MAX-ACCESS      read-write
    STATUS      current
    DESCRIPTION
        "Get/Set the port bandwidth egress rate.
         Fast Ethernet port range: 66~102400(Kb)
         Gigabit Ethernet port range: 66~1024000(Kb)"
    ::= { es2126PortBandwidthEntry 3 }

es2126PortBandwidthStormType    OBJECT-TYPE
    SYNTAX      INTEGER(0..4)
    MAX-ACCESS      read-write
    STATUS      current
    DESCRIPTION
        "This is the bandwidth storm type.
        0:Disable
                1:Broadcast Storm Control
                2:Multicast Storm Control
                3:Unknown Unicast Storm Control
                4:Broadcast, Multicast, and Unknown Unicast Storm Control"
    ::= { es2126PortBandwidth 2 }

es2126PortBandwidthStormRate    OBJECT-TYPE
    SYNTAX      INTEGER(1..100)
    MAX-ACCESS      read-write
    STATUS      current
    DESCRIPTION
        "This is the storm rate."
    ::= { es2126PortBandwidth 3 }

es2126LoopDetectedConf              OBJECT IDENTIFIER ::= { es2126Produces 10 }

es2126LoopDetectedNumber OBJECT-TYPE
    SYNTAX      INTEGER(1..2147483647)
    MAX-ACCESS      read-only
    STATUS      current
    DESCRIPTION
        "Get the number of loop detected entry."
    ::= { es2126LoopDetectedConf 1 }

es2126LoopDetectedTable OBJECT-TYPE
    SYNTAX      SEQUENCE OF ES2126LoopDetectedEntry
    MAX-ACCESS  not-accessible
    STATUS      current
    DESCRIPTION
        "This is a list of loop detected entry. The number of entries are given by the value of es2126LoopDetectedNumber."
    ::= { es2126LoopDetectedConf 2 }

ES2126LoopDetectedEntry ::=
SEQUENCE {
    es2126LoopDetectedfIndex           INTEGER,
    es2126LoopDetectedStateEbl         INTEGER,
    es2126LoopDetectedCurrentStatus    INTEGER,
    es2126LoopDetectedResumed          INTEGER
}

es2126LoopDetectedEntry OBJECT-TYPE
    SYNTAX      ES2126LoopDetectedEntry
    MAX-ACCESS      not-accessible
    STATUS      current
    DESCRIPTION
        "Entry(s) for loop detected information."
    INDEX {es2126LoopDetectedfIndex}
    ::= { es2126LoopDetectedTable 1 }

es2126LoopDetectedfIndex    OBJECT-TYPE
    SYNTAX      INTEGER(1..2147483647)
    MAX-ACCESS      read-only
    STATUS      current
    DESCRIPTION
        "This is the index of the loop detected entry."
    ::= { es2126LoopDetectedEntry 1 }

es2126LoopDetectedStateEbl  OBJECT-TYPE
    SYNTAX      INTEGER(0|1)
    MAX-ACCESS      read-write
    STATUS      current
    DESCRIPTION
        "The state of the loop detected entry.
         0 - disabled.
         1 - enabled. "
    ::= { es2126LoopDetectedEntry 2 }

es2126LoopDetectedCurrentStatus OBJECT-TYPE
    SYNTAX      INTEGER(0|1)
    MAX-ACCESS      read-only
    STATUS      current
    DESCRIPTION
        "The current status of the loop detected port.
         0 - Unlocked
         1 - Locked due to the loop condition "
    ::= { es2126LoopDetectedEntry 3 }

es2126LoopDetectedResumed   OBJECT-TYPE
    SYNTAX      INTEGER(0|1)
    MAX-ACCESS      read-write
    STATUS      current
    DESCRIPTION
        "Unlock the port which is locked due to loop condition. Get this OID always return zero.
         1 - Unlock the port,
         0 - do nothing."
    ::= { es2126LoopDetectedEntry 4 }

es2126LoopDetectedAction OBJECT-TYPE
    SYNTAX      INTEGER(0|1)
    MAX-ACCESS      read-write
    STATUS      current
    DESCRIPTION
        "Set the corresponding action while loop is detected.
         1 - Lock the loop port,
         0 - do nothing."
    ::= { es2126LoopDetectedConf 3 }

es2126TrapEntry        OBJECT IDENTIFIER ::= { es2126Produces 20 }

es2126ModuleInserted NOTIFICATION-TYPE
    OBJECTS { ifIndex }
    STATUS    current
    DESCRIPTION
        "Send the trap when a module is inserted to the system. The OID value means
         the port number."
    ::= { es2126TrapEntry 1 }

es2126ModuleRemoved NOTIFICATION-TYPE
    OBJECTS { ifIndex }
    STATUS    current
    DESCRIPTION
        "Send the trap when a module is removed from the system. The OID value means
         the port number."
    ::= { es2126TrapEntry 2 }

es2126DualMediaSwapped NOTIFICATION-TYPE
    OBJECTS { ifIndex }
    STATUS    current
    DESCRIPTION
        "Send the trap when the dual media port changed. The OID value means the port number."
    ::= { es2126TrapEntry 3 }

es2126LoopDetected NOTIFICATION-TYPE
    OBJECTS { ifIndex }
    STATUS    current
    DESCRIPTION
        "Send the trap when loop condition has been detected. The OID value means the port number."
    ::= { es2126TrapEntry 4 }

es2126StpStateDisabled NOTIFICATION-TYPE
    STATUS      current
    DESCRIPTION
       "Send the trap when the operational state of STP is from enabled to disabled. "
    ::= { es2126TrapEntry 100 }

es2126StpStateEnabled NOTIFICATION-TYPE
    STATUS      current
    DESCRIPTION
       "Send the trap when the operational state of STP is from disabled to enabled. "
    ::= { es2126TrapEntry 101 }

es2126StpTopologyChanged NOTIFICATION-TYPE
    OBJECTS { ifIndex }
    STATUS      current
    DESCRIPTION
       "Send the trap when RSTP determines a port should enter the FORWARDING state
        (a topology change occurs). The OID value is the ifIndex of the port that
        produces the topology change."
    ::= { es2126TrapEntry 102 }

es2126RmonRisingAlarm NOTIFICATION-TYPE
    STATUS      current
    DESCRIPTION
       "Send the trap when an RMON rising alarm happened. The OID value is the value
        of another OID variable sampled by the RMON Alarm Group that exceeds its
        own RisingThreshold "
    ::= { es2126TrapEntry 110 }

es2126RmonFallingAlarm NOTIFICATION-TYPE
    STATUS      current
    DESCRIPTION
           "Send the trap when an RMON falling alarm happened. The OID value is the value
        of another OID variable sampled by the RMON Alarm Group that is smaller than its
        own FallingThreshold "
    ::= { es2126TrapEntry 111 }

es2126LacpStateDisabled NOTIFICATION-TYPE
    OBJECTS {ifIndex, groupId}
    STATUS      current
    DESCRIPTION
       "Send the trap when the operational state of LACP is from enabled to disabled.
        The OID value means the disabled Group ID."
    ::= { es2126TrapEntry 120 }

es2126LacpStateEnabled NOTIFICATION-TYPE
    OBJECTS {ifIndex, groupId}
    STATUS      current
    DESCRIPTION
       "Send the trap when the operational state of LACP is from disabled to enabled.
        The OID value means the disabled Group ID."
    ::= { es2126TrapEntry 121 }

es2126LacpPortAdded NOTIFICATION-TYPE
    OBJECTS   { ifIndex, actorkey, partnerkey }
    STATUS      current
    DESCRIPTION
       "Send the trap when the state of port is in 'trunk ready'."
    ::= { es2126TrapEntry 123 }

es2126LacpPortTrunkFailure NOTIFICATION-TYPE
    OBJECTS   { ifIndex, actorkey, partnerkey}
    STATUS      current
    DESCRIPTION
       "Send the trap when one port is not able to be aggregated
        due to duplex-mode of the port. "
    ::= { es2126TrapEntry 124 }

es2126GvrpStateDisabled NOTIFICATION-TYPE
    STATUS      current
    DESCRIPTION
       "Send the trap when the operational state of GVRP is from enabled to disabled. "
    ::= { es2126TrapEntry 140 }

es2126GvrpStateEnabled NOTIFICATION-TYPE
    STATUS      current
    DESCRIPTION
       "Send the trap when the operational state of LACP is from disabled to enabled. "
    ::= { es2126TrapEntry 141 }

es2126VlanPortBaseEnabled NOTIFICATION-TYPE
    STATUS      current
    DESCRIPTION
       "Send the trap when the operational state of vlan is changed to port-based vlan."
    ::= { es2126TrapEntry 151 }

es2126VlanTagBaseEnabled NOTIFICATION-TYPE
    STATUS      current
    DESCRIPTION
       "Send the trap when the operational state of vlan is changed to tag-based vlan."
    ::= { es2126TrapEntry 152 }

es2126VlanMetroBaseEnabled NOTIFICATION-TYPE
    STATUS      current
    DESCRIPTION
       "Send the trap when the operational state of vlan is changed to metro-based vlan."
    ::= { es2126TrapEntry 153 }

es2126UserLogin NOTIFICATION-TYPE
    OBJECTS   {username}
    STATUS      current
    DESCRIPTION
       "Send the trap when one user logins the system."
    ::= { es2126TrapEntry 200 }

es2126UserLogout NOTIFICATION-TYPE
    OBJECTS   {username}
    STATUS      current
    DESCRIPTION
       "Send the trap when one user logouts the system."
    ::= { es2126TrapEntry 201 }

es2126TrapVariable  OBJECT IDENTIFIER ::= { es2126Produces 21 }

username OBJECT-TYPE
    SYNTAX      DisplayString
    MAX-ACCESS  read-only
    STATUS      current
    DESCRIPTION
        "System account name."
    ::= { es2126TrapVariable 1 }

groupId OBJECT-TYPE
    SYNTAX      INTEGER(1..8)
    MAX-ACCESS  read-only
    STATUS      current
    DESCRIPTION
        "The Trunk group ID of LACP."
    ::= { es2126TrapVariable 2 }

actorkey OBJECT-TYPE
    SYNTAX  INTEGER(1..2147483647)
    MAX-ACCESS  read-only
    STATUS      current
    DESCRIPTION
        "The actor key information for LACP."
    ::= { es2126TrapVariable 3 }

partnerkey OBJECT-TYPE
    SYNTAX  INTEGER(1..2147483647)
    MAX-ACCESS  read-only
    STATUS      current
    DESCRIPTION
        "The partner key information for LACP."
    ::= { es2126TrapVariable 4 }

uplink OBJECT-TYPE
    SYNTAX  DisplayString
    MAX-ACCESS  read-only
    STATUS      current
    DESCRIPTION
        "Uplink port(s) in the metro-mode vlan."
    ::= { es2126TrapVariable 5 }

END

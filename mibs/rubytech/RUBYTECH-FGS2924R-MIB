RUBYTECH-FGS2924R-MIB DEFINITIONS ::= BEGIN

IMPORTS
    DisplayString FROM SNMPv2-TC
    MODULE-COMPLIANCE,OBJECT-GROUP, NOTIFICATION-GROUP       FROM SNMPv2-CONF
    enterprises,MODULE-IDENTITY,OBJECT-TYPE,NOTIFICATION-TYPE,Counter32,IpAddress        FROM SNMPv2-SMI
    MacAddress FROM BRIDGE-MIB
    ifIndex    FROM RFC1213-MIB;


rubytech MODULE-IDENTITY
        LAST-UPDATED "200904020000Z"
        ORGANIZATION "Ruby Tech Corp."
        CONTACT-INFO
            "2F, No.7, Lane 50, Nan Kang Road, Sec.3, Taipei, Taiwan
             Email: rubytech@mail.rubytech.com.tw
             TEL: 886-2-2785-3961
             FAX: 886-2-2786-3012"
        DESCRIPTION
            "The MIB module is for Ruby Tech."
        ::= { enterprises 5205 }

switch                       OBJECT IDENTIFIER ::= { rubytech 2 }

fgs2924rProductID         OBJECT IDENTIFIER ::= { switch 34 }

fgs2924rProduces            OBJECT IDENTIFIER ::= { fgs2924rProductID 1 }

fgs2924rSystem            OBJECT IDENTIFIER ::= { fgs2924rProduces 1 }

fgs2924rCommonSys            OBJECT IDENTIFIER ::= { fgs2924rSystem 1 }

fgs2924rReboot OBJECT-TYPE
 SYNTAX  INTEGER(0|1)
 MAX-ACCESS     read-write
 STATUS  current
 DESCRIPTION
  "Reboot the system. Get this OID always return zero.
            0 - do nothing
   1 - Reboot without saving start"
 ::= { fgs2924rCommonSys 1 }

fgs2924rBiosVsersion OBJECT-TYPE
 SYNTAX  DisplayString
 MAX-ACCESS     read-only
 STATUS  current
 DESCRIPTION
  "Get the BIOS version of the system."
 ::= { fgs2924rCommonSys 2 }

fgs2924rFirmwareVersion OBJECT-TYPE
 SYNTAX  DisplayString
 MAX-ACCESS     read-only
 STATUS  current
 DESCRIPTION
  "Get the firmware version of the system."
 ::= { fgs2924rCommonSys 3 }

fgs2924rHardwareVersion OBJECT-TYPE
 SYNTAX  DisplayString
 MAX-ACCESS     read-only
 STATUS  current
 DESCRIPTION
  "Get the hardware version of the system."
 ::= { fgs2924rCommonSys 4 }

fgs2924rMechanicalVersion OBJECT-TYPE
 SYNTAX  DisplayString
 MAX-ACCESS      read-only
 STATUS  current
 DESCRIPTION
  "Get the mechanical version of the system."
 ::= { fgs2924rCommonSys 5 }

fgs2924rSerialNumber OBJECT-TYPE
 SYNTAX  DisplayString
 MAX-ACCESS     read-only
 STATUS  current
 DESCRIPTION
  "Get the Serial number of the system."
 ::= { fgs2924rCommonSys 6 }

fgs2924rHostMacAddress OBJECT-TYPE
 SYNTAX  DisplayString
 MAX-ACCESS     read-only
 STATUS  current
 DESCRIPTION
  "Get the MAC address of the system."
 ::= { fgs2924rCommonSys 7 }

fgs2924rDevicePort OBJECT-TYPE
 SYNTAX  DisplayString
 MAX-ACCESS   read-only
 STATUS  current
 DESCRIPTION
  "Get the quantity of ports that this system owns now."
 ::= { fgs2924rCommonSys 8 }

fgs2924rRamSize  OBJECT-TYPE
    SYNTAX      DisplayString
    MAX-ACCESS      read-only
    STATUS      current
    DESCRIPTION
        "Get the RAM size of the system."
 ::= { fgs2924rCommonSys 9 }

fgs2924rFlashSize  OBJECT-TYPE
    SYNTAX      DisplayString
    MAX-ACCESS      read-only
    STATUS      current
    DESCRIPTION
        "Get the flash size of the system."
 ::= { fgs2924rCommonSys 10 }

fgs2924rDeviceName  OBJECT-TYPE
    SYNTAX      DisplayString
    MAX-ACCESS      read-write
    STATUS      current
    DESCRIPTION
        "Get/Set the device name of the system."
 ::= { fgs2924rCommonSys 11 }

fgs2924rSystemDescription  OBJECT-TYPE
    SYNTAX      DisplayString
    MAX-ACCESS      read-only
    STATUS      current
    DESCRIPTION
        "Get the system desctiption of the system."
 ::= { fgs2924rCommonSys 12 }

fgs2924rCpuLoad  OBJECT-TYPE
    SYNTAX      DisplayString
    MAX-ACCESS      read-only
    STATUS      current
    DESCRIPTION
        "Get the CPU Load."
 ::= { fgs2924rCommonSys 13 }

fgs2924rIP            OBJECT IDENTIFIER ::= { fgs2924rSystem 2 }

fgs2924rDhcpSetting OBJECT-TYPE
 SYNTAX      INTEGER(0|1)
 MAX-ACCESS         read-write
 STATUS      current
 DESCRIPTION
  "Get/Set DHCP status of the system.
   0 - DHCP disable
   1 - DHCP enable"
 ::= { fgs2924rIP 1 }

fgs2924rIPAddress OBJECT-TYPE
 SYNTAX      IpAddress
 MAX-ACCESS     read-write
 STATUS  current
 DESCRIPTION
  "Get/Set the IP address of the system.
   You can't set this OID if DHCP status is enabled."
 ::= { fgs2924rIP 2 }

fgs2924rNetMask OBJECT-TYPE
 SYNTAX      IpAddress
 MAX-ACCESS     read-write
 STATUS  current
 DESCRIPTION
  "Get/Set the subnet mask of the system.
   You can't set this OID if DHCP status is enabled."
 ::= { fgs2924rIP 3 }

fgs2924rDefaultGateway OBJECT-TYPE
 SYNTAX      IpAddress
 MAX-ACCESS     read-write
 STATUS  current
 DESCRIPTION
  "Get/Set the default gateway of the system.
   You can't set this OID if DHCP status is enabled."
 ::= { fgs2924rIP 4 }

fgs2924rDnsConf OBJECT-TYPE
 SYNTAX      INTEGER(0|1)
 MAX-ACCESS     read-write
 STATUS  current
 DESCRIPTION
  "Get/Set DNS state.
  Change of this value will be kept in buffer and only take effect while DHCP is enabled.
   0 - manual, the DNS server is from manual setting
   1 - auto, the DNS server is assigned by DHCP server."
 ::= { fgs2924rIP 5 }

fgs2924rDnsState OBJECT-TYPE
 SYNTAX      INTEGER(0|1)
 MAX-ACCESS     read-only
 STATUS  current
 DESCRIPTION
  "Get the DNS real state.
   0 - manual, the DNS server is from manual setting
   1 - auto, the DNS server is assigned by DHCP server."
 ::= { fgs2924rIP 6 }

fgs2924rDnsServer OBJECT-TYPE
 SYNTAX      IpAddress
 MAX-ACCESS     read-write
 STATUS  current
 DESCRIPTION
  "Get/Set the DNS server of the system."
 ::= { fgs2924rIP 7 }

fgs2924rTime            OBJECT IDENTIFIER ::= { fgs2924rSystem 3 }

fgs2924rSystemCurrentTime OBJECT-TYPE
 SYNTAX      DisplayString
 MAX-ACCESS     read-only
 STATUS  current
 DESCRIPTION
  "Get the current time of the system."
 ::= { fgs2924rTime 1 }

fgs2924rManualTimeSetting OBJECT-TYPE
 SYNTAX      DisplayString
 MAX-ACCESS     read-write
 STATUS  current
 DESCRIPTION
  "Get/Set the system time of the device.
        The input format is 'Year/Month/Day/Hour/Minute/Second'.
        ex: 2004/1/1/12/34/25  means 2004/1/1 - 12:24:25 .
        The value range:
        Year    : 2000 - 2036,
        Mouth   : 1 - 12,
        Day     : 1 - 31,
        Hour    : 0 - 23,
        Minute  : 0 - 59,
        Sec     : 0 - 59."
 ::= { fgs2924rTime 2 }

fgs2924rNTPServer OBJECT-TYPE
 SYNTAX      DisplayString
 MAX-ACCESS     read-write
 STATUS  current
 DESCRIPTION
  "Get/Set the NTP Time Server. You can use the IP address or domain name."
 ::= { fgs2924rTime 3 }

fgs2924rNTPTimeZone OBJECT-TYPE
 SYNTAX      INTEGER(-12..13)
 MAX-ACCESS     read-write
 STATUS  current
 DESCRIPTION
  "Get/Set the NTP Time Zone.
  The value range is between -12 and 13
  -12 - GMT -12:00,
  -11 - GMT -11:00,
  -10 - GMT -10:00,
   -9 - GMT -09:00,
   -8 - GMT -08:00,
   -7 - GMT -07:00,
   -6 - GMT -06:00,
   -5 - GMT -05:00,
   -4 - GMT -04:00,
   -3 - GMT -03:00,
   -2 - GMT -02:00,
   -1 - GMT -01:00,
    0 - GMT +00:00,
    1 - GMT +01:00,
    2 - GMT +02:00,
    3 - GMT +03:00,
    4 - GMT +04:00,
    5 - GMT +05:00,
    6 - GMT +06:00,
    7 - GMT +07:00,
    8 - GMT +08:00,
    9 - GMT +09:00,
   10 - GMT +10:00,
   11 - GMT +11:00,
   12 - GMT +12:00,
   13 - GMT +13:00. "
 ::= { fgs2924rTime 4 }

fgs2924rNTPTimeSync OBJECT-TYPE
 SYNTAX      INTEGER(0|1)
 MAX-ACCESS     read-write
 STATUS  current
 DESCRIPTION
  "Sync time from NTP Server. Get this OID always return zero.
  Set the Time Server and Time Zone before doing time sync.
  Notice that time server must be correct!
  The value range (0|1):
  1 - sync.
        0 - do nothing."
 ::= { fgs2924rTime 5 }

fgs2924rDaylightSavingTime OBJECT-TYPE
 SYNTAX      INTEGER(-5..5)
 MAX-ACCESS     read-write
 STATUS  current
 DESCRIPTION
  "Get/Set the daylight saving time.
  The value range is between -5 and 5. (Unit: hour)"
 ::= { fgs2924rTime 6 }

fgs2924rDaylightStartTime OBJECT-TYPE
 SYNTAX      DisplayString
 MAX-ACCESS     read-write
 STATUS  current
 DESCRIPTION
  "Get/Set the Start time of Daylight Saving.
  The input format is 'MM/DD/HH',
  and daylight saving start month can't equal end month.
  example: month/day/hour   10/01/00
  month: 01~12, day: 01~31, hour: 00~23 ."
 ::= { fgs2924rTime 7 }

fgs2924rDaylightEndTime OBJECT-TYPE
 SYNTAX      DisplayString
 MAX-ACCESS     read-write
 STATUS  current
 DESCRIPTION
  "Get/Set the End time of Daylight Saving.
  The input format is 'MM/DD/HH',
  and daylight saving start month can't equal end month.
  example: month/day/hour   04/01/00
  month: 01~12, day: 01~31, hour: 00~23 ."
 ::= { fgs2924rTime 8 }


fgs2924rAccount            OBJECT IDENTIFIER ::= { fgs2924rSystem 4 }

fgs2924rAccountNumber OBJECT-TYPE
 SYNTAX      INTEGER(1..5)
 MAX-ACCESS     read-only
 STATUS  current
 DESCRIPTION
  "Get the current account number(s) of the system."
 ::= { fgs2924rAccount 1 }

fgs2924rAccountTable OBJECT-TYPE
 SYNTAX  SEQUENCE OF FGS2924RAccountEntry
 MAX-ACCESS not-accessible
 STATUS  current
 DESCRIPTION
  "This is a list of FGS2924RAccountEntry. The numbers of entries are given by
  the value of fgs2924rAccountNumber."
 ::= { fgs2924rAccount 2 }

FGS2924RAccountEntry ::=
SEQUENCE {
    fgs2924rAccountIndex      INTEGER,
    fgs2924rAccountAuthorization DisplayString,
    fgs2924rAccountName             DisplayString,
    fgs2924rAccountPassword         DisplayString
}

fgs2924rAccountEntry OBJECT-TYPE
 SYNTAX  FGS2924RAccountEntry
 MAX-ACCESS     not-accessible
 STATUS  current
 DESCRIPTION
  "This is the Entry(s) for account information."
 INDEX {fgs2924rAccountIndex}
 ::= { fgs2924rAccountTable 1 }

fgs2924rAccountIndex OBJECT-TYPE
 SYNTAX  INTEGER(1..5)
 MAX-ACCESS     read-only
 STATUS  current
 DESCRIPTION
  "This is the index of the account entry."
 ::= { fgs2924rAccountEntry 1 }

fgs2924rAccountAuthorization OBJECT-TYPE
 SYNTAX  DisplayString
 MAX-ACCESS     read-only
 STATUS  current
 DESCRIPTION
  "This is the authorization of the account entry."
 ::= { fgs2924rAccountEntry 2 }

fgs2924rAccountName OBJECT-TYPE
 SYNTAX  DisplayString
 MAX-ACCESS     read-write
 STATUS  current
 DESCRIPTION
  "This is the username of the account entry."
 ::= { fgs2924rAccountEntry 3 }

fgs2924rAccountPassword OBJECT-TYPE
 SYNTAX  DisplayString
 MAX-ACCESS     read-write
 STATUS  current
 DESCRIPTION
  "This is the password of the account entry. The return value is always '********'."
 ::= { fgs2924rAccountEntry 4 }

fgs2924rAccountAddAuthorization OBJECT-TYPE
 SYNTAX      INTEGER(0..2)
 MAX-ACCESS     read-write
 STATUS  current
 DESCRIPTION
  "Specify the limits of authority when add an account. 0:guest, 1:operator."
 ::= { fgs2924rAccount 3 }

fgs2924rAccountAddName OBJECT-TYPE
 SYNTAX      DisplayString
 MAX-ACCESS     read-write
 STATUS  current
 DESCRIPTION
  "This is the account name for adding operation."
 ::= { fgs2924rAccount 4 }

fgs2924rAccountAddPassword OBJECT-TYPE
 SYNTAX      DisplayString
 MAX-ACCESS     read-write
 STATUS  current
 DESCRIPTION
  "This is the account password for adding operation. The return value is always '********'."
 ::= { fgs2924rAccount 5 }

fgs2924rDoAccountAdd OBJECT-TYPE
 SYNTAX      INTEGER(0|1)
 MAX-ACCESS     read-write
 STATUS  current
 DESCRIPTION
  "Add account name. OID fgs2924rAccountAddName and fgs2924rAccountAddPassword must be
        filled first. Get this OID always return zero.
            1 - add account.
            0 - do nothing."
 ::= { fgs2924rAccount 6 }

fgs2924rAccountDel OBJECT-TYPE
 SYNTAX  INTEGER(2..5)
 MAX-ACCESS     read-write
 STATUS  current
 DESCRIPTION
  "Delete account. The value is valid fgs2924rAccountIndex(Can't delete administrator)."
 ::= { fgs2924rAccount 7 }

fgs2924rVsm            OBJECT IDENTIFIER ::= { fgs2924rSystem 5 }

fgs2924rVsmState OBJECT-TYPE
 SYNTAX  INTEGER(0|1)
 MAX-ACCESS     read-write
 STATUS  current
 DESCRIPTION
  "VSM state.
   0 - Disable
   1 - Enable"
 ::= { fgs2924rVsm 1 }

fgs2924rVsmRole OBJECT-TYPE
 SYNTAX  INTEGER(0|1)
 MAX-ACCESS     read-write
 STATUS  current
 DESCRIPTION
  "VSM Role.
   0 - Slave
   1 - Master"
 ::= { fgs2924rVsm 2 }

fgs2924rVsmGroupid OBJECT-TYPE
 SYNTAX      DisplayString
 MAX-ACCESS     read-write
 STATUS  current
 DESCRIPTION
  "VSM Group ID."
 ::= { fgs2924rVsm 3 }



fgs2924rSnmp            OBJECT IDENTIFIER ::= { fgs2924rProduces 2 }

fgs2924rGetCommunity OBJECT-TYPE
 SYNTAX      DisplayString
 MAX-ACCESS     read-write
 STATUS  current
 DESCRIPTION
  "Get/Set the get-community of the SNMP."
 ::= { fgs2924rSnmp 1 }

fgs2924rSetCommunity OBJECT-TYPE
 SYNTAX      DisplayString
 MAX-ACCESS     read-write
 STATUS  current
 DESCRIPTION
  "Get/Set the set-community of the SNMP."
 ::= { fgs2924rSnmp 2 }

fgs2924rTrapHostNumber OBJECT-TYPE
 SYNTAX      INTEGER(1..6)
 MAX-ACCESS     read-only
 STATUS  current
 DESCRIPTION
  "Get the number of trap hosts."
 ::= { fgs2924rSnmp 3 }

fgs2924rTrapHostTable OBJECT-TYPE
 SYNTAX  SEQUENCE OF FGS2924RTrapHostEntry
 MAX-ACCESS not-accessible
 STATUS  current
 DESCRIPTION
  "A list of trap host entry. The numbers of entries are given by the value of fgs2924rTrapHostNumber."
    ::= { fgs2924rSnmp 4 }

FGS2924RTrapHostEntry ::=
SEQUENCE {
    fgs2924rTrapHostIndex      INTEGER,
    fgs2924rTrapHostIP           IpAddress,
    fgs2924rTrapHostPort            INTEGER,
    fgs2924rTrapHostCommunity       DisplayString
}

fgs2924rTrapHostEntry OBJECT-TYPE
 SYNTAX  FGS2924RTrapHostEntry
 MAX-ACCESS     not-accessible
 STATUS  current
 DESCRIPTION
  "This is the entry information for trap host."
 INDEX {fgs2924rTrapHostIndex}
 ::= { fgs2924rTrapHostTable 1 }

fgs2924rTrapHostIndex OBJECT-TYPE
 SYNTAX  INTEGER(1..6)
 MAX-ACCESS     read-only
 STATUS  current
 DESCRIPTION
  "The index of the trap host entry."
 ::= { fgs2924rTrapHostEntry 1 }

fgs2924rTrapHostIP OBJECT-TYPE
 SYNTAX  IpAddress
 MAX-ACCESS     read-write
 STATUS  current
 DESCRIPTION
  "This is the IP of the trap host."
 ::= { fgs2924rTrapHostEntry 2 }


fgs2924rTrapHostPort OBJECT-TYPE
 SYNTAX  INTEGER(1..65535)
 MAX-ACCESS     read-write
 STATUS  current
 DESCRIPTION
  "This is the receiving-port number of the trap host."
 ::= { fgs2924rTrapHostEntry 3 }


fgs2924rTrapHostCommunity OBJECT-TYPE
 SYNTAX  DisplayString
 MAX-ACCESS     read-write
 STATUS  current
 DESCRIPTION
  "The community name for the trap PDU."
 ::= { fgs2924rTrapHostEntry 4 }



fgs2924rAlarm            OBJECT IDENTIFIER ::= { fgs2924rProduces 3 }

fgs2924rEvent            OBJECT IDENTIFIER ::= { fgs2924rAlarm 1 }

fgs2924rEventNumber OBJECT-TYPE
 SYNTAX      INTEGER(1..2147483647)
 MAX-ACCESS     read-only
 STATUS  current
 DESCRIPTION
  "Get the total number of alarm events."
 ::= { fgs2924rEvent 1 }

fgs2924rEventTable OBJECT-TYPE
 SYNTAX  SEQUENCE OF FGS2924REventEntry
 MAX-ACCESS not-accessible
 STATUS  current
    DESCRIPTION
        "This is a list of alarm event entry. The numbers of entries are given by the value of fgs2924rEventNumber."
 ::= { fgs2924rEvent 2 }

FGS2924REventEntry ::=
SEQUENCE {
    fgs2924rEventIndex      INTEGER,
    fgs2924rEventName           DisplayString,
    fgs2924rEventSendEmail      INTEGER,
    fgs2924rEventSendTrap       INTEGER
}

fgs2924rEventEntry OBJECT-TYPE
 SYNTAX  FGS2924REventEntry
 MAX-ACCESS     not-accessible
 STATUS  current
 DESCRIPTION
  "This is the entry information for alarm event."
 INDEX {fgs2924rEventIndex}
 ::= { fgs2924rEventTable 1 }

fgs2924rEventIndex OBJECT-TYPE
 SYNTAX  INTEGER(1..2147483647)
 MAX-ACCESS     read-only
 STATUS  current
 DESCRIPTION
  "This is the index of the alarm event entry."
 ::= { fgs2924rEventEntry 1 }

fgs2924rEventName OBJECT-TYPE
 SYNTAX  DisplayString
 MAX-ACCESS     read-only
 STATUS  current
 DESCRIPTION
  "This is the alarm event name."
 ::= { fgs2924rEventEntry 2 }

fgs2924rEventSendEmail OBJECT-TYPE
 SYNTAX  INTEGER(0|1)
 MAX-ACCESS     read-write
 STATUS  current
 DESCRIPTION
  "Send email when alarm event is triggered."
 ::= { fgs2924rEventEntry 3 }

fgs2924rEventSendTrap OBJECT-TYPE
 SYNTAX  INTEGER(0|1)
 MAX-ACCESS     read-write
 STATUS  current
 DESCRIPTION
  "Send trap when alarm event is triggered."
 ::= { fgs2924rEventEntry 4 }




fgs2924rEmail            OBJECT IDENTIFIER ::= { fgs2924rAlarm 2 }

fgs2924rEmailServer OBJECT-TYPE
 SYNTAX      DisplayString
 MAX-ACCESS     read-write
 STATUS  current
 DESCRIPTION
  "This is the SMTP server for alarm event."
 ::= { fgs2924rEmail 1 }

fgs2924rEmailUsername OBJECT-TYPE
 SYNTAX      DisplayString
 MAX-ACCESS     read-write
 STATUS  current
 DESCRIPTION
  "This is the Username of SMTP server."
 ::= { fgs2924rEmail 2 }

fgs2924rEmailPassword OBJECT-TYPE
 SYNTAX      DisplayString
 MAX-ACCESS     read-write
 STATUS  current
 DESCRIPTION
  "This is the User Password of SMTP server."
 ::= { fgs2924rEmail 3 }

fgs2924rEmailSender OBJECT-TYPE
 SYNTAX      DisplayString
 MAX-ACCESS     read-write
 STATUS  current
 DESCRIPTION
  "This is the Sender of SMTP server."
 ::= { fgs2924rEmail 4 }

fgs2924rEmailReturnPath OBJECT-TYPE
 SYNTAX      DisplayString
 MAX-ACCESS     read-write
 STATUS  current
 DESCRIPTION
  "This is the return path of mail."
-- @@ACTION ruby_alarm_email
 ::= { fgs2924rEmail 5 }

fgs2924rEmailUserNumber OBJECT-TYPE
 SYNTAX      INTEGER(1..6)
 MAX-ACCESS     read-only
 STATUS  current
 DESCRIPTION
  "The number of the email users that you want to send the alarm notification."
 ::= { fgs2924rEmail 6 }

fgs2924rEmailUserTable OBJECT-TYPE
 SYNTAX  SEQUENCE OF FGS2924REmailUserEntry
 MAX-ACCESS not-accessible
 STATUS  current
    DESCRIPTION
        "This is a list of email user entry. The numbers of entries are given by the value of fgs2924rEmailUserNumber."
 ::= { fgs2924rEmail 7 }

FGS2924REmailUserEntry ::=
SEQUENCE {
    fgs2924rEmailUserIndex      INTEGER,
    fgs2924rEmailUserAddress        DisplayString
}

fgs2924rEmailUserEntry OBJECT-TYPE
 SYNTAX  FGS2924REmailUserEntry
 MAX-ACCESS     not-accessible
 STATUS  current
 DESCRIPTION
  "This is the Entry information for email user entry."
 INDEX {fgs2924rEmailUserIndex}
 ::= { fgs2924rEmailUserTable 1 }

fgs2924rEmailUserIndex OBJECT-TYPE
 SYNTAX  INTEGER(1..6)
 MAX-ACCESS     read-only
 STATUS  current
 DESCRIPTION
  "This is the index of the email user entry."
 ::= { fgs2924rEmailUserEntry 1 }

fgs2924rEmailUserAddress OBJECT-TYPE
 SYNTAX  DisplayString
 MAX-ACCESS     read-write
 STATUS  current
 DESCRIPTION
  "This is the email address of the email user entry."
 ::= { fgs2924rEmailUserEntry 2 }

fgs2924rConfiguration            OBJECT IDENTIFIER ::= { fgs2924rProduces 5 }

fgs2924rSaveRestore            OBJECT IDENTIFIER ::= { fgs2924rConfiguration 1 }

fgs2924rSaveStart OBJECT-TYPE
 SYNTAX      INTEGER(0|1)
 MAX-ACCESS     read-write
 STATUS  current
 DESCRIPTION
  "Save current configuration into flash memory (Save as Start Configuration).
        Get this OID always return zero.
            1 - save.
            0 - do nothing. "
 ::= { fgs2924rSaveRestore 1 }

fgs2924rSaveUser OBJECT-TYPE
 SYNTAX      INTEGER(0|1)
 MAX-ACCESS     read-write
 STATUS  current
 DESCRIPTION
  "Save current configuration into flash memory (Save as User Configuration).
        Get this OID always return zero.
            1 - save.
            0 - do nothing. "
 ::= { fgs2924rSaveRestore 2 }

fgs2924rRestoreDefault OBJECT-TYPE
 SYNTAX      INTEGER(0|1|2)
 MAX-ACCESS     read-write
 STATUS  current
 DESCRIPTION
  "Restore factory default configuration.
        Get this OID always return zero.
            2 - restore default included default ip address.
            1 - restore default without changing current ip address.
            0 - do nothing. "
 ::= { fgs2924rSaveRestore 3 }

fgs2924rRestoreUser OBJECT-TYPE
 SYNTAX      INTEGER(0|1)
 MAX-ACCESS     read-write
 STATUS  current
 DESCRIPTION
  "Restore user configuration.
        Get this OID always return zero.
            1 - restore.
            0 - do nothing. "
 ::= { fgs2924rSaveRestore 4 }




fgs2924rConfigFile            OBJECT IDENTIFIER ::= { fgs2924rConfiguration 2 }

fgs2924rExportIpAddress OBJECT-TYPE
 SYNTAX      IpAddress
 MAX-ACCESS     read-write
 STATUS  current
 DESCRIPTION
  "Get/Set the export tftp server."
 ::= { fgs2924rConfigFile 1 }

fgs2924rDoExportConfig OBJECT-TYPE
 SYNTAX      INTEGER(1|2)
 MAX-ACCESS     read-write
 STATUS  current
 DESCRIPTION
  "Do export-config.
        Get this OID always return zero.
   1 - export current section.
   2 - export user section."
 ::= { fgs2924rConfigFile 2 }

fgs2924rImportIpAddress OBJECT-TYPE
 SYNTAX      IpAddress
 MAX-ACCESS     read-write
 STATUS  current
 DESCRIPTION
  "Get/Set the import tftp server."
 ::= { fgs2924rConfigFile 3 }

fgs2924rImportConfigName OBJECT-TYPE
 SYNTAX      DisplayString
 MAX-ACCESS     read-write
 STATUS  current
 DESCRIPTION
        "Get/Set the import file path and name."
 ::= { fgs2924rConfigFile 4 }

fgs2924rDoImportConfig OBJECT-TYPE
 SYNTAX      INTEGER(1|2)
 MAX-ACCESS     read-write
 STATUS  current
 DESCRIPTION
  "Do import-config.
        Get this OID always return zero.
   1 - import current section.
   2 - import user section."
 ::= { fgs2924rConfigFile 5 }




fgs2924rLog            OBJECT IDENTIFIER ::= { fgs2924rProduces 7 }

fgs2924rClearLog OBJECT-TYPE
 SYNTAX      INTEGER(0|1)
 MAX-ACCESS     read-write
 STATUS  current
 DESCRIPTION
  "Clear system log.
        Get this OID always return zero.
            1 - clear log.
            0 - do nothing. "
 ::= { fgs2924rLog 1 }


fgs2924rLogNumber OBJECT-TYPE
 SYNTAX      INTEGER(0..120)
 MAX-ACCESS     read-only
 STATUS  current
 DESCRIPTION
  "Get the number of current system log. "
 ::= { fgs2924rLog 4 }

fgs2924rLogTable OBJECT-TYPE
 SYNTAX  SEQUENCE OF FGS2924RLogEntry
 MAX-ACCESS not-accessible
 STATUS  current
    DESCRIPTION
        "This is a list of log entry. The numbers of entries are given by the value of fgs2924rLogNumber."
 ::= { fgs2924rLog 5 }

FGS2924RLogEntry ::=
SEQUENCE {
    fgs2924rLogIndex      INTEGER,
    fgs2924rLogEvent            DisplayString
}

fgs2924rLogEntry OBJECT-TYPE
 SYNTAX  FGS2924RLogEntry
 MAX-ACCESS     not-accessible
 STATUS  current
 DESCRIPTION
  "This is the Entry information for system log."
 INDEX {fgs2924rLogIndex}
 ::= { fgs2924rLogTable 1 }

fgs2924rLogIndex OBJECT-TYPE
 SYNTAX  INTEGER(1..120)
 MAX-ACCESS     not-accessible
 STATUS  current
 DESCRIPTION
  "This is the index of the log entry."
 ::= { fgs2924rLogEntry 1 }

fgs2924rLogEvent OBJECT-TYPE
 SYNTAX  DisplayString
 MAX-ACCESS     read-only
 STATUS  current
 DESCRIPTION
  "This is the detail information of the log entry."
 ::= { fgs2924rLogEntry 2 }



fgs2924rFirmware            OBJECT IDENTIFIER ::= { fgs2924rProduces 8 }

fgs2924rFirmwareIpAddress OBJECT-TYPE
 SYNTAX      IpAddress
 MAX-ACCESS     read-write
 STATUS  current
 DESCRIPTION
  "Get/Set the firmware tftp server."
 ::= { fgs2924rFirmware 1 }

fgs2924rFirmwareFileName OBJECT-TYPE
 SYNTAX      DisplayString
 MAX-ACCESS     read-write
 STATUS  current
 DESCRIPTION
  "Get/Set the path and filename for firmware upgrading."
 ::= { fgs2924rFirmware 2 }

fgs2924rDoFirmwareUpgrade OBJECT-TYPE
 SYNTAX      INTEGER(0|1)
 MAX-ACCESS     read-write
 STATUS  current
 DESCRIPTION
  "Do firmware upgrade. Get this OID always return zero.
            1 - do firmware upgrade.
            0 - do nothing."
 ::= { fgs2924rFirmware 3 }



fgs2924rPort            OBJECT IDENTIFIER ::= { fgs2924rProduces 9 }

fgs2924rPortStatus            OBJECT IDENTIFIER ::= { fgs2924rPort 1 }

fgs2924rPortStatusNumber OBJECT-TYPE
 SYNTAX      INTEGER(1..2147483647)
 MAX-ACCESS     read-only
 STATUS  current
 DESCRIPTION
  "Get the number of port."
 ::= { fgs2924rPortStatus 1 }

fgs2924rPortStatusTable OBJECT-TYPE
 SYNTAX  SEQUENCE OF FGS2924RPortStatusEntry
 MAX-ACCESS not-accessible
 STATUS  current
    DESCRIPTION
        "This is a list of port status entry. The numbers of entries are given by the value of fgs2924rPortStatusNumber."
 ::= { fgs2924rPortStatus 2 }

FGS2924RPortStatusEntry ::=
SEQUENCE {
    fgs2924rPortStatusIndex     INTEGER,
    fgs2924rPortStatusMedia          DisplayString,
    fgs2924rPortStatusPortState      DisplayString,
    fgs2924rPortStatusLink           DisplayString,
    fgs2924rPortStatusAutoNego       DisplayString,
    fgs2924rPortStatusSpdDpx         DisplayString,
    fgs2924rPortStatusFlwCtrlRx      DisplayString,
    fgs2924rPortStatusFlwCtrlTx      DisplayString,
    fgs2924rPortStatuDescription     DisplayString
}

fgs2924rPortStatusEntry OBJECT-TYPE
 SYNTAX  FGS2924RPortStatusEntry
 MAX-ACCESS     not-accessible
 STATUS  current
 DESCRIPTION
  "This is the entry(s) for port status information."
 INDEX {fgs2924rPortStatusIndex}
 ::= { fgs2924rPortStatusTable 1 }

fgs2924rPortStatusIndex OBJECT-TYPE
 SYNTAX  INTEGER(1..2147483647)
 MAX-ACCESS     read-only
 STATUS  current
 DESCRIPTION
  "This is the index of the port status entry."
 ::= { fgs2924rPortStatusEntry 1 }

fgs2924rPortStatusMedia OBJECT-TYPE
 SYNTAX  DisplayString
 MAX-ACCESS     read-only
 STATUS  current
 DESCRIPTION
  "The port media type of the port status entry."
 ::= { fgs2924rPortStatusEntry 2 }

fgs2924rPortStatusPortState        OBJECT-TYPE
        SYNTAX                DisplayString
        MAX-ACCESS            read-only
        STATUS                current
        DESCRIPTION
                "This is the port state of the port status entry."
        ::= { fgs2924rPortStatusEntry 3 }

fgs2924rPortStatusLink OBJECT-TYPE
 SYNTAX  DisplayString
 MAX-ACCESS     read-only
 STATUS  current
 DESCRIPTION
  "This is the port link of the port status entry."
 ::= { fgs2924rPortStatusEntry 4 }

fgs2924rPortStatusAutoNego        OBJECT-TYPE
        SYNTAX                DisplayString
        MAX-ACCESS            read-only
        STATUS                current
        DESCRIPTION
                "This is the auto negotiation of the port status entry."
        ::= { fgs2924rPortStatusEntry 5 }

fgs2924rPortStatusSpdDpx  OBJECT-TYPE
 SYNTAX  DisplayString
 MAX-ACCESS     read-only
 STATUS  current
 DESCRIPTION
  "This is the speed/duplex of the port status entry."
 ::= { fgs2924rPortStatusEntry 6 }

fgs2924rPortStatusFlwCtrlRx  OBJECT-TYPE
 SYNTAX  DisplayString
 MAX-ACCESS     read-only
 STATUS  current
 DESCRIPTION
  "This is the Rx flow control of the port status entry."
 ::= { fgs2924rPortStatusEntry 7 }

fgs2924rPortStatusFlwCtrlTx  OBJECT-TYPE
 SYNTAX  DisplayString
 MAX-ACCESS     read-only
 STATUS  current
 DESCRIPTION
  "This is the Tx flow control of the port status entry."
 ::= { fgs2924rPortStatusEntry 8 }

fgs2924rPortStatuDescription OBJECT-TYPE
 SYNTAX  DisplayString
 MAX-ACCESS     read-only
 STATUS  current
 DESCRIPTION
  "This is the description of port."
 ::= { fgs2924rPortStatusEntry 9 }

fgs2924rPortConf            OBJECT IDENTIFIER ::= { fgs2924rPort 2 }

fgs2924rPortConfNumber OBJECT-TYPE
 SYNTAX      INTEGER(1..2147483647)
 MAX-ACCESS     read-only
 STATUS  current
 DESCRIPTION
  "Get the number of port configuration."
 ::= { fgs2924rPortConf 1 }

fgs2924rPortConfTable OBJECT-TYPE
 SYNTAX  SEQUENCE OF FGS2924RPortConfEntry
 MAX-ACCESS not-accessible
 STATUS  current
    DESCRIPTION
        "This is a list of port configuration entry. The numbers of entries are given by the value of fgs2924rPortConfNumber."
 ::= { fgs2924rPortConf 2 }

FGS2924RPortConfEntry ::=
SEQUENCE {
    fgs2924rPortConfIndex      INTEGER,
    fgs2924rPortConfPortState        INTEGER,
    fgs2924rPortConfTPSpdDpx         INTEGER,
    fgs2924rPortConfSFPSpdDpx        INTEGER,
    fgs2924rPortConfFlwCtrl          INTEGER,
    fgs2924rPortConfExcessiveCollisionMode      INTEGER,
    fgs2924rPortConfDescription      DisplayString,
    fgs2924rPortConfPowerSaving      INTEGER
}

fgs2924rPortConfEntry OBJECT-TYPE
 SYNTAX  FGS2924RPortConfEntry
 MAX-ACCESS     not-accessible
 STATUS  current
 DESCRIPTION
  "This is the Entry(s) for port configuration information."
 INDEX {fgs2924rPortConfIndex}
 ::= { fgs2924rPortConfTable 1 }

fgs2924rPortConfIndex OBJECT-TYPE
 SYNTAX  INTEGER(1..2147483647)
 MAX-ACCESS     read-only
 STATUS  current
 DESCRIPTION
  "This is the index of the port configuration entry."
 ::= { fgs2924rPortConfEntry 1 }

fgs2924rPortConfPortState OBJECT-TYPE
 SYNTAX  INTEGER(0|1)
 MAX-ACCESS     read-write
 STATUS  current
 DESCRIPTION
  "This is the port state of the port configuration entry.
   0 - disabled.
   1 - enabled. "
 ::= { fgs2924rPortConfEntry 2 }

fgs2924rPortConfTPSpdDpx OBJECT-TYPE
 SYNTAX  INTEGER(0..5)
 MAX-ACCESS     read-write
 STATUS  current
 DESCRIPTION
  "This is the speed/duplex of the TP port configuration entry.
   0 - auto.
   1 - 10M/Half.
   2 - 10M/Full.
   3 - 100M/Half.
   4 - 100M/Full.
   5 - 1G/Full.
   -1 - no support."
 ::= { fgs2924rPortConfEntry 3 }

fgs2924rPortConfSFPSpdDpx OBJECT-TYPE
 SYNTAX  INTEGER(0|5)
 MAX-ACCESS     read-write
 STATUS  current
 DESCRIPTION
  "This is the speed/duplex of the SFP port configuration entry.
   0 - auto.
   5 - 1G/Full.
   -1 - no support."
 ::= { fgs2924rPortConfEntry 4 }

fgs2924rPortConfFlwCtrl OBJECT-TYPE
 SYNTAX  INTEGER(0|1)
 MAX-ACCESS     read-write
 STATUS  current
 DESCRIPTION
  "This is the flow control of the port configuration entry.
   0 - disabled.
   1 - symmetric.
         2 - asymmetric(Tx).
         3 - symmetric & asymmetric(Rx)."
 ::= { fgs2924rPortConfEntry 5 }

fgs2924rPortConfExcessiveCollisionMode OBJECT-TYPE
 SYNTAX  INTEGER(0|1)
 MAX-ACCESS     read-write
 STATUS  current
 DESCRIPTION
  "Set excessive collision mode.
   0 - Discard.
   1 - Restart.  "
 ::= { fgs2924rPortConfEntry 6 }

fgs2924rPortConfDescription OBJECT-TYPE
 SYNTAX  DisplayString
 MAX-ACCESS     read-write
 STATUS  current
 DESCRIPTION
  "This is the description of port."
 ::= { fgs2924rPortConfEntry 7 }

fgs2924rPortConfPowerSaving OBJECT-TYPE
 SYNTAX  INTEGER(0|1)
 MAX-ACCESS     read-write
 STATUS  current
 DESCRIPTION
  "Set port power saving mode.
   0 - Disable.
   1 - Enable.
   Only 1~8 ports support power saving mode. -1 will be returned when access 9~24 ports."
 ::= { fgs2924rPortConfEntry 8 }

fgs2924rSFPInfo            OBJECT IDENTIFIER ::= { fgs2924rPort 3 }

fgs2924rSFPInfoNumber OBJECT-TYPE
 SYNTAX      INTEGER(1..2147483647)
 MAX-ACCESS     read-only
 STATUS  current
 DESCRIPTION
  "Get the number of sfp info entry."
 ::= { fgs2924rSFPInfo 1 }

fgs2924rSFPInfoTable OBJECT-TYPE
 SYNTAX  SEQUENCE OF FGS2924RSFPInfoEntry
 MAX-ACCESS not-accessible
 STATUS  current
    DESCRIPTION
        "A list of sfp info entry. The numbers of entries are given by the value of fgs2924rSFPInfoNumber."
 ::= { fgs2924rSFPInfo 2 }

FGS2924RSFPInfoEntry ::=
SEQUENCE {
    fgs2924rSFPInfoIndex INTEGER,
    fgs2924rSFPConnectorType DisplayString,
    fgs2924rSFPFiberType DisplayString,
    fgs2924rSFPWavelength DisplayString,
    fgs2924rSFPBaudRate DisplayString,
    fgs2924rSFPVendorOUI DisplayString,
    fgs2924rSFPVendorName DisplayString,
    fgs2924rSFPVendorPN DisplayString,
    fgs2924rSFPVendorRev DisplayString,
    fgs2924rSFPVendorSN DisplayString,
    fgs2924rSFPDateCode DisplayString,
    fgs2924rSFPTemperature DisplayString,
    fgs2924rSFPVcc DisplayString,
    fgs2924rSFPTxBias DisplayString,
    fgs2924rSFPTxPWR DisplayString,
    fgs2924rSFPRxPWR DisplayString
}

fgs2924rSFPInfoEntry OBJECT-TYPE
 SYNTAX  FGS2924RSFPInfoEntry
 MAX-ACCESS     not-accessible
 STATUS  current
 DESCRIPTION
  "Entry(s) for SFP information."
 INDEX {fgs2924rSFPInfoIndex}
 ::= { fgs2924rSFPInfoTable 1 }

fgs2924rSFPInfoIndex OBJECT-TYPE
 SYNTAX  INTEGER(1..2147483647)
 MAX-ACCESS     read-only
 STATUS  current
 DESCRIPTION
  "The index of the sfp info entry."
 ::= { fgs2924rSFPInfoEntry 1 }

fgs2924rSFPConnectorType OBJECT-TYPE
 SYNTAX  DisplayString
 MAX-ACCESS     read-only
 STATUS  current
 DESCRIPTION
  "Get connector type of the sfp."
 ::= { fgs2924rSFPInfoEntry 2 }

fgs2924rSFPFiberType OBJECT-TYPE
 SYNTAX  DisplayString
 MAX-ACCESS     read-only
 STATUS  current
 DESCRIPTION
  "Get fiber type of the sfp."
 ::= { fgs2924rSFPInfoEntry 3 }

fgs2924rSFPWavelength OBJECT-TYPE
 SYNTAX  DisplayString
 MAX-ACCESS     read-only
 STATUS  current
 DESCRIPTION
  "Get tx central wavelength of the sfp."
 ::= { fgs2924rSFPInfoEntry 4 }

fgs2924rSFPBaudRate OBJECT-TYPE
 SYNTAX  DisplayString
 MAX-ACCESS     read-only
 STATUS  current
 DESCRIPTION
  "Get baud rate of the sfp."
 ::= { fgs2924rSFPInfoEntry 5 }

fgs2924rSFPVendorOUI OBJECT-TYPE
 SYNTAX  DisplayString
 MAX-ACCESS     read-only
 STATUS  current
 DESCRIPTION
  "Get vendor OUI of the sfp."
 ::= { fgs2924rSFPInfoEntry 6 }

fgs2924rSFPVendorName OBJECT-TYPE
 SYNTAX  DisplayString
 MAX-ACCESS     read-only
 STATUS  current
 DESCRIPTION
  "Get vendor name of the sfp."
 ::= { fgs2924rSFPInfoEntry 7 }

fgs2924rSFPVendorPN OBJECT-TYPE
 SYNTAX  DisplayString
 MAX-ACCESS     read-only
 STATUS  current
 DESCRIPTION
  "Get vendor part number of the sfp."
 ::= { fgs2924rSFPInfoEntry 8 }

fgs2924rSFPVendorRev OBJECT-TYPE
 SYNTAX  DisplayString
 MAX-ACCESS     read-only
 STATUS  current
 DESCRIPTION
  "Get vendor revision number of the sfp."
 ::= { fgs2924rSFPInfoEntry 9 }

fgs2924rSFPVendorSN OBJECT-TYPE
 SYNTAX  DisplayString
 MAX-ACCESS     read-only
 STATUS  current
 DESCRIPTION
  "Get vendor serial number of the sfp."
 ::= { fgs2924rSFPInfoEntry 10 }

fgs2924rSFPDateCode OBJECT-TYPE
 SYNTAX  DisplayString
 MAX-ACCESS     read-only
 STATUS  current
 DESCRIPTION
  "Get data code of the sfp."
 ::= { fgs2924rSFPInfoEntry 11 }

fgs2924rSFPTemperature OBJECT-TYPE
 SYNTAX  DisplayString
 MAX-ACCESS     read-only
 STATUS  current
 DESCRIPTION
  "Get current temperature of the sfp."
 ::= { fgs2924rSFPInfoEntry 12 }

fgs2924rSFPVcc OBJECT-TYPE
 SYNTAX  DisplayString
 MAX-ACCESS     read-only
 STATUS  current
 DESCRIPTION
  "Get current internal supply voltage of the sfp."
 ::= { fgs2924rSFPInfoEntry 13 }

fgs2924rSFPTxBias OBJECT-TYPE
 SYNTAX  DisplayString
 MAX-ACCESS     read-only
 STATUS  current
 DESCRIPTION
  "Get current TX Bias of the sfp."
 ::= { fgs2924rSFPInfoEntry 14 }

fgs2924rSFPTxPWR OBJECT-TYPE
 SYNTAX  DisplayString
 MAX-ACCESS     read-only
 STATUS  current
 DESCRIPTION
  "Get current TX output power of the sfp."
 ::= { fgs2924rSFPInfoEntry 15 }

fgs2924rSFPRxPWR OBJECT-TYPE
 SYNTAX  DisplayString
 MAX-ACCESS     read-only
 STATUS  current
 DESCRIPTION
  "Get current Received Power of the sfp."
 ::= { fgs2924rSFPInfoEntry 16 }

fgs2924rMirror            OBJECT IDENTIFIER ::= { fgs2924rProduces 10 }

fgs2924rMirroringPort OBJECT-TYPE
 SYNTAX      INTEGER(0..2147483647)
 MAX-ACCESS     read-write
 STATUS  current
 DESCRIPTION
  "Get/Set the mirroring port.
   The port range is from 1 to 24."
 ::= { fgs2924rMirror 1 }

fgs2924rMirroredPortsTable OBJECT-TYPE
 SYNTAX  SEQUENCE OF FGS2924RMirroredPortsEntry
 MAX-ACCESS not-accessible
 STATUS  current
    DESCRIPTION
        "This is a list of port configuration entry. The numbers of entries are given by the value of fgs2924rPortConfNumber."
 ::= { fgs2924rMirror 2 }

FGS2924RMirroredPortsEntry ::=
SEQUENCE {
    fgs2924rMirroredPortIndex       INTEGER,
    fgs2924rMirroredPortSrouceEnable         INTEGER,
    fgs2924rMirroredPortDestinationEnable        INTEGER
}

fgs2924rMirroredPortsEntry OBJECT-TYPE
 SYNTAX  FGS2924RMirroredPortsEntry
 MAX-ACCESS     not-accessible
 STATUS  current
 DESCRIPTION
  "This is the Entry(s) for port configuration information."
 INDEX {fgs2924rMirroredPortIndex}
 ::= { fgs2924rMirroredPortsTable 1 }

fgs2924rMirroredPortIndex OBJECT-TYPE
 SYNTAX  INTEGER(1..24)
 MAX-ACCESS     read-only
 STATUS  current
 DESCRIPTION
  "This is the index of the mirrored port."
 ::= { fgs2924rMirroredPortsEntry 1 }

fgs2924rMirroredPortSrouceEnable OBJECT-TYPE
 SYNTAX  INTEGER(0|1)
 MAX-ACCESS     read-write
 STATUS  current
 DESCRIPTION
  "Set monitor source port.
   0 - disabled.
   1 - enabled."
 ::= { fgs2924rMirroredPortsEntry 2 }

fgs2924rMirroredPortDestinationEnable OBJECT-TYPE
 SYNTAX  INTEGER(0|1)
 MAX-ACCESS     read-write
 STATUS  current
 DESCRIPTION
  "Set monitor destination port.
   0 - disabled.
   1 - enabled."
 ::= { fgs2924rMirroredPortsEntry 3 }

fgs2924rMaxPktLen            OBJECT IDENTIFIER ::= { fgs2924rProduces 11 }

fgs2924rMaxPktLenPortNumber OBJECT-TYPE
 SYNTAX      INTEGER(1..24)
 MAX-ACCESS     read-only
 STATUS  current
 DESCRIPTION
  "Get the number of Max. packet length."
 ::= { fgs2924rMaxPktLen 1 }

fgs2924rMaxPktLenConfTable OBJECT-TYPE
 SYNTAX  SEQUENCE OF FGS2924RMaxPktLenConfEntry
 MAX-ACCESS not-accessible
 STATUS  current
    DESCRIPTION
        "This is a list of Max. packet length entry. The numbers of entries are given by the value of fgs2924rMaxPktLenPortNumber."
 ::= { fgs2924rMaxPktLen 2 }

FGS2924RMaxPktLenConfEntry ::=
SEQUENCE {
    fgs2924rMaxPktLenConfIndex      INTEGER,
    fgs2924rMaxPktLenConfSetting         INTEGER
}

fgs2924rMaxPktLenConfEntry OBJECT-TYPE
 SYNTAX  FGS2924RMaxPktLenConfEntry
 MAX-ACCESS     not-accessible
 STATUS  current
 DESCRIPTION
  "Entry(s) for Max. packet length information."
 INDEX {fgs2924rMaxPktLenConfIndex}
 ::= { fgs2924rMaxPktLenConfTable 1 }

fgs2924rMaxPktLenConfIndex OBJECT-TYPE
 SYNTAX  INTEGER(1..24)
 MAX-ACCESS     read-only
 STATUS  current
 DESCRIPTION
  "This is the index of the Max. packet length entry."
 ::= { fgs2924rMaxPktLenConfEntry 1 }

fgs2924rMaxPktLenConfSetting OBJECT-TYPE
 SYNTAX  INTEGER(1518..9600)
 MAX-ACCESS     read-write
 STATUS  current
 DESCRIPTION
  "Get/Set the Max. packet length.
   The Max. packet length is 1518~9600.  "
 ::= { fgs2924rMaxPktLenConfEntry 2 }

fgs2924rLoopDetectedConf            OBJECT IDENTIFIER ::= { fgs2924rProduces 12 }

fgs2924rLoopDetectedNumber OBJECT-TYPE
 SYNTAX      INTEGER(1..2147483647)
 MAX-ACCESS     read-only
 STATUS  current
 DESCRIPTION
  "Get the number of loop detected entry."
 ::= { fgs2924rLoopDetectedConf 1 }

fgs2924rLoopDetectedTable OBJECT-TYPE
 SYNTAX  SEQUENCE OF FGS2924RLoopDetectedEntry
 MAX-ACCESS not-accessible
 STATUS  current
    DESCRIPTION
        "A list of loop detected entry. The numbers of entries are given by the value of fgs2924rLoopDetectedNumber."
 ::= { fgs2924rLoopDetectedConf 2 }

FGS2924RLoopDetectedEntry ::=
SEQUENCE {
    fgs2924rLoopDetectedfIndex           INTEGER,
    fgs2924rLoopDetectedPort             INTEGER,
    fgs2924rLoopDetectedLockedPort       INTEGER
}

fgs2924rLoopDetectedEntry OBJECT-TYPE
 SYNTAX  FGS2924RLoopDetectedEntry
 MAX-ACCESS     not-accessible
 STATUS  current
 DESCRIPTION
  "Entry(s) for loop detected information."
 INDEX {fgs2924rLoopDetectedfIndex}
 ::= { fgs2924rLoopDetectedTable 1 }

fgs2924rLoopDetectedfIndex OBJECT-TYPE
 SYNTAX  INTEGER(1..2147483647)
 MAX-ACCESS     read-only
 STATUS  current
 DESCRIPTION
  "The index of the loop detected entry."
 ::= { fgs2924rLoopDetectedEntry 1 }

fgs2924rLoopDetectedPort OBJECT-TYPE
 SYNTAX  INTEGER(0|1)
 MAX-ACCESS     read-write
 STATUS  current
 DESCRIPTION
  "The state of the loop detected entry.
   0 - disabled.
   1 - enabled. "
 ::= { fgs2924rLoopDetectedEntry 2 }

fgs2924rLoopDetectedLockedPort OBJECT-TYPE
 SYNTAX  INTEGER(0|1)
 MAX-ACCESS     read-write
 STATUS  current
 DESCRIPTION
  "The current status of the loop detected port.
   Get:
         0 - unlocked
         1 - locked due to the loop condition
         Set:
         0 - unlock the port
         1 - do nothing"
 ::= { fgs2924rLoopDetectedEntry 3 }


fgs2924rManagementPolicy            OBJECT IDENTIFIER ::= { fgs2924rProduces 13 }

fgs2924rManagementSecurityNumber OBJECT-TYPE
 SYNTAX      INTEGER(0..64)
 MAX-ACCESS     read-only
 STATUS  current
 DESCRIPTION
  "This is the index of the management security entry."
 ::= { fgs2924rManagementPolicy 1 }

fgs2924rManagementSecurityEntryCreate OBJECT-TYPE
 SYNTAX      INTEGER(0..64)
 MAX-ACCESS     read-write
 STATUS  current
 DESCRIPTION
  "Create management security entry"
 ::= { fgs2924rManagementPolicy 2 }

fgs2924rManagementSecurityTable OBJECT-TYPE
 SYNTAX  SEQUENCE OF FGS2924RManagementSecurityEntry
 MAX-ACCESS not-accessible
 STATUS  current
    DESCRIPTION
        "This is a list of FGS2924RManagementSecurityEntry. The numbers of entries are given by ManagementSecurityNumber."
 ::= { fgs2924rManagementPolicy 3 }

FGS2924RManagementSecurityEntry ::=
SEQUENCE {
    fgs2924rManagementSecurityIndex         INTEGER,
    fgs2924rManagementSecurityName            DisplayString,
    fgs2924rManagementSecurityIpRange         DisplayString,
    fgs2924rManagementSecurityIncomigPort     DisplayString,
    fgs2924rManagementSecurityAccessType      DisplayString,
    fgs2924rManagementSecurityAction          INTEGER,
    fgs2924rManagementSecurityEntryAction     INTEGER
}

fgs2924rManagementSecurityEntry OBJECT-TYPE
 SYNTAX  FGS2924RManagementSecurityEntry
 MAX-ACCESS     not-accessible
 STATUS  current
 DESCRIPTION
  "This is the Entry(s) for Management Security configuration information."
 INDEX {fgs2924rManagementSecurityIndex}
 ::= { fgs2924rManagementSecurityTable 1 }

fgs2924rManagementSecurityIndex OBJECT-TYPE
 SYNTAX  INTEGER(1..64)
 MAX-ACCESS     read-only
 STATUS  current
 DESCRIPTION
  "This is the index of the management policy configuration entry."
 ::= { fgs2924rManagementSecurityEntry 1 }

fgs2924rManagementSecurityName OBJECT-TYPE
 SYNTAX  DisplayString
 MAX-ACCESS     read-write
 STATUS  current
 DESCRIPTION
  "This is the username of the management security entry."
 ::= { fgs2924rManagementSecurityEntry 2 }

fgs2924rManagementSecurityIpRange OBJECT-TYPE
 SYNTAX  DisplayString
 MAX-ACCESS     read-write
 STATUS  current
 DESCRIPTION
  "This is the ip range of the management security entry."
 ::= { fgs2924rManagementSecurityEntry 3 }

fgs2924rManagementSecurityIncomigPort OBJECT-TYPE
 SYNTAX  DisplayString
 MAX-ACCESS     read-write
 STATUS  current
 DESCRIPTION
  "This is the incoming port of the management security entry."
 ::= { fgs2924rManagementSecurityEntry 4 }

fgs2924rManagementSecurityAccessType OBJECT-TYPE
 SYNTAX  DisplayString
 MAX-ACCESS     read-write
 STATUS  current
 DESCRIPTION
  "Set management security access type.
   0 - any.
   1 - http.
   2 - telnet
   3 - snmp"
 ::= { fgs2924rManagementSecurityEntry 5 }

fgs2924rManagementSecurityAction OBJECT-TYPE
 SYNTAX  INTEGER(0|1)
 MAX-ACCESS     read-write
 STATUS  current
 DESCRIPTION
  "Set management security action.
   0 - deny.
   1 - accept."
 ::= { fgs2924rManagementSecurityEntry 6 }

fgs2924rManagementSecurityEntryAction OBJECT-TYPE
 SYNTAX  INTEGER(1..3)
 MAX-ACCESS     read-write
 STATUS  current
 DESCRIPTION
  "The row status of management security entry.
   1 - active.
   2 - notInService.
   3 - delete."
 ::= { fgs2924rManagementSecurityEntry 7 }



fgs2924rVLAN            OBJECT IDENTIFIER ::= { fgs2924rProduces 14 }

fgs2924rVlanConf            OBJECT IDENTIFIER ::= { fgs2924rVLAN 1 }

fgs2924rVlanMode OBJECT-TYPE
 SYNTAX      INTEGER(0|1)
 MAX-ACCESS     read-write
 STATUS  current
 DESCRIPTION
  "This is the VLAN Mode configuration, default is tag base.
   0 - tag-base
   1 - port-base"
 ::= { fgs2924rVlanConf 1 }

fgs2924rManagementVlan OBJECT-TYPE
 SYNTAX      INTEGER(1..4094)
 MAX-ACCESS     read-write
 STATUS  current
 DESCRIPTION
  "To specify a vlan id that can communicate with the device."
 ::= { fgs2924rVlanConf 2 }

fgs2924rPortIsolation OBJECT-TYPE
 SYNTAX      DisplayString
 MAX-ACCESS     read-write
 STATUS  current
 DESCRIPTION
  "Selected port(s) only can communicate with unselected port(s).
  Selected port(s) will be isolated with each other."
 ::= { fgs2924rVlanConf 3 }

fgs2924rTagIdentifier OBJECT-TYPE
 SYNTAX      INTEGER(0|1)
 MAX-ACCESS     read-write
 STATUS  current
 DESCRIPTION
  "Set double tag type.
  0: 0x8100
  1: 0x88a8"
 ::= { fgs2924rVlanConf 4 }

fgs2924rTagBaseVlanGroup         OBJECT IDENTIFIER ::= { fgs2924rVLAN 2 }

fgs2924rTagBaseVlanNumber OBJECT-TYPE
 SYNTAX      INTEGER(1..4094)
 MAX-ACCESS     read-write
 STATUS  current
 DESCRIPTION
  "The number of tagged-based VLAN."
 ::= { fgs2924rTagBaseVlanGroup 1 }

fgs2924rTagBaseVlanGroupEntryCreate OBJECT-TYPE
 SYNTAX      INTEGER(0..4094)
 MAX-ACCESS     read-write
 STATUS  current
 DESCRIPTION
  "To create a VLAN entry in the tagged-based VLAN table.
         0 : none,
         1~4094 : specify the vid of the created VLAN."
 ::= { fgs2924rTagBaseVlanGroup 2 }

fgs2924rTagBaseVlanGroupTable OBJECT-TYPE
 SYNTAX  SEQUENCE OF FGS2924RTagBaseVlanGroupEntry
 MAX-ACCESS not-accessible
 STATUS  current
    DESCRIPTION
        "A list of tagged-based VLAN group entry. The number of entries can be taken from fgs2924rTagBaseVlanNumber."
 ::= { fgs2924rTagBaseVlanGroup 3 }

FGS2924RTagBaseVlanGroupEntry ::=
SEQUENCE {
    fgs2924rTagBaseVlanVid          INTEGER,
    fgs2924rTagBaseVlanName          DisplayString,
    fgs2924rTagBaseVlanIgmpProxy     INTEGER,
    fgs2924rTagBaseVlanPrivateVlan   INTEGER,
    fgs2924rTagBaseVlanGvrp     INTEGER,
    fgs2924rTagBaseVlanMemberPort    DisplayString,
    fgs2924rTagBaseVlanEntryAction   INTEGER
}

fgs2924rTagBaseVlanGroupEntry OBJECT-TYPE
 SYNTAX  FGS2924RTagBaseVlanGroupEntry
 MAX-ACCESS     not-accessible
 STATUS  current
 DESCRIPTION
  "This is the Entry(s) for Tag Base VLAN Group configuration information."
 INDEX {fgs2924rTagBaseVlanVid}
 ::= { fgs2924rTagBaseVlanGroupTable 1 }

fgs2924rTagBaseVlanVid OBJECT-TYPE
 SYNTAX  INTEGER(1..4094)
 MAX-ACCESS     not-accessible
 STATUS  current
 DESCRIPTION
  "This is the index of the Tag Base VLAN Group configuration entry."
 ::= { fgs2924rTagBaseVlanGroupEntry 1 }

fgs2924rTagBaseVlanName OBJECT-TYPE
 SYNTAX  DisplayString
 MAX-ACCESS     read-write
 STATUS  current
 DESCRIPTION
  "This is the name of the VLAN."
 ::= { fgs2924rTagBaseVlanGroupEntry 2 }

fgs2924rTagBaseVlanIgmpProxy OBJECT-TYPE
 SYNTAX  INTEGER(0|1)
 MAX-ACCESS     read-write
 STATUS  current
 DESCRIPTION
  "To support IGMP proxy in this VLAN.
   0 - Disable
   1 - Enable"
 ::= { fgs2924rTagBaseVlanGroupEntry 3 }

fgs2924rTagBaseVlanPrivateVlan OBJECT-TYPE
 SYNTAX  INTEGER(0|1)
 MAX-ACCESS     read-write
 STATUS  current
 DESCRIPTION
  "To apply the port isolation configuration.
   0 - Disable
   1 - Enable"
 ::= { fgs2924rTagBaseVlanGroupEntry 4 }

fgs2924rTagBaseVlanGvrp OBJECT-TYPE
 SYNTAX  INTEGER(0|1)
 MAX-ACCESS     read-write
 STATUS  current
 DESCRIPTION
  "This VLAN can be propagated by gvrp.
   0 - Disable
   1 - Enable"
 ::= { fgs2924rTagBaseVlanGroupEntry 5 }

fgs2924rTagBaseVlanMemberPort OBJECT-TYPE
 SYNTAX  DisplayString
 MAX-ACCESS     read-write
 STATUS  current
 DESCRIPTION
  "The member port(s) of this VLAN."
 ::= { fgs2924rTagBaseVlanGroupEntry 6 }

fgs2924rTagBaseVlanEntryAction OBJECT-TYPE
 SYNTAX  INTEGER(1..3)
 MAX-ACCESS     read-write
 STATUS  current
 DESCRIPTION
  "The row status of VLAN.
   1 - active
   2 - notInService
   3 - delete"
 ::= { fgs2924rTagBaseVlanGroupEntry 7 }

fgs2924rVlanPortConfTable OBJECT-TYPE
 SYNTAX  SEQUENCE OF FGS2924RVlanPortConfEntry
 MAX-ACCESS not-accessible
 STATUS  current
    DESCRIPTION
        "This is the port parameters for tagged-based VLAN."
 ::= { fgs2924rVLAN 3 }

FGS2924RVlanPortConfEntry ::=
SEQUENCE {
    fgs2924rVlanPortConfIndex              INTEGER,
    fgs2924rVlanPortConfVlanAware            INTEGER,
    fgs2924rVlanPortConfIngressFiltering     INTEGER,
    fgs2924rVlanPortConfFrameType            INTEGER,
    fgs2924rVlanPortConfPvid                 INTEGER,
    fgs2924rVlanPortConfRole                 INTEGER,
    fgs2924rVlanPortConfUntagVid             INTEGER,
    fgs2924rVlanPortConfDoubleTag            INTEGER
}

fgs2924rVlanPortConfEntry OBJECT-TYPE
 SYNTAX  FGS2924RVlanPortConfEntry
 MAX-ACCESS     not-accessible
 STATUS  current
 DESCRIPTION
  "These are the tagged-based VLAN parameters for each ports."
 INDEX {fgs2924rVlanPortConfIndex}
 ::= { fgs2924rVlanPortConfTable 1 }

fgs2924rVlanPortConfIndex OBJECT-TYPE
 SYNTAX  INTEGER(1..24)
 MAX-ACCESS     not-accessible
 STATUS  current
 DESCRIPTION
  "This is the index of the Port Base VLAN Group configuration entry."
 ::= { fgs2924rVlanPortConfEntry 1 }

fgs2924rVlanPortConfVlanAware OBJECT-TYPE
 SYNTAX  INTEGER(0|1)
 MAX-ACCESS     read-write
 STATUS  current
 DESCRIPTION
  "Set vlan awareness.
   0 - Ignore incoming VLAN tag, using pvid as VLAN classification.
   1 - Using VLAN tag information first."
 ::= { fgs2924rVlanPortConfEntry 2 }

fgs2924rVlanPortConfIngressFiltering OBJECT-TYPE
 SYNTAX  INTEGER(0|1)
 MAX-ACCESS     read-write
 STATUS  current
 DESCRIPTION
  "If the packet is tagged with VLAN information, the ingress port will first determine if the
   ingress port itself is a member of the tagged VLAN.
   0 - Disable, don't care about the VLAN information of the packet.
   1 - Enable."
 ::= { fgs2924rVlanPortConfEntry 3 }

fgs2924rVlanPortConfFrameType OBJECT-TYPE
 SYNTAX  INTEGER(0|1)
 MAX-ACCESS     read-write
 STATUS  current
 DESCRIPTION
  "To determine what kind of packet the port should accept.
   0 - All
   1 - Only tagged packet"
 ::= { fgs2924rVlanPortConfEntry 4 }

fgs2924rVlanPortConfPvid OBJECT-TYPE
 SYNTAX  INTEGER(1..4094)
 MAX-ACCESS     read-write
 STATUS  current
 DESCRIPTION
  "Each physical port has a parameter called PVID.
  All untagged frames are assigned to the LAN specified in the PVID parameter.
  When a tagged frame is received by a port, the tag is respected.
  If the frame is untagged, the value contained in the PVID is considered as a tag. "
 ::= { fgs2924rVlanPortConfEntry 5 }

fgs2924rVlanPortConfRole OBJECT-TYPE
 SYNTAX  INTEGER(0..2)
 MAX-ACCESS     read-write
 STATUS  current
 DESCRIPTION
  "Set egress rule: configure the port role.
   0 - Access: won't send packet with tag.
   1 - Trunk: always send packet with tag.
   2 - Hybrid: always send packet with tag but one."
 ::= { fgs2924rVlanPortConfEntry 6 }

fgs2924rVlanPortConfUntagVid OBJECT-TYPE
 SYNTAX  INTEGER(1..4094)
 MAX-ACCESS     read-write
 STATUS  current
 DESCRIPTION
  "Won't send packet with tag in one specific vid. Only available in hybrid mode.
   "
 ::= { fgs2924rVlanPortConfEntry 7 }

fgs2924rVlanPortConfDoubleTag OBJECT-TYPE
 SYNTAX  INTEGER(0..2)
 MAX-ACCESS     read-write
 STATUS  current
 DESCRIPTION
  "This is the double tag configuration for ports.
   0 -- Disable,
    1 -- Service,
    2 -- Customer
   "
 ::= { fgs2924rVlanPortConfEntry 8 }

fgs2924rPortBaseVlanGroup         OBJECT IDENTIFIER ::= { fgs2924rVLAN 4 }

fgs2924rPortBaseVlanNumber OBJECT-TYPE
 SYNTAX      INTEGER(1..24)
 MAX-ACCESS     read-write
 STATUS  current
 DESCRIPTION
  "Total numbers for port based vlan."
 ::= { fgs2924rPortBaseVlanGroup 1 }

fgs2924rPortBaseVlanGroupEntryCreate OBJECT-TYPE
 SYNTAX      INTEGER(0..24)
 MAX-ACCESS     read-write
 STATUS  current
 DESCRIPTION
  "Create a temp vlan in port-based vlan table.
         0 : none,
         1 : create a new port-based vlan."
 ::= { fgs2924rPortBaseVlanGroup 2 }

fgs2924rPortBaseVlanGroupTable OBJECT-TYPE
 SYNTAX  SEQUENCE OF FGS2924RPortBaseVlanGroupEntry
 MAX-ACCESS not-accessible
 STATUS  current
    DESCRIPTION
        "A list of port base vlan group entry. The numbers of entries are given by the value of fgs2924rPortBaseVlanNumber."
 ::= { fgs2924rPortBaseVlanGroup 3 }

FGS2924RPortBaseVlanGroupEntry ::=
SEQUENCE {
    fgs2924rPortBaseVlanGroupIndex        INTEGER,
    fgs2924rPortBaseVlanGroupName          DisplayString,
    fgs2924rPortBaseVlanGroupMembers       DisplayString,
    fgs2924rPortBaseVlanGroupEntryAction   INTEGER
}

fgs2924rPortBaseVlanGroupEntry OBJECT-TYPE
 SYNTAX  FGS2924RPortBaseVlanGroupEntry
 MAX-ACCESS     not-accessible
 STATUS  current
 DESCRIPTION
  "This is the Entry(s) for Port Base VLAN Group configuration information."
 INDEX {fgs2924rPortBaseVlanGroupIndex}
 ::= { fgs2924rPortBaseVlanGroupTable 1 }

fgs2924rPortBaseVlanGroupIndex OBJECT-TYPE
 SYNTAX  INTEGER(1..24)
 MAX-ACCESS     not-accessible
 STATUS  current
 DESCRIPTION
  "This is the index of the Port Base VLAN Group configuration entry."
 ::= { fgs2924rPortBaseVlanGroupEntry 1 }

fgs2924rPortBaseVlanGroupName OBJECT-TYPE
 SYNTAX  DisplayString
 MAX-ACCESS     read-write
 STATUS  current
 DESCRIPTION
  "The name of vlan."
 ::= { fgs2924rPortBaseVlanGroupEntry 2 }

fgs2924rPortBaseVlanGroupMembers OBJECT-TYPE
 SYNTAX  DisplayString
 MAX-ACCESS     read-write
 STATUS  current
 DESCRIPTION
  "The member of vlan."
 ::= { fgs2924rPortBaseVlanGroupEntry 3 }

fgs2924rPortBaseVlanGroupEntryAction OBJECT-TYPE
 SYNTAX  INTEGER(1..3)
 MAX-ACCESS     read-write
 STATUS  current
 DESCRIPTION
  "The row status of vlan.
   1 - active
   2 - notInService
   3 - delete"
 ::= { fgs2924rPortBaseVlanGroupEntry 4 }

fgs2924rMacTableInfo            OBJECT IDENTIFIER ::= { fgs2924rProduces 15 }

fgs2924rMacTableConf            OBJECT IDENTIFIER ::= { fgs2924rMacTableInfo 1 }

fgs2924rMacAgeTime OBJECT-TYPE
 SYNTAX      INTEGER(10..1000000)
 MAX-ACCESS     read-write
 STATUS  current
 DESCRIPTION
  "Set the Mac Table Aging Time (10~1000000 Secs).
         0 : Disable."
 ::= { fgs2924rMacTableConf 1 }

fgs2924rMacTableLearningConfTable OBJECT-TYPE
 SYNTAX  SEQUENCE OF FGS2924RMacTableLearningConfEntry
 MAX-ACCESS not-accessible
 STATUS  current
    DESCRIPTION
        "A list of Mac Learning entry."
 ::= { fgs2924rMacTableConf 2 }

FGS2924RMacTableLearningConfEntry ::=
SEQUENCE {
    fgs2924rMacTableLearningConfIndex   INTEGER,
    fgs2924rMacTableLearningConfstate   INTEGER
}

fgs2924rMacTableLearningConfEntry OBJECT-TYPE
 SYNTAX  FGS2924RMacTableLearningConfEntry
 MAX-ACCESS     not-accessible
 STATUS  current
 DESCRIPTION
  "This is the Entry(s) for Mac Learning table information."
 INDEX {fgs2924rMacTableLearningConfIndex}
 ::= { fgs2924rMacTableLearningConfTable 1 }

fgs2924rMacTableLearningConfIndex OBJECT-TYPE
 SYNTAX  INTEGER(1..24)
 MAX-ACCESS     not-accessible
 STATUS  current
 DESCRIPTION
  "This is the index of the Learning MAC Table Group configuration entry."
 ::= { fgs2924rMacTableLearningConfEntry 1 }

fgs2924rMacTableLearningConfstate OBJECT-TYPE
 SYNTAX  INTEGER(0|1|2)
 MAX-ACCESS     read-write
 STATUS  current
 DESCRIPTION
  "Set mac table learning.
   0 - Auto
   1 - Disable
   2 - Secure"
 ::= { fgs2924rMacTableLearningConfEntry 2 }

fgs2924rMacTableStaticFilter            OBJECT IDENTIFIER ::= { fgs2924rMacTableInfo 2 }

fgs2924rMacTableStaticFilterNumber OBJECT-TYPE
 SYNTAX      INTEGER(0..512)
 MAX-ACCESS     read-only
 STATUS  current
 DESCRIPTION
  "Total numbers for static filter entry of Mac Table."
 ::= { fgs2924rMacTableStaticFilter 1 }

fgs2924rMacTableStaticFilterEntryCreate OBJECT-TYPE
 SYNTAX      INTEGER(0..512)
 MAX-ACCESS     read-write
 STATUS  current
 DESCRIPTION
  "Create a temp Filter entry in Mac Table.
         0 : none,
         1 : create a new entry"
 ::= { fgs2924rMacTableStaticFilter 2 }

fgs2924rMacTableStaticFilterTable OBJECT-TYPE
 SYNTAX  SEQUENCE OF FGS2924RMacTableStaticFilterEntry
 MAX-ACCESS not-accessible
 STATUS  current
    DESCRIPTION
        "A list of static filter entry. The numbers of entries are given by the value of fgs2924rMacTableStaticFilterNumber."
 ::= { fgs2924rMacTableStaticFilter 3 }

FGS2924RMacTableStaticFilterEntry ::=
SEQUENCE {
    fgs2924rMacTableStaticFilterIndex         INTEGER,
    fgs2924rMacTableStaticFilterMac           DisplayString,
    fgs2924rMacTableStaticFilterVid           INTEGER,
    fgs2924rMacTableStaticFilterAlias         DisplayString,
    fgs2924rMacTableStaticFilterEntryAction   INTEGER
}

fgs2924rMacTableStaticFilterEntry OBJECT-TYPE
 SYNTAX  FGS2924RMacTableStaticFilterEntry
 MAX-ACCESS     not-accessible
 STATUS  current
 DESCRIPTION
  "This is the Entry(s) for static filter information."
 INDEX {fgs2924rMacTableStaticFilterIndex}
 ::= { fgs2924rMacTableStaticFilterTable 1 }

fgs2924rMacTableStaticFilterIndex OBJECT-TYPE
 SYNTAX  INTEGER(1..512)
 MAX-ACCESS     not-accessible
 STATUS  current
 DESCRIPTION
  "This is the index of the Static Filter MAC Table Group configuration entry."
 ::= { fgs2924rMacTableStaticFilterEntry 1 }

fgs2924rMacTableStaticFilterMac OBJECT-TYPE
 SYNTAX  DisplayString
 MAX-ACCESS     read-write
 STATUS  current
 DESCRIPTION
  "The static filter mac in Mac Table"
 ::= { fgs2924rMacTableStaticFilterEntry 2 }

fgs2924rMacTableStaticFilterVid OBJECT-TYPE
 SYNTAX  INTEGER(1..4094)
 MAX-ACCESS     read-write
 STATUS  current
 DESCRIPTION
  "The filter vid in Mac Table"
 ::= { fgs2924rMacTableStaticFilterEntry 3 }

fgs2924rMacTableStaticFilterAlias OBJECT-TYPE
 SYNTAX  DisplayString
 MAX-ACCESS     read-write
 STATUS  current
 DESCRIPTION
  "The filter alias name in Mac Table"
 ::= { fgs2924rMacTableStaticFilterEntry 4 }

fgs2924rMacTableStaticFilterEntryAction OBJECT-TYPE
 SYNTAX  INTEGER(1..3)
 MAX-ACCESS     read-write
 STATUS  current
 DESCRIPTION
  "The row status of filter entry.
   1 - active
   2 - notInService
   3 - delete"
 ::= { fgs2924rMacTableStaticFilterEntry 5 }

fgs2924rMacTableStaticForward            OBJECT IDENTIFIER ::= { fgs2924rMacTableInfo 3 }

fgs2924rMacTableStaticForwardNumber OBJECT-TYPE
 SYNTAX      INTEGER(0..512)
 MAX-ACCESS     read-only
 STATUS  current
 DESCRIPTION
  "Total numbers for static forward entry of Mac Table."
 ::= { fgs2924rMacTableStaticForward 1 }

fgs2924rMacTableStaticForwardEntryCreate OBJECT-TYPE
 SYNTAX      INTEGER(0..512)
 MAX-ACCESS     read-write
 STATUS  current
 DESCRIPTION
  "Create a temp forward entry in Mac Table.
         0 : none,
         1 : create a new entry"
 ::= { fgs2924rMacTableStaticForward 2 }

fgs2924rMacTableStaticForwardTable OBJECT-TYPE
 SYNTAX  SEQUENCE OF FGS2924RMacTableStaticForwardEntry
 MAX-ACCESS not-accessible
 STATUS  current
    DESCRIPTION
        "A list of static forward entry. The numbers of entries are given by the value of fgs2924rMacTableStaticForwardNumber."
 ::= { fgs2924rMacTableStaticForward 3 }

FGS2924RMacTableStaticForwardEntry ::=
SEQUENCE {
    fgs2924rMacTableStaticForwardIndex         INTEGER,
    fgs2924rMacTableStaticForwardMac           DisplayString,
    fgs2924rMacTableStaticForwardPort          INTEGER,
    fgs2924rMacTableStaticForwardVid           INTEGER,
    fgs2924rMacTableStaticForwardAlias         DisplayString,
    fgs2924rMacTableStaticForwardEntryAction   INTEGER
}

fgs2924rMacTableStaticForwardEntry OBJECT-TYPE
 SYNTAX  FGS2924RMacTableStaticForwardEntry
 MAX-ACCESS     not-accessible
 STATUS  current
 DESCRIPTION
  "A list of static forwarding table entry."
 INDEX {fgs2924rMacTableStaticForwardIndex}
 ::= { fgs2924rMacTableStaticForwardTable 1 }

fgs2924rMacTableStaticForwardIndex OBJECT-TYPE
 SYNTAX  INTEGER(1..512)
 MAX-ACCESS     not-accessible
 STATUS  current
 DESCRIPTION
  "This is the index of the Static Forward MAC Table Group configuration entry."
 ::= { fgs2924rMacTableStaticForwardEntry 1 }

fgs2924rMacTableStaticForwardMac OBJECT-TYPE
 SYNTAX  DisplayString
 MAX-ACCESS     read-write
 STATUS  current
 DESCRIPTION
  "The static forwarding Mac in Mac Table"
 ::= { fgs2924rMacTableStaticForwardEntry 2 }

fgs2924rMacTableStaticForwardPort OBJECT-TYPE
 SYNTAX  INTEGER(1..24)
 MAX-ACCESS     read-write
 STATUS  current
 DESCRIPTION
  "To specify a destination port for a mac address in mac table."
 ::= { fgs2924rMacTableStaticForwardEntry 3 }

fgs2924rMacTableStaticForwardVid OBJECT-TYPE
 SYNTAX  INTEGER(1..4094)
 MAX-ACCESS     read-write
 STATUS  current
 DESCRIPTION
  "To specify a VLAN ID for a mac address in mac table."
 ::= { fgs2924rMacTableStaticForwardEntry 4 }

fgs2924rMacTableStaticForwardAlias OBJECT-TYPE
 SYNTAX  DisplayString
 MAX-ACCESS     read-write
 STATUS  current
 DESCRIPTION
  "To specify an alias for a mac address in mac table."
 ::= { fgs2924rMacTableStaticForwardEntry 5 }

fgs2924rMacTableStaticForwardEntryAction OBJECT-TYPE
 SYNTAX  INTEGER(1..3)
 MAX-ACCESS     read-write
 STATUS  current
 DESCRIPTION
  "The row status of filter entry.
   1 - active
   2 - notInService
   3 - delete"
 ::= { fgs2924rMacTableStaticForwardEntry 6 }

fgs2924rMacAlias            OBJECT IDENTIFIER ::= { fgs2924rMacTableInfo 4 }

fgs2924rMacAliasNumber OBJECT-TYPE
 SYNTAX      INTEGER(0..1024)
 MAX-ACCESS     read-only
 STATUS  current
 DESCRIPTION
  "Mac Alias Total Number(0~1024)."
 ::= { fgs2924rMacAlias 1 }

fgs2924rMacAliasEntryCreate OBJECT-TYPE
 SYNTAX      INTEGER(0..1024)
 MAX-ACCESS     read-only
 STATUS  current
 DESCRIPTION
  "Create a temp Mac alias entry in Mac Table.
         0 : none,
         1 : create a new entry"
 ::= { fgs2924rMacAlias 2 }

fgs2924rMacAliasTable OBJECT-TYPE
 SYNTAX  SEQUENCE OF FGS2924RMacAliasEntry
 MAX-ACCESS not-accessible
 STATUS  current
    DESCRIPTION
        "A list of Mac Alias entry. The numbers of entries are given by the value of fgs2924rMacAliasNumber."
 ::= { fgs2924rMacAlias 3 }

FGS2924RMacAliasEntry ::=
SEQUENCE {
    fgs2924rMacAliasIndex         INTEGER,
    fgs2924rAliasMac              DisplayString,
    fgs2924rAliasName             DisplayString,
    fgs2924rMacAliasEntryAction   INTEGER
}

fgs2924rMacAliasEntry OBJECT-TYPE
 SYNTAX  FGS2924RMacAliasEntry
 MAX-ACCESS     not-accessible
 STATUS  current
 DESCRIPTION
  "Entry(s) for Mac Alias."
 INDEX {fgs2924rMacAliasIndex}
 ::= { fgs2924rMacAliasTable 1 }

fgs2924rMacAliasIndex OBJECT-TYPE
 SYNTAX  INTEGER(1..1024)
 MAX-ACCESS     not-accessible
 STATUS  current
 DESCRIPTION
  "The index of the static mac alias entry."
 ::= { fgs2924rMacAliasEntry 1 }

fgs2924rAliasMac OBJECT-TYPE
 SYNTAX  DisplayString
 MAX-ACCESS     read-write
 STATUS  current
 DESCRIPTION
  "The Mac of the static mac alias entry."
 ::= { fgs2924rMacAliasEntry 2 }

fgs2924rAliasName OBJECT-TYPE
 SYNTAX  DisplayString
 MAX-ACCESS     read-write
 STATUS  current
 DESCRIPTION
  "The alias name of the static mac alias entry."
 ::= { fgs2924rMacAliasEntry 3 }

fgs2924rMacAliasEntryAction OBJECT-TYPE
 SYNTAX  INTEGER(1..3)
 MAX-ACCESS     read-write
 STATUS  current
 DESCRIPTION
  "The row status of mac alias entry.
   1 - active
   2 - notInService
   3 - delete"
 ::= { fgs2924rMacAliasEntry 4 }


fgs2924rGVRPInfo            OBJECT IDENTIFIER ::= { fgs2924rProduces 16 }

fgs2924rGvrpConf            OBJECT IDENTIFIER ::= { fgs2924rGVRPInfo 1 }

fgs2924rGvrpConfState OBJECT-TYPE
 SYNTAX      INTEGER(0|1)
 MAX-ACCESS     read-write
 STATUS  current
 DESCRIPTION
  "The GVRP state
   0 - Disable
   1 - Enable
    "
 ::= { fgs2924rGvrpConf 1 }

fgs2924rGvrpConfTable OBJECT-TYPE
 SYNTAX  SEQUENCE OF FGS2924RGvrpConfEntry
 MAX-ACCESS not-accessible
 STATUS  current
    DESCRIPTION
        "A list of GVRP entry."
 ::= { fgs2924rGvrpConf 2 }

FGS2924RGvrpConfEntry ::=
SEQUENCE {
    fgs2924rGvrpConfIndex             INTEGER,
    fgs2924rGvrpConfJoinTime          INTEGER,
    fgs2924rGvrpConfLeaveTime         INTEGER,
    fgs2924rGvrpConfLeaveAllTime      INTEGER,
    fgs2924rGvrpConfDefaultAppMode    INTEGER,
    fgs2924rGvrpConfDefaultRegMode    INTEGER,
    fgs2924rGvrpConfRestrictedMode    INTEGER
}

fgs2924rGvrpConfEntry OBJECT-TYPE
 SYNTAX  FGS2924RGvrpConfEntry
 MAX-ACCESS     not-accessible
 STATUS  current
 DESCRIPTION
  "This is the Entry(s) for gvrp information."
 INDEX {fgs2924rGvrpConfIndex}
 ::= { fgs2924rGvrpConfTable 1 }

fgs2924rGvrpConfIndex OBJECT-TYPE
 SYNTAX  INTEGER(1..24)
 MAX-ACCESS     not-accessible
 STATUS  current
 DESCRIPTION
  "This is the index of the gvrp entry."
 ::= { fgs2924rGvrpConfEntry 1 }

fgs2924rGvrpConfJoinTime OBJECT-TYPE
 SYNTAX  INTEGER(20..100)
 MAX-ACCESS     read-write
 STATUS  current
 DESCRIPTION
  "This is the join-time of the gvrp entry."
 ::= { fgs2924rGvrpConfEntry 2 }

fgs2924rGvrpConfLeaveTime OBJECT-TYPE
 SYNTAX  INTEGER(60..300)
 MAX-ACCESS     read-write
 STATUS  current
 DESCRIPTION
  "This is the leave-time of the gvrp entry.
  default:60 centisecond"
 ::= { fgs2924rGvrpConfEntry 3 }

fgs2924rGvrpConfLeaveAllTime OBJECT-TYPE
 SYNTAX  INTEGER(1000..5000)
 MAX-ACCESS     read-write
 STATUS  current
 DESCRIPTION
  "Set GVRP leave_all_time.
   default: 1000 unit time"
 ::= { fgs2924rGvrpConfEntry 4 }

fgs2924rGvrpConfDefaultAppMode OBJECT-TYPE
 SYNTAX  INTEGER(0|1)
 MAX-ACCESS     read-write
 STATUS  current
 DESCRIPTION
  "Set GVRP applicant.
   [default: Normal]
   0 - Normal
   1 - Non-Participant"
 ::= { fgs2924rGvrpConfEntry 5 }

fgs2924rGvrpConfDefaultRegMode OBJECT-TYPE
 SYNTAX  INTEGER(0|1|2)
 MAX-ACCESS     read-write
 STATUS  current
 DESCRIPTION
  "Set GVRP registrar.
   [default: Normal]
   0 - Normal
   1 - Fixed
   2 - Forbidden"
 ::= { fgs2924rGvrpConfEntry 6 }

fgs2924rGvrpConfRestrictedMode OBJECT-TYPE
 SYNTAX  INTEGER(0|1)
 MAX-ACCESS     read-write
 STATUS  current
 DESCRIPTION
  "Set GVRP restricted.
   [default: Disable]
   0 - Disable
   1 - Enable"
 ::= { fgs2924rGvrpConfEntry 7 }

fgs2924rGvrpCounter            OBJECT IDENTIFIER ::= { fgs2924rGVRPInfo 2 }

fgs2924rGvrpCounterTable OBJECT-TYPE
 SYNTAX  SEQUENCE OF FGS2924RGvrpCounterEntry
 MAX-ACCESS not-accessible
 STATUS  current
    DESCRIPTION
        "This is a list of FGS2924RGvrpCounterEntry."
 ::= { fgs2924rGvrpCounter 1 }

FGS2924RGvrpCounterEntry ::=
SEQUENCE {
    fgs2924rGvrpCounterIndex              INTEGER,
    fgs2924rGvrpCounterRxTotalGvrpPkts    Counter32,
    fgs2924rGvrpCounterRxInvalidGvrpPkts  Counter32,
    fgs2924rGvrpCounterRxLeaveAllMsg      Counter32,
    fgs2924rGvrpCounterRxJoinEmptyMsg     Counter32,
    fgs2924rGvrpCounterRxJoinInMsg        Counter32,
    fgs2924rGvrpCounterRxLeaveEmptyMsg    Counter32,
    fgs2924rGvrpCounterRxEmptyMsg         Counter32,
    fgs2924rGvrpCounterTxTotalGvrpPkts    Counter32,
    fgs2924rGvrpCounterTxLeaveAllMsg      Counter32,
    fgs2924rGvrpCounterTxJoinEmptyMsg     Counter32,
    fgs2924rGvrpCounterTxJoinInMsg        Counter32,
    fgs2924rGvrpCounterTxLeaveEmptyMsg    Counter32,
    fgs2924rGvrpCounterTxEmptyMsg         Counter32
}

fgs2924rGvrpCounterEntry OBJECT-TYPE
 SYNTAX  FGS2924RGvrpCounterEntry
 MAX-ACCESS     not-accessible
 STATUS  current
 DESCRIPTION
  "This is the Entry(s) for gvrp counter information."
 INDEX {fgs2924rGvrpCounterIndex}
 ::= { fgs2924rGvrpCounterTable 1 }

fgs2924rGvrpCounterIndex OBJECT-TYPE
 SYNTAX  INTEGER(1..24)
 MAX-ACCESS     not-accessible
 STATUS  current
 DESCRIPTION
  "This is the index of the gvrp counter entry."
 ::= { fgs2924rGvrpCounterEntry 1 }

fgs2924rGvrpCounterRxTotalGvrpPkts OBJECT-TYPE
 SYNTAX  Counter32
 MAX-ACCESS     read-only
 STATUS  current
 DESCRIPTION
  "Get the amount of all received gvrp packets of the gvrp counter entry."
 ::= { fgs2924rGvrpCounterEntry 2 }

fgs2924rGvrpCounterRxInvalidGvrpPkts OBJECT-TYPE
 SYNTAX  Counter32
 MAX-ACCESS     read-only
 STATUS  current
 DESCRIPTION
  "Get the amount of received invalid gvrp packets of the gvrp counter entry."
 ::= { fgs2924rGvrpCounterEntry 3 }

fgs2924rGvrpCounterRxLeaveAllMsg OBJECT-TYPE
 SYNTAX  Counter32
 MAX-ACCESS     read-only
 STATUS  current
 DESCRIPTION
  "Get the amount of received leave-all-message of the gvrp counter entry."
 ::= { fgs2924rGvrpCounterEntry 4 }

fgs2924rGvrpCounterRxJoinEmptyMsg OBJECT-TYPE
 SYNTAX  Counter32
 MAX-ACCESS     read-only
 STATUS  current
 DESCRIPTION
  "Get the amount of received join-empty-message of the gvrp counter entry."
 ::= { fgs2924rGvrpCounterEntry 5 }

fgs2924rGvrpCounterRxJoinInMsg OBJECT-TYPE
 SYNTAX  Counter32
 MAX-ACCESS     read-only
 STATUS  current
 DESCRIPTION
  "Get the amount of received join-in-message of the gvrp counter entry."
 ::= { fgs2924rGvrpCounterEntry 6 }

fgs2924rGvrpCounterRxLeaveEmptyMsg OBJECT-TYPE
 SYNTAX  Counter32
 MAX-ACCESS     read-only
 STATUS  current
 DESCRIPTION
  "Get the amount of received leave-empty-message of the gvrp counter entry."
 ::= { fgs2924rGvrpCounterEntry 7 }

fgs2924rGvrpCounterRxEmptyMsg OBJECT-TYPE
 SYNTAX  Counter32
 MAX-ACCESS     read-only
 STATUS  current
 DESCRIPTION
  "Get the amount of received empty-message of the gvrp counter entry."
 ::= { fgs2924rGvrpCounterEntry 8 }

fgs2924rGvrpCounterTxTotalGvrpPkts OBJECT-TYPE
 SYNTAX  Counter32
 MAX-ACCESS     read-only
 STATUS  current
 DESCRIPTION
  "Get the amount of all transmitted gvrp packets of the gvrp counter entry."
 ::= { fgs2924rGvrpCounterEntry 9 }

fgs2924rGvrpCounterTxLeaveAllMsg OBJECT-TYPE
 SYNTAX  Counter32
 MAX-ACCESS     read-only
 STATUS  current
 DESCRIPTION
  "Get the amount of transmitted leave-all-message of the gvrp counter entry."
 ::= { fgs2924rGvrpCounterEntry 10 }

fgs2924rGvrpCounterTxJoinEmptyMsg OBJECT-TYPE
 SYNTAX  Counter32
 MAX-ACCESS     read-only
 STATUS  current
 DESCRIPTION
  "Get the amount of transmitted join-empty-message of the gvrp counter entry."
 ::= { fgs2924rGvrpCounterEntry 11 }

fgs2924rGvrpCounterTxJoinInMsg OBJECT-TYPE
 SYNTAX  Counter32
 MAX-ACCESS     read-only
 STATUS  current
 DESCRIPTION
  "Get the amount of transmitted join-in-message of the gvrp counter entry."
 ::= { fgs2924rGvrpCounterEntry 12 }

fgs2924rGvrpCounterTxLeaveEmptyMsg OBJECT-TYPE
 SYNTAX  Counter32
 MAX-ACCESS     read-only
 STATUS  current
 DESCRIPTION
  "Get the amount of transmitted leave-empty-message of the gvrp counter entry."
 ::= { fgs2924rGvrpCounterEntry 13 }

fgs2924rGvrpCounterTxEmptyMsg OBJECT-TYPE
 SYNTAX  Counter32
 MAX-ACCESS     read-only
 STATUS  current
 DESCRIPTION
  "Get the amount of transmitted empty-message of the gvrp counter entry."
 ::= { fgs2924rGvrpCounterEntry 14 }

fgs2924rGvrpGroup            OBJECT IDENTIFIER ::= { fgs2924rGVRPInfo 3 }

fgs2924rGvrpGroupNumber OBJECT-TYPE
 SYNTAX  INTEGER(0..4094)
 MAX-ACCESS     read-only
 STATUS  current
 DESCRIPTION
  "Get the number of the gvrp group entry."
 ::= { fgs2924rGvrpGroup 1 }

fgs2924rGvrpGroupTable OBJECT-TYPE
 SYNTAX  SEQUENCE OF FGS2924RGvrpGroupEntry
 MAX-ACCESS not-accessible
 STATUS  current
    DESCRIPTION
        "This is a list of FGS2924RGvrpGroupEntry."
 ::= { fgs2924rGvrpGroup 2 }

FGS2924RGvrpGroupEntry ::=
SEQUENCE {
    fgs2924rGvrpGroupId            INTEGER,
    fgs2924rGvrpGroupVid           INTEGER,
    fgs2924rGvrpGroupMemberPort    DisplayString
}

fgs2924rGvrpGroupEntry OBJECT-TYPE
 SYNTAX  FGS2924RGvrpGroupEntry
 MAX-ACCESS     not-accessible
 STATUS  current
 DESCRIPTION
  "This is the Entry(s) for gvrp group information."
 INDEX {fgs2924rGvrpGroupId}
 ::= { fgs2924rGvrpGroupTable 1 }

fgs2924rGvrpGroupId OBJECT-TYPE
 SYNTAX  INTEGER(1..4094)
 MAX-ACCESS     read-only
 STATUS  current
 DESCRIPTION
  "This is the index of the gvrp group entry."
 ::= { fgs2924rGvrpGroupEntry 1 }

fgs2924rGvrpGroupVid OBJECT-TYPE
 SYNTAX  INTEGER(1..4094)
 MAX-ACCESS     read-only
 STATUS  current
 DESCRIPTION
  "This is the vlan id of the gvrp grout entry."
 ::= { fgs2924rGvrpGroupEntry 2 }

fgs2924rGvrpGroupMemberPort OBJECT-TYPE
 SYNTAX  DisplayString
 MAX-ACCESS     read-only
 STATUS  current
 DESCRIPTION
  "The member ports of the gvrp grout entry."
 ::= { fgs2924rGvrpGroupEntry 3 }

fgs2924rGvrpGroupAdministrativeCtrlTable OBJECT-TYPE
 SYNTAX  SEQUENCE OF FGS2924RGvrpGroupAdministrativeCtrlEntry
 MAX-ACCESS not-accessible
 STATUS  current
    DESCRIPTION
        "This is a list of FGS2924RGvrpGroupAdministrativeCtrlEntry."
 ::= { fgs2924rGvrpGroup 3 }

FGS2924RGvrpGroupAdministrativeCtrlEntry ::=
SEQUENCE {
    fgs2924rGvrpGroupAdministrativeCtrlVid    INTEGER,
    fgs2924rGvrpGroupAdministrativeCtrlPort   INTEGER,
    fgs2924rGvrpGroupAdministrativeCtrlApp    INTEGER,
    fgs2924rGvrpGroupAdministrativeCtrlReg    INTEGER
}

fgs2924rGvrpGroupAdministrativeCtrlEntry OBJECT-TYPE
 SYNTAX  FGS2924RGvrpGroupAdministrativeCtrlEntry
 MAX-ACCESS     not-accessible
 STATUS  current
 DESCRIPTION
  "This is the Entry(s) for gvrp group administrative information."
 INDEX {fgs2924rGvrpGroupAdministrativeCtrlVid, fgs2924rGvrpGroupAdministrativeCtrlPort}
 ::= { fgs2924rGvrpGroupAdministrativeCtrlTable 1 }

fgs2924rGvrpGroupAdministrativeCtrlVid OBJECT-TYPE
 SYNTAX  INTEGER(1..4094)
 MAX-ACCESS     read-only
 STATUS  current
 DESCRIPTION
  "This is the vlan id of the gvrp-group-admin entry."
 ::= { fgs2924rGvrpGroupAdministrativeCtrlEntry 1 }

fgs2924rGvrpGroupAdministrativeCtrlPort OBJECT-TYPE
 SYNTAX  INTEGER(1..24)
 MAX-ACCESS     read-only
 STATUS  current
 DESCRIPTION
  "This is the port number of the gvrp-group-admin entry."
 ::= { fgs2924rGvrpGroupAdministrativeCtrlEntry 2 }

fgs2924rGvrpGroupAdministrativeCtrlApp OBJECT-TYPE
 SYNTAX  INTEGER(0|1)
 MAX-ACCESS     read-write
 STATUS  current
 DESCRIPTION
  "Set gvrp applicant.
   0 - Normal
   1 - Non-Participant"
 ::= { fgs2924rGvrpGroupAdministrativeCtrlEntry 3 }

fgs2924rGvrpGroupAdministrativeCtrlReg OBJECT-TYPE
 SYNTAX  INTEGER(0..2)
 MAX-ACCESS     read-write
 STATUS  current
 DESCRIPTION
  "Set gvrp registrar.
   0 - Normal
   1 - Fixed
   2 - Forbidden"
 ::= { fgs2924rGvrpGroupAdministrativeCtrlEntry 4 }

fgs2924rQosInfo            OBJECT IDENTIFIER ::= { fgs2924rProduces 17 }

fgs2924rQosPortConf            OBJECT IDENTIFIER ::= { fgs2924rQosInfo 1 }

fgs2924rQosNumOfClasses OBJECT-TYPE
 SYNTAX      INTEGER(1|2|4)
 MAX-ACCESS     read-write
 STATUS  current
 DESCRIPTION
  "Effective class number, it can be set 1, 2, or 4.
  1 means only one class available, all packets will be treat the same.
  2 means two classes available, packets will be divided into high and low queue.
  4 means for classes available, packets will be divided into low/normal/medium/high queue"
 ::= { fgs2924rQosPortConf 1 }

fgs2924rQosPortConfTable OBJECT-TYPE
 SYNTAX  SEQUENCE OF FGS2924RQosPortConfEntry
 MAX-ACCESS not-accessible
 STATUS  current
    DESCRIPTION
        "QoS parameter for ports."
 ::= { fgs2924rQosPortConf 2 }

FGS2924RQosPortConfEntry ::=
SEQUENCE {
    fgs2924rQosPortConfIndex                INTEGER,
    fgs2924rQosPortConfDefaultClasses       INTEGER,
    fgs2924rQosPortConfQCL                  INTEGER,
    fgs2924rQosPortConfUserPriority         INTEGER,
    fgs2924rQosPortConfQueuingMode          INTEGER,
    fgs2924rQosPortConfQueueWeightedLow     INTEGER,
    fgs2924rQosPortConfQueueWeightedNormal  INTEGER,
    fgs2924rQosPortConfQueueWeightedMedium  INTEGER,
    fgs2924rQosPortConfQueueWeightedHigh    INTEGER
}

fgs2924rQosPortConfEntry OBJECT-TYPE
 SYNTAX  FGS2924RQosPortConfEntry
 MAX-ACCESS     not-accessible
 STATUS  current
 DESCRIPTION
  "QoS parameter for ports."
 INDEX {fgs2924rQosPortConfIndex}
 ::= { fgs2924rQosPortConfTable 1 }

fgs2924rQosPortConfIndex OBJECT-TYPE
 SYNTAX  INTEGER(1..24)
 MAX-ACCESS     not-accessible
 STATUS  current
 DESCRIPTION
  "This is the port number for QoS configuration."
 ::= { fgs2924rQosPortConfEntry 1 }

fgs2924rQosPortConfDefaultClasses OBJECT-TYPE
 SYNTAX  INTEGER(0..3)
 MAX-ACCESS     read-write
 STATUS  current
 DESCRIPTION
  "This is the default class for packets mismatch the specified QCL setting.
   0 - Low
   1 - Normal
   2 - Medium
   3 - High"
 ::= { fgs2924rQosPortConfEntry 2 }

fgs2924rQosPortConfQCL OBJECT-TYPE
 SYNTAX  INTEGER(1..24)
 MAX-ACCESS     read-write
 STATUS  current
 DESCRIPTION
 "Designate the QCL for the specific port. QCL is from 1 to 24."
 ::= { fgs2924rQosPortConfEntry 3 }

fgs2924rQosPortConfUserPriority OBJECT-TYPE
 SYNTAX  INTEGER(0..7)
 MAX-ACCESS     read-write
 STATUS  current
 DESCRIPTION
		"This is the default ingress VLAN tag priority. Priority is from 0 to 7."
 ::= { fgs2924rQosPortConfEntry 4 }

fgs2924rQosPortConfQueuingMode OBJECT-TYPE
 SYNTAX  INTEGER(0|1)
 MAX-ACCESS     read-write
 STATUS  current
 DESCRIPTION
  "Set qos port queuing mode.
   0 - Strict Priority
   1 - Weighted Fair"
 ::= { fgs2924rQosPortConfEntry 5 }

fgs2924rQosPortConfQueueWeightedLow OBJECT-TYPE
 SYNTAX  INTEGER(1|2|4|8)
 MAX-ACCESS     read-write
 STATUS  current
 DESCRIPTION
  "To specify how many quotas the low queue can be distributed.
		 Only available when the queuing mode is Weighted Fair. QueueWeighted is 1, 2, 4, 8."
 ::= { fgs2924rQosPortConfEntry 6 }

fgs2924rQosPortConfQueueWeightedNormal OBJECT-TYPE
 SYNTAX  INTEGER(1|2|4|8)
 MAX-ACCESS     read-write
 STATUS  current
 DESCRIPTION
  "To specify how many quotas the normal queue can be distributed.
		 Only available when the queuing mode is Weighted Fair. QueueWeighted is 1, 2, 4, 8."
 ::= { fgs2924rQosPortConfEntry 7 }

fgs2924rQosPortConfQueueWeightedMedium OBJECT-TYPE
 SYNTAX  INTEGER(1|2|4|8)
 MAX-ACCESS     read-write
 STATUS  current
 DESCRIPTION
  "To specify how many quotas the medium queue can be distributed.
		 Only available when the queuing mode is Weighted Fair. QueueWeighted is 1, 2, 4, 8."
 ::= { fgs2924rQosPortConfEntry 8 }

fgs2924rQosPortConfQueueWeightedHigh OBJECT-TYPE
 SYNTAX  INTEGER(1|2|4|8)
 MAX-ACCESS     read-write
 STATUS  current
 DESCRIPTION
  "To specify how many quotas the high queue can be distributed.
		 Only available when the queuing mode is Weighted Fair. QueueWeighted is 1, 2, 4, 8."
 ::= { fgs2924rQosPortConfEntry 9 }

fgs2924rQosRateLimiters           OBJECT IDENTIFIER ::= { fgs2924rQosInfo 3 }

fgs2924rQosRateLimitersTable OBJECT-TYPE
 SYNTAX  SEQUENCE OF FGS2924RQosRateLimitersEntry
 MAX-ACCESS not-accessible
 STATUS  current
    DESCRIPTION
        "This is the port bandwidth configuration."
 ::= { fgs2924rQosRateLimiters 1 }

FGS2924RQosRateLimitersEntry ::=
SEQUENCE {
    fgs2924rQosRateLimitersIndex         INTEGER,
    fgs2924rQosRateLimitersPolicer       INTEGER,
    fgs2924rQosRateLimitersPolicerRate   INTEGER,
    fgs2924rQosRateLimitersShaper        INTEGER,
    fgs2924rQosRateLimitersShaperRate    INTEGER
}

fgs2924rQosRateLimitersEntry OBJECT-TYPE
 SYNTAX  FGS2924RQosRateLimitersEntry
 MAX-ACCESS     not-accessible
 STATUS  current
 DESCRIPTION
  "This is the port bandwidth configuration."
 INDEX {fgs2924rQosRateLimitersIndex}
 ::= { fgs2924rQosRateLimitersTable 1 }

fgs2924rQosRateLimitersIndex OBJECT-TYPE
 SYNTAX  INTEGER(1..24)
 MAX-ACCESS     not-accessible
 STATUS  current
 DESCRIPTION
  "This is the port number for rate limit configuration"
 ::= { fgs2924rQosRateLimitersEntry 1 }

fgs2924rQosRateLimitersPolicer OBJECT-TYPE
 SYNTAX  INTEGER(0|1)
 MAX-ACCESS     read-write
 STATUS  current
 DESCRIPTION
  "This is the ingress bandwidth function for specific port.
   0 - Disable
   1 - Enable"
 ::= { fgs2924rQosRateLimitersEntry 2 }

fgs2924rQosRateLimitersPolicerRate OBJECT-TYPE
 SYNTAX  INTEGER(1..1000000)
 MAX-ACCESS     read-write
 STATUS  current
 DESCRIPTION
  "To set the ingress bandwidth for specific port.
   Available value is from 500k to 1000000k"
 ::= { fgs2924rQosRateLimitersEntry 3 }


fgs2924rQosRateLimitersShaper OBJECT-TYPE
 SYNTAX  INTEGER(0|1)
 MAX-ACCESS     read-write
 STATUS  current
 DESCRIPTION
  "This is the egress bandwidth function for specific port.
   0 - Disable
   1 - Enable"
 ::= { fgs2924rQosRateLimitersEntry 4 }

fgs2924rQosRateLimitersShaperRate OBJECT-TYPE
 SYNTAX  INTEGER(1..1000000)
 MAX-ACCESS     read-write
 STATUS  current
 DESCRIPTION
  "To set the ingress bandwidth for specific port.
   Available value is from 500k to 1000000k"
 ::= { fgs2924rQosRateLimitersEntry 5 }


fgs2924rQosStormCtrl           OBJECT IDENTIFIER ::= { fgs2924rQosInfo 4 }

fgs2924rQosStromCtrlFloodedUnicastStatus OBJECT-TYPE
 SYNTAX      INTEGER(0|1)
 MAX-ACCESS     read-write
 STATUS  current
 DESCRIPTION
  "This is the flooded unicast suppression function for this device.
   0 - Disable
   1 - Enable"
 ::= { fgs2924rQosStormCtrl 1 }

fgs2924rQosStromCtrlFloodedUnicastRate OBJECT-TYPE
 SYNTAX      DisplayString
 MAX-ACCESS     read-write
 STATUS  current
 DESCRIPTION
  "To set the flooded unicast suppression for this device.
   1 | 2 | 4 | 8 | 16 | 32 | 64 | 128 | 256 | 512 | 1k | 2k | 4k | 8k | 16k | 32k |64k | 128k | 256k | 512k | 1024k(Rate:pps)
    "
 ::= { fgs2924rQosStormCtrl 2 }

fgs2924rQosStromCtrlMulticastStatus OBJECT-TYPE
 SYNTAX      INTEGER(0|1)
 MAX-ACCESS     read-write
 STATUS  current
 DESCRIPTION
  "This is the multicast suppression function for this device.
   0 - Disable
   1 - Enable"
 ::= { fgs2924rQosStormCtrl 3 }

fgs2924rQosStromCtrlMulticastRate OBJECT-TYPE
 SYNTAX      DisplayString
 MAX-ACCESS     read-write
 STATUS  current
 DESCRIPTION
  "To set the multicast suppression for this device.
   1 | 2 | 4 | 8 | 16 | 32 | 64 | 128 | 256 | 512 | 1k | 2k | 4k | 8k | 16k | 32k |64k | 128k | 256k | 512k | 1024k(Rate:pps)    "
 ::= { fgs2924rQosStormCtrl 4 }

fgs2924rQosStromCtrlBroadcastStatus OBJECT-TYPE
 SYNTAX      INTEGER(0|1)
 MAX-ACCESS     read-write
 STATUS  current
 DESCRIPTION
  "This is the broadcast suppression function for this device.
   0 - Disable
   1 - Enable"
 ::= { fgs2924rQosStormCtrl 5 }

fgs2924rQosStromCtrlBroadcastRate OBJECT-TYPE
 SYNTAX      DisplayString
 MAX-ACCESS     read-write
 STATUS  current
 DESCRIPTION
  "To set the broadcast suppression for this device.
   1 | 2 | 4 | 8 | 16 | 32 | 64 | 128 | 256 | 512 | 1k | 2k | 4k | 8k | 16k | 32k |64k | 128k | 256k | 512k | 1024k(Rate:pps)    "
 ::= { fgs2924rQosStormCtrl 6 }

fgs2924rQosQCL           OBJECT IDENTIFIER ::= { fgs2924rQosInfo 5 }

fgs2924rQosQclCreate OBJECT-TYPE
 SYNTAX      INTEGER(1..24)
 MAX-ACCESS     read-write
 STATUS  current
 DESCRIPTION
  "Specify a QCL number where the QCE will be created. Parameter is available from 1 ~ 24."
 ::= { fgs2924rQosQCL 1 }

fgs2924rQosQclTable OBJECT-TYPE
 SYNTAX  SEQUENCE OF FGS2924RQosQclEntry
 MAX-ACCESS not-accessible
 STATUS  current
    DESCRIPTION
        "This is the Qcl table."
 ::= { fgs2924rQosQCL 2 }

FGS2924RQosQclEntry ::=
SEQUENCE {
    fgs2924rQosQclNo                   INTEGER,
    fgs2924rQosQclQceListNo            INTEGER,
    fgs2924rQosQclQceMoveTo            INTEGER,
    fgs2924rQosQclQceType              INTEGER,
    fgs2924rQosQclQceValue             DisplayString,
    fgs2924rQosQclQceTrafficClass      DisplayString,
    fgs2924rQosQclQcePriority0Class    DisplayString,
    fgs2924rQosQclQcePriority1Class    DisplayString,
    fgs2924rQosQclQcePriority2Class    DisplayString,
    fgs2924rQosQclQcePriority3Class    DisplayString,
    fgs2924rQosQclQcePriority4Class    DisplayString,
    fgs2924rQosQclQcePriority5Class    DisplayString,
    fgs2924rQosQclQcePriority6Class    DisplayString,
    fgs2924rQosQclQcePriority7Class    DisplayString,
    fgs2924rQosQclQceEntryAction       INTEGER
}

fgs2924rQosQclEntry OBJECT-TYPE
 SYNTAX  FGS2924RQosQclEntry
 MAX-ACCESS     not-accessible
 STATUS  current
 DESCRIPTION
  "This is the Entry(s) for qcl entry information."
 INDEX {fgs2924rQosQclNo,fgs2924rQosQclQceListNo}
 ::= { fgs2924rQosQclTable 1 }

fgs2924rQosQclNo OBJECT-TYPE
 SYNTAX  INTEGER(1..24)
 MAX-ACCESS     not-accessible
 STATUS  current
 DESCRIPTION
  "Display which QCL is specified."
 ::= { fgs2924rQosQclEntry 1 }

fgs2924rQosQclQceListNo OBJECT-TYPE
 SYNTAX  INTEGER(1..24)
 MAX-ACCESS     not-accessible
 STATUS  current
 DESCRIPTION
  "Index of qce entry."
 ::= { fgs2924rQosQclEntry 2 }

fgs2924rQosQclQceMoveTo OBJECT-TYPE
 SYNTAX  INTEGER(1..24)
 MAX-ACCESS     not-accessible
 STATUS  current
 DESCRIPTION
  "Designate the position where the QCE will be moved to."
 ::= { fgs2924rQosQclEntry 3 }

fgs2924rQosQclQceType OBJECT-TYPE
 SYNTAX  INTEGER(0..5)
 MAX-ACCESS     read-write
 STATUS  current
 DESCRIPTION
  "Specify the qce type.
  0:EthernetType 1:VLAN ID 2:UDP/TCP Port
3:DSCP 4:Tos 5:TagPriority"
 ::= { fgs2924rQosQclEntry 4 }

fgs2924rQosQclQceValue OBJECT-TYPE
 SYNTAX  DisplayString
 MAX-ACCESS     read-write
 STATUS  current
 DESCRIPTION
  "Specify the qce entry value. Only available for 0:EthernetType 1:VLAN ID 2:UDP/TCP Port 3:DSCP.
  Input numbers in hexadecimal for 0:Ethernet Type, decimal for 1:VLAN ID 2:UDP/TCP Port 3:DSCP.
  You can also specify a range value for 2:UDP/TCP. EX: 5000-6000"
 ::= { fgs2924rQosQclEntry 5 }

fgs2924rQosQclQceTrafficClass OBJECT-TYPE
 SYNTAX  DisplayString
 MAX-ACCESS     read-write
 STATUS  current
 DESCRIPTION
  "Specify the qce entry traffic class. Available options are: low, normal, medium and high."
 ::= { fgs2924rQosQclEntry 6 }

fgs2924rQosQclQcePriority0Class OBJECT-TYPE
 SYNTAX  DisplayString
 MAX-ACCESS     read-write
 STATUS  current
 DESCRIPTION
  "Specify the qce entry traffic class. Available options are: low, normal, medium and high.
  Only works on 4:Tos 5:TagPriority."
 ::= { fgs2924rQosQclEntry 7 }

fgs2924rQosQclQcePriority1Class OBJECT-TYPE
 SYNTAX  DisplayString
 MAX-ACCESS     read-write
 STATUS  current
 DESCRIPTION
  "Specify the qce entry traffic class. Available options are: low, normal, medium and high.
  Only works on 4:Tos 5:TagPriority."
 ::= { fgs2924rQosQclEntry 8 }

fgs2924rQosQclQcePriority2Class OBJECT-TYPE
 SYNTAX  DisplayString
 MAX-ACCESS     read-write
 STATUS  current
 DESCRIPTION
  "Specify the qce entry traffic class. Available options are: low, normal, medium and high.
  Only works on 4:Tos 5:TagPriority."
 ::= { fgs2924rQosQclEntry 9 }

fgs2924rQosQclQcePriority3Class OBJECT-TYPE
 SYNTAX  DisplayString
 MAX-ACCESS     read-write
 STATUS  current
 DESCRIPTION
  "Specify the qce entry traffic class. Available options are: low, normal, medium and high.
  Only works on 4:Tos 5:TagPriority."
 ::= { fgs2924rQosQclEntry 10 }

fgs2924rQosQclQcePriority4Class OBJECT-TYPE
 SYNTAX  DisplayString
 MAX-ACCESS     read-write
 STATUS  current
 DESCRIPTION
  "Specify the qce entry traffic class. Available options are: low, normal, medium and high.
  Only works on 4:Tos 5:TagPriority."
 ::= { fgs2924rQosQclEntry 11 }

fgs2924rQosQclQcePriority5Class OBJECT-TYPE
 SYNTAX  DisplayString
 MAX-ACCESS     read-write
 STATUS  current
 DESCRIPTION
  "Specify the qce entry traffic class. Available options are: low, normal, medium and high.
  Only works on 4:Tos 5:TagPriority."
 ::= { fgs2924rQosQclEntry 12 }

fgs2924rQosQclQcePriority6Class OBJECT-TYPE
 SYNTAX  DisplayString
 MAX-ACCESS     read-write
 STATUS  current
 DESCRIPTION
  "Specify the qce entry traffic class. Available options are: low, normal, medium and high.
  Only works on 4:Tos 5:TagPriority."
 ::= { fgs2924rQosQclEntry 13 }

fgs2924rQosQclQcePriority7Class OBJECT-TYPE
 SYNTAX  DisplayString
 MAX-ACCESS     read-write
 STATUS  current
 DESCRIPTION
  "Specify the qce entry traffic class. Available options are: low, normal, medium and high.
  Only works on 4:Tos 5:TagPriority."
 ::= { fgs2924rQosQclEntry 14 }

fgs2924rQosQclQceEntryAction OBJECT-TYPE
 SYNTAX  INTEGER(1..3)
 MAX-ACCESS  read-write
 STATUS  current
 DESCRIPTION
  "Set qce entry state.
  1:active 2:notInService or edit 3:delete"
 ::= { fgs2924rQosQclEntry 15 }


fgs2924rAclInfo            OBJECT IDENTIFIER ::= { fgs2924rProduces 18 }

fgs2924rAclPortsConfTable OBJECT-TYPE
 SYNTAX  SEQUENCE OF FGS2924RAclPortsConfEntry
 MAX-ACCESS not-accessible
 STATUS  current
    DESCRIPTION
        "This is a list of port configuration entry. "
 ::= { fgs2924rAclInfo 1 }

FGS2924RAclPortsConfEntry ::=
SEQUENCE {
    fgs2924rAclPortsConfIndex           INTEGER,
    fgs2924rAclPortsConfPolicyId        INTEGER,
    fgs2924rAclPortsConfAction          INTEGER,
    fgs2924rAclPortsConfRateLimiterId   INTEGER,
    fgs2924rAclPortsConfPortCopy        INTEGER,
    fgs2924rAclPortsConfCounter         Counter32
}

fgs2924rAclPortsConfEntry OBJECT-TYPE
 SYNTAX  FGS2924RAclPortsConfEntry
 MAX-ACCESS     not-accessible
 STATUS  current
 DESCRIPTION
  "This is the Entry(s) for ACL port information."
 INDEX {fgs2924rAclPortsConfIndex}
 ::= { fgs2924rAclPortsConfTable 1 }

fgs2924rAclPortsConfIndex OBJECT-TYPE
 SYNTAX  INTEGER(1..24)
 MAX-ACCESS     not-accessible
 STATUS  current
 DESCRIPTION
  "This is the port number of the ACL port entry."
 ::= { fgs2924rAclPortsConfEntry 1 }

fgs2924rAclPortsConfPolicyId OBJECT-TYPE
 SYNTAX  INTEGER(1..8)
 MAX-ACCESS     read-write
 STATUS  current
 DESCRIPTION
  "This is the policy id of the ACL port entry.(1-8)"
 ::= { fgs2924rAclPortsConfEntry 2 }

fgs2924rAclPortsConfAction OBJECT-TYPE
 SYNTAX  INTEGER(0|1)
 MAX-ACCESS     read-write
 STATUS  current
 DESCRIPTION
  "Set the action of the ACL port entry.
   0 - Deny
   1 - Permit"
 ::= { fgs2924rAclPortsConfEntry 3 }

fgs2924rAclPortsConfRateLimiterId OBJECT-TYPE
 SYNTAX  INTEGER(0..24)
 MAX-ACCESS     read-write
 STATUS  current
 DESCRIPTION
  " Set the rate limiter id of the ACL port entry.(1-16)
   0 - Disable"
 ::= { fgs2924rAclPortsConfEntry 4 }

fgs2924rAclPortsConfPortCopy OBJECT-TYPE
 SYNTAX  INTEGER(0..24)
 MAX-ACCESS     read-write
 STATUS  current
 DESCRIPTION
  "Set the mirror port of the ACL port entry.(1-24)
   0 - Disable"
 ::= { fgs2924rAclPortsConfEntry 5 }

fgs2924rAclPortsConfCounter OBJECT-TYPE
 SYNTAX  Counter32
 MAX-ACCESS     read-only
 STATUS  current
 DESCRIPTION
  "This is the port counter of the ACL port entry."
 ::= { fgs2924rAclPortsConfEntry 6 }

fgs2924rAclRateLimiter           OBJECT IDENTIFIER ::= { fgs2924rAclInfo 2 }

fgs2924rAclRateLimiterTable OBJECT-TYPE
 SYNTAX  SEQUENCE OF FGS2924RAclRateLimiterEntry
 MAX-ACCESS not-accessible
 STATUS  current
    DESCRIPTION
        "This is a list of FGS2924RRateLimiterEntry."
 ::= { fgs2924rAclRateLimiter 1 }

FGS2924RAclRateLimiterEntry ::=
SEQUENCE {
    fgs2924rAclRateLimiterIndex        INTEGER,
    fgs2924rAclRateLimiterRate         DisplayString
}

fgs2924rAclRateLimiterEntry OBJECT-TYPE
 SYNTAX  FGS2924RAclRateLimiterEntry
 MAX-ACCESS     not-accessible
 STATUS  current
 DESCRIPTION
  "This is the Entry(s) for rate limiter information."
 INDEX {fgs2924rAclRateLimiterIndex}
 ::= { fgs2924rAclRateLimiterTable 1 }

fgs2924rAclRateLimiterIndex OBJECT-TYPE
 SYNTAX  INTEGER(1..24)
 MAX-ACCESS     not-accessible
 STATUS  current
 DESCRIPTION
  "This is the index of the rate limiter entry."
 ::= { fgs2924rAclRateLimiterEntry 1 }

fgs2924rAclRateLimiterRate OBJECT-TYPE
 SYNTAX  DisplayString
 MAX-ACCESS     read-write
 STATUS  current
 DESCRIPTION
  "Set acl rate limite.
  (pps) 1 | 2 | 4 | 8 | 16 | 32 | 64 | 128 | 256 | 512 | 1k | 2k | 4k | 8k | 16k | 32k |64k | 128k | 256k | 512k | 1024k"
 ::= { fgs2924rAclRateLimiterEntry 2 }

fgs2924rAclInfoViewTable OBJECT-TYPE
 SYNTAX  SEQUENCE OF FGS2924RAclInfoViewEntry
 MAX-ACCESS not-accessible
 STATUS  current
    DESCRIPTION
        "This is a list of FGS2924RAclInfoViewEntry."
 ::= { fgs2924rAclInfo 3 }

FGS2924RAclInfoViewEntry ::=
SEQUENCE {
    fgs2924rAclInfoViewNo              INTEGER,
    fgs2924rAceIngressPort             DisplayString,
    fgs2924rAceFrameType               DisplayString,
    fgs2924rAceAction                  DisplayString,
    fgs2924rAceRateLimiter             DisplayString,
    fgs2924rAcePortCopy                DisplayString,
    fgs2924rAceCounter                 Counter32,
    fgs2924rSmacFilter                 DisplayString,
    fgs2924rDmacFilter                 DisplayString,
    fgs2924rVlanIdFilter               DisplayString,
    fgs2924rVlanTagPriority            DisplayString,
    fgs2924rEtherTypeFilter            DisplayString,
    fgs2924rArpRarp                    DisplayString,
    fgs2924rArpRequestReply            DisplayString,
    fgs2924rArpSenderIpFilter          DisplayString,
    fgs2924rArpSenderIpAddress         DisplayString,
    fgs2924rArpSenderIpMask            DisplayString,
    fgs2924rArpTargetIpFilter          DisplayString,
    fgs2924rArpTargetIpAddress         DisplayString,
    fgs2924rArpTargetIpMask            DisplayString,
    fgs2924rArpSmacMatch               DisplayString,
    fgs2924rArpRarpDmacMatch           DisplayString,
    fgs2924rArpIpEthernetLength        DisplayString,
    fgs2924rArpIp                      DisplayString,
    fgs2924rArpEthernet                DisplayString,
    fgs2924rIpProtocolFilter           DisplayString,
    fgs2924rIpProtocolValue            DisplayString,
    fgs2924rIpTTL                      DisplayString,
    fgs2924rIpFragment                 DisplayString,
    fgs2924rIpOption                   DisplayString,
    fgs2924rSipFilter                  DisplayString,
    fgs2924rSipAddress                 DisplayString,
    fgs2924rSipMask                    DisplayString,
    fgs2924rDipFilter                  DisplayString,
    fgs2924rDipAddress                 DisplayString,
    fgs2924rDipMask                    DisplayString,
    fgs2924rIcmpTypeFilter             DisplayString,
    fgs2924rIcmpCodeFilter             DisplayString,
    fgs2924rUdpSourcePortFilter        DisplayString,
    fgs2924rUdpDestPortFilter          DisplayString,
    fgs2924rTcpSourcePortFilter        DisplayString,
    fgs2924rTcpDestPortFilter          DisplayString,
    fgs2924rTcpFIN                     DisplayString,
    fgs2924rTcpSYN                     DisplayString,
    fgs2924rTcpRST                     DisplayString,
    fgs2924rTcpPSH                     DisplayString,
    fgs2924rTcpACK                     DisplayString,
    fgs2924rTcpURG                     DisplayString,
    fgs2924rAclInfoEntryAction         INTEGER
}

fgs2924rAclInfoViewEntry OBJECT-TYPE
 SYNTAX  FGS2924RAclInfoViewEntry
 MAX-ACCESS     not-accessible
 STATUS  current
 DESCRIPTION
  "Show acl entry information."
 INDEX {fgs2924rAclInfoViewNo}
 ::= { fgs2924rAclInfoViewTable 1 }


fgs2924rAclInfoViewNo OBJECT-TYPE
 SYNTAX  INTEGER(1..128)
 MAX-ACCESS     not-accessible
 STATUS  current
 DESCRIPTION
  "Index of the ACL entry."
 ::= { fgs2924rAclInfoViewEntry 1 }

fgs2924rAceIngressPort OBJECT-TYPE
 SYNTAX  DisplayString
 MAX-ACCESS     read-only
 STATUS  current
 DESCRIPTION
  "Ace ingress port number."
 ::= { fgs2924rAclInfoViewEntry 2 }

fgs2924rAceFrameType OBJECT-TYPE
 SYNTAX  DisplayString
 MAX-ACCESS     read-only
 STATUS  current
 DESCRIPTION
  "Ace frame type."
 ::= { fgs2924rAclInfoViewEntry 3 }

fgs2924rAceAction OBJECT-TYPE
 SYNTAX  DisplayString
 MAX-ACCESS     read-only
 STATUS  current
 DESCRIPTION
  "Ace action."
 ::= { fgs2924rAclInfoViewEntry 4 }

fgs2924rAceRateLimiter OBJECT-TYPE
 SYNTAX  DisplayString
 MAX-ACCESS     read-only
 STATUS  current
 DESCRIPTION
  "Ace rate limiter number."
 ::= { fgs2924rAclInfoViewEntry 5 }

fgs2924rAcePortCopy OBJECT-TYPE
 SYNTAX  DisplayString
 MAX-ACCESS     read-only
 STATUS  current
 DESCRIPTION
  "Specify the port which packet will be copied to."
 ::= { fgs2924rAclInfoViewEntry 6 }

fgs2924rAceCounter OBJECT-TYPE
 SYNTAX  Counter32
 MAX-ACCESS     read-only
 STATUS  current
 DESCRIPTION
  "Display the number of packets hit this ace."
 ::= { fgs2924rAclInfoViewEntry 7 }

fgs2924rSmacFilter OBJECT-TYPE
 SYNTAX  DisplayString
 MAX-ACCESS     read-only
 STATUS  current
 DESCRIPTION
  "Display the source mac field of the ace."
 ::= { fgs2924rAclInfoViewEntry 8 }

fgs2924rDmacFilter OBJECT-TYPE
 SYNTAX  DisplayString
 MAX-ACCESS     read-only
 STATUS  current
 DESCRIPTION
  "Display the destination mac field of the ace."
 ::= { fgs2924rAclInfoViewEntry 9 }

fgs2924rVlanIdFilter OBJECT-TYPE
 SYNTAX  DisplayString
 MAX-ACCESS     read-only
 STATUS  current
 DESCRIPTION
  "Display the vid field of the ace."
 ::= { fgs2924rAclInfoViewEntry 10 }

fgs2924rVlanTagPriority OBJECT-TYPE
 SYNTAX  DisplayString
 MAX-ACCESS     read-only
 STATUS  current
 DESCRIPTION
  "Display the vlan tag priority field of the ace."
 ::= { fgs2924rAclInfoViewEntry 11 }

fgs2924rEtherTypeFilter OBJECT-TYPE
 SYNTAX  DisplayString
 MAX-ACCESS     read-only
 STATUS  current
 DESCRIPTION
  "Display the ether type field of the ace."
 ::= { fgs2924rAclInfoViewEntry 12 }

fgs2924rArpRarp OBJECT-TYPE
 SYNTAX  DisplayString
 MAX-ACCESS     read-only
 STATUS  current
 DESCRIPTION
  "Display the arp and rarp field of the ace."
 ::= { fgs2924rAclInfoViewEntry 13 }

fgs2924rArpRequestReply OBJECT-TYPE
 SYNTAX  DisplayString
 MAX-ACCESS     read-only
 STATUS  current
 DESCRIPTION
  "Display the arp-request and arp-replay field of the ace."
 ::= { fgs2924rAclInfoViewEntry 14 }

fgs2924rArpSenderIpFilter OBJECT-TYPE
 SYNTAX  DisplayString
 MAX-ACCESS     read-only
 STATUS  current
 DESCRIPTION
  "Display the arp sender ip filter field of the ace."
 ::= { fgs2924rAclInfoViewEntry 15 }

fgs2924rArpSenderIpAddress OBJECT-TYPE
 SYNTAX  DisplayString
 MAX-ACCESS     read-only
 STATUS  current
 DESCRIPTION
  "Display the arp sender ip address field of the ace."
 ::= { fgs2924rAclInfoViewEntry 16 }

fgs2924rArpSenderIpMask OBJECT-TYPE
 SYNTAX  DisplayString
 MAX-ACCESS     read-only
 STATUS  current
 DESCRIPTION
  "Display the arp sender ip mask field of the ace."
 ::= { fgs2924rAclInfoViewEntry 17 }

fgs2924rArpTargetIpFilter OBJECT-TYPE
 SYNTAX  DisplayString
 MAX-ACCESS     read-only
 STATUS  current
 DESCRIPTION
  "Display the arp target ip filter field of the ace."
 ::= { fgs2924rAclInfoViewEntry 18 }

fgs2924rArpTargetIpAddress OBJECT-TYPE
 SYNTAX  DisplayString
 MAX-ACCESS     read-only
 STATUS  current
 DESCRIPTION
  "Display the arp target ip address field of the ace."
 ::= { fgs2924rAclInfoViewEntry 19 }

fgs2924rArpTargetIpMask OBJECT-TYPE
 SYNTAX  DisplayString
 MAX-ACCESS     read-only
 STATUS  current
 DESCRIPTION
  "Display the arp target ip mask field of the ace."
 ::= { fgs2924rAclInfoViewEntry 20 }

fgs2924rArpSmacMatch OBJECT-TYPE
 SYNTAX  DisplayString
 MAX-ACCESS     read-only
 STATUS  current
 DESCRIPTION
  "Display the arp smac match field of the ace."
 ::= { fgs2924rAclInfoViewEntry 21 }

fgs2924rArpRarpDmacMatch OBJECT-TYPE
 SYNTAX  DisplayString
 MAX-ACCESS     read-only
 STATUS  current
 DESCRIPTION
  "Display the rarp dmac match field of the ace."
 ::= { fgs2924rAclInfoViewEntry 22 }

fgs2924rArpIpEthernetLength OBJECT-TYPE
 SYNTAX  DisplayString
 MAX-ACCESS     read-only
 STATUS  current
 DESCRIPTION
  "Display the rarp ethernet length field of the ace."
 ::= { fgs2924rAclInfoViewEntry 23 }

fgs2924rArpIp OBJECT-TYPE
 SYNTAX  DisplayString
 MAX-ACCESS     read-only
 STATUS  current
 DESCRIPTION
  "Display the arp ip field of the ace."
 ::= { fgs2924rAclInfoViewEntry 24 }

fgs2924rArpEthernet OBJECT-TYPE
 SYNTAX  DisplayString
 MAX-ACCESS     read-only
 STATUS  current
 DESCRIPTION
  "Display the arp ethernet field of the ace."
 ::= { fgs2924rAclInfoViewEntry 25 }

fgs2924rIpProtocolFilter OBJECT-TYPE
 SYNTAX  DisplayString
 MAX-ACCESS     read-only
 STATUS  current
 DESCRIPTION
  "Display the ip protocol filter field of the ace."
 ::= { fgs2924rAclInfoViewEntry 26 }

fgs2924rIpProtocolValue OBJECT-TYPE
 SYNTAX  DisplayString
 MAX-ACCESS     read-only
 STATUS  current
 DESCRIPTION
  "Display the ip protocol value field of the ace."
 ::= { fgs2924rAclInfoViewEntry 27 }

fgs2924rIpTTL OBJECT-TYPE
 SYNTAX  DisplayString
 MAX-ACCESS     read-only
 STATUS  current
 DESCRIPTION
  "Display the ip ttl field of the ace. "
 ::= { fgs2924rAclInfoViewEntry 28 }

fgs2924rIpFragment OBJECT-TYPE
 SYNTAX  DisplayString
 MAX-ACCESS     read-only
 STATUS  current
 DESCRIPTION
  "Display the ip fragment field of the ace."
 ::= { fgs2924rAclInfoViewEntry 29 }

fgs2924rIpOption OBJECT-TYPE
 SYNTAX  DisplayString
 MAX-ACCESS     read-only
 STATUS  current
 DESCRIPTION
  "Display the ip option field of the ace."
 ::= { fgs2924rAclInfoViewEntry 30 }

fgs2924rSipFilter OBJECT-TYPE
 SYNTAX  DisplayString
 MAX-ACCESS     read-only
 STATUS  current
 DESCRIPTION
  "Display the sip filter field of the ace."
 ::= { fgs2924rAclInfoViewEntry 31 }

fgs2924rSipAddress OBJECT-TYPE
 SYNTAX  DisplayString
 MAX-ACCESS     read-only
 STATUS  current
 DESCRIPTION
  "Display the sip address field of the ace."
 ::= { fgs2924rAclInfoViewEntry 32 }

fgs2924rSipMask OBJECT-TYPE
 SYNTAX  DisplayString
 MAX-ACCESS     read-only
 STATUS  current
 DESCRIPTION
  "Display the sip mask field of the ace."
 ::= { fgs2924rAclInfoViewEntry 33 }

fgs2924rDipFilter OBJECT-TYPE
 SYNTAX  DisplayString
 MAX-ACCESS     read-only
 STATUS  current
 DESCRIPTION
  "Display the dip filter field of the ace."
 ::= { fgs2924rAclInfoViewEntry 34 }

fgs2924rDipAddress OBJECT-TYPE
 SYNTAX  DisplayString
 MAX-ACCESS     read-only
 STATUS  current
 DESCRIPTION
  "Display the dip address field of the ace."
 ::= { fgs2924rAclInfoViewEntry 35 }

fgs2924rDipMask OBJECT-TYPE
 SYNTAX  DisplayString
 MAX-ACCESS     read-only
 STATUS  current
 DESCRIPTION
  "Display the dip mask field of the ace."
 ::= { fgs2924rAclInfoViewEntry 36 }

fgs2924rIcmpTypeFilter OBJECT-TYPE
 SYNTAX  DisplayString
 MAX-ACCESS     read-only
 STATUS  current
 DESCRIPTION
  "Display the icmp type field of the ace."
 ::= { fgs2924rAclInfoViewEntry 37 }

fgs2924rIcmpCodeFilter OBJECT-TYPE
 SYNTAX  DisplayString
 MAX-ACCESS     read-only
 STATUS  current
 DESCRIPTION
  "Display the icmp code field of the ace."
 ::= { fgs2924rAclInfoViewEntry 38 }

fgs2924rUdpSourcePortFilter OBJECT-TYPE
 SYNTAX  DisplayString
 MAX-ACCESS     read-only
 STATUS  current
 DESCRIPTION
  "Display the udp source port field of the ace."
 ::= { fgs2924rAclInfoViewEntry 39 }

fgs2924rUdpDestPortFilter OBJECT-TYPE
 SYNTAX  DisplayString
 MAX-ACCESS     read-only
 STATUS  current
 DESCRIPTION
  "Display the udp destination port field of the ace."
 ::= { fgs2924rAclInfoViewEntry 40 }

fgs2924rTcpSourcePortFilter OBJECT-TYPE
 SYNTAX  DisplayString
 MAX-ACCESS     read-only
 STATUS  current
 DESCRIPTION
  "Display the tcp source port field of the ace."
 ::= { fgs2924rAclInfoViewEntry 41 }

fgs2924rTcpDestPortFilter OBJECT-TYPE
 SYNTAX  DisplayString
 MAX-ACCESS     read-only
 STATUS  current
 DESCRIPTION
  "Display the tcp destination port field of the ace."
 ::= { fgs2924rAclInfoViewEntry 42 }

fgs2924rTcpFIN OBJECT-TYPE
 SYNTAX  DisplayString
 MAX-ACCESS     read-only
 STATUS  current
 DESCRIPTION
  "Display the tcp fin field of the ace."
 ::= { fgs2924rAclInfoViewEntry 43 }

fgs2924rTcpSYN OBJECT-TYPE
 SYNTAX  DisplayString
 MAX-ACCESS     read-only
 STATUS  current
 DESCRIPTION
  "Display the tcp syn field of the ace."
 ::= { fgs2924rAclInfoViewEntry 44 }

fgs2924rTcpRST OBJECT-TYPE
 SYNTAX  DisplayString
 MAX-ACCESS     read-only
 STATUS  current
 DESCRIPTION
  "Display the tcp rst field of the ace."
 ::= { fgs2924rAclInfoViewEntry 45 }

fgs2924rTcpPSH OBJECT-TYPE
 SYNTAX  DisplayString
 MAX-ACCESS     read-only
 STATUS  current
 DESCRIPTION
  "Display the tcp psh field of the ace."
 ::= { fgs2924rAclInfoViewEntry 46 }

fgs2924rTcpACK OBJECT-TYPE
 SYNTAX  DisplayString
 MAX-ACCESS     read-only
 STATUS  current
 DESCRIPTION
  "Display the tcp ack field of the ace."
 ::= { fgs2924rAclInfoViewEntry 47 }

fgs2924rTcpURG OBJECT-TYPE
 SYNTAX  DisplayString
 MAX-ACCESS     read-only
 STATUS  current
 DESCRIPTION
  "Display the tcp urg field of the ace."
 ::= { fgs2924rAclInfoViewEntry 48 }

fgs2924rAclInfoEntryAction OBJECT-TYPE
 SYNTAX  INTEGER(1..4)
 MAX-ACCESS     read-write
 STATUS  current
 DESCRIPTION
  "1. set the entry active / the entry is active when get state.
   2. edit the specific entry.
   3. delete the specific entry.
   4. undo. free the buffer."
 ::= { fgs2924rAclInfoViewEntry 49 }


fgs2924rAclInfoConf           OBJECT IDENTIFIER ::= { fgs2924rAclInfo 4 }

fgs2924rAceNo OBJECT-TYPE
 SYNTAX  INTEGER(0..128)
 MAX-ACCESS     read-write
 STATUS  current
 DESCRIPTION
  "set 1 will create an ACL entry for edit, and return the entry index.
  others will return 0."
 ::= { fgs2924rAclInfoConf 1 }

fgs2924rAceMoveTo OBJECT-TYPE
 SYNTAX  INTEGER(1..128)
 MAX-ACCESS     read-write
 STATUS  current
 DESCRIPTION
  "Move the ace entry."
 ::= { fgs2924rAclInfoConf 2 }

fgs2924rAceIngressPortConf OBJECT-TYPE
 SYNTAX  DisplayString
 MAX-ACCESS     read-write
 STATUS  current
 DESCRIPTION
  "This is the ingress port number of the ace.
  Available parameter: any, Policy1~8, Port1~8."
 ::= { fgs2924rAclInfoConf 3 }

fgs2924rAceFrameTypeConf OBJECT-TYPE
 SYNTAX  INTEGER(0..3)
 MAX-ACCESS     read-write
 STATUS  current
 DESCRIPTION
  "This is the frame type of the ace.
  0:any 1: ethernet type 2:ARP 3:Ipv4 [default:0]"
 ::= { fgs2924rAclInfoConf 4 }

fgs2924rAceFrameTypeParameters           OBJECT IDENTIFIER ::= { fgs2924rAclInfoConf 5 }

fgs2924rEthernetTypeFilter OBJECT-TYPE
 SYNTAX  DisplayString
 MAX-ACCESS     read-write
 STATUS  current
 DESCRIPTION
  "This is the ethernet type of the ace."
 ::= { fgs2924rAceFrameTypeParameters 1 }

fgs2924rAclArpParameters           OBJECT IDENTIFIER ::= { fgs2924rAceFrameTypeParameters 2 }

fgs2924rAceArpRarp OBJECT-TYPE
 SYNTAX  INTEGER(0..3)
 MAX-ACCESS     read-write
 STATUS  current
 DESCRIPTION
  "This is the arp type of the ace.
  0:Any 1:Arp 2:Rarp 3:Other [default:0] "
 ::= { fgs2924rAclArpParameters 1 }

fgs2924rAceArpRequestReply OBJECT-TYPE
 SYNTAX  INTEGER(0..2)
 MAX-ACCESS     read-write
 STATUS  current
 DESCRIPTION
  "0:Any 1:Request 2:Reply [default:0]  "
 ::= { fgs2924rAclArpParameters 2 }

fgs2924rAceArpSenderIpFilter OBJECT-TYPE
 SYNTAX  INTEGER(0..2)
 MAX-ACCESS     read-write
 STATUS  current
 DESCRIPTION
  "0:Any 1:Host 2:Network"
 ::= { fgs2924rAclArpParameters 3 }

fgs2924rAceArpSenderIpAddress OBJECT-TYPE
 SYNTAX  DisplayString
 MAX-ACCESS     read-write
 STATUS  current
 DESCRIPTION
  "This is the arp sender ip address of the ace."
 ::= { fgs2924rAclArpParameters 4 }

fgs2924rAceArpSenderIpMask OBJECT-TYPE
 SYNTAX  DisplayString
 MAX-ACCESS     read-write
 STATUS  current
 DESCRIPTION
  "This is the arp sender ip mask of the ace."
 ::= { fgs2924rAclArpParameters 5 }

fgs2924rAceArpTargetIpFilter OBJECT-TYPE
 SYNTAX  INTEGER(0..2)
 MAX-ACCESS     read-write
 STATUS  current
 DESCRIPTION
  "0:Any 1:Host 2:Network  "
 ::= { fgs2924rAclArpParameters 6 }

fgs2924rAceArpTargetIpAddress OBJECT-TYPE
 SYNTAX  DisplayString
 MAX-ACCESS     read-write
 STATUS  current
 DESCRIPTION
  "0:Any 1:Host 2:Network  "
 ::= { fgs2924rAclArpParameters 7 }

fgs2924rAceArpTargetIpMask OBJECT-TYPE
 SYNTAX  DisplayString
 MAX-ACCESS     read-write
 STATUS  current
 DESCRIPTION
  "This is the arp target ip address of the ace."
 ::= { fgs2924rAclArpParameters 8 }

fgs2924rAceArpSmacMatch OBJECT-TYPE
 SYNTAX  DisplayString
 MAX-ACCESS     read-write
 STATUS  current
 DESCRIPTION
  "any / 0 / 1"
 ::= { fgs2924rAclArpParameters 9 }

fgs2924rAceArpRarpDmacMatch OBJECT-TYPE
 SYNTAX  DisplayString
 MAX-ACCESS     read-write
 STATUS  current
 DESCRIPTION
  "any / 0 / 1"
 ::= { fgs2924rAclArpParameters 10 }

fgs2924rAceArpIpEthernetLength OBJECT-TYPE
 SYNTAX  DisplayString
 MAX-ACCESS     read-write
 STATUS  current
 DESCRIPTION
  "any / 0 / 1"
 ::= { fgs2924rAclArpParameters 11 }

fgs2924rAceArpIp OBJECT-TYPE
 SYNTAX  DisplayString
 MAX-ACCESS     read-write
 STATUS  current
 DESCRIPTION
  "any / 0 / 1"
 ::= { fgs2924rAclArpParameters 12 }

fgs2924rAceArpEthernet OBJECT-TYPE
 SYNTAX  DisplayString
 MAX-ACCESS     read-write
 STATUS  current
 DESCRIPTION
  "any / 0 / 1"
 ::= { fgs2924rAclArpParameters 13 }


fgs2924rAclIpParameters           OBJECT IDENTIFIER ::= { fgs2924rAceFrameTypeParameters 3 }

fgs2924rAceIpProtocolFilter OBJECT-TYPE
 SYNTAX  INTEGER(0..4)
 MAX-ACCESS     read-write
 STATUS  current
 DESCRIPTION
  "This is the ip protocol of the ace.
  0:Any 1:ICMP 2:UDP 3:TCP 4:Other "
 ::= { fgs2924rAclIpParameters 1 }

fgs2924rAceIpProtocolFilterParameters          OBJECT IDENTIFIER ::= { fgs2924rAclIpParameters 2 }

fgs2924rAceIcmpParameters          OBJECT IDENTIFIER ::= { fgs2924rAceIpProtocolFilterParameters 1 }

fgs2924rAceIcmpTypeFilter OBJECT-TYPE
 SYNTAX  DisplayString
 MAX-ACCESS     read-write
 STATUS  current
 DESCRIPTION
  "This is the icmp type filter of the ace."
 ::= { fgs2924rAceIcmpParameters 1 }

fgs2924rAceIcmpCodeFilter OBJECT-TYPE
 SYNTAX  DisplayString
 MAX-ACCESS     read-write
 STATUS  current
 DESCRIPTION
  "This is the icmp code filter of the ace."
 ::= { fgs2924rAceIcmpParameters 2 }

fgs2924rAceUdpParameters         OBJECT IDENTIFIER ::= { fgs2924rAceIpProtocolFilterParameters 2 }

fgs2924rUdpSourcePortFilterConf OBJECT-TYPE
 SYNTAX  DisplayString
 MAX-ACCESS     read-write
 STATUS  current
 DESCRIPTION
  "This is the udp source port of the ace."
 ::= { fgs2924rAceUdpParameters 1 }

fgs2924rUdpDestPortFilterConf OBJECT-TYPE
 SYNTAX  DisplayString
 MAX-ACCESS     read-write
 STATUS  current
 DESCRIPTION
  "This is the udp destination port of the ace."
 ::= { fgs2924rAceUdpParameters 2 }

fgs2924rAceTcpParameters          OBJECT IDENTIFIER ::= { fgs2924rAceIpProtocolFilterParameters 3 }

fgs2924rTcpSourcePortFilterConf OBJECT-TYPE
 SYNTAX  DisplayString
 MAX-ACCESS     read-write
 STATUS  current
 DESCRIPTION
  "This is the tcp source port of the ace."
 ::= { fgs2924rAceTcpParameters 1 }

fgs2924rTcpDestPortFilterConf OBJECT-TYPE
 SYNTAX  DisplayString
 MAX-ACCESS     read-write
 STATUS  current
 DESCRIPTION
  "This is the tcp destination port of the ace."
 ::= { fgs2924rAceTcpParameters 2 }

fgs2924rTcpFINConf OBJECT-TYPE
 SYNTAX  DisplayString
 MAX-ACCESS     read-write
 STATUS  current
 DESCRIPTION
  "This is the tcp fin of the ace."
 ::= { fgs2924rAceTcpParameters 3 }

fgs2924rTcpSYNConf OBJECT-TYPE
 SYNTAX  DisplayString
 MAX-ACCESS     read-write
 STATUS  current
 DESCRIPTION
  "This is the tcp syn of the ace."
 ::= { fgs2924rAceTcpParameters 4 }

fgs2924rTcpRSTConf OBJECT-TYPE
 SYNTAX  DisplayString
 MAX-ACCESS     read-write
 STATUS  current
 DESCRIPTION
  "This is the tcp rst of the ace."
 ::= { fgs2924rAceTcpParameters 5 }

fgs2924rTcpPSHConf OBJECT-TYPE
 SYNTAX  DisplayString
 MAX-ACCESS     read-write
 STATUS  current
 DESCRIPTION
  "This is the tcp psh of the ace."
 ::= { fgs2924rAceTcpParameters 6 }

fgs2924rTcpACKConf OBJECT-TYPE
 SYNTAX  DisplayString
 MAX-ACCESS     read-write
 STATUS  current
 DESCRIPTION
  "This is the tcp ack of the ace."
 ::= { fgs2924rAceTcpParameters 7 }

fgs2924rTcpURGConf OBJECT-TYPE
 SYNTAX  DisplayString
 MAX-ACCESS     read-write
 STATUS  current
 DESCRIPTION
  "This is the tcp urg of the ace."
 ::= { fgs2924rAceTcpParameters 8 }


fgs2924rAceIpProtocolValue OBJECT-TYPE
 SYNTAX  INTEGER(0..4)
 MAX-ACCESS     read-write
 STATUS  current
 DESCRIPTION
  "This is the tcp protocol value of the ace."
 ::= { fgs2924rAclIpParameters 3 }

fgs2924rAceIpTTL OBJECT-TYPE
 SYNTAX  DisplayString
 MAX-ACCESS     read-write
 STATUS  current
 DESCRIPTION
  "Any / Zero / Non-zero "
 ::= { fgs2924rAclIpParameters 4 }

fgs2924rAceIpFragment OBJECT-TYPE
 SYNTAX  DisplayString
 MAX-ACCESS     read-write
 STATUS  current
 DESCRIPTION
  "Any/ Yes / No  "
 ::= { fgs2924rAclIpParameters 5 }

fgs2924rAceIpOption OBJECT-TYPE
 SYNTAX  DisplayString
 MAX-ACCESS     read-write
 STATUS  current
 DESCRIPTION
  "Any/ Yes / No  "
 ::= { fgs2924rAclIpParameters 6 }

fgs2924rAceSipFilter OBJECT-TYPE
 SYNTAX  INTEGER(0..2)
 MAX-ACCESS     read-write
 STATUS  current
 DESCRIPTION
  "0:Any 1:Host 2:Network"
 ::= { fgs2924rAclIpParameters 7 }

fgs2924rAceSipAddress OBJECT-TYPE
 SYNTAX  DisplayString
 MAX-ACCESS     read-write
 STATUS  current
 DESCRIPTION
  "This is the source ip address of the ace."
 ::= { fgs2924rAclIpParameters 8 }

fgs2924rAceSipMask OBJECT-TYPE
 SYNTAX  DisplayString
 MAX-ACCESS     read-write
 STATUS  current
 DESCRIPTION
  "This is the source ip mask of the ace."
 ::= { fgs2924rAclIpParameters 9 }

fgs2924rAceDipFilter OBJECT-TYPE
 SYNTAX  INTEGER(0..2)
 MAX-ACCESS     read-write
 STATUS  current
 DESCRIPTION
  "0:Any 1:Host 2:Network"
 ::= { fgs2924rAclIpParameters 10 }

fgs2924rAceDipAddress OBJECT-TYPE
 SYNTAX  DisplayString
 MAX-ACCESS     read-write
 STATUS  current
 DESCRIPTION
  "This is the destination ip address of the ace."
 ::= { fgs2924rAclIpParameters 11 }

fgs2924rAceDipMask OBJECT-TYPE
 SYNTAX  DisplayString
 MAX-ACCESS     read-write
 STATUS  current
 DESCRIPTION
  "This is the destination ip mask of the ace."
 ::= { fgs2924rAclIpParameters 12 }


fgs2924rAceActionConf OBJECT-TYPE
 SYNTAX  INTEGER(0|1)
 MAX-ACCESS     read-write
 STATUS  current
 DESCRIPTION
  "0:Deny 1:Permit [default:1] "
 ::= { fgs2924rAclInfoConf 6 }

fgs2924rAceRateLimiterConf OBJECT-TYPE
 SYNTAX  INTEGER(0..16)
 MAX-ACCESS     read-write
 STATUS  current
 DESCRIPTION
  "Specify a rate limiter which is available from 0 to 16(0 means disable) for an ACE."
 ::= { fgs2924rAclInfoConf 7 }

fgs2924rAcePortCopyConf OBJECT-TYPE
 SYNTAX  INTEGER(0..24)
 MAX-ACCESS     read-write
 STATUS  current
 DESCRIPTION
  "Packets will be copied to this port if hit this ACE rule.
  Port number is available from 0 to 24(0 means disable)."
 ::= { fgs2924rAclInfoConf 8 }

fgs2924rAceMacParameters           OBJECT IDENTIFIER ::= { fgs2924rAclInfoConf 9 }

fgs2924rAceSmacFilter OBJECT-TYPE
 SYNTAX  DisplayString
 MAX-ACCESS     read-write
 STATUS  current
 DESCRIPTION
  "This is the source mac of the ace."
 ::= { fgs2924rAceMacParameters 1 }

fgs2924rAceDmacFilter OBJECT-TYPE
 SYNTAX  DisplayString
 MAX-ACCESS     read-write
 STATUS  current
 DESCRIPTION
  "This is the destination mac of the ace."
 ::= { fgs2924rAceMacParameters 2 }


fgs2924rAceVlanParameters           OBJECT IDENTIFIER ::= { fgs2924rAclInfoConf 10 }

fgs2924rAceVlanIdFilter OBJECT-TYPE
 SYNTAX  DisplayString
 MAX-ACCESS     read-write
 STATUS  current
 DESCRIPTION
  "Specify the VID for the ACE. Available parameter: any, 1~4094."
 ::= { fgs2924rAceVlanParameters 1 }

fgs2924rAceTagPriority OBJECT-TYPE
 SYNTAX  DisplayString
 MAX-ACCESS     read-write
 STATUS  current
 DESCRIPTION
  "Specify the tag priority for the ACE. Available parameter: any, 0~7."
 ::= { fgs2924rAceVlanParameters 2 }


fgs2924rAceInfoEntryAction OBJECT-TYPE
 SYNTAX  INTEGER(1..4)
 MAX-ACCESS     read-write
 STATUS  current
 DESCRIPTION
  "1:active 2:notInService 3:delete 4:Undo "
 ::= { fgs2924rAclInfoConf 11 }

fgs2924rIpMacBind            OBJECT IDENTIFIER ::= { fgs2924rProduces 19 }

fgs2924rIpMacBindConf           OBJECT IDENTIFIER ::= { fgs2924rIpMacBind 1 }

fgs2924rIpMacBindstate OBJECT-TYPE
 SYNTAX  INTEGER(0|1)
 MAX-ACCESS     read-write
 STATUS  current
 DESCRIPTION
  " Set ip mac binding state.
   0 - Disable
   1 - Enable"
 ::= { fgs2924rIpMacBindConf 1 }

fgs2924rIpMacBindTrustPort OBJECT-TYPE
 SYNTAX  DisplayString
 MAX-ACCESS     read-write
 STATUS  current
 DESCRIPTION
  "Set trustport,
   Port range : 1,5-7, available from 1 to 24"
 ::= { fgs2924rIpMacBindConf 2 }

fgs2924rIpMacBindSetting           OBJECT IDENTIFIER ::= { fgs2924rIpMacBind 2 }

fgs2924rIpMacBindSettingNumber OBJECT-TYPE
 SYNTAX  INTEGER(0..1024)
 MAX-ACCESS     read-write
 STATUS  current
 DESCRIPTION
  "Get the amount of ip_mac_binding entry."
 ::= { fgs2924rIpMacBindSetting 1 }

fgs2924rIpMacBindSettingEntryCreate OBJECT-TYPE
 SYNTAX  INTEGER(0|1)
 MAX-ACCESS     read-write
 STATUS  current
 DESCRIPTION
  "Create ip_mac_binding entry.
   0: none
   1: creat a entry."
 ::= { fgs2924rIpMacBindSetting 2 }

fgs2924rIpMacBindSettingTable OBJECT-TYPE
 SYNTAX  SEQUENCE OF FGS2924RIpMacBindSettingEntry
 MAX-ACCESS not-accessible
 STATUS  current
    DESCRIPTION
        "This is a list of FGS2924RIpMacBindSettingEntry."
 ::= { fgs2924rIpMacBindSetting 3 }

FGS2924RIpMacBindSettingEntry ::=
SEQUENCE {
    fgs2924rIpMacBindSettingIndex        INTEGER,
    fgs2924rIpMacBindSettingMAC          DisplayString,
    fgs2924rIpMacBindSettingIP           IpAddress,
    fgs2924rIpMacBindSettingPort         INTEGER,
    fgs2924rIpMacBindSettingVID          INTEGER,
    fgs2924rIpMacBindSettingEntryAction  INTEGER
}

fgs2924rIpMacBindSettingEntry OBJECT-TYPE
 SYNTAX  FGS2924RIpMacBindSettingEntry
 MAX-ACCESS     not-accessible
 STATUS  current
 DESCRIPTION
  "This is the entry of the ip_mac_binding information."
 INDEX {fgs2924rIpMacBindSettingIndex}
 ::= { fgs2924rIpMacBindSettingTable 1 }

fgs2924rIpMacBindSettingIndex OBJECT-TYPE
 SYNTAX  INTEGER(1..1024)
 MAX-ACCESS     not-accessible
 STATUS  current
 DESCRIPTION
  "This is the index of the ip_mac_binding entry."
 ::= { fgs2924rIpMacBindSettingEntry 1 }

fgs2924rIpMacBindSettingMAC OBJECT-TYPE
 SYNTAX  DisplayString
 MAX-ACCESS     read-write
 STATUS  current
 DESCRIPTION
  "This is the mac address of the ip_mac_binding entry."
 ::= { fgs2924rIpMacBindSettingEntry 2 }

fgs2924rIpMacBindSettingIP OBJECT-TYPE
 SYNTAX  IpAddress
 MAX-ACCESS     read-write
 STATUS  current
 DESCRIPTION
  "This is the ip address of the ip_mac_binding entry."
 ::= { fgs2924rIpMacBindSettingEntry 3 }

fgs2924rIpMacBindSettingPort OBJECT-TYPE
 SYNTAX  INTEGER(1..24)
 MAX-ACCESS     read-write
 STATUS  current
 DESCRIPTION
  "This is the port number of the ip_mac_binding entry."
 ::= { fgs2924rIpMacBindSettingEntry 4 }

fgs2924rIpMacBindSettingVID OBJECT-TYPE
 SYNTAX  INTEGER(1..4094)
 MAX-ACCESS     read-write
 STATUS  current
 DESCRIPTION
  "This is the vid of the ip_mac_binding entry."
 ::= { fgs2924rIpMacBindSettingEntry 5 }

fgs2924rIpMacBindSettingEntryAction OBJECT-TYPE
 SYNTAX  INTEGER(1..3)
 MAX-ACCESS     read-write
 STATUS  current
 DESCRIPTION
  "This is the action of the ip_mac_binding entry.
   1 - active
   2 - notInService
   3 - delete"
 ::= { fgs2924rIpMacBindSettingEntry 6 }

fgs2924rDot1X            OBJECT IDENTIFIER ::= { fgs2924rProduces 23 }

fgs2924rDot1XServerConf           OBJECT IDENTIFIER ::= { fgs2924rDot1X 1 }

fgs2924rDot1XServerConfAuthenticationServerIp OBJECT-TYPE
 SYNTAX  IpAddress
 MAX-ACCESS     read-write
 STATUS  current
 DESCRIPTION
  "Get/Set authentication server ip"
 ::= { fgs2924rDot1XServerConf 1 }

fgs2924rDot1XServerConfAuthenticationUdpPort OBJECT-TYPE
 SYNTAX  INTEGER(1..65535)
 MAX-ACCESS     read-write
 STATUS  current
 DESCRIPTION
  "Get/Set IEEE 802.1X authentication UDP port number"
 ::= { fgs2924rDot1XServerConf 2 }

fgs2924rDot1XServerConfAuthenticationServerIp2 OBJECT-TYPE
 SYNTAX  IpAddress
 MAX-ACCESS     read-write
 STATUS  current
 DESCRIPTION
  "Get/Set authentication server ip 2"
 ::= { fgs2924rDot1XServerConf 3 }

fgs2924rDot1XServerConfAuthenticationUdpPort2 OBJECT-TYPE
 SYNTAX  INTEGER(1..65535)
 MAX-ACCESS     read-write
 STATUS  current
 DESCRIPTION
  "Get/Set IEEE 802.1X authentication UDP port number"
 ::= { fgs2924rDot1XServerConf 4 }

fgs2924rDot1XServerConfAuthenticationSecretKey OBJECT-TYPE
 SYNTAX  DisplayString
 MAX-ACCESS     read-write
 STATUS  current
 DESCRIPTION
  "Get/Set IEEE 802.1X authentication secret key"
 ::= { fgs2924rDot1XServerConf 5 }

fgs2924rDot1XServerConfAccountingServerIp OBJECT-TYPE
 SYNTAX  IpAddress
 MAX-ACCESS     read-write
 STATUS  current
 DESCRIPTION
  "Get/Set IEEE 802.1X accounting service IP"
 ::= { fgs2924rDot1XServerConf 6 }

fgs2924rDot1XServerConfAccountingUdpPort OBJECT-TYPE
 SYNTAX  INTEGER(1..65535)
 MAX-ACCESS     read-write
 STATUS  current
 DESCRIPTION
  "Get/Set IEEE 802.1X accounting UDP port number"
 ::= { fgs2924rDot1XServerConf 7 }

fgs2924rDot1XServerConfAccountingServerIp2 OBJECT-TYPE
 SYNTAX  IpAddress
 MAX-ACCESS     read-write
 STATUS  current
 DESCRIPTION
  "Get/Set IEEE 802.1X accounting service IP 2"
 ::= { fgs2924rDot1XServerConf 8 }

fgs2924rDot1XServerConfAccountingUdpPort2 OBJECT-TYPE
 SYNTAX  INTEGER(1..65535)
 MAX-ACCESS     read-write
 STATUS  current
 DESCRIPTION
  "Get/Set IEEE 802.1X accounting UDP port number"
 ::= { fgs2924rDot1XServerConf 9 }

fgs2924rDot1XServerConfAccountingSecretKey OBJECT-TYPE
 SYNTAX  DisplayString
 MAX-ACCESS     read-write
 STATUS  current
 DESCRIPTION
  "Get/Set IEEE 802.1X accounting secret key"
 ::= { fgs2924rDot1XServerConf 10 }

fgs2924rDot1XPortConfTable OBJECT-TYPE
 SYNTAX  SEQUENCE OF FGS2924RDot1XPortConfEntry
 MAX-ACCESS not-accessible
 STATUS  current
    DESCRIPTION
        "A table that contains the configuration objects for the
         Authenticator PAE associated with each port."
 ::= { fgs2924rDot1X 2 }

FGS2924RDot1XPortConfEntry ::=
SEQUENCE {
    fgs2924rDot1XPort                INTEGER,
    fgs2924rDot1XPortMode            INTEGER,
    fgs2924rDot1XPortControl         INTEGER,
    fgs2924rDot1XPortreAuthMax       INTEGER,
    fgs2924rDot1XPorttxPeriod        INTEGER,
    fgs2924rDot1XPortquietPeriod     INTEGER,
    fgs2924rDot1XPortreAuthEnabled   INTEGER,
    fgs2924rDot1XPortreAuthPeriod    INTEGER,
    fgs2924rDot1XPortmaxReq          INTEGER,
    fgs2924rDot1XPortsuppTimeout     INTEGER,
    fgs2924rDot1XPortserverTimeout   INTEGER,
    fgs2924rDot1XPortVlanAssignment  INTEGER,
    fgs2924rDot1XPortGuestVlan       INTEGER,
    fgs2924rDot1XPortAuthFailedVlan  INTEGER
}

fgs2924rDot1XPortConfEntry OBJECT-TYPE
 SYNTAX  FGS2924RDot1XPortConfEntry
 MAX-ACCESS     not-accessible
 STATUS  current
 DESCRIPTION
  "The configuration information for an Authenticator PAE."
 INDEX {fgs2924rDot1XPort}
 ::= { fgs2924rDot1XPortConfTable 1 }

fgs2924rDot1XPort OBJECT-TYPE
 SYNTAX  INTEGER(1..24)
 MAX-ACCESS     read-write
 STATUS  current
 DESCRIPTION
   "The port index of 802.1X port configuration table."
 ::= { fgs2924rDot1XPortConfEntry 1 }

fgs2924rDot1XPortMode OBJECT-TYPE
 SYNTAX  INTEGER(0..4)
 MAX-ACCESS     read-write
 STATUS  current
 DESCRIPTION
  "Get/Set IEEE 802.1X port mode.
   0 - Disable
   1 - Normal
   2 - Advanced
   3 - Clientless
   4 - Auto"
 ::= { fgs2924rDot1XPortConfEntry 2 }

fgs2924rDot1XPortControl OBJECT-TYPE
 SYNTAX  INTEGER(0..2)
 MAX-ACCESS     read-write
 STATUS  current
 DESCRIPTION
  "The current value of the controlled Port
   control parameter of the Port.
  0 : ForceUnauthorized,
  1 : ForceAuthorized,
  2 : Auto
        "
 ::= { fgs2924rDot1XPortConfEntry 3 }

fgs2924rDot1XPortreAuthMax OBJECT-TYPE
 SYNTAX  INTEGER(1..10)
 MAX-ACCESS     read-write
 STATUS  current
 DESCRIPTION
  "The value of the reAuthMax constant currently in use by
   the Authenticator PAE state machine. Value : 1-10."
 ::= { fgs2924rDot1XPortConfEntry 4 }


fgs2924rDot1XPorttxPeriod OBJECT-TYPE
 SYNTAX  INTEGER(1..65535)
 MAX-ACCESS     read-write
 STATUS  current
 DESCRIPTION
  "The value, in seconds, of the txPeriod constant
   currently in use by the Authenticator PAE state
   machine. Value : 1-65535."
 ::= { fgs2924rDot1XPortConfEntry 5 }

fgs2924rDot1XPortquietPeriod OBJECT-TYPE
 SYNTAX  INTEGER(0..65535)
 MAX-ACCESS     read-write
 STATUS  current
 DESCRIPTION
  "The value, in seconds, of the quietPeriod constant
   currently in use by the Authenticator PAE state
   machine. Value : 0-65535."
 ::= { fgs2924rDot1XPortConfEntry 6 }

fgs2924rDot1XPortreAuthEnabled OBJECT-TYPE
 SYNTAX  INTEGER(0|1)
 MAX-ACCESS     read-write
 STATUS  current
 DESCRIPTION
  "The enable/disable control used by the Reauthentication
   Timer state machine.
   0 - Disable
   1 - Enable"
 ::= { fgs2924rDot1XPortConfEntry 7 }

fgs2924rDot1XPortreAuthPeriod OBJECT-TYPE
 SYNTAX  INTEGER(1..65535)
 MAX-ACCESS     read-write
 STATUS  current
 DESCRIPTION
		"The value(1..65535), in seconds, of the reAuthPeriod constant
   currently in use by the Reauthentication Timer state
   machine."
 ::= { fgs2924rDot1XPortConfEntry 8 }

fgs2924rDot1XPortmaxReq OBJECT-TYPE
 SYNTAX  INTEGER(1..10)
 MAX-ACCESS     read-write
 STATUS  current
 DESCRIPTION
		"The value(1..10) of the maxReq constant currently in use by
   the Backend Authentication state machine."
 ::= { fgs2924rDot1XPortConfEntry 9 }

fgs2924rDot1XPortsuppTimeout OBJECT-TYPE
 SYNTAX  INTEGER(1..255)
 MAX-ACCESS     read-write
 STATUS  current
 DESCRIPTION
		"The value(1..255), in seconds, of the suppTimeout constant
   currently in use by the Backend Authentication state
   machine."
 ::= { fgs2924rDot1XPortConfEntry 10 }

fgs2924rDot1XPortserverTimeout OBJECT-TYPE
 SYNTAX  INTEGER(1..255)
 MAX-ACCESS     read-write
 STATUS  current
 DESCRIPTION
		"The value(1..255), in seconds, of the serverTimeout constant
   currently in use by the Backend Authentication state
   machine."
 ::= { fgs2924rDot1XPortConfEntry 11 }

fgs2924rDot1XPortVlanAssignment OBJECT-TYPE
 SYNTAX  INTEGER(0..1)
 MAX-ACCESS     read-write
 STATUS  current
 DESCRIPTION
  "Get/Set IEEE 802.1X's VlanAssignment mode.
   0 - Disable
   1 - Enable"
 ::= { fgs2924rDot1XPortConfEntry 12 }

fgs2924rDot1XPortGuestVlan OBJECT-TYPE
 SYNTAX  INTEGER(0..4094)
 MAX-ACCESS     read-write
 STATUS  current
 DESCRIPTION
  "Get/Set IEEE 802.1X Guest Vlan.
   0 : N/A
   1~4094 : The VlanID"
 ::= { fgs2924rDot1XPortConfEntry 13 }

fgs2924rDot1XPortAuthFailedVlan OBJECT-TYPE
 SYNTAX  INTEGER(0..4094)
 MAX-ACCESS     read-write
 STATUS  current
 DESCRIPTION
  "Get/Set IEEE 802.1X Authentication Failed Vlan.
   0 : N/A
   1~4094 : The VlanID"
 ::= { fgs2924rDot1XPortConfEntry 14 }

fgs2924rDot1XStatusTable OBJECT-TYPE
 SYNTAX  SEQUENCE OF FGS2924RDot1XStatusEntry
 MAX-ACCESS not-accessible
 STATUS  current
    DESCRIPTION
        "A table that contains the status objects for the
         Authenticator PAE associated with each port."
 ::= { fgs2924rDot1X 3 }

FGS2924RDot1XStatusEntry ::=
SEQUENCE {
    fgs2924rDot1XStatusIndex   INTEGER,
    fgs2924rDot1XStatusMode    DisplayString,
    fgs2924rDot1XStatusStatus  DisplayString,
    fgs2924rDot1XVlanPolicy     DisplayString
}

fgs2924rDot1XStatusEntry OBJECT-TYPE
 SYNTAX  FGS2924RDot1XStatusEntry
 MAX-ACCESS     not-accessible
 STATUS  current
 DESCRIPTION
  "The status information for an Authenticator PAE."
 INDEX {fgs2924rDot1XStatusIndex}
 ::= { fgs2924rDot1XStatusTable 1 }

fgs2924rDot1XStatusIndex OBJECT-TYPE
 SYNTAX  INTEGER(1..24)
 MAX-ACCESS     not-accessible
 STATUS  current
 DESCRIPTION
  "The port index of 802.1X status table."
 ::= { fgs2924rDot1XStatusEntry 1 }

fgs2924rDot1XStatusMode OBJECT-TYPE
 SYNTAX  DisplayString
 MAX-ACCESS     read-only
 STATUS  current
 DESCRIPTION
  "The current mode of the controlled port."
 ::= { fgs2924rDot1XStatusEntry 2 }

fgs2924rDot1XStatusStatus OBJECT-TYPE
 SYNTAX  DisplayString
 MAX-ACCESS     read-only
 STATUS  current
 DESCRIPTION
  "The current status of the controlled port."
 ::= { fgs2924rDot1XStatusEntry 3 }

fgs2924rDot1XVlanPolicy OBJECT-TYPE
 SYNTAX  DisplayString
 MAX-ACCESS     read-only
 STATUS  current
 DESCRIPTION
  "The current Vlan Policy of the controlled port."
 ::= { fgs2924rDot1XStatusEntry 4 }

fgs2924rDot1XStatisticsTable OBJECT-TYPE
 SYNTAX  SEQUENCE OF FGS2924RDot1XStatisticsEntry
 MAX-ACCESS not-accessible
 STATUS  current
    DESCRIPTION
        "A table that contains the statistics objects for the
         Authenticator PAE associated with each port."
 ::= { fgs2924rDot1X 4 }

FGS2924RDot1XStatisticsEntry ::=
SEQUENCE {
    fgs2924rDot1XStatisticsIndex                        INTEGER,
    fgs2924rDot1XClearCounter                           INTEGER,
    fgs2924rDot1XAuthEntersConnecting                   Counter32,
    fgs2924rDot1XauthEapLogoffsWhileConnecting          Counter32,
    fgs2924rDot1XAuthEntersAuthenticating               Counter32,
    fgs2924rDot1XAuthAuthSuccessesWhileAuthenticating   Counter32,
    fgs2924rDot1XAuthAuthTimeoutsWhileAuthenticating    Counter32,
    fgs2924rDot1XAuthAuthFailWhileAuthenticating        Counter32,
    fgs2924rDot1XAuthAuthEapStartsWhileAuthenticating   Counter32,
    fgs2924rDot1XAuthAuthEapLogoffWhileAuthenticating   Counter32,
    fgs2924rDot1XAuthAuthReauthsWhileAuthenticated      Counter32,
    fgs2924rDot1XAuthAuthEapStartsWhileAuthenticated    Counter32,
    fgs2924rDot1XAuthAuthEapLogoffWhileAuthenticated    Counter32,
    fgs2924rDot1XBackendResponses                       Counter32,
    fgs2924rDot1XBackendAccessChallenges                Counter32,
    fgs2924rDot1XBackendOtherRequestsToSupplicant       Counter32,
    fgs2924rDot1XBackendAuthSuccesses                   Counter32,
    fgs2924rDot1XBackendAuthFails                       Counter32,
    fgs2924rDot1XAuthEapolFramesRx                      Counter32,
    fgs2924rDot1XAuthEapolFramesTx                      Counter32,
    fgs2924rDot1XAuthEapolStartFramesRx                 Counter32,
    fgs2924rDot1XAuthEapolLogoffFramesRx                Counter32,
    fgs2924rDot1XAuthEapolRespIdFramesRx                Counter32,
    fgs2924rDot1XAuthEapolRespFramesRx                  Counter32,
    fgs2924rDot1XAuthEapolReqIdFramesTx                 Counter32,
    fgs2924rDot1XAuthEapolReqFramesTx                   Counter32,
    fgs2924rDot1XAuthInvalidEapolFramesRx               Counter32,
    fgs2924rDot1XAuthEapLengthErrorFramesRx             Counter32,
    fgs2924rDot1XAuthLastEapolFrameVersion              Counter32,
    fgs2924rDot1XAuthLastEapolFrameSource               DisplayString
}

fgs2924rDot1XStatisticsEntry OBJECT-TYPE
 SYNTAX  FGS2924RDot1XStatisticsEntry
 MAX-ACCESS     not-accessible
 STATUS  current
 DESCRIPTION
  "The statistics information for an Authenticator PAE."
 INDEX {fgs2924rDot1XStatisticsIndex}
 ::= { fgs2924rDot1XStatisticsTable 1 }

fgs2924rDot1XStatisticsIndex OBJECT-TYPE
 SYNTAX  INTEGER(1..24)
 MAX-ACCESS     not-accessible
 STATUS  current
 DESCRIPTION
  "The port index of the 802.1X statistics table."
 ::= { fgs2924rDot1XStatisticsEntry 1 }

fgs2924rDot1XClearCounter OBJECT-TYPE
 SYNTAX  INTEGER(0|1)
 MAX-ACCESS     read-write
 STATUS  current
 DESCRIPTION
  "Reset the 802.1X counter associated with this port.
   0 - do nothing
   1 - clear "
 ::= { fgs2924rDot1XStatisticsEntry 2 }

fgs2924rDot1XAuthEntersConnecting OBJECT-TYPE
 SYNTAX  Counter32
 MAX-ACCESS     read-only
 STATUS  current
 DESCRIPTION
  "Counts the number of times that the state machine
   transitions to the CONNECTING state from any other
   state."
 ::= { fgs2924rDot1XStatisticsEntry 3 }

fgs2924rDot1XauthEapLogoffsWhileConnecting OBJECT-TYPE
 SYNTAX  Counter32
 MAX-ACCESS     read-only
 STATUS  current
 DESCRIPTION
  "Counts the number of times that the state machine
   transitions from CONNECTING to DISCONNECTED as a result
   of receiving an EAPOL-Logoff message."
 ::= { fgs2924rDot1XStatisticsEntry 4 }

fgs2924rDot1XAuthEntersAuthenticating OBJECT-TYPE
 SYNTAX  Counter32
 MAX-ACCESS     read-only
 STATUS  current
 DESCRIPTION
  "Counts the number of times that the state machine
   transitions from CONNECTING to AUTHENTICATING, as a
   result of an EAP-Response/Identity message being
   received from the Supplicant."
 ::= { fgs2924rDot1XStatisticsEntry 5 }

fgs2924rDot1XAuthAuthSuccessesWhileAuthenticating OBJECT-TYPE
 SYNTAX  Counter32
 MAX-ACCESS     read-only
 STATUS  current
 DESCRIPTION
  "Counts the number of times that the state machine
   transitions from AUTHENTICATING to AUTHENTICATED, as a
   result of the Backend Authentication state machine
   indicating successful authentication of the Supplicant."
 ::= { fgs2924rDot1XStatisticsEntry 6 }

fgs2924rDot1XAuthAuthTimeoutsWhileAuthenticating OBJECT-TYPE
 SYNTAX  Counter32
 MAX-ACCESS     read-only
 STATUS  current
 DESCRIPTION
  "Counts the number of times that the state machine
   transitions from AUTHENTICATING to ABORTING, as a result
   of the Backend Authentication state machine indicating
   authentication timeout."
 ::= { fgs2924rDot1XStatisticsEntry 7 }

fgs2924rDot1XAuthAuthFailWhileAuthenticating OBJECT-TYPE
 SYNTAX  Counter32
 MAX-ACCESS     read-only
 STATUS  current
 DESCRIPTION
  "Counts the number of times that the state machine
   transitions from AUTHENTICATING to HELD, as a result
   of the Backend Authentication state machine indicating
   authentication failure."
 ::= { fgs2924rDot1XStatisticsEntry 8 }

fgs2924rDot1XAuthAuthEapStartsWhileAuthenticating OBJECT-TYPE
 SYNTAX  Counter32
 MAX-ACCESS     read-only
 STATUS  current
 DESCRIPTION
  "Counts the number of times that the state machine
   transitions from AUTHENTICATING to ABORTING, as a result
   of an EAPOL-Start message being received from the
   Supplicant."
 ::= { fgs2924rDot1XStatisticsEntry 9 }

fgs2924rDot1XAuthAuthEapLogoffWhileAuthenticating OBJECT-TYPE
 SYNTAX  Counter32
 MAX-ACCESS     read-only
 STATUS  current
 DESCRIPTION
  "Counts the number of times that the state machine
   transitions from AUTHENTICATING to ABORTING, as a result
   of an EAPOL-Logoff message being received from the
   Supplicant."
 ::= { fgs2924rDot1XStatisticsEntry 10 }

fgs2924rDot1XAuthAuthReauthsWhileAuthenticated OBJECT-TYPE
 SYNTAX  Counter32
 MAX-ACCESS     read-only
 STATUS  current
 DESCRIPTION
  "Counts the number of times that the state machine
   transitions from AUTHENTICATED to CONNECTING, as a
   result of a reauthentication request."
 ::= { fgs2924rDot1XStatisticsEntry 11 }

fgs2924rDot1XAuthAuthEapStartsWhileAuthenticated OBJECT-TYPE
 SYNTAX  Counter32
 MAX-ACCESS     read-only
 STATUS  current
 DESCRIPTION
  "Counts the number of times that the state machine
   transitions from AUTHENTICATED to CONNECTING, as a
   result of an EAPOL-Start message being received from
   the Supplicant."
 ::= { fgs2924rDot1XStatisticsEntry 12 }

fgs2924rDot1XAuthAuthEapLogoffWhileAuthenticated OBJECT-TYPE
 SYNTAX  Counter32
 MAX-ACCESS     read-only
 STATUS  current
 DESCRIPTION
  "Counts the number of times that the state machine
   transitions from AUTHENTICATED to DISCONNECTED, as a
   result of an EAPOL-Logoff message being received from
   the Supplicant."
 ::= { fgs2924rDot1XStatisticsEntry 13 }

fgs2924rDot1XBackendResponses OBJECT-TYPE
 SYNTAX  Counter32
 MAX-ACCESS     read-only
 STATUS  current
 DESCRIPTION
  "Counts the number of times that the state machine sends
   an initial Access-Request packet to the Authentication
   server (i.e., executes sendRespToServer on entry to the
   RESPONSE state). Indicates that the Authenticator
   attempted communication with the Authentication Server."
 ::= { fgs2924rDot1XStatisticsEntry 14 }

fgs2924rDot1XBackendAccessChallenges OBJECT-TYPE
 SYNTAX  Counter32
 MAX-ACCESS     read-only
 STATUS  current
 DESCRIPTION
  "Counts the number of times that the state machine receives
   an initial Access-Challenge packet from the Authentication
   server (i.e., aReq becomes TRUE, causing exit from the
   RESPONSE state). Indicates that the Authentication Server
   has communication with the Authenticator."
 ::= { fgs2924rDot1XStatisticsEntry 15 }

fgs2924rDot1XBackendOtherRequestsToSupplicant OBJECT-TYPE
 SYNTAX  Counter32
 MAX-ACCESS     read-only
 STATUS  current
 DESCRIPTION
  "Counts the number of times that the state machine sends
   an EAP-Request packet (other than Identity, Notification,
   Failure or Success message) to the Supplicant (i.e.,
   executes txReq on entry to the REQUEST state). Indicates
   that Authenticator chose an EAP-method."
 ::= { fgs2924rDot1XStatisticsEntry 16 }

fgs2924rDot1XBackendAuthSuccesses OBJECT-TYPE
 SYNTAX  Counter32
 MAX-ACCESS     read-only
 STATUS  current
 DESCRIPTION
  "Counts the number of times that the state machine receives
   an EAP-Success message from the Authentication Server (i.e.,
   aSuccess becomes TRUE, causing a transitions from RESPONSE to
   SUCCESS). Indicates that the Supplicant has successfully
   authenticated to the Authentication Server."
 ::= { fgs2924rDot1XStatisticsEntry 17 }

fgs2924rDot1XBackendAuthFails OBJECT-TYPE
 SYNTAX  Counter32
 MAX-ACCESS     read-only
 STATUS  current
 DESCRIPTION
  "Counts the number of times that the state machine receives
   an EAP-Failure message from the Authentication Server (i.e.,
   aFail becomes TRUE, causing a transitions from RESPONSE to
   FAIL). Indicates that the Supplicant has not authenticated
   to the Authentication Server."
 ::= { fgs2924rDot1XStatisticsEntry 18 }

fgs2924rDot1XAuthEapolFramesRx OBJECT-TYPE
 SYNTAX  Counter32
 MAX-ACCESS     read-only
 STATUS  current
 DESCRIPTION
  "The number of valid EAPOL frames of any type
   that have been received by this Authenticator."
 ::= { fgs2924rDot1XStatisticsEntry 19 }

fgs2924rDot1XAuthEapolFramesTx OBJECT-TYPE
 SYNTAX  Counter32
 MAX-ACCESS     read-only
 STATUS  current
 DESCRIPTION
  "The number of valid EAPOL frames of any type
   that have been transmitted by this Authenticator."
 ::= { fgs2924rDot1XStatisticsEntry 20 }

fgs2924rDot1XAuthEapolStartFramesRx OBJECT-TYPE
 SYNTAX  Counter32
 MAX-ACCESS     read-only
 STATUS  current
 DESCRIPTION
  "The number of EAPOL Start frames that have
   been received by this Authenticator."
 ::= { fgs2924rDot1XStatisticsEntry 21 }

fgs2924rDot1XAuthEapolLogoffFramesRx OBJECT-TYPE
 SYNTAX  Counter32
 MAX-ACCESS     read-only
 STATUS  current
 DESCRIPTION
  "The number of EAPOL Logoff frames that have
   been received by this Authenticator."
 ::= { fgs2924rDot1XStatisticsEntry 22 }

fgs2924rDot1XAuthEapolRespIdFramesRx OBJECT-TYPE
 SYNTAX  Counter32
 MAX-ACCESS     read-only
 STATUS  current
 DESCRIPTION
  "The number of EAP Resp/Id frames that have
   been received by this Authenticator."
 ::= { fgs2924rDot1XStatisticsEntry 23 }

fgs2924rDot1XAuthEapolRespFramesRx OBJECT-TYPE
 SYNTAX  Counter32
 MAX-ACCESS     read-only
 STATUS  current
 DESCRIPTION
  "The number of valid EAP Response frames
   (other than Resp/Id frames) that have been
   received by this Authenticator."
 ::= { fgs2924rDot1XStatisticsEntry 24 }

fgs2924rDot1XAuthEapolReqIdFramesTx OBJECT-TYPE
 SYNTAX  Counter32
 MAX-ACCESS     read-only
 STATUS  current
 DESCRIPTION
  "The number of EAP Req/Id frames that have
   been transmitted by this Authenticator."
 ::= { fgs2924rDot1XStatisticsEntry 25 }

fgs2924rDot1XAuthEapolReqFramesTx OBJECT-TYPE
 SYNTAX  Counter32
 MAX-ACCESS     read-only
 STATUS  current
 DESCRIPTION
  "The number of valid EAP Request frames
   (other than Req/Id frames) that have been
   transmitted by this Authenticator."
 ::= { fgs2924rDot1XStatisticsEntry 26 }

fgs2924rDot1XAuthInvalidEapolFramesRx OBJECT-TYPE
 SYNTAX  Counter32
 MAX-ACCESS     read-only
 STATUS  current
 DESCRIPTION
  "The number of EAPOL frames that have been
   received by this Authenticator in which the
   frame type is not recognized."
 ::= { fgs2924rDot1XStatisticsEntry 27 }

fgs2924rDot1XAuthEapLengthErrorFramesRx OBJECT-TYPE
 SYNTAX  Counter32
 MAX-ACCESS     read-only
 STATUS  current
 DESCRIPTION
  "The number of EAPOL frames that have been
   received by this Authenticator in which the
   Packet Body Length field is invalid."
 ::= { fgs2924rDot1XStatisticsEntry 28 }

fgs2924rDot1XAuthLastEapolFrameVersion OBJECT-TYPE
 SYNTAX  Counter32
 MAX-ACCESS     read-only
 STATUS  current
 DESCRIPTION
  "The protocol version number carried in the
   most recently received EAPOL frames."
 ::= { fgs2924rDot1XStatisticsEntry 29 }

fgs2924rDot1XAuthLastEapolFrameSource OBJECT-TYPE
 SYNTAX  DisplayString
 MAX-ACCESS     read-only
 STATUS  current
 DESCRIPTION
  "The source MAC address carried in the
   most recently received EAPOL frames."
 ::= { fgs2924rDot1XStatisticsEntry 30 }


fgs2924rTrunkInfo       OBJECT IDENTIFIER ::= { fgs2924rProduces 24 }

fgs2924rTrunkPort      OBJECT IDENTIFIER ::= { fgs2924rTrunkInfo 1 }

fgs2924rTrunkPortTable OBJECT-TYPE
 SYNTAX  SEQUENCE OF FGS2924RTrunkPortEntry
 MAX-ACCESS not-accessible
 STATUS  current
    DESCRIPTION
        "This is a list of FGS2924RTrunkPortEntry."
 ::= { fgs2924rTrunkPort 1 }

FGS2924RTrunkPortEntry ::=
SEQUENCE {
    fgs2924rTrunkPortIndex INTEGER,
    fgs2924rTrunkPortMethod    INTEGER,
    fgs2924rTrunkPortGroup  INTEGER,
    fgs2924rTrunkPortActiveLacp INTEGER,
    fgs2924rTrunkPortAggtr INTEGER,
    fgs2924rTrunkPortStatus INTEGER,
    fgs2924rTrunkPortCurrentMode INTEGER
}

fgs2924rTrunkPortEntry OBJECT-TYPE
 SYNTAX  FGS2924RTrunkPortEntry
 MAX-ACCESS     not-accessible
 STATUS  current
 DESCRIPTION
        "Entry(s) for trunk table."
 INDEX {fgs2924rTrunkPortIndex}
 ::= { fgs2924rTrunkPortTable 1 }

fgs2924rTrunkPortIndex OBJECT-TYPE
 SYNTAX  INTEGER(1..24)
 MAX-ACCESS     not-accessible
 STATUS  current
 DESCRIPTION
        "The port index of trunk table."
 ::= { fgs2924rTrunkPortEntry 1 }

fgs2924rTrunkPortMethod  OBJECT-TYPE
    SYNTAX      INTEGER(0..2)
    MAX-ACCESS  read-write
    STATUS      current
    DESCRIPTION
        "The method of trunk port.
  0 : None,
  1 : LACP,
  2 : Static.
        "
    ::= { fgs2924rTrunkPortEntry 2 }

fgs2924rTrunkPortGroup  OBJECT-TYPE
    SYNTAX      INTEGER(0..12)
    MAX-ACCESS  read-write
    STATUS      current
    DESCRIPTION
        "The group(0~12) of trunk port."
    ::= { fgs2924rTrunkPortEntry 3 }

fgs2924rTrunkPortActiveLacp  OBJECT-TYPE
    SYNTAX      INTEGER(0|1)
    MAX-ACCESS  read-write
    STATUS      current
    DESCRIPTION
        "The active lacp mode of trunk port.
  0 : Passive,
  1 : Active.
        "
    ::= { fgs2924rTrunkPortEntry 4 }

fgs2924rTrunkPortAggtr  OBJECT-TYPE
    SYNTAX      INTEGER(1..24)
    MAX-ACCESS  read-only
    STATUS      current
    DESCRIPTION
        "The Aggtr of trunk port."
    ::= { fgs2924rTrunkPortEntry 5 }

fgs2924rTrunkPortStatus  OBJECT-TYPE
    SYNTAX      INTEGER(0|1)
    MAX-ACCESS  read-only
    STATUS      current
    DESCRIPTION
        "The status of trunk port.
         0 : None,
         1 : Ready.
        "
    ::= { fgs2924rTrunkPortEntry 6 }

fgs2924rTrunkPortCurrentMode  OBJECT-TYPE
    SYNTAX      INTEGER(0..2)
    MAX-ACCESS  read-write
    STATUS      current
    DESCRIPTION
        "The current mode of trunk port entry.
  0 : Active mode,
  1 : Edit mode,
  2 : Do edit.
        "
    ::= { fgs2924rTrunkPortEntry 7 }

fgs2924rAggregatorView      OBJECT IDENTIFIER ::= { fgs2924rTrunkInfo 2 }

fgs2924rAggregatorViewTable  OBJECT-TYPE
    SYNTAX      SEQUENCE OF FGS2924RAggregatorViewEntry
    MAX-ACCESS  not-accessible
    STATUS      current
    DESCRIPTION
        "This is a list of FGS2924RAggregatorViewEntry."
    ::= { fgs2924rAggregatorView 1 }

FGS2924RAggregatorViewEntry ::=
SEQUENCE {
    fgs2924rAggregatorViewIndex  INTEGER,
    fgs2924rAggregatorViewMethod  INTEGER,
    fgs2924rAggregatorViewMemberPorts  DisplayString,
    fgs2924rAggregatorViewReadyPorts DisplayString
}

fgs2924rAggregatorViewEntry OBJECT-TYPE
    SYNTAX      FGS2924RAggregatorViewEntry
    MAX-ACCESS  not-accessible
    STATUS      current
    DESCRIPTION
        "Entry(s) for aggregator view table."
    INDEX {fgs2924rAggregatorViewIndex}
    ::= { fgs2924rAggregatorViewTable 1 }

fgs2924rAggregatorViewIndex  OBJECT-TYPE
    SYNTAX      INTEGER(1..24)
    MAX-ACCESS  not-accessible
    STATUS      current
    DESCRIPTION
        "The port index of aggregator view table."
    ::= { fgs2924rAggregatorViewEntry 1 }

fgs2924rAggregatorViewMethod  OBJECT-TYPE
    SYNTAX      INTEGER(0..2)
    MAX-ACCESS  read-only
    STATUS      current
    DESCRIPTION
        "The method of aggregator view table.
         0 : None,
  1 : LACP,
  2 : Static.
        "
    ::= { fgs2924rAggregatorViewEntry 2 }

fgs2924rAggregatorViewMemberPorts  OBJECT-TYPE
    SYNTAX      DisplayString
    MAX-ACCESS  read-only
    STATUS      current
    DESCRIPTION
        "The member ports of aggregator view table."
    ::= { fgs2924rAggregatorViewEntry 3 }

fgs2924rAggregatorViewReadyPorts  OBJECT-TYPE
    SYNTAX      DisplayString
    MAX-ACCESS  read-only
    STATUS      current
    DESCRIPTION
        "The ready ports of aggregator view table."
    ::= { fgs2924rAggregatorViewEntry 4 }

fgs2924rLacpSystemPriority OBJECT-TYPE
 SYNTAX  INTEGER(1..65535)
 MAX-ACCESS     read-write
 STATUS  current
 DESCRIPTION
  "Set lacp system priority. (Range:1~65535)"
 ::= { fgs2924rTrunkInfo 3 }

fgs2924rAggregationHashMode            OBJECT IDENTIFIER ::= { fgs2924rTrunkInfo 4 }

fgs2924rHashCodeSourceMacAddress OBJECT-TYPE
 SYNTAX  INTEGER(0|1)
 MAX-ACCESS     read-write
 STATUS  current
 DESCRIPTION
  "Set hash mode : Source MAC Hash Enable."
 ::= { fgs2924rAggregationHashMode 1 }

fgs2924rHashCodeDestinationMacAddress OBJECT-TYPE
 SYNTAX  INTEGER(0|1)
 MAX-ACCESS     read-write
 STATUS  current
 DESCRIPTION
  "Set hash mode : Destination MAC Hash Enable."
 ::= { fgs2924rAggregationHashMode 2 }

fgs2924rHashCodeIpAddress OBJECT-TYPE
 SYNTAX  INTEGER(0|1)
 MAX-ACCESS     read-write
 STATUS  current
 DESCRIPTION
  "Set hash mode : IP Hash Enable."
 ::= { fgs2924rAggregationHashMode 3 }

fgs2924rHashCodeTcpUdpPortNumber OBJECT-TYPE
 SYNTAX  INTEGER(0|1)
 MAX-ACCESS     read-write
 STATUS  current
 DESCRIPTION
  "Set hash mode : TCP/UDP Port Hash Enable."
 ::= { fgs2924rAggregationHashMode 4 }


fgs2924rMulticastInfo            OBJECT IDENTIFIER ::= { fgs2924rProduces 25 }

fgs2924rIGMPMode OBJECT-TYPE
 SYNTAX      INTEGER(0|1|2)
 MAX-ACCESS     read-write
 STATUS  current
 DESCRIPTION
  "Get/Set the IGMP Proxy/Snooping state.
   0 - disabled.
   1 - proxy.
   2 - snooping.  "
 ::= { fgs2924rMulticastInfo 1 }

fgs2924rIGMPGroupAllowConf         OBJECT IDENTIFIER ::= { fgs2924rMulticastInfo 2 }

fgs2924rIGMPGroupAllowNumber OBJECT-TYPE
 SYNTAX      INTEGER(1..16)
 MAX-ACCESS     read-only
 STATUS  current
 DESCRIPTION
  "Get the amount of the IGMP group allow."
 ::= { fgs2924rIGMPGroupAllowConf 1  }

fgs2924rIGMPGroupAllowEntryCreate  OBJECT-TYPE
 SYNTAX      INTEGER(0..4094)
 MAX-ACCESS     read-write
 STATUS  current
 DESCRIPTION
  "Create IGMP group allow entry."
 ::= { fgs2924rIGMPGroupAllowConf 2 }

fgs2924rIGMPGroupAllowTable OBJECT-TYPE
 SYNTAX  SEQUENCE OF FGS2924RIGMPGroupAllowEntry
 MAX-ACCESS not-accessible
 STATUS  current
    DESCRIPTION
        "Display IGMP group allow information."
 ::= { fgs2924rIGMPGroupAllowConf 3 }

FGS2924RIGMPGroupAllowEntry ::=
SEQUENCE {
    fgs2924rIGMPGroupAllowNo          INTEGER,
    fgs2924rIGMPGroupAllowVid        INTEGER,
    fgs2924rIGMPGroupAllowStartAddress     DisplayString,
    fgs2924rIGMPGroupAllowEndAddress      DisplayString,
    fgs2924rIGMPGroupAllowEntryAction   INTEGER
}

fgs2924rIGMPGroupAllowEntry OBJECT-TYPE
 SYNTAX  FGS2924RIGMPGroupAllowEntry
 MAX-ACCESS     not-accessible
 STATUS  current
 DESCRIPTION
  "This is the Entry(s) for IGMP Group Allow configuration information."
 INDEX {fgs2924rIGMPGroupAllowNo}
 ::= { fgs2924rIGMPGroupAllowTable 1 }

fgs2924rIGMPGroupAllowNo  OBJECT-TYPE
    SYNTAX      INTEGER(1..256)
    MAX-ACCESS  not-accessible
    STATUS      current
    DESCRIPTION
        "The index of IGMP Group Allow table."
    ::= { fgs2924rIGMPGroupAllowEntry 1 }

fgs2924rIGMPGroupAllowVid  OBJECT-TYPE
    SYNTAX      INTEGER(0..4094)
    MAX-ACCESS  read-write
    STATUS      current
    DESCRIPTION
        "Add group allow for this IGMP."
    ::= { fgs2924rIGMPGroupAllowEntry 2 }

fgs2924rIGMPGroupAllowStartAddress OBJECT-TYPE
 SYNTAX  DisplayString
 MAX-ACCESS     read-write
 STATUS  current
 DESCRIPTION
  "Add start address of IGMP group allow."
 ::= { fgs2924rIGMPGroupAllowEntry 3}

fgs2924rIGMPGroupAllowEndAddress OBJECT-TYPE
 SYNTAX  DisplayString
 MAX-ACCESS     read-write
 STATUS  current
 DESCRIPTION
  "Add end address of IGMP group allow."
 ::= { fgs2924rIGMPGroupAllowEntry 4 }

fgs2924rIGMPGroupAllowEntryAction OBJECT-TYPE
 SYNTAX  INTEGER(1..4)
 MAX-ACCESS     read-write
 STATUS  current
 DESCRIPTION
  "
   1 - active
   2 - notInService
   3 - delete
   4 - undo"
 ::= { fgs2924rIGMPGroupAllowEntry 5 }

fgs2924rIGMPProxy         OBJECT IDENTIFIER ::= { fgs2924rMulticastInfo 3 }

fgs2924rIgmpProxyConfGeneralQueryInterval OBJECT-TYPE
 SYNTAX      INTEGER(1..3600)
 MAX-ACCESS     read-write
 STATUS  current
 DESCRIPTION
  "Get/Set IGMP general query interval(Unit: second)."
 ::= { fgs2924rIGMPProxy 1 }

fgs2924rIgmpProxyConfGeneralQueryRepTimeout OBJECT-TYPE
 SYNTAX      INTEGER(1..25)
 MAX-ACCESS     read-write
 STATUS  current
 DESCRIPTION
  "Get/Set IGMP general query response timeout(Unit: second)."
 ::= { fgs2924rIGMPProxy 2 }

fgs2924rIgmpProxyConfGeneralQueryMaxRepTime OBJECT-TYPE
 SYNTAX      INTEGER(1..25)
 MAX-ACCESS     read-write
 STATUS  current
 DESCRIPTION
  "Get/Set IGMP general query maximum response time(Unit: second)."
 ::= { fgs2924rIGMPProxy 3 }

fgs2924rIgmpProxyConfLastMemberQueryCount OBJECT-TYPE
 SYNTAX      INTEGER(1..16)
 MAX-ACCESS     read-write
 STATUS  current
 DESCRIPTION
  "Get/Set IGMP specific query robust count."
 ::= { fgs2924rIGMPProxy 4 }

fgs2924rIgmpProxyConfLastMemberQueryInterval OBJECT-TYPE
 SYNTAX      INTEGER(1..25)
 MAX-ACCESS     read-write
 STATUS  current
 DESCRIPTION
  "Get/Set IGMP specific query interval(Unit: second)."
 ::= { fgs2924rIGMPProxy 5 }

fgs2924rIgmpProxyConfLastMemberQueryMaxRepTime OBJECT-TYPE
 SYNTAX      INTEGER(1..25)
 MAX-ACCESS     read-write
 STATUS  current
 DESCRIPTION
  "Get/Set IGMP specific query maximum response time(Unit: second)."
 ::= { fgs2924rIGMPProxy 6 }

fgs2924rIgmpProxyConfRouterPorts OBJECT-TYPE
 SYNTAX      DisplayString
 MAX-ACCESS     read-write
 STATUS  current
 DESCRIPTION
  " Get/Set IGMP router port(s)."
 ::= { fgs2924rIGMPProxy 7 }

fgs2924rIgmpProxyGroupMembershipNumber OBJECT-TYPE
 SYNTAX      INTEGER(0..1024)
 MAX-ACCESS     read-write
 STATUS  current
 DESCRIPTION
  "Get the amount of multicast group membership."
 ::= { fgs2924rIGMPProxy 8 }

fgs2924rIgmpProxyGroupMembershipTable  OBJECT-TYPE
    SYNTAX      SEQUENCE OF FGS2924RIgmpProxyGroupMembershipEntry
    MAX-ACCESS  not-accessible
    STATUS      current
    DESCRIPTION
        "Get multicast group membership."
    ::= { fgs2924rIGMPProxy 9 }

FGS2924RIgmpProxyGroupMembershipEntry ::=
SEQUENCE {
    fgs2924rIgmpProxyGroupNo         INTEGER,
    fgs2924rIgmpProxyGroupAddress     DisplayString,
    fgs2924rIgmpProxyGroupVLANId      INTEGER,
    fgs2924rIgmpProxyGroupPortMembers  DisplayString
}

fgs2924rIgmpProxyGroupMembershipEntry OBJECT-TYPE
    SYNTAX      FGS2924RIgmpProxyGroupMembershipEntry
    MAX-ACCESS  not-accessible
    STATUS      current
    DESCRIPTION
        "Entry(s) for Igmp Proxy Group Membership table."
    INDEX {fgs2924rIgmpProxyGroupNo}
    ::= { fgs2924rIgmpProxyGroupMembershipTable 1 }

fgs2924rIgmpProxyGroupNo  OBJECT-TYPE
    SYNTAX      INTEGER(1..1024)
    MAX-ACCESS  not-accessible
    STATUS      current
    DESCRIPTION
        "The port index of Igmp Proxy Group Membership table."
    ::= { fgs2924rIgmpProxyGroupMembershipEntry 1 }

fgs2924rIgmpProxyGroupAddress  OBJECT-TYPE
    SYNTAX      DisplayString
    MAX-ACCESS  read-only
    STATUS      current
    DESCRIPTION
        "The group address of multicast group membership entry."
    ::= { fgs2924rIgmpProxyGroupMembershipEntry 2 }

fgs2924rIgmpProxyGroupVLANId  OBJECT-TYPE
    SYNTAX      INTEGER(1..4094)
    MAX-ACCESS  read-only
    STATUS      current
    DESCRIPTION
        "The vlan id of multicast group membership entry."
    ::= { fgs2924rIgmpProxyGroupMembershipEntry 3 }

fgs2924rIgmpProxyGroupPortMembers  OBJECT-TYPE
    SYNTAX      DisplayString
    MAX-ACCESS  read-only
    STATUS      current
    DESCRIPTION
        "The port member of multicast group membership entry."
    ::= { fgs2924rIgmpProxyGroupMembershipEntry 4 }

fgs2924rIGMPSnooping         OBJECT IDENTIFIER ::= { fgs2924rMulticastInfo 4 }

fgs2924rIgmpSnoopingConfHostTimeout OBJECT-TYPE
 SYNTAX      INTEGER(1..65535)
 MAX-ACCESS     read-write
 STATUS  current
 DESCRIPTION
  "This is the host timeout of the igmp snooping."
 ::= { fgs2924rIGMPSnooping 1 }


fgs2924rIgmpSnoopingConfFastLeave OBJECT-TYPE
 SYNTAX      DisplayString
 MAX-ACCESS     read-write
 STATUS  current
 DESCRIPTION
  "This is the fast-leave of the igmp snooping."
 ::= { fgs2924rIGMPSnooping 2 }

fgs2924rIgmpSnoopingConfRouterPorts  OBJECT-TYPE
 SYNTAX      DisplayString
 MAX-ACCESS     read-write
 STATUS  current
 DESCRIPTION
  "These ports are router ports of the igmp snooping."
 ::= { fgs2924rIGMPSnooping 3 }

fgs2924rIgmpSnoopingGroupMembershipNumber OBJECT-TYPE
 SYNTAX      INTEGER(0..1024)
 MAX-ACCESS     read-write
 STATUS  current
 DESCRIPTION
  "These are groups membership of the igmp snooping."
 ::= { fgs2924rIGMPSnooping 4 }

fgs2924rIgmpSnoopingGroupMembershipTable  OBJECT-TYPE
    SYNTAX      SEQUENCE OF FGS2924RIgmpSnoopingGroupMembershipEntry
    MAX-ACCESS  not-accessible
    STATUS      current
    DESCRIPTION
        "Display group menbership information."
 ::= { fgs2924rIGMPSnooping 5 }


FGS2924RIgmpSnoopingGroupMembershipEntry ::=
SEQUENCE {
    fgs2924rIgmpSnoopingGroupNo         INTEGER,
    fgs2924rIgmpSnoopingGroupAddress     DisplayString,
    fgs2924rIgmpSnoopingGroupVLANId      INTEGER,
    fgs2924rIgmpSnoopingGroupPortMembers  DisplayString
}

fgs2924rIgmpSnoopingGroupMembershipEntry OBJECT-TYPE
    SYNTAX      FGS2924RIgmpSnoopingGroupMembershipEntry
    MAX-ACCESS  not-accessible
    STATUS      current
    DESCRIPTION
        "Entry(s) for Igmp Snooping Group Membership table."
    INDEX {fgs2924rIgmpSnoopingGroupNo}
    ::= { fgs2924rIgmpSnoopingGroupMembershipTable 1 }

fgs2924rIgmpSnoopingGroupNo  OBJECT-TYPE
    SYNTAX      INTEGER(1..1024)
    MAX-ACCESS  not-accessible
    STATUS      current
    DESCRIPTION
        "The port index of Igmp Snooping Group Membership table."
    ::= { fgs2924rIgmpSnoopingGroupMembershipEntry 1 }

fgs2924rIgmpSnoopingGroupAddress  OBJECT-TYPE
    SYNTAX      DisplayString
    MAX-ACCESS  read-only
    STATUS      current
    DESCRIPTION
        "This is the group address of the igmp snooping."
    ::= { fgs2924rIgmpSnoopingGroupMembershipEntry 2 }

fgs2924rIgmpSnoopingGroupVLANId  OBJECT-TYPE
    SYNTAX      INTEGER(1..4094)
    MAX-ACCESS  read-only
    STATUS      current
    DESCRIPTION
        "The vlan id of igmp snooping group."
    ::= { fgs2924rIgmpSnoopingGroupMembershipEntry 3 }

fgs2924rIgmpSnoopingGroupPortMembers  OBJECT-TYPE
    SYNTAX      DisplayString
    MAX-ACCESS  read-only
    STATUS      current
    DESCRIPTION
        "The members of igmp snooping group."
    ::= { fgs2924rIgmpSnoopingGroupMembershipEntry 4 }


fgs2924rMVR         OBJECT IDENTIFIER ::= { fgs2924rMulticastInfo 5 }

fgs2924rMVRMode OBJECT-TYPE
 SYNTAX      INTEGER(0|1)
 MAX-ACCESS     read-write
 STATUS  current
 DESCRIPTION
  "Get/Set the MVR state.
   0 - disabled.
   1 - enabled.  "
 ::= { fgs2924rMVR 1 }

fgs2924rMVRConfHostTimeout OBJECT-TYPE
 SYNTAX      INTEGER(1..65535)
 MAX-ACCESS     read-write
 STATUS  current
 DESCRIPTION
  "This is the host timeout of the mvr."
 ::= { fgs2924rMVR 2 }

fgs2924rMVRConfFastLeave OBJECT-TYPE
 SYNTAX      DisplayString
 MAX-ACCESS     read-write
 STATUS  current
 DESCRIPTION
  "This is the fast-leave of the mvr."
 ::= { fgs2924rMVR 3 }


fgs2924rMVIDConf         OBJECT IDENTIFIER ::= { fgs2924rMVR 4 }

fgs2924rMVIDNumber OBJECT-TYPE
 SYNTAX      INTEGER(1..4094)
 MAX-ACCESS     read-only
 STATUS  current
 DESCRIPTION
  "The vid of mvr group."
 ::= { fgs2924rMVIDConf 1 }

fgs2924rMVIDEntryCreate OBJECT-TYPE
 SYNTAX      INTEGER(0..4094)
 MAX-ACCESS     read-write
 STATUS  current
 DESCRIPTION
  "Create mvr group entry."
 ::= { fgs2924rMVIDConf 2 }

fgs2924rMVIDGroupTable OBJECT-TYPE
 SYNTAX  SEQUENCE OF FGS2924RMVIDGroupEntry
 MAX-ACCESS not-accessible
 STATUS  current
    DESCRIPTION
        "Display mvid group information."
 ::= { fgs2924rMVIDConf 3 }

FGS2924RMVIDGroupEntry ::=
SEQUENCE {
    fgs2924rMVID          INTEGER,
    fgs2924rMVIDMemberPort      DisplayString,
    fgs2924rMVIDRouterPorts     DisplayString,
    fgs2924rMVIDEntryAction     INTEGER
}

fgs2924rMVIDGroupEntry OBJECT-TYPE
 SYNTAX  FGS2924RMVIDGroupEntry
 MAX-ACCESS     not-accessible
 STATUS  current
 DESCRIPTION
  "This is the Entry(s) for MVID Group configuration information."
 INDEX {fgs2924rMVID}
 ::= { fgs2924rMVIDGroupTable 1 }

fgs2924rMVID OBJECT-TYPE
 SYNTAX  INTEGER(1..4094)
 MAX-ACCESS     not-accessible
 STATUS  current
 DESCRIPTION
  "This is the index of the MVID Group configuration entry."
 ::= { fgs2924rMVIDGroupEntry 1 }

fgs2924rMVIDMemberPort OBJECT-TYPE
 SYNTAX  DisplayString
 MAX-ACCESS     read-write
 STATUS  current
 DESCRIPTION
  "Member ports of the mvid group."
 ::= { fgs2924rMVIDGroupEntry 2 }

fgs2924rMVIDRouterPorts  OBJECT-TYPE
 SYNTAX  DisplayString
 MAX-ACCESS     read-write
 STATUS  current
 DESCRIPTION
  "Router ports of the mvid group."
 ::= { fgs2924rMVIDGroupEntry 3 }

fgs2924rMVIDEntryAction OBJECT-TYPE
 SYNTAX  INTEGER(1..4)
 MAX-ACCESS     read-write
 STATUS  current
 DESCRIPTION
  "
   1 - active
   2 - notInService
   3 - delete
   4 - undo"
 ::= { fgs2924rMVIDGroupEntry 4 }


fgs2924rMVIDGroupAllowConf         OBJECT IDENTIFIER ::= { fgs2924rMVR 5 }

fgs2924rMVIDGroupAllowNumber OBJECT-TYPE
 SYNTAX      INTEGER(1..16)
 MAX-ACCESS     read-only
 STATUS  current
 DESCRIPTION
  "Get the amount of the mvid group allow."
 ::= { fgs2924rMVIDGroupAllowConf 1  }

fgs2924rMVIDGroupAllowEntryCreate  OBJECT-TYPE
 SYNTAX      INTEGER(0..4094)
 MAX-ACCESS     read-write
 STATUS  current
 DESCRIPTION
  "Create mvid group allow entry."
 ::= { fgs2924rMVIDGroupAllowConf 2 }

fgs2924rMVIDGroupAllowTable OBJECT-TYPE
 SYNTAX  SEQUENCE OF FGS2924RMVIDGroupAllowEntry
 MAX-ACCESS not-accessible
 STATUS  current
    DESCRIPTION
        "Display mvid group allow information."
 ::= { fgs2924rMVIDGroupAllowConf 3 }

FGS2924RMVIDGroupAllowEntry ::=
SEQUENCE {
    fgs2924rMVIDGroupAllowNo          INTEGER,
    fgs2924rMVIDGroupAllowMvid        INTEGER,
    fgs2924rMVIDGroupAllowStartAddress     DisplayString,
    fgs2924rMVIDGroupAllowEndAddress      DisplayString,
    fgs2924rMVIDGroupAllowEntryAction   INTEGER
}

fgs2924rMVIDGroupAllowEntry OBJECT-TYPE
 SYNTAX  FGS2924RMVIDGroupAllowEntry
 MAX-ACCESS     not-accessible
 STATUS  current
 DESCRIPTION
  "This is the Entry(s) for MVID Group Allow configuration information."
 INDEX {fgs2924rMVIDGroupAllowNo}
 ::= { fgs2924rMVIDGroupAllowTable 1 }

fgs2924rMVIDGroupAllowNo  OBJECT-TYPE
    SYNTAX      INTEGER(1..256)
    MAX-ACCESS  not-accessible
    STATUS      current
    DESCRIPTION
        "The index of MVID Group Allow table."
    ::= { fgs2924rMVIDGroupAllowEntry 1 }

fgs2924rMVIDGroupAllowMvid  OBJECT-TYPE
    SYNTAX      INTEGER(0..4094)
    MAX-ACCESS  read-write
    STATUS      current
    DESCRIPTION
        "Add group allow for this mvid."
    ::= { fgs2924rMVIDGroupAllowEntry 2 }

fgs2924rMVIDGroupAllowStartAddress OBJECT-TYPE
 SYNTAX  DisplayString
 MAX-ACCESS     read-write
 STATUS  current
 DESCRIPTION
  "Add start address of mvid group allow."
 ::= { fgs2924rMVIDGroupAllowEntry 3}

fgs2924rMVIDGroupAllowEndAddress OBJECT-TYPE
 SYNTAX  DisplayString
 MAX-ACCESS     read-write
 STATUS  current
 DESCRIPTION
  "Add end address of mvid group allow."
 ::= { fgs2924rMVIDGroupAllowEntry 4 }

fgs2924rMVIDGroupAllowEntryAction OBJECT-TYPE
 SYNTAX  INTEGER(1..4)
 MAX-ACCESS     read-write
 STATUS  current
 DESCRIPTION
  "
   1 - active
   2 - notInService
   3 - delete
   4 - undo"
 ::= { fgs2924rMVIDGroupAllowEntry 5 }

fgs2924rMVRGroupMembershipNumber OBJECT-TYPE
 SYNTAX      INTEGER(0..1024)
 MAX-ACCESS     read-only
 STATUS  current
 DESCRIPTION
  "Get the amount of mvr group membership."
 ::= { fgs2924rMVR 6 }

fgs2924rMVRGroupMembershipTable  OBJECT-TYPE
    SYNTAX      SEQUENCE OF FGS2924RMVRGroupMembershipEntry
    MAX-ACCESS  not-accessible
    STATUS      current
    DESCRIPTION
        "Get mvr group membership."
 ::= { fgs2924rMVR 7 }


FGS2924RMVRGroupMembershipEntry ::=
SEQUENCE {
    fgs2924rMVRGroupNo         INTEGER,
    fgs2924rMVRGroupAddress     DisplayString,
    fgs2924rMVRGroupVLANId      INTEGER,
    fgs2924rMVRGroupPortMembers  DisplayString
}

fgs2924rMVRGroupMembershipEntry OBJECT-TYPE
    SYNTAX      FGS2924RMVRGroupMembershipEntry
    MAX-ACCESS  not-accessible
    STATUS      current
    DESCRIPTION
        "Entry(s) for MVR Group Membership table."
    INDEX {fgs2924rMVRGroupNo}
    ::= { fgs2924rMVRGroupMembershipTable 1 }

fgs2924rMVRGroupNo  OBJECT-TYPE
    SYNTAX      INTEGER(1..1024)
    MAX-ACCESS  not-accessible
    STATUS      current
    DESCRIPTION
        "The port index of MVR Group Membership table."
    ::= { fgs2924rMVRGroupMembershipEntry 1 }

fgs2924rMVRGroupAddress  OBJECT-TYPE
    SYNTAX      DisplayString
    MAX-ACCESS  read-only
    STATUS      current
    DESCRIPTION
        "The group address of mvr group membership entry."
    ::= { fgs2924rMVRGroupMembershipEntry 2 }

fgs2924rMVRGroupVLANId  OBJECT-TYPE
    SYNTAX      INTEGER(1..4094)
    MAX-ACCESS  read-only
    STATUS      current
    DESCRIPTION
        "The vlan id of mvr group membership entry."
    ::= { fgs2924rMVRGroupMembershipEntry 3 }

fgs2924rMVRGroupPortMembers  OBJECT-TYPE
    SYNTAX      DisplayString
    MAX-ACCESS  read-only
    STATUS      current
    DESCRIPTION
        "The port member of mvr group membership entry."
    ::= { fgs2924rMVRGroupMembershipEntry 4 }

fgs2924rDhcpSnooping            OBJECT IDENTIFIER ::= { fgs2924rProduces 26 }

fgs2924rDhcpSnoopingState OBJECT-TYPE
 SYNTAX      INTEGER(0|1)
 MAX-ACCESS     read-write
 STATUS  current
 DESCRIPTION
  "Get/Set the Dhcp Snooping state.
   0 - disabled.
   1 - enable."
 ::= { fgs2924rDhcpSnooping 1 }

fgs2924rDhcpSnoopingInfo         OBJECT IDENTIFIER ::= { fgs2924rDhcpSnooping 2 }

fgs2924rDhcpSnoopingCreate OBJECT-TYPE
 SYNTAX      INTEGER(0|1)
 MAX-ACCESS     read-write
 STATUS  current
 DESCRIPTION
  "create DHCP Snooping entry.
   0 - none.
   1 - create."
 ::= { fgs2924rDhcpSnoopingInfo 1 }

fgs2924rDhcpSnoopingTable  OBJECT-TYPE
    SYNTAX      SEQUENCE OF FGS2924RDhcpSnoopingEntry
    MAX-ACCESS  not-accessible
    STATUS      current
    DESCRIPTION
        "This is a list of DhcpSnoopingEntry."
 ::= { fgs2924rDhcpSnoopingInfo 2 }


FGS2924RDhcpSnoopingEntry ::=
SEQUENCE {
    fgs2924rDhcpSnoopingIndex                   INTEGER,
    fgs2924rDhcpSnoopingVID                     INTEGER,
    fgs2924rDhcpSnoopingTrustPort1              INTEGER,
    fgs2924rDhcpSnoopingTrustPort2              INTEGER,
    fgs2924rDhcpSnoopingServerIP                IpAddress,
    fgs2924rDhcpSnoopingOption82                INTEGER,
    fgs2924rDhcpSnoopingAction                INTEGER,
    fgs2924rDhcpSnoopingEntryAction             INTEGER
}

fgs2924rDhcpSnoopingEntry OBJECT-TYPE
    SYNTAX      FGS2924RDhcpSnoopingEntry
    MAX-ACCESS  not-accessible
    STATUS      current
    DESCRIPTION
        "Entry(s) for Dhcp Snooping table."
    INDEX {fgs2924rDhcpSnoopingIndex}
    ::= { fgs2924rDhcpSnoopingTable 1 }

fgs2924rDhcpSnoopingIndex  OBJECT-TYPE
    SYNTAX      INTEGER(1..256)
    MAX-ACCESS  not-accessible
    STATUS      current
    DESCRIPTION
        "The index of Dhcp Snooping table."
    ::= { fgs2924rDhcpSnoopingEntry 1 }

fgs2924rDhcpSnoopingVID  OBJECT-TYPE
    SYNTAX      INTEGER(1..4094)
    MAX-ACCESS  read-write
    STATUS      current
    DESCRIPTION
        "The vid of the dhcp snooping entry."
    ::= { fgs2924rDhcpSnoopingEntry 2 }

fgs2924rDhcpSnoopingTrustPort1 OBJECT-TYPE
 SYNTAX      INTEGER(0..24)
 MAX-ACCESS     read-write
 STATUS  current
 DESCRIPTION
  "The trust port1 of the dhcp snooping entry.
  0:disable"
 ::= { fgs2924rDhcpSnoopingEntry 3 }

fgs2924rDhcpSnoopingTrustPort2 OBJECT-TYPE
 SYNTAX      INTEGER(0..24)
 MAX-ACCESS     read-write
 STATUS  current
 DESCRIPTION
  "The trust port2 of the dhcp snooping entry.
  0:disable"
 ::= { fgs2924rDhcpSnoopingEntry 4 }

fgs2924rDhcpSnoopingServerIP OBJECT-TYPE
 SYNTAX      IpAddress
 MAX-ACCESS     read-write
 STATUS  current
 DESCRIPTION
  "The server ip of the dhcp snooping entry."
 ::= { fgs2924rDhcpSnoopingEntry 5 }

fgs2924rDhcpSnoopingOption82 OBJECT-TYPE
 SYNTAX      INTEGER(0|1)
 MAX-ACCESS     read-write
 STATUS  current
 DESCRIPTION
  "0:disable
   1:enable"
 ::= { fgs2924rDhcpSnoopingEntry 6 }

fgs2924rDhcpSnoopingAction OBJECT-TYPE
 SYNTAX      INTEGER(0..2)
 MAX-ACCESS     read-write
 STATUS  current
 DESCRIPTION
  "0:keep
   1: drop
   2: replace"
 ::= { fgs2924rDhcpSnoopingEntry 7 }

fgs2924rDhcpSnoopingEntryAction  OBJECT-TYPE
    SYNTAX      INTEGER(0..2)
    MAX-ACCESS  read-write
    STATUS      current
    DESCRIPTION
        "The current mode of Dhcp Snooping default entry.
  0 : Active mode,
  1 : Edit mode,
  2 : Do edit. "
 ::= { fgs2924rDhcpSnoopingEntry 8 }


fgs2924rDhcpSnoopingDefaultData     OBJECT IDENTIFIER ::= { fgs2924rDhcpSnoopingInfo 3 }

fgs2924rDhcpSnoopingDefaultVID OBJECT-TYPE
 SYNTAX      INTEGER(1..4094)
 MAX-ACCESS     read-write
 STATUS  current
 DESCRIPTION
  "The vid of the dhcp_snooping default entry."
 ::= { fgs2924rDhcpSnoopingDefaultData 1 }

fgs2924rDhcpSnoopingDefaultTrustPort1 OBJECT-TYPE
 SYNTAX      INTEGER(0..24)
 MAX-ACCESS     read-write
 STATUS  current
 DESCRIPTION
  "The trust port1 of the dhcp_snooping default entry.
  0:disable"
 ::= { fgs2924rDhcpSnoopingDefaultData 2 }

fgs2924rDhcpSnoopingDefaultTrustPort2 OBJECT-TYPE
 SYNTAX      INTEGER(0..24)
 MAX-ACCESS     read-write
 STATUS  current
 DESCRIPTION
  "The trust port2 of the dhcp_snooping default entry.
  0:disable"
 ::= { fgs2924rDhcpSnoopingDefaultData 3 }

fgs2924rDhcpSnoopingDefaultServerIP OBJECT-TYPE
 SYNTAX      IpAddress
 MAX-ACCESS     read-write
 STATUS  current
 DESCRIPTION
  "The server ip of the dhcp_snooping default entry."
 ::= { fgs2924rDhcpSnoopingDefaultData 4 }

fgs2924rDhcpSnoopingDefaultOption82 OBJECT-TYPE
 SYNTAX      INTEGER(0|1)
 MAX-ACCESS     read-write
 STATUS  current
 DESCRIPTION
  "0:disable
   1:enable"
 ::= { fgs2924rDhcpSnoopingDefaultData 5 }

fgs2924rDhcpSnoopingDefaultAction OBJECT-TYPE
 SYNTAX      INTEGER(0..2)
 MAX-ACCESS     read-write
 STATUS  current
 DESCRIPTION
  "0:keep
   1: drop
   2: replace"
 ::= { fgs2924rDhcpSnoopingDefaultData 6 }

fgs2924rDhcpSnoopingDefaultEntryAction  OBJECT-TYPE
    SYNTAX      INTEGER(0..2)
    MAX-ACCESS  read-write
    STATUS      current
    DESCRIPTION
        "The current mode of Dhcp Snooping default entry.
  0 : Active mode,
  1 : Edit mode,
  2 : Do edit,
  3 : Undo."
 ::= { fgs2924rDhcpSnoopingDefaultData 7 }

fgs2924rDhcpSnoopingClientTable  OBJECT-TYPE
    SYNTAX      SEQUENCE OF FGS2924RDhcpSnoopingClientEntry
    MAX-ACCESS  not-accessible
    STATUS      current
    DESCRIPTION
        "The list of the DhcpSnoopingClientEntry."
 ::= { fgs2924rDhcpSnooping 3 }

FGS2924RDhcpSnoopingClientEntry ::=
SEQUENCE {
    fgs2924rDhcpSnoopingClientIndex    INTEGER,
    fgs2924rDhcpSnoopingClientMac      DisplayString,
    fgs2924rDhcpSnoopingClientVID      INTEGER,
    fgs2924rDhcpSnoopingClientPort     INTEGER,
    fgs2924rDhcpSnoopingClientIP       IpAddress,
    fgs2924rDhcpSnoopingClientLease    DisplayString
}

fgs2924rDhcpSnoopingClientEntry OBJECT-TYPE
    SYNTAX      FGS2924RDhcpSnoopingClientEntry
    MAX-ACCESS  not-accessible
    STATUS      current
    DESCRIPTION
        "Entry(s) for Dhcp Snooping Client table."
    INDEX {fgs2924rDhcpSnoopingClientIndex}
    ::= { fgs2924rDhcpSnoopingClientTable 1 }

fgs2924rDhcpSnoopingClientIndex  OBJECT-TYPE
    SYNTAX      INTEGER(1..10000)
    MAX-ACCESS  not-accessible
    STATUS      current
    DESCRIPTION
        "The index of Dhcp Snooping Client table."
    ::= { fgs2924rDhcpSnoopingClientEntry 1 }

fgs2924rDhcpSnoopingClientMac  OBJECT-TYPE
    SYNTAX      DisplayString
    MAX-ACCESS  read-only
    STATUS      current
    DESCRIPTION
        "The mac address of the dhcp_snooping client entry."
    ::= { fgs2924rDhcpSnoopingClientEntry 2 }

fgs2924rDhcpSnoopingClientVID  OBJECT-TYPE
    SYNTAX      INTEGER(1..4094)
    MAX-ACCESS  read-only
    STATUS      current
    DESCRIPTION
        "The vid of the dhcp_snooping client entry."
    ::= { fgs2924rDhcpSnoopingClientEntry 3 }

fgs2924rDhcpSnoopingClientPort  OBJECT-TYPE
    SYNTAX      INTEGER(1..24)
    MAX-ACCESS  read-only
    STATUS      current
    DESCRIPTION
        "The port number of the dhcp_snooping client entry."
    ::= { fgs2924rDhcpSnoopingClientEntry 4 }

fgs2924rDhcpSnoopingClientIP  OBJECT-TYPE
    SYNTAX      IpAddress
    MAX-ACCESS  read-only
    STATUS      current
    DESCRIPTION
        "The ip address of the dhcp_snooping client entry."
    ::= { fgs2924rDhcpSnoopingClientEntry 5 }

fgs2924rDhcpSnoopingClientLease  OBJECT-TYPE
    SYNTAX      DisplayString
    MAX-ACCESS  read-only
    STATUS      current
    DESCRIPTION
        "The dhcp lease time of the dhcp_snooping client entry."
    ::= { fgs2924rDhcpSnoopingClientEntry 6 }


fgs2924rTrapEntry        OBJECT IDENTIFIER ::= { fgs2924rProduces 20 }

fgs2924rUserLogin NOTIFICATION-TYPE
    OBJECTS   {username}
 STATUS  current
 DESCRIPTION
    "Send the trap when one user logins the system."
 ::= { fgs2924rTrapEntry 1 }

fgs2924rUserLogout NOTIFICATION-TYPE
    OBJECTS   {username}
 STATUS  current
 DESCRIPTION
    "Send the trap when one user logouts the system."
 ::= { fgs2924rTrapEntry 2 }

fgs2924rModuleInserted NOTIFICATION-TYPE
    OBJECTS { ifIndex }
 STATUS    current
 DESCRIPTION
     "Send the trap when a module is inserted to the system. The OID value means
      the port number."
 ::= { fgs2924rTrapEntry 3 }

fgs2924rModuleRemoved NOTIFICATION-TYPE
    OBJECTS { ifIndex }
 STATUS    current
 DESCRIPTION
     "Send the trap when a module is removed from the system. The OID value means
      the port number."
 ::= { fgs2924rTrapEntry 4 }

fgs2924rDualMediaSwapped NOTIFICATION-TYPE
    OBJECTS { ifIndex, swapto }
 STATUS    current
 DESCRIPTION
     "Send the trap when the dual media port changed. The OID value means the port number."
 ::= { fgs2924rTrapEntry 5 }

fgs2924rLoopDetected NOTIFICATION-TYPE
    OBJECTS { ifIndex }
 STATUS    current
 DESCRIPTION
     "Send the trap when loop condition has been detected. The OID value means the port number."
 ::= { fgs2924rTrapEntry 6 }

fgs2924rStpStateDisabled NOTIFICATION-TYPE
 STATUS  current
 DESCRIPTION
    "Send the trap when the operational state of STP is from enabled to disabled. "
 ::= { fgs2924rTrapEntry 7 }

fgs2924rStpStateEnabled NOTIFICATION-TYPE
 STATUS  current
 DESCRIPTION
    "Send the trap when the operational state of STP is from disabled to enabled. "
 ::= { fgs2924rTrapEntry 8 }

fgs2924rStpTopologyChanged NOTIFICATION-TYPE
    OBJECTS { ifIndex }
 STATUS  current
 DESCRIPTION
    "Send the trap when RSTP determines a port should enter the FORWARDING state
     (a topology change occurs). The OID value is the ifIndex of the port that
     produces the topology change."
 ::= { fgs2924rTrapEntry 9 }

fgs2924rLacpStateDisabled NOTIFICATION-TYPE
    OBJECTS {ifIndex, groupId}
 STATUS  current
 DESCRIPTION
    "Send the trap when the operational state of LACP is from enabled to disabled.
     The OID value means the disabled Group ID."
 ::= { fgs2924rTrapEntry 10 }

fgs2924rLacpStateEnabled NOTIFICATION-TYPE
    OBJECTS {ifIndex, groupId}
 STATUS  current
 DESCRIPTION
    "Send the trap when the operational state of LACP is from disabled to enabled.
     The OID value means the disabled Group ID."
 ::= { fgs2924rTrapEntry 11 }

fgs2924rLacpPortAdded NOTIFICATION-TYPE
    OBJECTS   { ifIndex, actorkey, partnerkey }
 STATUS  current
 DESCRIPTION
    "Send the trap when the state of port is in 'trunk ready'."
 ::= { fgs2924rTrapEntry 12 }

fgs2924rLacpPortTrunkFailure NOTIFICATION-TYPE
    OBJECTS   { ifIndex, actorkey, partnerkey}
 STATUS  current
 DESCRIPTION
    "Send the trap when one port is not able to be aggregated
     due to duplex-mode of the port."
 ::= { fgs2924rTrapEntry 13 }

fgs2924rGvrpStateDisabled NOTIFICATION-TYPE
 STATUS  current
 DESCRIPTION
    "Send the trap when the operational state of GVRP is from enabled to disabled."
 ::= { fgs2924rTrapEntry 14 }

fgs2924rGvrpStateEnabled NOTIFICATION-TYPE
 STATUS  current
 DESCRIPTION
    "Send the trap when the operational state of LACP is from disabled to enabled. "
 ::= { fgs2924rTrapEntry 15 }

fgs2924rVlanPortBaseEnabled NOTIFICATION-TYPE
 STATUS  current
 DESCRIPTION
    "Send the trap when the operational state of vlan is changed to port-based vlan."
 ::= { fgs2924rTrapEntry 17 }

fgs2924rVlanTagBaseEnabled NOTIFICATION-TYPE
 STATUS  current
 DESCRIPTION
    "Send the trap when the operational state of vlan is changed to tag-based vlan."
 ::= { fgs2924rTrapEntry 18 }

fgs2924rIpmbStateEnabled NOTIFICATION-TYPE
 STATUS  current
 DESCRIPTION
    "Send trap when ip_mac_binding is enabled."
 ::= { fgs2924rTrapEntry 19 }

fgs2924rIpmbStateDisabled NOTIFICATION-TYPE
 STATUS  current
 DESCRIPTION
    "Send trap when ip_mac_binding is disabled."
 ::= { fgs2924rTrapEntry 20 }

fgs2924rIpmbEntryFailure NOTIFICATION-TYPE
    OBJECTS   { ipmacIp, ipmacMac, ifIndex}
 STATUS  current
 DESCRIPTION
    "Send trap when ip_mac_binding entry is not exist."
 ::= { fgs2924rTrapEntry 21 }

fgs2924rTrapVariable OBJECT IDENTIFIER ::= { fgs2924rProduces 21 }

username OBJECT-TYPE
    SYNTAX      DisplayString
 MAX-ACCESS  read-only
 STATUS      current
 DESCRIPTION
     "System account name."
 ::= { fgs2924rTrapVariable 1 }

groupId OBJECT-TYPE
    SYNTAX      INTEGER(1..2147483647)
 MAX-ACCESS  read-only
 STATUS      current
 DESCRIPTION
     "The Trunk group ID of LACP."
 ::= { fgs2924rTrapVariable 2 }

actorkey OBJECT-TYPE
    SYNTAX INTEGER(1..2147483647)
 MAX-ACCESS  read-only
 STATUS      current
 DESCRIPTION
     "This is the actor key information for LACP."
 ::= { fgs2924rTrapVariable 3 }

partnerkey OBJECT-TYPE
    SYNTAX INTEGER(1..2147483647)
 MAX-ACCESS  read-only
 STATUS      current
 DESCRIPTION
     "This is the partner key information for LACP."
 ::= { fgs2924rTrapVariable 4 }

swapto OBJECT-TYPE
    SYNTAX      DisplayString
 MAX-ACCESS  read-only
 STATUS      current
 DESCRIPTION
     "A notification for dual port changes media type."
 ::= { fgs2924rTrapVariable 6 }

ipmacIp OBJECT-TYPE
    SYNTAX DisplayString
 MAX-ACCESS  read-only
 STATUS      current
 DESCRIPTION
     "IP address of the ip_mac_binding entry."
 ::= { fgs2924rTrapVariable 7 }

ipmacMac OBJECT-TYPE
    SYNTAX DisplayString
 MAX-ACCESS  read-only
 STATUS      current
 DESCRIPTION
     "MAC address of the ip_mac_binding entry."
 ::= { fgs2924rTrapVariable 8 }

END

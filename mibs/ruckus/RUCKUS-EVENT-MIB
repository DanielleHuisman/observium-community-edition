--
-- Copyright (c) 2010 by Ruckus Wireless, Inc.
-- All Rights Reserved
--

RUCKUS-EVENT-MIB DEFINITIONS ::= BEGIN

IMPORTS
    ruckusEvents
        FROM RUCKUS-ROOT-MIB
    MacAddress,
    DisplayString
        FROM SNMPv2-TC
    OBJECT-GROUP,
    MODULE-COMPLIANCE
        FROM SNMPv2-CONF
    MODULE-IDENTITY,
    OBJECT-TYPE,
    Unsigned32
        FROM SNMPv2-SMI;

ruckusEventMIB MODULE-IDENTITY
    LAST-UPDATED "201010150000Z"
    ORGANIZATION "Ruckus Wireless, Inc."
    CONTACT-INFO
        "Ruckus Wireless Inc.

        Postal:
        350 West Java Dr.
        Sunnyvale, CA 94089
        USA

        EMail: support@ruckuswireless.com

        Phone: +1-650-265-4200"
    DESCRIPTION
        "Ruckus event objects, including trap OID and trap payload."
    ::= { ruckusEvents 1 }


-- Groups
--

ruckusEventTraps OBJECT IDENTIFIER      ::= { ruckusEventMIB 1 }

ruckusEventObjects OBJECT IDENTIFIER    ::= { ruckusEventMIB 2 }


-- Ruckus Traps
--

ruckusEventAssocTrap NOTIFICATION-TYPE
    OBJECTS     { ruckusEventClientMacAddr }
    STATUS      current
    DESCRIPTION
        "Trigger when there is an client association event. 
         The client's MAC address is enclosed."
    ::= { ruckusEventTraps 1 } 


ruckusEventDiassocTrap NOTIFICATION-TYPE
    OBJECTS     { ruckusEventClientMacAddr }
    STATUS      current
    DESCRIPTION
        "Trigger when there is an client diassociation event. 
         The client's MAC address is enclosed."
    ::= { ruckusEventTraps 2 } 


ruckusEventSetErrorTrap NOTIFICATION-TYPE
    OBJECTS     { ruckusEventSetErrorOID }
    STATUS      current
    DESCRIPTION
        "Trigger when there is an snmp-set error event. 
         The OID of the snmp-set is enclosed."
    ::= { ruckusEventTraps 3 } 

ruckusEventConnectTrap NOTIFICATION-TYPE
    OBJECTS     { ruckusEventClientMacAddr }
    STATUS      current
    DESCRIPTION
        "Trigger when there is an AP connect event. 
         The AP's MAC address is enclosed."
    ::= { ruckusEventTraps 25 } 

ruckusEventDisconnectTrap NOTIFICATION-TYPE
    OBJECTS     { ruckusEventClientMacAddr }
    STATUS      current
    DESCRIPTION
        "Trigger when there is an AP disconnect event. 
         The AP's MAC address is enclosed."
    ::= { ruckusEventTraps 26 } 


--  Trap payload
--

ruckusEventClientMacAddr OBJECT-TYPE
    SYNTAX      OCTET STRING
    MAX-ACCESS  accessible-for-notify
    STATUS      current
    DESCRIPTION
        "The client's MAC address."
    ::= { ruckusEventObjects 15 }


ruckusEventSetErrorOID OBJECT-TYPE
    SYNTAX      OBJECT IDENTIFIER
    MAX-ACCESS  accessible-for-notify
    STATUS      current
    DESCRIPTION
        "OID of the error snmp-set."
    ::= { ruckusEventObjects 20 }


-- Conformance & Compliance
--

END

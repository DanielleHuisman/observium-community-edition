--
-- Copyright 2010-2014 Ruckus Wireless, Inc. All rights reserved.
--
-- RUCKUS WIRELESS, INC. CONFIDENTIAL -
-- This is an unpublished, proprietary work of Ruckus Wireless, Inc., and is
-- fully protected under copyright and trade secret laws. You may not view,
-- use, disclose, copy, or distribute this file or any information contained
-- herein except pursuant to a valid license from Ruckus.
--

RUCKUS-PRODUCTS-MIB DEFINITIONS ::= BEGIN

IMPORTS
    ruckusProducts
        FROM RUCKUS-ROOT-MIB
    TruthValue,
    DisplayString,
    MacAddress
        FROM SNMPv2-TC
    IpAddress,
    TimeTicks,
    Unsigned32,
    OBJECT-TYPE,
    MODULE-IDENTITY
        FROM SNMPv2-SMI
    RuckusCountryCode
        FROM RUCKUS-TC-MIB;


ruckusProductsMIB MODULE-IDENTITY
    LAST-UPDATED "201405191100Z"
    ORGANIZATION "Ruckus Wireless, Inc."
    CONTACT-INFO
        "Ruckus Wireless, Inc.

        350 West Java Dr.
        Sunnyvale, CA 94089
        USA

        T: +1 (650) 265-4200
        F: +1 (408) 738-2065
        EMail: info@ruckuswireless.com
        Web: www.ruckuswireless.com"
    DESCRIPTION
        "Ruckus product OID registration mib."
    ::= { ruckusProducts 1 }


-- Scalars and Tables
--

ruckusWirelessRouterProducts  OBJECT IDENTIFIER ::= { ruckusProductsMIB 1 }

ruckusWirelessAdapterProducts OBJECT IDENTIFIER ::= { ruckusProductsMIB 2 }

ruckusWirelessMetroProducts   OBJECT IDENTIFIER ::= { ruckusProductsMIB 3 }

ruckusWirelessHotzoneProducts OBJECT IDENTIFIER ::= { ruckusProductsMIB 4 }

ruckusWirelessControllerProducts OBJECT IDENTIFIER ::= { ruckusProductsMIB 5 }

ruckusWirelessSmartCellGatewayProducts OBJECT IDENTIFIER ::= { ruckusProductsMIB 10 }

ruckusWirelessSmartZoneProducts OBJECT IDENTIFIER ::= { ruckusProductsMIB 11 }

--
-- Wireless Router Products
--
-- VF2825 - 802.11b/g AP, 5 Ethernet ports, 8MB Flash, 32MB DRAM
ruckusVF2825 OBJECT IDENTIFIER  ::= { ruckusWirelessRouterProducts 1 }

-- VF2811 - 802.11b/g AP, 1 Ethernet port, 8MB Flash, 16MB DRAM
ruckusVF2811 OBJECT IDENTIFIER  ::= { ruckusWirelessRouterProducts 2 }

-- VF2821 - 802.11b/g AP, 1 Ethernet port, 8MB Flash, 32MB DRAM
ruckusVF2821 OBJECT IDENTIFIER  ::= { ruckusWirelessRouterProducts 3 }

-- VF2835 - 802.11b/g AP, 5 Ethernet ports, 16MB Flash, 32MB DRAM
ruckusVF2835 OBJECT IDENTIFIER  ::= { ruckusWirelessRouterProducts 4 }

-- VF7811 - 802.11n AP, 1 Ethernet port, 16MB Flash, 32MB DRAM
ruckusVF7811 OBJECT IDENTIFIER  ::= { ruckusWirelessRouterProducts 5 }

--
-- Wireless Adapter Products
--
-- VF2111 - 802.11b/g Adapter, 1 Ethernet port, 8MB Flash, 16MB DRAM
ruckusVF2111 OBJECT IDENTIFIER  ::= { ruckusWirelessAdapterProducts 1 }

-- VF2121 - 802.11b/g Adapter, 1 Ethernet port, 8MB Flash, 16MB DRAM
ruckusVF2121 OBJECT IDENTIFIER  ::= { ruckusWirelessAdapterProducts 2 }

-- VF7111 - 802.11n Adapter, 1 Ethernet port, 16MB Flash, 32MB DRAM
ruckusVF7111 OBJECT IDENTIFIER  ::= { ruckusWirelessAdapterProducts 3 }

--
-- Wireless Metro Products
--
-- MM2225 - 802.11b/g Metro CPE, 5 Ethernet ports, 16MB Flash, 32MB DRAM
ruckusMM2225 OBJECT IDENTIFIER  ::= { ruckusWirelessMetroProducts 1 }

-- MM2211 - 802.11b/g Metro CPE, 1 Ethernet port, 16MB Flash, 32MB DRAM
ruckusMM2211 OBJECT IDENTIFIER  ::= { ruckusWirelessMetroProducts 2 }

-- MM2221 - 802.11b/g Metro CPE, 1 Ethernet port, 16MB Flash, 32MB DRAM
ruckusMM2221 OBJECT IDENTIFIER  ::= { ruckusWirelessMetroProducts 3 }

--
-- Wireless Hotzone Products
--
-- ZF2925 - 802.11b/g AP, 5 Ethernet ports, 8MB Flash, 32MB DRAM
ruckusZF2925 OBJECT IDENTIFIER  ::= { ruckusWirelessHotzoneProducts 1 }
   
-- ZF2942 - 802.11b/g AP, 2 Ethernet ports, 16MB Flash, 32MB DRAM
ruckusZF2942 OBJECT IDENTIFIER  ::= { ruckusWirelessHotzoneProducts 2 }
 
-- ZF7942 - 802.11n AP, 2 Ethernet ports, 16MB Flash, 64MB DRAM
ruckusZF7942 OBJECT IDENTIFIER  ::= { ruckusWirelessHotzoneProducts 3 }

-- ZF7962 - 802.11n Dual-Band AP, 2 Ethernet ports, 16B Flash, 64MB DRAM
ruckusZF7962 OBJECT IDENTIFIER  ::= { ruckusWirelessHotzoneProducts 4 }

-- ZF2741 - 802.11b/g AP, 1 Ethernet ports, 16MB Flash, 32MB DRAM
ruckusZF2741 OBJECT IDENTIFIER  ::= { ruckusWirelessHotzoneProducts 5 }

-- ZF7762 - 802.11n Dual-Band Outdoor AP, 2 Ethernet ports, 16MB Flash, 32MB DRAM
ruckusZF7762 OBJECT IDENTIFIER  ::= { ruckusWirelessHotzoneProducts 6 }

-- ZF7762-S -
ruckusZF7762S OBJECT IDENTIFIER  ::= { ruckusWirelessHotzoneProducts 8 }

-- ZF7762-T -
ruckusZF7762T OBJECT IDENTIFIER  ::= { ruckusWirelessHotzoneProducts 9 }
   
-- ZF7762-N -
ruckusZF7762N OBJECT IDENTIFIER  ::= { ruckusWirelessHotzoneProducts 10 }
   
-- ZF7343 -
ruckusZF7343 OBJECT IDENTIFIER  ::= { ruckusWirelessHotzoneProducts 12 }
   
-- ZF7363 -
ruckusZF7363 OBJECT IDENTIFIER  ::= { ruckusWirelessHotzoneProducts 13 }
   
-- ZF7341 -
ruckusZF7341 OBJECT IDENTIFIER  ::= { ruckusWirelessHotzoneProducts 14 }

-- ZF7211 -
--ruckusZF7211 OBJECT IDENTIFIER  ::= { ruckusWirelessHotzoneProducts 15 }

-- ZF7731 -
ruckusZF7731 OBJECT IDENTIFIER  ::= { ruckusWirelessHotzoneProducts 16 }

-- ZF7025 -
ruckusZF7025 OBJECT IDENTIFIER  ::= { ruckusWirelessHotzoneProducts 20 }

-- ZF7321 -
ruckusZF7321 OBJECT IDENTIFIER  ::= { ruckusWirelessHotzoneProducts 22 }

-- ZF7321-U -
ruckusZF7321U OBJECT IDENTIFIER  ::= { ruckusWirelessHotzoneProducts 23 }

-- ZF2741-EXT -
ruckusZF2741EXT OBJECT IDENTIFIER  ::= { ruckusWirelessHotzoneProducts 24 }

-- ZF7982 -
ruckusZF7982 OBJECT IDENTIFIER  ::= { ruckusWirelessHotzoneProducts 25 }

-- ZF7782 -
ruckusZF7782 OBJECT IDENTIFIER  ::= { ruckusWirelessHotzoneProducts 28 }

-- ZF7782-S -
ruckusZF7782S OBJECT IDENTIFIER  ::= { ruckusWirelessHotzoneProducts 29 }

-- ZF7782-N -
ruckusZF7782N OBJECT IDENTIFIER  ::= { ruckusWirelessHotzoneProducts 30 }

-- ZF7782-E -
ruckusZF7782E OBJECT IDENTIFIER  ::= { ruckusWirelessHotzoneProducts 31 }

-- ZF8800-s-ac -
ruckusZF8800SAC OBJECT IDENTIFIER  ::= { ruckusWirelessHotzoneProducts 32 }

-- ZF7762-AC -
ruckusZF7762AC OBJECT IDENTIFIER  ::= { ruckusWirelessHotzoneProducts 35 }

-- ZF7762-S-AC -
ruckusZF7762SAC OBJECT IDENTIFIER  ::= { ruckusWirelessHotzoneProducts 36 }

-- ZF7762-T-AC -
ruckusZF7762TAC OBJECT IDENTIFIER  ::= { ruckusWirelessHotzoneProducts 37 }

-- ZF7372 -
ruckusZF7372 OBJECT IDENTIFIER  ::= { ruckusWirelessHotzoneProducts 40 }

-- ZF7372-E -
ruckusZF7372E OBJECT IDENTIFIER  ::= { ruckusWirelessHotzoneProducts 41 }

-- ZF7441 -
ruckusZF7441 OBJECT IDENTIFIER  ::= { ruckusWirelessHotzoneProducts 42 }

-- ZF7352 -
ruckusZF7352 OBJECT IDENTIFIER  ::= { ruckusWirelessHotzoneProducts 45 }

-- ZF7351 -
ruckusZF7351 OBJECT IDENTIFIER  ::= { ruckusWirelessHotzoneProducts 48 }

-- ZF7742 -
ruckusZF7742 OBJECT IDENTIFIER  ::= { ruckusWirelessHotzoneProducts 50 }

-- ZF7055 -
ruckusZF7055 OBJECT IDENTIFIER  ::= { ruckusWirelessHotzoneProducts 52 }

-- ZF7781-M -
ruckusZF7781M OBJECT IDENTIFIER  ::= { ruckusWirelessHotzoneProducts 55 }

-- ZF7781CM -
ruckusZF7781CM OBJECT IDENTIFIER  ::= { ruckusWirelessHotzoneProducts 56 }

-- ZF7781CM-E -
ruckusZF7781CME OBJECT IDENTIFIER  ::= { ruckusWirelessHotzoneProducts 57 }

-- ZF7781CM-S -
ruckusZF7781CMS OBJECT IDENTIFIER  ::= { ruckusWirelessHotzoneProducts 58 }

-- ZF7781-FN -
ruckusZF7781FN OBJECT IDENTIFIER  ::= { ruckusWirelessHotzoneProducts 60 }

-- ZF7781-FN-E -
ruckusZF7781FNE OBJECT IDENTIFIER  ::= { ruckusWirelessHotzoneProducts 61 }

-- ZF7781-FN-S -
ruckusZF7781FNS OBJECT IDENTIFIER  ::= { ruckusWirelessHotzoneProducts 62 }

-- SC8800-S-AC -
ruckusSC8800SAC OBJECT IDENTIFIER  ::= { ruckusWirelessHotzoneProducts 65 }

-- SC8800-S -
ruckusSC8800S OBJECT IDENTIFIER  ::= { ruckusWirelessHotzoneProducts 66 }

-- R300 -
ruckusR300 OBJECT IDENTIFIER  ::= { ruckusWirelessHotzoneProducts 67 }

-- R700 -
ruckusR700 OBJECT IDENTIFIER  ::= { ruckusWirelessHotzoneProducts 68 }

-- R710 -
ruckusR710 OBJECT IDENTIFIER  ::= { ruckusWirelessHotzoneProducts 69 }

-- R500E -
ruckusR500E OBJECT IDENTIFIER  ::= { ruckusWirelessHotzoneProducts 70 }

-- R500 -
ruckusR500 OBJECT IDENTIFIER  ::= { ruckusWirelessHotzoneProducts 71 }

-- R600 -
ruckusR600 OBJECT IDENTIFIER  ::= { ruckusWirelessHotzoneProducts 72 }

-- T300 -
ruckusT300 OBJECT IDENTIFIER  ::= { ruckusWirelessHotzoneProducts 74 }

-- T300E -
ruckusT300E OBJECT IDENTIFIER  ::= { ruckusWirelessHotzoneProducts 75 }

-- T301N -
ruckusT301N OBJECT IDENTIFIER  ::= { ruckusWirelessHotzoneProducts 76 }

-- T301S -
ruckusT301S OBJECT IDENTIFIER  ::= { ruckusWirelessHotzoneProducts 77 }

-- H500
ruckusH500 OBJECT IDENTIFIER  ::= { ruckusWirelessHotzoneProducts 78 }

-- C500
ruckusC500 OBJECT IDENTIFIER  ::= { ruckusWirelessHotzoneProducts 79 }

-- P300
ruckusP300 OBJECT IDENTIFIER  ::= { ruckusWirelessHotzoneProducts 81 }

-- FZM300
ruckusFZM300 OBJECT IDENTIFIER  ::= { ruckusWirelessHotzoneProducts 85 }

-- FZP300
ruckusFZP300 OBJECT IDENTIFIER  ::= { ruckusWirelessHotzoneProducts 86 }

-- R310
ruckusR310 OBJECT IDENTIFIER  ::= { ruckusWirelessHotzoneProducts 88 }

-- R320
ruckusR320 OBJECT IDENTIFIER  ::= { ruckusWirelessHotzoneProducts 89 }

-- T710
ruckusT710 OBJECT IDENTIFIER  ::= { ruckusWirelessHotzoneProducts 90 }

-- R510
ruckusR510 OBJECT IDENTIFIER  ::= { ruckusWirelessHotzoneProducts 91 }

-- H510
ruckusH510 OBJECT IDENTIFIER  ::= { ruckusWirelessHotzoneProducts 92 }

-- H320
ruckusH320 OBJECT IDENTIFIER  ::= { ruckusWirelessHotzoneProducts 93 }

-- E510 -
ruckusE510 OBJECT IDENTIFIER  ::= { ruckusWirelessHotzoneProducts 94 }

-- C110
ruckusC110 OBJECT IDENTIFIER  ::= { ruckusWirelessHotzoneProducts 95 }

-- CMM310
ruckusCMM310 OBJECT IDENTIFIER  ::= { ruckusWirelessHotzoneProducts 96 }

-- T811CM
ruckusT811CM OBJECT IDENTIFIER  ::= { ruckusWirelessHotzoneProducts 97 }

-- T610S
ruckusT610S OBJECT IDENTIFIER  ::= { ruckusWirelessHotzoneProducts 99 }

-- R610
ruckusR610 OBJECT IDENTIFIER  ::= { ruckusWirelessHotzoneProducts 100 }

-- T610
ruckusT610 OBJECT IDENTIFIER  ::= { ruckusWirelessHotzoneProducts 101 }

-- R720
ruckusR720 OBJECT IDENTIFIER  ::= { ruckusWirelessHotzoneProducts 102 }

-- T310C -
ruckusT310C OBJECT IDENTIFIER  ::= { ruckusWirelessHotzoneProducts 103 }

-- T310D -
ruckusT310D OBJECT IDENTIFIER  ::= { ruckusWirelessHotzoneProducts 104 }

-- T310N -
ruckusT310N OBJECT IDENTIFIER  ::= { ruckusWirelessHotzoneProducts 105 }

-- T310S -
ruckusT310S OBJECT IDENTIFIER  ::= { ruckusWirelessHotzoneProducts 106 }

-- M510 -
ruckusM510 OBJECT IDENTIFIER  ::= { ruckusWirelessHotzoneProducts 107 }

-- R730 -
ruckusR730 OBJECT IDENTIFIER  ::= { ruckusWirelessHotzoneProducts 108 }

-- R750 -
ruckusR750 OBJECT IDENTIFIER  ::= { ruckusWirelessHotzoneProducts 109 }

-- T305I -
ruckusT305I OBJECT IDENTIFIER  ::= { ruckusWirelessHotzoneProducts 110 }

-- T305E -
ruckusT305E OBJECT IDENTIFIER  ::= { ruckusWirelessHotzoneProducts 111 }

-- T750 -
ruckusT750 OBJECT IDENTIFIER  ::= { ruckusWirelessHotzoneProducts 112 }

-- R650 -
ruckusR650 OBJECT IDENTIFIER  ::= { ruckusWirelessHotzoneProducts 113 }

-- R550 -
ruckusR550 OBJECT IDENTIFIER  ::= { ruckusWirelessHotzoneProducts 114 }

-- R850 -
ruckusR850 OBJECT IDENTIFIER  ::= { ruckusWirelessHotzoneProducts 115 }

-- T750SE -
ruckusT750SE OBJECT IDENTIFIER  ::= { ruckusWirelessHotzoneProducts 116 }

-- H550 -
ruckusH550 OBJECT IDENTIFIER  ::= { ruckusWirelessHotzoneProducts 117 }

-- T350C -
ruckusT350C OBJECT IDENTIFIER  ::= { ruckusWirelessHotzoneProducts 118 }

-- T350D -
ruckusT350D OBJECT IDENTIFIER  ::= { ruckusWirelessHotzoneProducts 119 }

-- T350NS -
ruckusT350NS OBJECT IDENTIFIER  ::= { ruckusWirelessHotzoneProducts 120 }

-- R350 -
ruckusR350 OBJECT IDENTIFIER  ::= { ruckusWirelessHotzoneProducts 121 }

ruckusC110ControlLED OBJECT-TYPE
   SYNTAX  INTEGER {
         softResetAP(10),
         factoryResetAP(12),
         softResetCM(13),
         factoryResetCM(15) }
    MAX-ACCESS read-write
    STATUS current
    DESCRIPTION
        "softResetAP(10):                  Soft reset of Access Point,
         factoryResetAP(12):               Reset Access Point to factory defaults,
         softResetCM(13):                  Soft reset of Cable Modem,
         factoryResetCM(15):               Reset Cable Modem to factory defaults"
    DEFVAL { ledPerCM }
    ::= { ruckusC110 3 }

ruckusC110WanIPAddr OBJECT-TYPE
    SYNTAX  IpAddress
    MAX-ACCESS read-only
    STATUS current
    DESCRIPTION
        "Specifies the IP address of the Cable Modem WAN interface."
    ::= { ruckusC110 4 }

ruckusC110Customization OBJECT IDENTIFIER          ::= { ruckusC110 5 }

ruckusC110HTTPService OBJECT-TYPE
    SYNTAX  TruthValue
    MAX-ACCESS read-write
    STATUS current
    DESCRIPTION
        "Enable/disable HTTP service."
    DEFVAL { false }
    ::= { ruckusC110Customization 1 }

ruckusC110TelnetService OBJECT-TYPE
    SYNTAX  TruthValue
    MAX-ACCESS read-write
    STATUS current
    DESCRIPTION
        "Enable/disable Telnet service."
    DEFVAL { false }
    ::= { ruckusC110Customization 2 }

ruckusC110SSHService OBJECT-TYPE
    SYNTAX  TruthValue
    MAX-ACCESS read-write
    STATUS current
    DESCRIPTION
        "Enable/disable SSH service."
    DEFVAL { true }
    ::= { ruckusC110Customization 3 }

ruckusC110Username OBJECT-TYPE
    SYNTAX  DisplayString (SIZE (1..64))
    MAX-ACCESS read-write
    STATUS current
    DESCRIPTION
        "Specifies username of cable modem. "
    ::= { ruckusC110Customization 4 }

ruckusC110Password OBJECT-TYPE
    SYNTAX  DisplayString (SIZE (1..64))
    MAX-ACCESS read-write
    STATUS current
    DESCRIPTION
        "Specifies password of cable modem. "
    ::= { ruckusC110Customization 5 }

ruckusC110CpeAgingOutTimer OBJECT-TYPE
    SYNTAX  INTEGER (0..86400)
    MAX-ACCESS read-write
    STATUS current
    DESCRIPTION
        "While CM is adding the CPE in the learning table, 
        if it reaches the number of MAX CPE it will remove 
        the existing CPE which has no upstream traffic for N seconds. 
        Where N is the value of this MIB. 
        N=0 means to follow original implementation. 
        That is no CPE will be removed for any new comers."
        DEFVAL { 0 }
    ::= { ruckusC110 9 }

ruckusC110WanIPV6Addr OBJECT-TYPE
    SYNTAX  DisplayString (SIZE (2..40))
    MAX-ACCESS read-only
    STATUS current
    DESCRIPTION
         "Specifies the IPV6 address of the Cable Modem WAN interface."    
    ::= { ruckusC110 10 }

ruckusT811CMControlLED OBJECT-TYPE
   SYNTAX  INTEGER {
         softResetAP(10),
         factoryResetAP(12),
         softResetCM(13),
         factoryResetCM(15) }
    MAX-ACCESS read-write
    STATUS current
    DESCRIPTION
        "softResetAP(10):                  Soft reset of Access Point,
         factoryResetAP(12):               Reset Access Point to factory defaults,
         softResetCM(13):                  Soft reset of Cable Modem,
         factoryResetCM(15):               Reset Cable Modem to factory defaults"
    DEFVAL { ledPerCM }
    ::= { ruckusT811CM 3 }

ruckusCMM310WanIPAddr OBJECT-TYPE
    SYNTAX  IpAddress
    MAX-ACCESS read-only
    STATUS current
    DESCRIPTION
        "Specifies the IP address of the Cable Modem WAN interface."
    ::= { ruckusT811CM 4 }

ruckusCMM310WanIPV6Addr OBJECT-TYPE
    SYNTAX  DisplayString (SIZE (2..40))
    MAX-ACCESS read-only
    STATUS current
    DESCRIPTION
         "Specifies the IPV6 address of the Cable Modem WAN interface."    
    ::= { ruckusT811CM 10 }

ruckusCMM310ControlLED OBJECT-TYPE
   SYNTAX  INTEGER {
         softResetAP(10),
         factoryResetAP(12),
         softResetCM(13),
         factoryResetCM(15) }
    MAX-ACCESS read-write
    STATUS current
    DESCRIPTION
        "softResetAP(10):                  Soft reset of Access Point,
         factoryResetAP(12):               Reset Access Point to factory defaults,
         softResetCM(13):                  Soft reset of Cable Modem,
         factoryResetCM(15):               Reset Cable Modem to factory defaults"
    DEFVAL { ledPerCM }
    ::= { ruckusCMM310 3 }

ruckusCMM310WanIPAddr OBJECT-TYPE
    SYNTAX  IpAddress
    MAX-ACCESS read-only
    STATUS current
    DESCRIPTION
        "Specifies the IP address of the Cable Modem WAN interface."
    ::= { ruckusCMM310 4 }

ruckusCMM310Customization OBJECT IDENTIFIER          ::= { ruckusCMM310 5 }

ruckusCMM310HTTPService OBJECT-TYPE
    SYNTAX  TruthValue
    MAX-ACCESS read-write
    STATUS current
    DESCRIPTION
        "Enable/disable HTTP service."
    DEFVAL { false }
    ::= { ruckusCMM310Customization 1 }

ruckusCMM310TelnetService OBJECT-TYPE
    SYNTAX  TruthValue
    MAX-ACCESS read-write
    STATUS current
    DESCRIPTION
        "Enable/disable Telnet service."
    DEFVAL { false }
    ::= { ruckusCMM310Customization 2 }

ruckusCMM310SSHService OBJECT IDENTIFIER             ::= { ruckusCMM310Customization 3 }

ruckusCMM310SSHLanService OBJECT-TYPE
    SYNTAX  TruthValue
    MAX-ACCESS read-write
    STATUS current
    DESCRIPTION
        "Enable/disable SSH service for Lan."
    DEFVAL { true }
    ::= { ruckusCMM310SSHService 1 }

ruckusCMM310SSHWanService OBJECT-TYPE
    SYNTAX  TruthValue
    MAX-ACCESS read-write
    STATUS current
    DESCRIPTION
        "Enable/disable SSH service for Wan."
    DEFVAL { false }
    ::= { ruckusCMM310SSHService 2 }

ruckusCMM310Username OBJECT-TYPE
    SYNTAX  DisplayString (SIZE (1..64))
    MAX-ACCESS read-write
    STATUS current
    DESCRIPTION
        "Specifies username of cable modem. "
    ::= { ruckusCMM310Customization 4 }

ruckusCMM310Password OBJECT-TYPE
    SYNTAX  DisplayString (SIZE (1..64))
    MAX-ACCESS read-write
    STATUS current
    DESCRIPTION
        "Specifies password of cable modem. "
    ::= { ruckusCMM310Customization 5 }

ruckusCMM310SKUInformation OBJECT IDENTIFIER   ::= { ruckusCMM310Customization 6 }

ruckusCMM310SKUID OBJECT-TYPE
    SYNTAX  INTEGER {
        ruckusCMM310-001(1),
        ruckusCMM310-002(2),
        ruckusCMM310-003(3),
        ruckusCMM310-004(4),
        ruckusCMM310-005(5) }
    MAX-ACCESS read-only
    STATUS current
    DESCRIPTION
        "Specifies the cable modem SKU
        SKU ID                                              RF CAPABILITY                          DEFAULT SPLIT
        ruckusCMM310-001(1):Base (NA) DOCSIS 3.1 SKU       (5-42, 108-1218), (5-85, 108-1218)     (5-85, 108-1218)
        ruckusCMM310-002(2):Charter (NA) DOCSIS 3.1 SKU    (5-46, 258-1218), (5-204, 258-1218)    (5-204, 258-1218)
        ruckusCMM310-003(3):Base (Euro) DOCSIS 3.1 SKU     (5-65, 258-1218), (5-204, 258-1218)    (5-204, 258-1218)
        ruckusCMM310-004(4):Base (NA) DOCSIS 3.0 SKU       (5-42, 54-1002)                        (5-42, 54-1002)
        ruckusCMM310-005(5):Base (Euro) DOCSIS 3.0 SKU     (5-65, 87.5-1002)                      (5-65, 87.5-1002)."
    ::= { ruckusCMM310SKUInformation 1 }

ruckusCMM310SKUCurrentRFSplit OBJECT-TYPE
    SYNTAX DisplayString (SIZE (1..256))
    MAX-ACCESS read-only
    STATUS current
    DESCRIPTION
        "Specifies the RF Split for the given SKU."
    ::= { ruckusCMM310SKUInformation 2 }

ruckusCMM310EthernetMonitorService OBJECT-TYPE
    SYNTAX  TruthValue
    MAX-ACCESS read-write
    STATUS current
    DESCRIPTION
        "Enable/disable Ethernet Monitor Service.
	 For Ruckus Internal use only."
    DEFVAL { true }
    ::= { ruckusCMM310Customization 7 }

ruckusCMM310CpeAgingOutTimer OBJECT-TYPE
    SYNTAX  INTEGER (0..86400)
    MAX-ACCESS read-write
    STATUS current
    DESCRIPTION
        "While CM is adding the CPE in the learning table,
        if it reaches the number of MAX CPE it will remove
        the existing CPE which has no upstream traffic for N seconds.
        Where N is the value of this MIB.
        N=0 means to follow original implementation.
        That is no CPE will be removed for any newcomer."
        DEFVAL { 0 }
    ::= { ruckusCMM310 9 }

ruckusCMM310WanIPV6Addr OBJECT-TYPE
    SYNTAX  DisplayString (SIZE (2..40))
    MAX-ACCESS read-only
    STATUS current
    DESCRIPTION
         "Specifies the IPV6 address of the Cable Modem WAN interface."
    ::= { ruckusCMM310 10 }

-- ZF7761CM - 802.11n Dual-Band Outdoor AP with CableModem, 2 Ethernet ports, 16MB Flash, 32MB DRAM
ruckusZF7761CM OBJECT IDENTIFIER  ::= { ruckusWirelessHotzoneProducts 7 }

ruckusZF7761CMControlLED OBJECT-TYPE
   SYNTAX  INTEGER {
         ledPerCM(1),
         ledPerAP(2),
         ledAlternateMode1Mode2OneHour(3),
         ledAlternateMode1Mode2Mode6(4),
         blueActive(5),
         blueActiveCMOnlineLed(6),
         ledAllOff(7),
         heartbeatOffCM(8),
         heartbeatOffAP(9),
         softResetAP(10),
         powerCycleAP(11),
         factoryResetAP(12),
         softResetCM(13),
         powerCycleCM(14),
         factoryResetCM(15) }
    MAX-ACCESS read-write
    STATUS current
    DESCRIPTION
        "ledPerCM(1):                      LEDs enabled per Cable Modem definition,
         ledPerAP(2):                      LEDs configured per Access Point definition,
         ledAlternateMode1Mode2OneHour(3): Alternalte between modes 1 and 2 at a 30 second period then disabled after one hour,
         ledAlternateMode1Mode2Mode6(4):   Alternalte between modes 1 and 2 at a 30 second period and then go to mode 6
         blueActive(5):                    Blue Active Surge Protection Indicator,
         blueActiveCMOnlineLed(6):         Blue Active Surge Protection Indicator and Cable Modem online Green LED enabled,
         ledAllOff(7):                     All LEDs disabled,
         heartbeatOffCM(8):                Disable Cable Modem heartbeat monitoring,
         heartbeatOffAP(9):                Disable Access Point heartbeat monitoring,
         softResetAP(10):                  Soft reset of Access Point,
         powerCycleAP(11):                 Power cycle Access Point,
         factoryResetAP(12):               Reset Access Point to factory defaults,
         softResetCM(13):                  Soft reset of Cable Modem,
         powerCycleCM(14):                 Power cycle Cable Modem,
         factoryResetCM(15):               Reset Cable Modem to factory defaults"
    DEFVAL { ledPerCM }
    ::= { ruckusZF7761CM 3 }

ruckusZF7761CMWanIPAddr OBJECT-TYPE
    SYNTAX  IpAddress
    MAX-ACCESS read-only
    STATUS current
    DESCRIPTION
        "Specifies the IP address of the Cable Modem WAN interface."
    ::= { ruckusZF7761CM 4 }

ruckusZF7761CMCustomization OBJECT IDENTIFIER          ::= { ruckusZF7761CM 5 }

ruckusZF7761CMHTTPService OBJECT-TYPE
    SYNTAX  TruthValue
    MAX-ACCESS read-write
    STATUS current
    DESCRIPTION
        "Enable/disable HTTP service."
    DEFVAL { false }
    ::= { ruckusZF7761CMCustomization 1 }

ruckusZF7761CMTelnetService OBJECT-TYPE
    SYNTAX  TruthValue
    MAX-ACCESS read-write
    STATUS current
    DESCRIPTION
        "Enable/disable Telnet service."
    DEFVAL { false }
    ::= { ruckusZF7761CMCustomization 2 }

ruckusZF7761CMSSHService OBJECT-TYPE
    SYNTAX  TruthValue
    MAX-ACCESS read-write
    STATUS current
    DESCRIPTION
        "Enable/disable SSH service."
    DEFVAL { true }
    ::= { ruckusZF7761CMCustomization 3 }

ruckusZF7761CMUsername OBJECT-TYPE
    SYNTAX  DisplayString (SIZE (1..64))
    MAX-ACCESS read-write
    STATUS current
    DESCRIPTION
        "Specifies username of cable modem. "
    ::= { ruckusZF7761CMCustomization 4 }

ruckusZF7761CMPassword OBJECT-TYPE
    SYNTAX  DisplayString (SIZE (1..64))
    MAX-ACCESS read-write
    STATUS current
    DESCRIPTION
        "Specifies password of cable modem. "
    ::= { ruckusZF7761CMCustomization 5 }

ruckusZF7761CMLEDMode OBJECT-TYPE
    SYNTAX  INTEGER {
         ledAllOff(0),
         blueActive(1),
         blueActiveCMOnlineLed(2) }
    MAX-ACCESS read-write
    STATUS current
    DESCRIPTION
        "ledAllOff(0):               All LEDs disabled after 3 second delay,
         blueActive(1):              Blue Active Surge Protection Indicator,
         blueActiveCMOnlineLed(2):   Blue Active Surge Protection Indicator and Cable Modem online Green LED enabled"
    ::= { ruckusZF7761CM 6 }

ruckusZF7761CMHeartbeatMonitorCM OBJECT-TYPE
    SYNTAX  TruthValue
    MAX-ACCESS read-write
    STATUS current
    DESCRIPTION
        "Enable/disable Cable Modem heartbeat monitoring."

    ::= { ruckusZF7761CM 7 }

ruckusZF7761CMHeartbeatMonitorAP OBJECT-TYPE
    SYNTAX  TruthValue
    MAX-ACCESS read-write
    STATUS current
    DESCRIPTION
         "Enable/disable Access Point heartbeat monitoring."    ::= { ruckusZF7761CM 8 }
--
-- Wireless Controller Products
--
-- ZD1000 - Access Controller, 2 Ethernet ports, 32MB Flash, 64MB DRAM
ruckusZD1000 OBJECT IDENTIFIER  ::= { ruckusWirelessControllerProducts 1 }

-- ZD1100 - Access Controller, 2 Ethernet ports
ruckusZD1100 OBJECT IDENTIFIER  ::= { ruckusWirelessControllerProducts 2 }

-- ZD3000 - Access Controller, 2 Ethernet ports, 2048MB Flash, 1024MB DRAM
ruckusZD3000 OBJECT IDENTIFIER  ::= { ruckusWirelessControllerProducts 3 }

-- ZD5000 - Access Controller,
ruckusZD5000 OBJECT IDENTIFIER  ::= { ruckusWirelessControllerProducts 8 }

-- ZD6000 - Access Controller,
--ruckusZD6000 OBJECT IDENTIFIER  ::= { ruckusWirelessControllerProducts 9 }

-- ZD1200 - Access Controller, 2 Ethernet ports, 2048MB Flash, 2048MB DRAM
ruckusZD1200 OBJECT IDENTIFIER  ::= { ruckusWirelessControllerProducts 15 }

ruckusZD1000SystemName OBJECT-TYPE
    SYNTAX  DisplayString
    MAX-ACCESS read-only
    STATUS current
    DESCRIPTION
        "System name"
    ::= { ruckusZD1000 1 }

ruckusZD1000SystemIPAddr OBJECT-TYPE
    SYNTAX  IpAddress
    MAX-ACCESS read-only
    STATUS current
    DESCRIPTION
        "IP Address"
    ::= { ruckusZD1000 2 }

ruckusZD1000SystemMacAddr OBJECT-TYPE
    SYNTAX  MacAddress
    MAX-ACCESS read-only
    STATUS current
    DESCRIPTION
        "MAC Address"
    ::= { ruckusZD1000 3 }

ruckusZD1000SystemUptime OBJECT-TYPE
    SYNTAX  TimeTicks
    MAX-ACCESS read-only
    STATUS current
    DESCRIPTION
        "Up time"
    ::= { ruckusZD1000 4 }

ruckusZD1000SystemModel OBJECT-TYPE
    SYNTAX  DisplayString
    MAX-ACCESS read-only
    STATUS current
    DESCRIPTION
        "Model"
    ::= { ruckusZD1000 5 }

ruckusZD1000SystemLicensedAPs OBJECT-TYPE
    SYNTAX  Unsigned32
    MAX-ACCESS read-only
    STATUS current
    DESCRIPTION
        "Licensed APs"
    ::= { ruckusZD1000 6 }

ruckusZD1000SystemSerialNumber OBJECT-TYPE
    SYNTAX  DisplayString
    MAX-ACCESS read-only
    STATUS current
    DESCRIPTION
        "Serial number"
    ::= { ruckusZD1000 7 }

ruckusZD1000SystemVersion OBJECT-TYPE
    SYNTAX  DisplayString
    MAX-ACCESS read-only
    STATUS current
    DESCRIPTION
        "Software version"
    ::= { ruckusZD1000 8 }

ruckusZD1000CountryCode OBJECT-TYPE
    SYNTAX  RuckusCountryCode
    MAX-ACCESS read-only
    STATUS current
    DESCRIPTION
        "Country code"
    ::= { ruckusZD1000 9 }


ruckusZD1100SystemName OBJECT-TYPE
    SYNTAX  DisplayString
    MAX-ACCESS read-only
    STATUS current
    DESCRIPTION
        "System name"
    ::= { ruckusZD1100 1 }

ruckusZD1100SystemIPAddr OBJECT-TYPE
    SYNTAX  IpAddress
    MAX-ACCESS read-only
    STATUS current
    DESCRIPTION
        "IP Address"
    ::= { ruckusZD1100 2 }

ruckusZD1100SystemMacAddr OBJECT-TYPE
    SYNTAX  MacAddress
    MAX-ACCESS read-only
    STATUS current
    DESCRIPTION
        "MAC Address"
    ::= { ruckusZD1100 3 }

ruckusZD1100SystemUptime OBJECT-TYPE
    SYNTAX  TimeTicks
    MAX-ACCESS read-only
    STATUS current
    DESCRIPTION
        "Up time"
    ::= { ruckusZD1100 4 }

ruckusZD1100SystemModel OBJECT-TYPE
    SYNTAX  DisplayString
    MAX-ACCESS read-only
    STATUS current
    DESCRIPTION
        "Model"
    ::= { ruckusZD1100 5 }

ruckusZD1100SystemLicensedAPs OBJECT-TYPE
    SYNTAX  Unsigned32
    MAX-ACCESS read-only
    STATUS current
    DESCRIPTION
        "Licensed APs"
    ::= { ruckusZD1100 6 }

ruckusZD1100SystemSerialNumber OBJECT-TYPE
    SYNTAX  DisplayString
    MAX-ACCESS read-only
    STATUS current
    DESCRIPTION
        "Serial number"
    ::= { ruckusZD1100 7 }

ruckusZD1100SystemVersion OBJECT-TYPE
    SYNTAX  DisplayString
    MAX-ACCESS read-only
    STATUS current
    DESCRIPTION
        "Software version"
    ::= { ruckusZD1100 8 }

ruckusZD1100CountryCode OBJECT-TYPE
    SYNTAX  RuckusCountryCode
    MAX-ACCESS read-only
    STATUS current
    DESCRIPTION
        "Country code"
    ::= { ruckusZD1100 9 }



ruckusZD3000SystemName OBJECT-TYPE
    SYNTAX  DisplayString
    MAX-ACCESS read-only
    STATUS current
    DESCRIPTION
        "System name"
    ::= { ruckusZD3000 1 }

ruckusZD3000SystemIPAddr OBJECT-TYPE
    SYNTAX  IpAddress
    MAX-ACCESS read-only
    STATUS current
    DESCRIPTION
        "IP Address"
    ::= { ruckusZD3000 2 }

ruckusZD3000SystemMacAddr OBJECT-TYPE
    SYNTAX  MacAddress
    MAX-ACCESS read-only
    STATUS current
    DESCRIPTION
        "MAC Address"
    ::= { ruckusZD3000 3 }

ruckusZD3000SystemUptime OBJECT-TYPE
    SYNTAX  TimeTicks
    MAX-ACCESS read-only
    STATUS current
    DESCRIPTION
        "Up time"
    ::= { ruckusZD3000 4 }

ruckusZD3000SystemModel OBJECT-TYPE
    SYNTAX  DisplayString
    MAX-ACCESS read-only
    STATUS current
    DESCRIPTION
        "Model"
    ::= { ruckusZD3000 5 }

ruckusZD3000SystemLicensedAPs OBJECT-TYPE
    SYNTAX  Unsigned32
    MAX-ACCESS read-only
    STATUS current
    DESCRIPTION
        "Licensed APs"
    ::= { ruckusZD3000 6 }

ruckusZD3000SystemSerialNumber OBJECT-TYPE
    SYNTAX  DisplayString
    MAX-ACCESS read-only
    STATUS current
    DESCRIPTION
        "Serial number"
    ::= { ruckusZD3000 7 }

ruckusZD3000SystemVersion OBJECT-TYPE
    SYNTAX  DisplayString
    MAX-ACCESS read-only
    STATUS current
    DESCRIPTION
        "Software version"
    ::= { ruckusZD3000 8 }

ruckusZD3000CountryCode OBJECT-TYPE
    SYNTAX  RuckusCountryCode
    MAX-ACCESS read-only
    STATUS current
    DESCRIPTION
        "Country code"
    ::= { ruckusZD3000 9 }


ruckusZD5000SystemName OBJECT-TYPE
    SYNTAX  DisplayString
    MAX-ACCESS read-only
    STATUS current
    DESCRIPTION
        "System name"
    ::= { ruckusZD5000 1 }

ruckusZD5000SystemIPAddr OBJECT-TYPE
    SYNTAX  IpAddress
    MAX-ACCESS read-only
    STATUS current
    DESCRIPTION
        "IP Address"
    ::= { ruckusZD5000 2 }

ruckusZD5000SystemMacAddr OBJECT-TYPE
    SYNTAX  MacAddress
    MAX-ACCESS read-only
    STATUS current
    DESCRIPTION
        "MAC Address"
    ::= { ruckusZD5000 3 }

ruckusZD5000SystemUptime OBJECT-TYPE
    SYNTAX  TimeTicks
    MAX-ACCESS read-only
    STATUS current
    DESCRIPTION
        "Up time"
    ::= { ruckusZD5000 4 }

ruckusZD5000SystemModel OBJECT-TYPE
    SYNTAX  DisplayString
    MAX-ACCESS read-only
    STATUS current
    DESCRIPTION
        "Model"
    ::= { ruckusZD5000 5 }

ruckusZD5000SystemLicensedAPs OBJECT-TYPE
    SYNTAX  Unsigned32
    MAX-ACCESS read-only
    STATUS current
    DESCRIPTION
        "Licensed APs"
    ::= { ruckusZD5000 6 }

ruckusZD5000SystemSerialNumber OBJECT-TYPE
    SYNTAX  DisplayString
    MAX-ACCESS read-only
    STATUS current
    DESCRIPTION
        "Serial number"
    ::= { ruckusZD5000 7 }

ruckusZD5000SystemVersion OBJECT-TYPE
    SYNTAX  DisplayString
    MAX-ACCESS read-only
    STATUS current
    DESCRIPTION
        "Software version"
    ::= { ruckusZD5000 8 }

ruckusZD5000CountryCode OBJECT-TYPE
    SYNTAX  RuckusCountryCode
    MAX-ACCESS read-only
    STATUS current
    DESCRIPTION
        "Country code"
    ::= { ruckusZD5000 9 }

ruckusZD1200SystemName OBJECT-TYPE
    SYNTAX  DisplayString
    MAX-ACCESS read-only
    STATUS current
    DESCRIPTION
        "System name"
    ::= { ruckusZD1200 1 }

ruckusZD1200SystemIPAddr OBJECT-TYPE
    SYNTAX  IpAddress
    MAX-ACCESS read-only
    STATUS current
    DESCRIPTION
        "IP Address"
    ::= { ruckusZD1200 2 }

ruckusZD1200SystemMacAddr OBJECT-TYPE
    SYNTAX  MacAddress
    MAX-ACCESS read-only
    STATUS current
    DESCRIPTION
        "MAC Address"
    ::= { ruckusZD1200 3 }

ruckusZD1200SystemUptime OBJECT-TYPE
    SYNTAX  TimeTicks
    MAX-ACCESS read-only
    STATUS current
    DESCRIPTION
        "Up time"
    ::= { ruckusZD1200 4 }

ruckusZD1200SystemModel OBJECT-TYPE
    SYNTAX  DisplayString
    MAX-ACCESS read-only
    STATUS current
    DESCRIPTION
        "Model"
    ::= { ruckusZD1200 5 }

ruckusZD1200SystemLicensedAPs OBJECT-TYPE
    SYNTAX  Unsigned32
    MAX-ACCESS read-only
    STATUS current
    DESCRIPTION
        "Licensed APs"
    ::= { ruckusZD1200 6 }

ruckusZD1200SystemSerialNumber OBJECT-TYPE
    SYNTAX  DisplayString
    MAX-ACCESS read-only
    STATUS current
    DESCRIPTION
        "Serial number"
    ::= { ruckusZD1200 7 }

ruckusZD1200SystemVersion OBJECT-TYPE
    SYNTAX  DisplayString
    MAX-ACCESS read-only
    STATUS current
    DESCRIPTION
        "Software version"
    ::= { ruckusZD1200 8 }

ruckusZD1200CountryCode OBJECT-TYPE
    SYNTAX  RuckusCountryCode
    MAX-ACCESS read-only
    STATUS current
    DESCRIPTION
        "Country code"
    ::= { ruckusZD1200 9 }

--
-- Wireless SmartCell Gateway Products
--
-- SCG200
ruckusSCG200 OBJECT IDENTIFIER  ::= { ruckusWirelessSmartCellGatewayProducts 1 }

--
-- Wireless SmartZone Products
--
-- SZ100
ruckusSZ100 OBJECT IDENTIFIER  ::= { ruckusWirelessSmartZoneProducts 1 }

ruckusSZ50 OBJECT IDENTIFIER  ::= { ruckusWirelessSmartZoneProducts 2 }

END

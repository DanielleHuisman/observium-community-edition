--
-- Copyright (c) 2010 by Ruckus Wireless, Inc.
-- All Rights Reserved
--

RUCKUS-RADIO-MIB DEFINITIONS ::= BEGIN

IMPORTS
    ruckusCommonRadioModule
        FROM RUCKUS-ROOT-MIB
    RuckusRadioMode,
    RuckusCountryCode,
    RuckusRate
        FROM RUCKUS-TC-MIB
    ifIndex,
    InterfaceIndex
        FROM IF-MIB
    MODULE-IDENTITY,
    OBJECT-TYPE,
    Integer32
        FROM SNMPv2-SMI;   
        
ruckusRadioMIB MODULE-IDENTITY
    LAST-UPDATED "201010150800Z"
    ORGANIZATION "Ruckus Wireless, Inc."
    CONTACT-INFO
        "Ruckus Wireless, Inc.

        Postal:
        350 West Java Dr.
        Sunnyvale, CA 94089
        USA

        EMail: support@ruckuswireless.com

        Phone: +1-650-265-4200"
    DESCRIPTION
        "Ruckus Radio mib"
    ::= { ruckusCommonRadioModule 1 }


-- Groups
--        

ruckusRadioObjects OBJECT IDENTIFIER     ::= { ruckusRadioMIB 1 }

ruckusRadioInfo OBJECT IDENTIFIER    ::= { ruckusRadioObjects 1 }


ruckusRadioNumber OBJECT-TYPE
    SYNTAX  INTEGER
    MAX-ACCESS read-only
    STATUS current
    DESCRIPTION
        "The number of radios present on this system."
    ::= { ruckusRadioInfo 1 }
    
-- This is the Radio table. 
--

ruckusRadioTable OBJECT-TYPE
    SYNTAX  SEQUENCE OF RuckusRadioEntry
    MAX-ACCESS not-accessible
    STATUS current
    DESCRIPTION
        "Radio table."
    ::= { ruckusRadioInfo 2 }

ruckusRadioEntry OBJECT-TYPE
    SYNTAX  RuckusRadioEntry
    MAX-ACCESS not-accessible
    STATUS current
    DESCRIPTION
        "Specifies each Radio entry."
    INDEX {
        ruckusRadioIndex }
    ::= { ruckusRadioTable 1 }

RuckusRadioEntry ::= SEQUENCE {
    ruckusRadioIndex		InterfaceIndex,
    ruckusRadioMode             INTEGER,
    ruckusRadioCountry          RuckusCountryCode,
    ruckusRadioBSSType          INTEGER,
    ruckusRadioChannel          INTEGER,
    ruckusRadioDataRate         OCTET STRING,
    ruckusRadioTxPower          INTEGER,
    ruckusRadioProtectionMode   INTEGER,
    ruckusRadioNoiseFloor       INTEGER
    }

ruckusRadioIndex OBJECT-TYPE
    SYNTAX  InterfaceIndex
    MAX-ACCESS read-only
    STATUS current
    DESCRIPTION
        "The index."
    ::= { ruckusRadioEntry 200 }

ruckusRadioMode OBJECT-TYPE
    SYNTAX  INTEGER {
            auto(0),
            ieee802dot11g-only(1),
            ieee802dot11b-only(2),
            ieee802dot11ng(3),
            ieee802dot11na(4),
            ieee802dot11a-only(5),
            ieee802dot11ac(6),
	    ieee802dot11ax(8)}
    MAX-ACCESS read-write
    STATUS current
    DESCRIPTION
        "Specifies the radio mode."
    ::= { ruckusRadioEntry 1 }


ruckusRadioCountry OBJECT-TYPE
    SYNTAX  RuckusCountryCode
    MAX-ACCESS read-write
    STATUS current
    DESCRIPTION
        "Specifies the country code."
    ::= { ruckusRadioEntry 2 }


ruckusRadioBSSType OBJECT-TYPE
    SYNTAX  INTEGER {
            station(1),
            master(2),
            independent(3) }
    MAX-ACCESS read-only
    STATUS current
    DESCRIPTION
        "Specifies the bss type."
    ::= { ruckusRadioEntry 3 }
          
          
ruckusRadioChannel OBJECT-TYPE
    SYNTAX  INTEGER (0..14)
    MAX-ACCESS read-write
    STATUS current
    DESCRIPTION
        "Specifies the current operating channel. When 0, it indicates 
        the system selects the best channel automatically."
    ::= { ruckusRadioEntry 4 }    
 
 
ruckusRadioDataRate OBJECT-TYPE
    SYNTAX  OCTET STRING (SIZE(6))
    MAX-ACCESS read-only
    STATUS current
    DESCRIPTION
        "Specifies the transmit rate of radio.
	 Here is the available value list.
	 11a/11g - auto, 1Mb, 2Mb, 5.5Mb, 
	 11Mb, 6Mb, 9Mb, 12Mb, 
         18Mb, 24Mb, 36Mb, 48Mb, 
         54Mb.
         11ng/11na - auto, 1Mb, 2Mb, 5.5Mb, 11Mb, 6Mb, 9Mb, 12Mb, 
         18Mb, 24Mb, 36Mb, 48Mb, 54Mb, 
         6.5Mb, 13Mb, 19.5Mb, 26Mb, 39Mb, 52Mb, 58.5Mb, 65Mb,
         78Mb, 104Mb, 117Mb, 130Mb,
         13.5Mb, 27.5Mb, 40.5Mb, 81.5Mb, 108Mb, 121.5Mb, 135Mb,
         27Mb, 81Mb, 162Mb, 162MB, 216Mb, 243Mb, 270Mb."
    ::= { ruckusRadioEntry 5 }  


ruckusRadioTxPower OBJECT-TYPE
    SYNTAX  INTEGER {
            		full(0),
            		minus1(1),
            		minus2(2),
            		half(3),
            		minus4(4),
            		minus5(5),
            		quarter(6),
            		minus7(7),
            		minus8(8),
            		eighth(9),
            		minus10(10),
            		minus24(24)
            		}
    MAX-ACCESS read-write
    STATUS current
    DESCRIPTION
        "Specifies the transmit power of radio"
    ::= { ruckusRadioEntry 6 }  


ruckusRadioProtectionMode OBJECT-TYPE
    SYNTAX  INTEGER {
            none(0),
            ctsOnly(1),
            ctsRts(2)}
    MAX-ACCESS read-write
    STATUS current
    DESCRIPTION
        "Enabled when 11g and 11b clients exist on the same network.
        none:
        Do not use any protection

        ctsOnly:
        AP will send a CTS frame prior to sending 11g frames.
        The CTS frame will silence 11b clients

        rtsCts:
        Require RTS to be sent by sender of 11g frame and responder
        to send CTS prior to any 11g frames being sent."
    ::= { ruckusRadioEntry 7 }  
 
ruckusRadioNoiseFloor OBJECT-TYPE
    SYNTAX  INTEGER
    MAX-ACCESS read-only
    STATUS current
    DESCRIPTION
        "Specifies the noise floor of radio"
    ::= { ruckusRadioEntry 8 }

 
--
--                  
-- new added MIBs for China Telecom
ruckusRadioStatsTable OBJECT-TYPE
    SYNTAX  SEQUENCE OF RuckusRadioStatsEntry
    MAX-ACCESS not-accessible
    STATUS current
    DESCRIPTION
        "Radios statistics table"
    ::= { ruckusRadioInfo 3 }


ruckusRadioStatsEntry OBJECT-TYPE
    SYNTAX  RuckusRadioStatsEntry
    MAX-ACCESS not-accessible
    STATUS current
    DESCRIPTION
        "Specifies radio statistics entry."
    INDEX {
        ruckusRadioStatsIndex }
    ::= { ruckusRadioStatsTable 1 }


RuckusRadioStatsEntry ::= SEQUENCE {

	ruckusRadioStatsIndex			   InterfaceIndex,
    ruckusRadioStatsMaxSta             Counter32,
    ruckusRadioStatsNumSta             Counter32,
    ruckusRadioStatsNumAuthSta         Counter32,
    ruckusRadioStatsNumAuthReq         Counter32,
    ruckusRadioStatsNumAuthResp        Counter32,
    ruckusRadioStatsNumAuthSuccess     Counter32,
    ruckusRadioStatsNumAuthFail        Counter32,
    ruckusRadioStatsNumAssocReq        Counter32,
    ruckusRadioStatsNumAssocResp       Counter32,
    ruckusRadioStatsNumAssocSuccess    Counter32,
    ruckusRadioStatsNumAssocFail       Counter32,
    ruckusRadioStatsAssocFailRate      Unsigned32,
    ruckusRadioStatsAuthFailRate       Unsigned32,
    ruckusRadioStatsAssocSuccessRate   Unsigned32,
    ruckusRadioStatsResourceUtil       Unsigned32,
    ruckusRadioStatsRxBytes            Counter32,     
    ruckusRadioStatsRxFrames           Counter32,
    ruckusRadioStatsRxWEPFail          Counter32,
    ruckusRadioStatsRxDecryptCRCError  Counter32,
    ruckusRadioStatsRxMICError         Counter32,
    ruckusRadioStatsRxErrors           Counter32,
    ruckusRadioStatsTxBytes            Counter32,
    ruckusRadioStatsTxFrames           Counter32,
    ruckusRadioStatsTotalAssocTime     TimeTicks,
    ruckusRadioStatsTotalAirtime       Counter32, 
    ruckusRadioStatsBusyAirtime        Counter32, 
    ruckusRadioStatsTxAirtime          Counter32,
    ruckusRadioStatsRxAirtime          Counter32
}

ruckusRadioStatsIndex OBJECT-TYPE
    SYNTAX  InterfaceIndex
    MAX-ACCESS read-only
    STATUS current
    DESCRIPTION
        "The index."
    ::= { ruckusRadioStatsEntry 200 }

ruckusRadioStatsMaxSta OBJECT-TYPE
    SYNTAX  Counter32
    MAX-ACCESS read-only
    STATUS current
    DESCRIPTION
        "Num of max stations allowed."
    ::= { ruckusRadioStatsEntry 1 }


ruckusRadioStatsNumSta OBJECT-TYPE
    SYNTAX  Counter32
    MAX-ACCESS read-only
    STATUS current
    DESCRIPTION
        "Num of associated stations."
    ::= { ruckusRadioStatsEntry 2 }

ruckusRadioStatsNumAuthSta OBJECT-TYPE
    SYNTAX  Counter32
    MAX-ACCESS read-only
    STATUS current
    DESCRIPTION
        "Num of authenticated stations."
    ::= { ruckusRadioStatsEntry 3 }


ruckusRadioStatsNumAuthReq OBJECT-TYPE
    SYNTAX  Counter32
    MAX-ACCESS read-only
    STATUS current
    DESCRIPTION
        "Number of authentication requests."
    ::= { ruckusRadioStatsEntry 4 }
                    
 
ruckusRadioStatsNumAuthResp OBJECT-TYPE
    SYNTAX  Counter32
    MAX-ACCESS read-only
    STATUS current
    DESCRIPTION
        "Number of authentication responses."
    ::= { ruckusRadioStatsEntry 5 }
                    

ruckusRadioStatsNumAuthSuccess OBJECT-TYPE
    SYNTAX  Counter32
    MAX-ACCESS read-only
    STATUS current
    DESCRIPTION
        "Number of successful authentications."
    ::= { ruckusRadioStatsEntry 6 }
                    

ruckusRadioStatsNumAuthFail OBJECT-TYPE
    SYNTAX  Counter32
    MAX-ACCESS read-only
    STATUS current
    DESCRIPTION
        "Number of authentication failures."
    ::= { ruckusRadioStatsEntry 7 }
                    

ruckusRadioStatsNumAssocReq OBJECT-TYPE
    SYNTAX  Counter32
    MAX-ACCESS read-only
    STATUS current
    DESCRIPTION
        "Number of association requests."
    ::= { ruckusRadioStatsEntry 8 }
                    

ruckusRadioStatsNumAssocResp OBJECT-TYPE
    SYNTAX  Counter32
    MAX-ACCESS read-only
    STATUS current
    DESCRIPTION
        "Number of association responses."
    ::= { ruckusRadioStatsEntry 9 }
                    

ruckusRadioStatsNumAssocSuccess OBJECT-TYPE
    SYNTAX  Counter32
    MAX-ACCESS read-only
    STATUS current
    DESCRIPTION
        "Number of successful associations."
    ::= { ruckusRadioStatsEntry 10 }
                    

ruckusRadioStatsNumAssocFail OBJECT-TYPE
    SYNTAX  Counter32
    MAX-ACCESS read-only
    STATUS current
    DESCRIPTION
        "Number of association failures."
    ::= { ruckusRadioStatsEntry 11 }
                    

ruckusRadioStatsAssocFailRate OBJECT-TYPE
    SYNTAX  Unsigned32
    MAX-ACCESS read-only
    STATUS current
    DESCRIPTION
        "Station association fail rate. ruckusRadioStatsNumAssocFail/ruckusRadioStatsNumAssocReq"
    ::= { ruckusRadioStatsEntry 12 }


ruckusRadioStatsAuthFailRate  OBJECT-TYPE
    SYNTAX  Unsigned32
    MAX-ACCESS read-only
    STATUS current
    DESCRIPTION
        "Station authentication fail rate. ruckusRadioStatsNumAuthFail/ruckusRadioStatsNumAuthReq"
    ::= { ruckusRadioStatsEntry 13 }


ruckusRadioStatsAssocSuccessRate OBJECT-TYPE
    SYNTAX  Unsigned32
    MAX-ACCESS read-only
    STATUS current
    DESCRIPTION
        "Station association success rate. ruckusRadioStatsNumAssocSuccess/ruckusRadioStatsNumAssocReq"
    ::= { ruckusRadioStatsEntry 14 }


ruckusRadioStatsResourceUtil OBJECT-TYPE
    SYNTAX  Unsigned32
    MAX-ACCESS read-only
    STATUS current
    DESCRIPTION
        "Wireless resource utilization rate. ruckusRadioStatsNumSta/ruckusRadioStatsMaxSta"
    ::= { ruckusRadioStatsEntry 15 }


ruckusRadioStatsRxBytes OBJECT-TYPE
    SYNTAX  Counter32
    MAX-ACCESS read-only
    STATUS current
    DESCRIPTION
        "Count of received bytes."
    ::= { ruckusRadioStatsEntry 16 }


ruckusRadioStatsRxFrames OBJECT-TYPE
    SYNTAX  Counter32
    MAX-ACCESS read-only
    STATUS current
    DESCRIPTION
        "Count of received frames."
    ::= { ruckusRadioStatsEntry 17 }


ruckusRadioStatsRxWEPFail OBJECT-TYPE
    SYNTAX  Counter32
    MAX-ACCESS read-only
    STATUS current
    DESCRIPTION
        "Count of received failured WEP frames."
    ::= { ruckusRadioStatsEntry 18 }
                    
ruckusRadioStatsRxDecryptCRCError OBJECT-TYPE
    SYNTAX  Counter32
    MAX-ACCESS read-only
    STATUS current
    DESCRIPTION
        "Count of received frames with decrypted CRC error."
    ::= { ruckusRadioStatsEntry 19 }
                    
ruckusRadioStatsRxMICError OBJECT-TYPE
    SYNTAX  Counter32
    MAX-ACCESS read-only
    STATUS current
    DESCRIPTION
        "Count of received frames with MIC error."
    ::= { ruckusRadioStatsEntry 20 }

ruckusRadioStatsRxErrors OBJECT-TYPE
    SYNTAX  Counter32
    MAX-ACCESS read-only
    STATUS current
    DESCRIPTION
        "Count of received error frames."
    ::= { ruckusRadioStatsEntry 21 }


ruckusRadioStatsTxBytes OBJECT-TYPE
    SYNTAX  Counter32
    MAX-ACCESS read-only
    STATUS current
    DESCRIPTION
        "Count of transmitted bytes."
    ::= { ruckusRadioStatsEntry 22 }

ruckusRadioStatsTxFrames OBJECT-TYPE
    SYNTAX  Counter32
    MAX-ACCESS read-only
    STATUS current
    DESCRIPTION
        "Count of transmitted frames."
    ::= { ruckusRadioStatsEntry 23 }

ruckusRadioStatsTotalAssocTime OBJECT-TYPE
    SYNTAX  TimeTicks 
    MAX-ACCESS read-only
    STATUS current
    DESCRIPTION
        "Client total association time."
    ::= { ruckusRadioStatsEntry 42 }

ruckusRadioStatsTotalAirtime OBJECT-TYPE
    SYNTAX Counter32
    MAX-ACCESS read-only
    STATUS current
    DESCRIPTION
        "total airtime."
        ::= { ruckusRadioStatsEntry 50 }

ruckusRadioStatsBusyAirtime OBJECT-TYPE
    SYNTAX Counter32
    MAX-ACCESS read-only
    STATUS current
    DESCRIPTION
        "busy airtime."
        ::= { ruckusRadioStatsEntry 51 }

ruckusRadioStatsTxAirtime OBJECT-TYPE
    SYNTAX Counter32
    MAX-ACCESS read-only
    STATUS current
    DESCRIPTION
        "tx airtime."
        ::= { ruckusRadioStatsEntry 52 }

ruckusRadioStatsRxAirtime OBJECT-TYPE
    SYNTAX Counter32
    MAX-ACCESS read-only
    STATUS current
    DESCRIPTION
        "rx airtime."
        ::= { ruckusRadioStatsEntry 53 }

END

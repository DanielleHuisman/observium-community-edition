-- *****************************************************************
-- MY-OSPF-MIB.mib:  My Ospf MIB file
--
-- $Copyright$
-- 
-- *****************************************************************
--

MY-OSPF-MIB DEFINITIONS ::= BEGIN

IMPORTS
        MODULE-IDENTITY,
        OBJECT-TYPE,
        NOTIFICATION-TYPE,
        Integer32,
        Counter32
                FROM SNMPv2-SMI
        TruthValue,
        DisplayString,
        RowStatus,
        MacAddress
                FROM SNMPv2-TC
        MODULE-COMPLIANCE,
        OBJECT-GROUP
                FROM SNMPv2-CONF
        ConfigStatus,
        IfIndex
                FROM MY-TC    
        EnabledStatus 
               FROM P-BRIDGE-MIB                
       AreaID,UpToMaxAge,Status,PositiveInteger,
       DesignatedRouterPriority,RouterID,HelloRange 
                FROM OSPF-MIB
        myMgmt
                FROM MY-SMI;

myOspfMIB MODULE-IDENTITY
        LAST-UPDATED "200211200000Z"
        ORGANIZATION "$Company$"
        CONTACT-INFO
                " 
                Tel: $Telephone$ 

                E-mail: $E-mail$"
        DESCRIPTION
                "This module defines my Ospf mibs."
        REVISION      "200211200000Z"
        DESCRIPTION
                "Initial version of this MIB module."
        ::= { myMgmt 30}

myOspfMIBObjects OBJECT IDENTIFIER ::= { myOspfMIB 1 }

-- general mib
myOspfGeneralMibsGroup OBJECT IDENTIFIER ::= { myOspfMIBObjects 1 }

--Minimum LSA interval
myOspfMiniLsaInterval  OBJECT-TYPE
    SYNTAX  Unsigned32
    MAX-ACCESS read-only
    STATUS current
    DESCRIPTION
           "Minimum LSA interval that the two LSA generate."
     ::={ myOspfGeneralMibsGroup 1 }
 
--Minimum LSA arrival
myOspfMiniLsaArrival  OBJECT-TYPE
    SYNTAX  Unsigned32
    MAX-ACCESS read-only
    STATUS current
    DESCRIPTION
           "Minimum LSA Interval of the two LSA arrival."
     ::={ myOspfGeneralMibsGroup 2 }
     
--Number of areas in this router
myOspfAreasNum OBJECT-TYPE   
    SYNTAX  Unsigned32
    MAX-ACCESS read-only
    STATUS current
    DESCRIPTION
           "Number of areas in this router"    
         ::={ myOspfGeneralMibsGroup 3 }
         
myOspfNormalAreasNum OBJECT-TYPE   
    SYNTAX  Unsigned32
    MAX-ACCESS read-only
    STATUS current
    DESCRIPTION
           "Number of normal areas in this router"    
         ::={ myOspfGeneralMibsGroup 4}   

myOspfStubAreasNum OBJECT-TYPE   
    SYNTAX  Unsigned32
    MAX-ACCESS read-only
    STATUS current
    DESCRIPTION
           "Number of stub areas in this router"    
         ::={ myOspfGeneralMibsGroup 5 }
                     
myOspfNssaAreasNum OBJECT-TYPE   
    SYNTAX  Unsigned32
    MAX-ACCESS read-only
    STATUS current
    DESCRIPTION
           "Number of nssa areas in this router"    
         ::={ myOspfGeneralMibsGroup 6 }
                       
myOspfSpfDelay OBJECT-TYPE   
    SYNTAX  Unsigned32(0..2147483647)
    MAX-ACCESS read-write
    STATUS current
    DESCRIPTION
           "Ospf Spf shedule time, an integer from 0 to 65535. The default is 5
           seconds,0 means no delay."
    DEFVAL {5}
         ::={ myOspfGeneralMibsGroup 7 }  
         
myOspfSpfHoldTime OBJECT-TYPE   
    SYNTAX  Unsigned32(0..2147483647)
    MAX-ACCESS read-write
    STATUS current
    DESCRIPTION
           "hold time between two Spfs.an integer from 0 to 65535. The default is
            10 seconds; 0 means no delay."
    DEFVAL {10}
         ::={ myOspfGeneralMibsGroup 8 }
         
myOspfAutoCostRefBandWidthRef OBJECT-TYPE
    SYNTAX  Unsigned32(0..2147483647)
    MAX-ACCESS read-write
    STATUS current
    DESCRIPTION
           "Set AutoCost bandwidth referenc value in unit of Mbits.
            Setting this value to 0 indicate that disable the feature of 
            autocost bandwidth referenc."
    DEFVAL {100}
         ::={ myOspfGeneralMibsGroup 9 }   
         
myOspfLsaGroupPacing OBJECT-TYPE
    SYNTAX  Unsigned32(10..1800)
    MAX-ACCESS read-write
    STATUS current
    DESCRIPTION
           "set  the group pacing of LSAs."
    DEFVAL {240}
         ::={ myOspfGeneralMibsGroup 10}
    
myOspfInterDistance OBJECT-TYPE
     SYNTAX   Unsigned32(1..255)
     MAX-ACCESS   read-write
     STATUS   current
     DESCRIPTION
        "Set  inter-area distance."
     DEFVAL {110}
    ::= { myOspfGeneralMibsGroup 11 }     
     
myOspfIntraDistance OBJECT-TYPE
     SYNTAX   Unsigned32(1..255)
     MAX-ACCESS   read-write
     STATUS   current
     DESCRIPTION
        "Set  intra-area distance."
     DEFVAL {110}
    ::= { myOspfGeneralMibsGroup 12 }
    
myOspfExternDistance OBJECT-TYPE
     SYNTAX   Unsigned32(1..255)
     MAX-ACCESS   read-write
     STATUS   current
     DESCRIPTION
        "Set  extern distance."
     DEFVAL {110}
    ::= { myOspfGeneralMibsGroup 13 }       

--LogAdjChangeNotify
myOspfLogAdjChangeNotify OBJECT-TYPE
     SYNTAX   EnabledStatus
     MAX-ACCESS   read-write
     STATUS   current
     DESCRIPTION
        "if enabled status is setted,
        Send syslog message when a neighbor state changes."
     DEFVAL {enabled}
     ::= { myOspfGeneralMibsGroup 14 } 
    
myOspfPassiveStatus  OBJECT-TYPE
    SYNTAX EnabledStatus
    MAX-ACCESS read-write
    STATUS current
    DESCRIPTION
          "The myOspfIfPassiveStatus of a interface equal to this object value
           when this interface is created. If you change this object value to 'enabled'
           or 'disabled'all interfaces which have exist will also change their 
           myOspfIfPassiveStatus to 'enabled' or 'disabled'."
    DEFVAL { disabled }
    ::={ myOspfGeneralMibsGroup 15 }

myOspfRFC1583Compatibility  OBJECT-TYPE
    SYNTAX EnabledStatus
    MAX-ACCESS read-write
    STATUS current
    DESCRIPTION
         "Controls the preference rules used in calculating AS external routes
         (RFC2328 Section 16.4) when choosing among multiple AS-external-LSAs 
         advertising the same destination. When set to 'enabled', the preference
         rules remain those specified by RFC 1583 ([Ref9]). When set
         to 'disabled', the preference rules are those stated in
         'RFC2328 Section 16.4.1' which prevent routing loops when AS-
         external-LSAs for the same destination have been originated
         from different areas. Set to 'enabled' by default."
    REFERENCE
       "OSPF Version 2(RFC2328), C.1 Global parameters"                   
    DEFVAL { enabled }
    ::={ myOspfGeneralMibsGroup 16 } 
 
myOspfRouteRedisDefMetricVal OBJECT-TYPE
     SYNTAX   Unsigned32(1..16777214)
     MAX-ACCESS   read-write
     STATUS   current
     DESCRIPTION
        "When this value is setted,Cause the current routing protocol(ospf) 
         to use the same metricvalue for all redistributed routes (BGP, RIP, and OSPF)." 
     DEFVAL {20}       
    ::= { myOspfGeneralMibsGroup 17} 
    
myOspfAdminiDistance OBJECT-TYPE
     SYNTAX   Unsigned32(1..255)
     MAX-ACCESS   read-write
     STATUS   current
     DESCRIPTION
        "ospf Administrative distance." 
     DEFVAL {110}       
    ::= { myOspfGeneralMibsGroup 18}     
 
 
--table mib
              
--myOspfAreaTable 
myOspfAreaTable OBJECT-TYPE
        SYNTAX SEQUENCE OF MyOspfAreaEntry
        MAX-ACCESS not-accessible
        STATUS current
        DESCRIPTION
            "Information describing the configured  parame-
             ters  and cumulative statistics of the router's
             attached areas.This table is superset of ospfAreaTable"
    ::= { myOspfMIBObjects 2}
    
myOspfAreaEntry OBJECT-TYPE
        SYNTAX MyOspfAreaEntry
        MAX-ACCESS not-accessible
        STATUS current
        DESCRIPTION
            "The entry of myOspfAreaTable."
        INDEX { myOspfAreaId}
    ::= { myOspfAreaTable 1 }
   
MyOspfAreaEntry ::=
        SEQUENCE {
         myOspfAreaId
                AreaID,
         myOspfAuthType
                INTEGER,
         myOspfImportAsExtern
                INTEGER,
         myOspfSpfRuns
                Counter32,
         myOspfAreaBdrRtrCount
                Gauge32,
         myOspfAsBdrRtrCount
                Gauge32,
         myOspfAreaLsaCount
                Gauge32,
         myOspfAreaLsaCksumSum
                Unsigned32,
         myOspfAreaSummary
                INTEGER,
         myOspfAreaStatus
                RowStatus,        
-- extend parts                
         myOspfAreaInterfaceNum
                Unsigned32,
         myOspfAreaNssaIsRedistribution
                TruthValue,
         myOspfAreaNssaIsDefInfoOriginate
                TruthValue
         }
    myOspfAreaId OBJECT-TYPE
        SYNTAX   AreaID
        MAX-ACCESS   read-only
        STATUS   current
        DESCRIPTION
           "A 32-bit integer uniquely identifying an area.
           Area ID 0.0.0.0 is used for the OSPF backbone."
       REFERENCE
          "OSPF Version 2, Appendix C.2 Area parameters"
      ::= { myOspfAreaEntry 1 }


    myOspfAuthType OBJECT-TYPE
        SYNTAX   INTEGER{
                    none(0),
                    simplePassword(1),
                    md5 (2)
                    -- reserved for specification by IANA (> 2)
                    }
        MAX-ACCESS   read-create
        STATUS   current
        DESCRIPTION
           "The authentication type specified for an area.
           Additional authentication types may be assigned
           locally on a per Area basis."
       REFERENCE
          "OSPF Version 2, Appendix E Authentication"
      DEFVAL { 0 }        -- no authentication, by default
      ::= { myOspfAreaEntry 2 }

    myOspfImportAsExtern OBJECT-TYPE
        SYNTAX   INTEGER    {
                    importExternal (1), --normal area
                    importNoExternal (2), -- stub area
                    importNssa (3)        -- NSSA area
                  }
        MAX-ACCESS   read-create
        STATUS   current
        DESCRIPTION
           "The area's support for importing  AS  external
           link- state advertisements."
       REFERENCE
          "OSPF Version 2, Appendix C.2 Area parameters"
      DEFVAL { importExternal }
      ::= { myOspfAreaEntry 3 }


    myOspfSpfRuns OBJECT-TYPE
        SYNTAX   Counter32
        MAX-ACCESS   read-only
        STATUS   current
        DESCRIPTION
           "The number of times that the intra-area  route
           table  has  been  calculated  using this area's
           link-state database.  This  is  typically  done
           using Dijkstra's algorithm."
       ::= { myOspfAreaEntry 4 } 
           
    myOspfAreaBdrRtrCount OBJECT-TYPE
        SYNTAX   Gauge32
        MAX-ACCESS   read-only
        STATUS   current
        DESCRIPTION
           "The total number of area border routers reach-
           able within this area.  This is initially zero,
           and is calculated in each SPF Pass."
       ::= { myOspfAreaEntry 5 }

    myOspfAsBdrRtrCount OBJECT-TYPE
        SYNTAX   Gauge32
        MAX-ACCESS   read-only
        STATUS   current
        DESCRIPTION
           "The total number of Autonomous  System  border
           routers  reachable  within  this area.  This is
           initially zero, and is calculated in  each  SPF
           Pass."
       ::= { myOspfAreaEntry 6 }


    myOspfAreaLsaCount OBJECT-TYPE
        SYNTAX   Gauge32
        MAX-ACCESS   read-only
        STATUS   current
        DESCRIPTION
           "The total number of link-state  advertisements
           in  this  area's link-state database, excluding
           AS External LSA's."
       ::= { myOspfAreaEntry 7 }


    myOspfAreaLsaCksumSum OBJECT-TYPE
        SYNTAX   Unsigned32
        MAX-ACCESS   read-only
        STATUS   current
        DESCRIPTION
           "The 32-bit unsigned sum of the link-state  ad-
           vertisements'  LS  checksums  contained in this
           area's link-state database.  This sum  excludes
           external (LS type 5) link-state advertisements.
           The sum can be used to determine if  there  has
           been  a  change  in a router's link state data-
           base, and to compare the link-state database of
           two routers."
       DEFVAL   { 0 }
       ::= { myOspfAreaEntry 8 }

    myOspfAreaSummary OBJECT-TYPE
        SYNTAX   INTEGER    {
                    noAreaSummary (1),
                    sendAreaSummary (2)
                  }
        MAX-ACCESS   read-create
        STATUS   current
        DESCRIPTION
           "The variable ospfAreaSummary controls the  im-
           port  of  summary LSAs into stub areas.  It has
           no effect on other areas.

           If it is noAreaSummary, the router will neither
           originate  nor  propagate summary LSAs into the
           stub area.  It will rely entirely  on  its  de-
           fault route.

           If it is sendAreaSummary, the router will  both
           summarize and propagate summary LSAs."
       DEFVAL   { sendAreaSummary }
       ::= { myOspfAreaEntry 9 }


    myOspfAreaStatus OBJECT-TYPE
        SYNTAX   RowStatus
        MAX-ACCESS   read-create
        STATUS   current
        DESCRIPTION
           "This variable displays the status of  the  en-
           try.  Setting it to 'invalid' has the effect of
           rendering it inoperative.  The internal  effect
           (row removal) is implementation dependent."
       ::= { myOspfAreaEntry 10 }
              
   myOspfAreaInterfaceNum OBJECT-TYPE   --for command "show 
        SYNTAX Unsigned32
        MAX-ACCESS read-only
        STATUS current
        DESCRIPTION
            " the interface number of this area" 
    ::= { myOspfAreaEntry 11 }
    
   myOspfAreaNssaIsRedistribution OBJECT-TYPE  
        SYNTAX TruthValue
        MAX-ACCESS read-create
        STATUS current
        DESCRIPTION
            " if it's disabled , when the router is an NSSA ABR and
            you want the redistribute command to import routes into normal
            areas, but not into the NSSA,
            this field is vaild for nssa area"
        DEFVAL {true}
    ::= { myOspfAreaEntry 12}
    
   myOspfAreaNssaIsDefInfoOriginate OBJECT-TYPE
        SYNTAX TruthValue
        MAX-ACCESS read-create
        STATUS current
        DESCRIPTION
            "if it's enabled it meaning that on an ABR to allow
            importing type 7 LSAs into the NSSA,
            this field is valid for nssa area"
        DEFVAL {false}
    ::= { myOspfAreaEntry 13}
   
    
--network address scope table   
myOspfAddressScopeTable OBJECT-TYPE
        SYNTAX SEQUENCE OF MyOspfAddressScopeEntry
        MAX-ACCESS not-accessible
        STATUS current
        DESCRIPTION
            "Define an interface on which OSPF runs and the area ID for that
            interface. You can use the wildcard-mask to use a single
            command to define one or more multiple interfaces to be
            associated with a specific OSPF area. "
    ::= { myOspfMIBObjects 3 }
    
myOspfAddressScopeEntry OBJECT-TYPE
        SYNTAX MyOspfAddressScopeEntry
        MAX-ACCESS not-accessible
        STATUS current
        DESCRIPTION
            "the entry define an scope of address for ospf routing."
        INDEX { myOspfNetWorkAreaID,myOspfNetWorkAddress, myOspfNetWorkMask}
    ::= { myOspfAddressScopeTable 1 }

    
MyOspfAddressScopeEntry ::=
        SEQUENCE {
        myOspfNetWorkAreaID
                IpAddress,
        myOspfNetWorkAddress
                IpAddress,
        myOspfNetWorkMask
                IpAddress,
        myOspfNetWorkStatus
                 RowStatus

        }
    
myOspfNetWorkAreaID OBJECT-TYPE
        SYNTAX IpAddress
        MAX-ACCESS read-only
        STATUS current
        DESCRIPTION
            "area ID"
    ::= { myOspfAddressScopeEntry 1 }
    
myOspfNetWorkAddress OBJECT-TYPE
        SYNTAX IpAddress
        MAX-ACCESS read-only
        STATUS current
        DESCRIPTION
            " Routing for Networks Ipaddress"
    ::= { myOspfAddressScopeEntry 2 }
    
myOspfNetWorkMask OBJECT-TYPE
        SYNTAX IpAddress
        MAX-ACCESS read-only
        STATUS current
        DESCRIPTION
            " Routing for Networks mask"
    ::= { myOspfAddressScopeEntry 3 }
    
myOspfNetWorkStatus    OBJECT-TYPE
        SYNTAX RowStatus
        MAX-ACCESS read-create
        STATUS current
        DESCRIPTION
            " when this value is destroy,the 
            entry will be deleted"
    ::= { myOspfAddressScopeEntry 4 }     


-- The Ospf Interface Configuration Table

myOspfIfTable OBJECT-TYPE
        SYNTAX   SEQUENCE OF MyOspfIfEntry
        MAX-ACCESS   not-accessible
        STATUS   current
        DESCRIPTION
           "The OSPF Interface Table describes the  interfaces 
           from the viewpoint of OSPF."
       REFERENCE
          "ospfIfTable in rfc1850"    
       ::= { myOspfMIBObjects  4 }

myOspfIfEntry OBJECT-TYPE
       SYNTAX   MyOspfIfEntry
       MAX-ACCESS   not-accessible
       STATUS   current
       DESCRIPTION
          "The OSPF Interface Entry describes one  inter-
           face configuration of OSPF."
      INDEX { myOspfIfIpAddress, myOspfAddressLessIf  }
      ::= { myOspfIfTable 1 }
    
MyOspfIfEntry ::=
        SEQUENCE {
         myOspfIfIpAddress
            IpAddress,
         myOspfAddressLessIf
            Unsigned32,
         myOspfIfAreaId
            AreaID,
         myOspfIfType
            INTEGER,
         myOspfIfAdminStat
            Status,
         myOspfIfRtrPriority
            DesignatedRouterPriority,
         myOspfIfTransitDelay
            Unsigned32,
         myOspfIfRetransInterval
            Unsigned32,
         myOspfIfHelloInterval
            HelloRange,
         myOspfIfRtrDeadInterval
            PositiveInteger,
         myOspfIfPollInterval
            PositiveInteger,
         myOspfIfState
            INTEGER,
         myOspfIfDesignatedRouter
            IpAddress,
         myOspfIfBackupDesignatedRouter
            IpAddress,
         myOspfIfEvents
            Counter32,
         myOspfIfAuthType
            INTEGER,
         myOspfIfAuthKey
            OCTET STRING,
         myOspfIfStatus
            RowStatus,
         myOspfIfMulticastForwarding
            INTEGER,
         myOspfIfDemand
            TruthValue,        
         myOspfIfDatabaseFilterAllOut
                EnabledStatus,
         myOspfIfDesignateRouterId     
                IpAddress,
         myOspfIfBackupDesignateRouterId 
                IpAddress,
         myOspfIfWaitInternal
                Unsigned32,
         myOspfIfPassiveStatus
                EnabledStatus,
         myOspfIfCurrentUsedMd5AuthKeyId
                Unsigned32
                 }
myOspfIfIpAddress OBJECT-TYPE
        SYNTAX   IpAddress
        MAX-ACCESS   read-only
        STATUS   current
        DESCRIPTION
           "The IP address of this OSPF interface."
       ::= { myOspfIfEntry 1 }

myOspfAddressLessIf OBJECT-TYPE
        SYNTAX   Unsigned32
        MAX-ACCESS   read-only
        STATUS   current
        DESCRIPTION
           "For the purpose of easing  the  instancing  of
           addressed   and  addressless  interfaces;  This
           variable takes the value 0 on  interfaces  with
           IP  Addresses,  and  the corresponding value of
           ifIndex for interfaces having no IP Address."
       ::= { myOspfIfEntry 2 }


myOspfIfAreaId OBJECT-TYPE
        SYNTAX   AreaID
        MAX-ACCESS   read-only
        STATUS   current
        DESCRIPTION
           "A 32-bit integer uniquely identifying the area
           to  which  the  interface  connects.   Area  ID
           0.0.0.0 is used for the OSPF backbone."
       DEFVAL   { '00000000'H }    -- 0.0.0.0
       ::= { myOspfIfEntry 3 }

myOspfIfType OBJECT-TYPE
        SYNTAX   INTEGER    {
                    broadcast (1),
                    nbma (2),
                    pointToPoint (3),
                    pointToMultipoint (5),
                    loopback(6)
                  }
        MAX-ACCESS   read-write
        STATUS   current
        DESCRIPTION
           "The OSPF interface type.

           By way of a default, this field may be intuited
           from the corresponding value of ifType.  Broad-
           cast LANs, such as  Ethernet  and  IEEE  802.5,
           take  the  value  'broadcast', X.25 and similar
           technologies take the value 'nbma',  and  links
           that  are  definitively point to point take the
           value 'pointToPoint'."
       ::= { myOspfIfEntry 4 }


myOspfIfAdminStat OBJECT-TYPE
        SYNTAX   Status
        MAX-ACCESS   read-only
        STATUS   current
        DESCRIPTION
           "The OSPF  interface's  administrative  status.
           The  value formed on the interface, and the in-
           terface will be advertised as an internal route
           to  some  area.   The  value 'disabled' denotes
           that the interface is external to OSPF."
       ::= { myOspfIfEntry 5 }

myOspfIfRtrPriority OBJECT-TYPE
        SYNTAX   DesignatedRouterPriority
        MAX-ACCESS   read-write
        STATUS   current
        DESCRIPTION
           "The  priority  of  this  interface.   Used  in
           multi-access  networks,  this  field is used in
           the designated router election algorithm.   The
           value 0 signifies that the router is not eligi-
           ble to become the  designated  router  on  this
           particular  network.   In the event of a tie in
           this value, routers will use their Router ID as
           a tie breaker."
       DEFVAL { 1 }
       ::= { myOspfIfEntry 6 }


myOspfIfTransitDelay OBJECT-TYPE
        SYNTAX   Unsigned32 (1..65535)
        MAX-ACCESS   read-write
        STATUS   current
        DESCRIPTION
           "The estimated number of seconds  it  takes  to
           transmit  a  link state update packet over this
           interface."
       DEFVAL { 1 }
       ::= { myOspfIfEntry 7 }


myOspfIfRetransInterval OBJECT-TYPE
        SYNTAX   Unsigned32 (1..65535)
        MAX-ACCESS   read-write
        STATUS   current
        DESCRIPTION
           "The number of seconds between  link-state  ad-
           vertisement  retransmissions,  for  adjacencies
           belonging to this  interface.   This  value  is
           also used when retransmitting database descrip-
           tion and link-state request packets."
       DEFVAL { 5 }
       ::= { myOspfIfEntry 8 }


myOspfIfHelloInterval OBJECT-TYPE
        SYNTAX   HelloRange
        MAX-ACCESS   read-write
        STATUS   current
        DESCRIPTION
           "The length of time, in  seconds,  between  the
           Hello  packets that the router sends on the in-
           terface.  This value must be the same  for  all
           routers attached to a common network."
       DEFVAL { 10 }
       ::= { myOspfIfEntry 9 }


myOspfIfRtrDeadInterval OBJECT-TYPE
        SYNTAX   PositiveInteger
        MAX-ACCESS   read-write
        STATUS   current
        DESCRIPTION
           "The number of seconds that  a  router's  Hello
           packets  have  not been seen before it's neigh-
           bors declare the router down.  This  should  be
           some  multiple  of  the  Hello  interval.  This
           value must be the same for all routers attached
           to a common network."
       DEFVAL { 40 }
       ::= { myOspfIfEntry 10 }


myOspfIfPollInterval OBJECT-TYPE
        SYNTAX   PositiveInteger
        MAX-ACCESS   read-only
        STATUS   current
        DESCRIPTION
           "The larger time interval, in seconds,  between
           the  Hello  packets  sent  to  an inactive non-
           broadcast multi- access neighbor."
       ::= { myOspfIfEntry 11 }


myOspfIfState OBJECT-TYPE
        SYNTAX   INTEGER    {
                    down (1),
                    loopback (2),
                    waiting (3),
                    pointToPoint (4),
                    designatedRouter (5),
                    backupDesignatedRouter (6),
                    otherDesignatedRouter (7)
                  }
        MAX-ACCESS   read-only
        STATUS   current
        DESCRIPTION
           "The OSPF Interface State."
       DEFVAL { down }
       ::= { myOspfIfEntry 12 }


myOspfIfDesignatedRouter OBJECT-TYPE
        SYNTAX   IpAddress
        MAX-ACCESS   read-only
        STATUS   current
        DESCRIPTION
           "The IP Address of the interface which connected the local router in 
            the Designated Router."
       DEFVAL   { '00000000'H }    -- 0.0.0.0
       ::= { myOspfIfEntry 13 }


myOspfIfBackupDesignatedRouter OBJECT-TYPE
        SYNTAX   IpAddress
        MAX-ACCESS   read-only
        STATUS   current
        DESCRIPTION
           "The IP Address of the interface which connected the local router in 
            the Backup Designated Router."
       DEFVAL   { '00000000'H }    -- 0.0.0.0
       ::= { myOspfIfEntry 14 }

myOspfIfEvents OBJECT-TYPE
        SYNTAX   Counter32
        MAX-ACCESS   read-only
        STATUS   current
        DESCRIPTION
           "The number of times this  OSPF  interface  has
           changed its state, or an error has occurred."
       ::= { myOspfIfEntry 15 }


myOspfIfAuthKey OBJECT-TYPE
        SYNTAX   OCTET STRING (SIZE (0..256))
        MAX-ACCESS   read-write
        STATUS   current
        DESCRIPTION
           "The Authentication Key.  If the Area's Author-
           ization  Type  is  simplePassword,  and the key
           length is shorter than 8 octets, the agent will
           left adjust and zero fill to 8 octets.

           Note that unauthenticated  interfaces  need  no
           authentication key, and simple password authen-
           tication cannot use a key of more  than  8  oc-
           tets.  Larger keys are useful only with authen-
           tication mechanisms not specified in this docu-
           ment.

           When read, myOspfIfAuthKey always returns an  Oc-
           tet String of length zero."
       REFERENCE
          "OSPF Version 2, Section 9  The  Interface  Data
          Structure"
      DEFVAL   { '0000000000000000'H }    -- 0.0.0.0.0.0.0.0
      ::= { myOspfIfEntry 16 }

myOspfIfStatus OBJECT-TYPE
        SYNTAX   RowStatus
        MAX-ACCESS   read-only
        STATUS   current
        DESCRIPTION
           "This value will be  active(1) always."
       ::= { myOspfIfEntry 17 }


myOspfIfMulticastForwarding OBJECT-TYPE
        SYNTAX   INTEGER    {
                            blocked (1),        -- no multicast forwarding
                            multicast (2),        -- using multicast address
                            unicast (3)        -- to each OSPF neighbor
                  }
        MAX-ACCESS   read-only
        STATUS   current
        DESCRIPTION
           "The way multicasts should  forwarded  on  this
           interface;  not  forwarded,  forwarded  as data
           link multicasts, or forwarded as data link uni-
           casts.   Data link multicasting is not meaning-
           ful on point to point and NBMA interfaces,  and
           setting ospfMulticastForwarding to 0 effective-
           ly disables all multicast forwarding."
       DEFVAL { blocked }
       ::= { myOspfIfEntry 18 }


myOspfIfDemand OBJECT-TYPE
        SYNTAX   TruthValue
        MAX-ACCESS   read-only
        STATUS   current
        DESCRIPTION
           "Indicates whether Demand OSPF procedures (hel-
           lo supression to FULL neighbors and setting the
           DoNotAge flag on proogated LSAs) should be per-
           formed on this interface."
       DEFVAL { false }
       ::= { myOspfIfEntry 19 }


myOspfIfAuthType OBJECT-TYPE
        SYNTAX   INTEGER (0..255)
                    -- none (0),
                    -- simplePassword (1)
                    -- md5 (2)
                    -- default (3)
                    -- reserved for specification by IANA (> 2)
        MAX-ACCESS   read-write
        STATUS   current
        DESCRIPTION
           "The authentication type specified for  an  interface. Setting this value to 
            'default' means using default authentication type referenced to Area Authentication, 
            this value only for set,not be read. Additional  authentication types may
            be assigned locally."
       REFERENCE
          "OSPF Version 2, Appendix E Authentication"
      DEFVAL { 0 }        -- no authentication, by default
      ::= { myOspfIfEntry 20 }
                              
myOspfIfDatabaseFilterAllOut OBJECT-TYPE
        SYNTAX   EnabledStatus                    
        MAX-ACCESS   read-write
        STATUS   current
        DESCRIPTION
           "Block flooding of OSPF LSA packets to the interface. By
           default, OSPF floods new LSAs over all interfaces in the same area,
           except the interface on which the LSA arrives."
        DEFVAL {disabled}
       ::= { myOspfIfEntry 21 } 
       
myOspfIfDesignateRouterId OBJECT-TYPE  
        SYNTAX   IpAddress                    
        MAX-ACCESS   read-only
        STATUS   current
        DESCRIPTION
           "DR RouterID of this interface,
           when DR does not selected,DR Id is 0.0.0.0"
        DEFVAL {'00000000'H}
       ::= { myOspfIfEntry 22 } 
       
myOspfIfBackupDesignateRouterId OBJECT-TYPE  
        SYNTAX   IpAddress                    
        MAX-ACCESS   read-only
        STATUS   current
        DESCRIPTION
           "Backup DR RouterId of this interface ,
           when Backup DR does not selected,BDR Id is 0.0.0.0"
        DEFVAL {'00000000'H}
       ::= { myOspfIfEntry 23 }  

myOspfIfWaitInternal OBJECT-TYPE  
        SYNTAX  TimeTicks                   
        MAX-ACCESS   read-only
        STATUS   current
        DESCRIPTION
           "The wait time of hello generate"
       ::= { myOspfIfEntry 24 }

myOspfIfPassiveStatus OBJECT-TYPE
        SYNTAX   EnabledStatus
        MAX-ACCESS   read-write
        STATUS   current
        DESCRIPTION
               "Setting this object value to 'enabled' ,the interface will 
               become a passive interface."
        DEFVAL { disabled }               
        ::= { myOspfIfEntry 25 } 
myOspfIfCurrentUsedMd5AuthKeyId     OBJECT-TYPE  
       SYNTAX   Unsigned32 (0..255)                    
        MAX-ACCESS   read-create
        STATUS   current
        DESCRIPTION
           "key-id which current used for md5 authentication,this value is 
            valid from 1 to 255, the value 0 is default value.."
        DEFVAL {0}
       ::= { myOspfIfEntry 26 }   


-- The Ospf Interface MD5 authentication key configuration table

myOspfIfMd5AuthKeyTable OBJECT-TYPE
        SYNTAX   SEQUENCE OF MyOspfIfMd5AuthKeyEntry
        MAX-ACCESS   not-accessible
        STATUS   current
        DESCRIPTION
           "Configuration table of the key-id for md5 authentication for OSPF protocol."
       ::= { myOspfMIBObjects  5 }

myOspfIfMd5AuthKeyEntry OBJECT-TYPE
       SYNTAX   MyOspfIfMd5AuthKeyEntry
       MAX-ACCESS   not-accessible
       STATUS   current
       DESCRIPTION
          "Configuration entry of the key-id for md5 authentication for OSPF protocol"
      INDEX {myOspfIfMd5AuthKeyIf, myOspfIfMd5AuthKeyId }
      ::= { myOspfIfMd5AuthKeyTable 1 }
    
MyOspfIfMd5AuthKeyEntry ::=
        SEQUENCE { 
         myOspfIfMd5AuthKeyIf
            Unsigned32,
         myOspfIfMd5AuthKeyId
            Unsigned32,
         myOspfIfMd5AuthKey
            OCTET STRING,
         myOspfIfMd5AuthKeySt   
            ConfigStatus
                 }
                 
myOspfIfMd5AuthKeyIf OBJECT-TYPE
        SYNTAX   Unsigned32
        MAX-ACCESS   read-only
        STATUS   current
        DESCRIPTION
           "Corresponding value of ifIndex for interfaces."
       ::= { myOspfIfMd5AuthKeyEntry 1 }

myOspfIfMd5AuthKeyId     OBJECT-TYPE  
        SYNTAX   Unsigned32 (1..255)                    
        MAX-ACCESS   read-only
        STATUS   current
        DESCRIPTION
           "the key-id for md5 authentication."
       ::= { myOspfIfMd5AuthKeyEntry 2 } 

myOspfIfMd5AuthKey OBJECT-TYPE
        SYNTAX   OCTET STRING (SIZE (0..256))
        MAX-ACCESS   read-create
        STATUS   current
        DESCRIPTION
           "The Authentication Key for MD5.
           
           When read, myOspfIfMd5AuthKey always returns an  Oc-
           tet String of length zero."
       REFERENCE
          "OSPF Version 2, Section 9  The  Interface  Data
          Structure"
      ::= { myOspfIfMd5AuthKeyEntry 3 }

myOspfIfMd5AuthKeySt OBJECT-TYPE
        SYNTAX   ConfigStatus
        MAX-ACCESS   read-write
        STATUS   current
        DESCRIPTION
           "Setting this value to 'invalid' will delete this entry.
            Setting this value to 'valid' will have no effect."
      ::= { myOspfIfMd5AuthKeyEntry 4 }



-- The My Ospf Virtual Link Table

myOspfVirtTable OBJECT-TYPE
        SYNTAX   SEQUENCE OF MyOspfVirtEntry
        MAX-ACCESS   not-accessible
        STATUS   current
        DESCRIPTION
           "Information about this router's virtual inter-
            faces.Include ospfVirtIfTable in rfc1850"
        REFERENCE
          "ospfVirtIfTable in rfc1850"    
       ::= { myOspfMIBObjects  6 }

myOspfVirtEntry OBJECT-TYPE
       SYNTAX   MyOspfVirtEntry
       MAX-ACCESS   not-accessible
       STATUS   current
       DESCRIPTION
          "Information about a single Virtual Interface"
      INDEX {myOspfVirtIfAreaId, myOspfVirtIfNeighbor}
      ::= { myOspfVirtTable 1 }
    
MyOspfVirtEntry ::=
        SEQUENCE {
      myOspfVirtIfAreaId
         AreaID,
      myOspfVirtIfNeighbor
         RouterID,
      myOspfVirtIfTransitDelay
         Unsigned32,
      myOspfVirtIfRetransInterval
         Unsigned32,
      myOspfVirtIfHelloInterval
         HelloRange,
      myOspfVirtIfRtrDeadInterval
         PositiveInteger,
      myOspfVirtIfState
         INTEGER,
      myOspfVirtIfEvents
         Counter32,
      myOspfVirtIfAuthType
         INTEGER,
      myOspfVirtIfAuthKey
         OCTET STRING,
      myOspfVirtIfStatus
         RowStatus,        
      myOspfVirtCost
            Unsigned32,
      myOspfVirtNativeIfIndex   
            INTEGER,
      myOspfVirtLinkState 
            INTEGER,     
      myOspfVirtHelloDueIn  
            TimeTicks,
     myOspfVirtCurrentUsedMd5AuthKeyId
            Unsigned32
                 }

    myOspfVirtIfAreaId OBJECT-TYPE
        SYNTAX   AreaID
        MAX-ACCESS   read-only
        STATUS   current
        DESCRIPTION
           "The  Transit  Area  that  the   Virtual   Link
           traverses.  By definition, this is not 0.0.0.0"
       ::= { myOspfVirtEntry 1 }


    myOspfVirtIfNeighbor OBJECT-TYPE
        SYNTAX   RouterID
        MAX-ACCESS   read-only
        STATUS   current
        DESCRIPTION
           "The Router ID of the Virtual Neighbor."
       ::= { myOspfVirtEntry 2 }


    myOspfVirtIfTransitDelay OBJECT-TYPE
        SYNTAX   Unsigned32 (1..65535)
        MAX-ACCESS   read-create
        STATUS   current
        DESCRIPTION
           "The estimated number of seconds  it  takes  to
           transmit  a link- state update packet over this
           interface."
       DEFVAL { 1 }
       ::= { myOspfVirtEntry 3 }


    myOspfVirtIfRetransInterval OBJECT-TYPE
        SYNTAX   Unsigned32 (1..65535)
        MAX-ACCESS   read-create
        STATUS   current
        DESCRIPTION
           "The number of seconds between  link-state  ad-
           vertisement  retransmissions,  for  adjacencies
           belonging to this  interface.   This  value  is
           also used when retransmitting database descrip-
           tion  and  link-state  request  packets.   This
           value  should  be well over the expected round-
           trip time."
       DEFVAL { 5 }
       ::= { myOspfVirtEntry 4 }


    myOspfVirtIfHelloInterval OBJECT-TYPE
        SYNTAX   HelloRange
        MAX-ACCESS   read-create
        STATUS   current
        DESCRIPTION
           "The length of time, in  seconds,  between  the
           Hello  packets that the router sends on the in-
           terface.  This value must be the same  for  the
           virtual neighbor."
       DEFVAL { 10 }
       ::= { myOspfVirtEntry 5 }


    myOspfVirtIfRtrDeadInterval OBJECT-TYPE
        SYNTAX   PositiveInteger
        MAX-ACCESS   read-create
        STATUS   current
        DESCRIPTION
           "The number of seconds that  a  router's  Hello
           packets  have  not been seen before it's neigh-
           bors declare the router down.  This  should  be
           some  multiple  of  the  Hello  interval.  This
           value must be the same for the  virtual  neigh-
           bor."
       DEFVAL { 40 }
       ::= { myOspfVirtEntry 6 }


    myOspfVirtIfState OBJECT-TYPE
        SYNTAX   INTEGER    {
                    down (1),            -- these use the same encoding
                    pointToPoint (4)     -- as the ospfIfTable
                  }
        MAX-ACCESS   read-only
        STATUS   current
        DESCRIPTION
           "OSPF virtual interface states."
       DEFVAL   { down }
       ::= { myOspfVirtEntry 7 }


    myOspfVirtIfEvents OBJECT-TYPE
        SYNTAX   Counter32
        MAX-ACCESS   read-only
        STATUS   current
        DESCRIPTION
           "The number of state changes or error events on
           this Virtual Link"
       ::= { myOspfVirtEntry 8 }


    myOspfVirtIfAuthKey OBJECT-TYPE
        SYNTAX   OCTET STRING (SIZE(0..256))
        MAX-ACCESS   read-create
        STATUS   current
        DESCRIPTION
           "If Authentication Type is simplePassword,  the
           device  will left adjust and zero fill to 8 oc-
           tets.

           Note that unauthenticated  interfaces  need  no
           authentication key, and simple password authen-
           tication cannot use a key of more  than  8  oc-
           tets.  Larger keys are useful only with authen-
           tication mechanisms not specified in this docu-
           ment.

           When  read,  ospfVifAuthKey  always  returns  a
           string of length zero."
       REFERENCE
          "OSPF Version 2, Section 9  The  Interface  Data
          Structure"
      DEFVAL   { '0000000000000000'H }    -- 0.0.0.0.0.0.0.0
      ::= { myOspfVirtEntry 9 }


    myOspfVirtIfStatus OBJECT-TYPE
        SYNTAX   RowStatus
        MAX-ACCESS   read-create
        STATUS   current
        DESCRIPTION
           "This variable displays the status of  the  en-
           try.  Setting it to 'invalid' has the effect of
           rendering it inoperative.  The internal  effect
           (row removal) is implementation dependent."
       ::= { myOspfVirtEntry 10 }


    myOspfVirtIfAuthType OBJECT-TYPE
        SYNTAX   INTEGER (0..255)
                    -- none (0),
                    -- simplePassword (1),
                    -- md5 (2),
                    -- default (3)
                    -- reserved for specification by IANA (> 2)
        MAX-ACCESS   read-create
        STATUS   current
        DESCRIPTION
           "The authentication type specified for a virtual  interface. Setting this value 
           'default' means using default authentication type referenced to Area Authentication,
            this value only for set,not be read. Additional authentication types
            may be assigned locally."
       REFERENCE
          "OSPF Version 2, Appendix E Authentication"
      DEFVAL { 0 }        -- no authentication, by default
      ::= { myOspfVirtEntry 11 }

                 
   myOspfVirtCost OBJECT-TYPE
        SYNTAX   Unsigned32 
        MAX-ACCESS   read-only
        STATUS   current
        DESCRIPTION
               "Explicitly specify the cost of sending a packet on the
                interface."
        ::= { myOspfVirtEntry 12 }   
        
    myOspfVirtNativeIfIndex OBJECT-TYPE 
        SYNTAX   INTEGER 
        MAX-ACCESS   read-only
        STATUS   current
        DESCRIPTION
               " the Interface's Index that The Virtual Link
                 via this interface."
        ::= { myOspfVirtEntry 13 } 
        
    myOspfVirtLinkState OBJECT-TYPE
        SYNTAX  INTEGER{
          		         up(1),
                        down(2)
                       }
        MAX-ACCESS   read-only
        STATUS   current
        DESCRIPTION
           "The  Virtual Link State is up or down."
       ::= { myOspfVirtEntry 14 }

    myOspfVirtHelloDueIn OBJECT-TYPE
        SYNTAX   TimeTicks 
        MAX-ACCESS   read-only
        STATUS   current
        DESCRIPTION
               " the time when hello due in." 
        ::= { myOspfVirtEntry 15 } 
        
    myOspfVirtCurrentUsedMd5AuthKeyId     OBJECT-TYPE  
       SYNTAX   Unsigned32 (0..255)                    
       MAX-ACCESS   read-write
        STATUS   current
        DESCRIPTION
           "the key-id which current used for md5 authentication,this value is 
            valid from 1 to 255, the value 0 is default value."
        DEFVAL {0}
       ::= { myOspfVirtEntry 16 }


-- The Ospf Virtual Interface MD5 authentication key configuration table

myOspfVirtIfMd5AuthKeyTable OBJECT-TYPE
        SYNTAX   SEQUENCE OF MyOspfVirtIfMd5AuthKeyEntry
        MAX-ACCESS   not-accessible
        STATUS   current
        DESCRIPTION
           "Configuration table of the key-id for md5 authentication in VirtIf 
            for OSPF protocol."
       ::= { myOspfMIBObjects  7 }

myOspfVirtIfMd5AuthKeyEntry OBJECT-TYPE
       SYNTAX   MyOspfVirtIfMd5AuthKeyEntry
       MAX-ACCESS   not-accessible
       STATUS   current
       DESCRIPTION
          "Configuration entry of the key-id for md5 authentication in VirtIf
           for OSPF protocol"
      INDEX {myOspfVirtIfMd5AuthKeyAreaId, myOspfVirtIfMd5AuthKeyNeighbor,
             myOspfVirtIfMd5AuthKeyId }
      ::= { myOspfVirtIfMd5AuthKeyTable 1 }
    
MyOspfVirtIfMd5AuthKeyEntry ::=
        SEQUENCE { 
         myOspfVirtIfMd5AuthKeyAreaId
            AreaID,
         myOspfVirtIfMd5AuthKeyNeighbor
            RouterID,
         myOspfVirtIfMd5AuthKeyId
            Unsigned32,
         myOspfVirtIfMd5AuthKey
            OCTET STRING,
         myOspfVirtIfMd5AuthKeySt   
            ConfigStatus
                 }
                 
myOspfVirtIfMd5AuthKeyAreaId OBJECT-TYPE
        SYNTAX   AreaID
        MAX-ACCESS   read-only
        STATUS   current
        DESCRIPTION
           "The  Transit  Area  that  the   Virtual   Link
           traverses.  By definition, this is not 0.0.0.0"
       ::= { myOspfVirtIfMd5AuthKeyEntry 1 }

myOspfVirtIfMd5AuthKeyNeighbor OBJECT-TYPE
        SYNTAX   RouterID
        MAX-ACCESS   read-only
        STATUS   current
        DESCRIPTION
           "The Router ID of the Virtual Neighbor."
       ::= { myOspfVirtIfMd5AuthKeyEntry 2 }

myOspfVirtIfMd5AuthKeyId     OBJECT-TYPE  
        SYNTAX   Unsigned32 (1..255)                    
        MAX-ACCESS   read-only
        STATUS   current
        DESCRIPTION
           "the key-id for md5 authentication."
       ::= { myOspfVirtIfMd5AuthKeyEntry 3 } 

myOspfVirtIfMd5AuthKey OBJECT-TYPE
        SYNTAX   OCTET STRING (SIZE (0..256))
        MAX-ACCESS   read-create
        STATUS   current
        DESCRIPTION
           "The Authentication Key for MD5.
           
           When read, myOspfVirtIfMd5AuthKey always returns an  Oc-
           tet String of length zero."
       REFERENCE
          "OSPF Version 2, Section 9  The  Interface  Data
          Structure"
      ::= { myOspfVirtIfMd5AuthKeyEntry 4 }

myOspfVirtIfMd5AuthKeySt OBJECT-TYPE
        SYNTAX   ConfigStatus
        MAX-ACCESS   read-write
        STATUS   current
        DESCRIPTION
           "Setting this value to 'invalid' will delete this entry.
            Setting this value to 'valid' will have no effect."
      ::= { myOspfVirtIfMd5AuthKeyEntry 5 }
                             
     
myOspfLsaDetailInfoMibsGroup OBJECT IDENTIFIER ::= { myOspfMIBObjects 8 }       


--  OSPF Link State Database

--      The Link State Database contains the Link State
--      Advertisements from throughout the areas that the
--      device is attached to.


myOspfLsdbTable OBJECT-TYPE
     SYNTAX   SEQUENCE OF MyOspfLsdbEntry
     MAX-ACCESS   not-accessible
     STATUS   current
     DESCRIPTION
        "The OSPF Process's Link State Database."
    REFERENCE
       "OSPF Version 2, Section 12  Link  State  Adver-
       tisements"
   ::= { myOspfLsaDetailInfoMibsGroup 1 }


myOspfLsdbEntry OBJECT-TYPE
     SYNTAX   MyOspfLsdbEntry
     MAX-ACCESS   not-accessible
     STATUS   current
     DESCRIPTION
        "A single Link State Advertisement."
    INDEX { myOspfLsdbAreaId, myOspfLsdbType,
            myOspfLsdbLsid, myOspfLsdbRouterId }
    ::= { myOspfLsdbTable 1 }

MyOspfLsdbEntry ::=
    SEQUENCE {
        myOspfLsdbAreaId
            AreaID,
        myOspfLsdbType
            INTEGER,
        myOspfLsdbLsid
            IpAddress,
        myOspfLsdbRouterId
            RouterID,
        myOspfLsdbSequence
            Unsigned32,
        myOspfLsdbAge
            Unsigned32,
        myOspfLsdbChecksum
            Unsigned32,
        myOspfLsdbAdvertisement
            OCTET STRING,
        myOspfLsdbLinkNum  --equal LinkCount 
            Unsigned32,
        myOspfLsdbPacketLength
            INTEGER,
        myOspfSummaryLsaNetworkMask
            IpAddress,
        myOspfSummaryLsaTos0Metric
            Unsigned32,
        myOspfNssaLsaDetailMetricType
            INTEGER,
        myOspfNssaLsaDetailForwardAddr 
            IpAddress,
        myOspfNssaLsaDetailRouteTag
            Unsigned32,
        myOspfLsdbOption
            Unsigned32  
              }
myOspfLsdbAreaId OBJECT-TYPE
        SYNTAX   AreaID
        MAX-ACCESS   read-only
        STATUS   current
        DESCRIPTION
           "The 32 bit identifier of the Area  from  which
           the LSA was received."
       REFERENCE
          "OSPF Version 2, Appendix C.2 Area parameters"
      ::= { myOspfLsdbEntry 1 }

-- External Link State Advertisements are permitted
-- for backward compatibility, but should be displayed in
-- the ospfExtLsdbTable rather than here.

myOspfLsdbType OBJECT-TYPE
        SYNTAX   INTEGER    {
                    routerLink (1),
                    networkLink (2),
                    summaryLink (3),
                    asSummaryLink (4),
                    asExternalLink (5), -- but see myOspfExtLsdbTable
                    multicastLink (6),
                    nssaExternalLink (7)
                  }
        MAX-ACCESS   read-only
        STATUS   current
        DESCRIPTION
           "The type  of  the  link  state  advertisement.
           Each  link state type has a separate advertise-
           ment format."
       REFERENCE
          "OSPF Version 2, Appendix A.4.1 The  Link  State
          Advertisement header"
      ::= { myOspfLsdbEntry 2 }

myOspfLsdbLsid OBJECT-TYPE
        SYNTAX   IpAddress
        MAX-ACCESS   read-only
        STATUS   current
        DESCRIPTION
           "The Link State ID is an LS Type Specific field
           containing either a Router ID or an IP Address;
           it identifies the piece of the  routing  domain
           that is being described by the advertisement."
       REFERENCE
          "OSPF Version 2, Section 12.1.4 Link State ID"
      ::= { myOspfLsdbEntry 3 }

myOspfLsdbRouterId OBJECT-TYPE
        SYNTAX   RouterID
        MAX-ACCESS   read-only
        STATUS   current
        DESCRIPTION
           "The 32 bit number that uniquely identifies the
           originating router in the Autonomous System."
       REFERENCE
          "OSPF Version 2, Appendix C.1 Global parameters"
      ::= { myOspfLsdbEntry 4 }

--  Note that the OSPF Sequence Number is a 32 bit signed
--  integer.  It mys with the value '80000001'h,
--  or -'7FFFFFFF'h, and increments until '7FFFFFFF'h
--  Thus, a typical sequence number will be very negative.

myOspfLsdbSequence OBJECT-TYPE
        SYNTAX   Unsigned32
        MAX-ACCESS   read-only
        STATUS   current
        DESCRIPTION
           "The sequence number field is a  signed  32-bit
           integer.   It  is used to detect old and dupli-
           cate link state advertisements.  The  space  of
           sequence  numbers  is  linearly  ordered.   The
           larger the sequence number the more recent  the
           advertisement."
       REFERENCE
          "OSPF Version  2,  Section  12.1.6  LS  sequence
          number"
      ::= { myOspfLsdbEntry 5 }

myOspfLsdbAge OBJECT-TYPE
        SYNTAX   Unsigned32    -- Should be 0..MaxAge
        MAX-ACCESS   read-only
        STATUS   current
        DESCRIPTION
           "This field is the age of the link state adver-
           tisement in seconds."
       REFERENCE
          "OSPF Version 2, Section 12.1.1 LS age"
      ::= { myOspfLsdbEntry 6 }

myOspfLsdbChecksum OBJECT-TYPE
        SYNTAX   Unsigned32
        MAX-ACCESS   read-only
        STATUS   current
        DESCRIPTION
           "This field is the  checksum  of  the  complete
           contents  of  the  advertisement, excepting the
           age field.  The age field is excepted  so  that
           an   advertisement's  age  can  be  incremented
           without updating the  checksum.   The  checksum
           used  is  the same that is used for ISO connec-
           tionless datagrams; it is commonly referred  to
           as the Fletcher checksum."
       REFERENCE
          "OSPF Version 2, Section 12.1.7 LS checksum"
      ::= { myOspfLsdbEntry 7 }

myOspfLsdbAdvertisement OBJECT-TYPE
        SYNTAX   OCTET STRING (SIZE (1..512))
        MAX-ACCESS   read-only
        STATUS   current
        DESCRIPTION
           "The entire Link State Advertisement, including
           its header."
       REFERENCE
          "OSPF Version 2, Section 12  Link  State  Adver-
          tisements"
      ::= { myOspfLsdbEntry 8 }
      
 myOspfLsdbLinkNum   OBJECT-TYPE                                            
        SYNTAX   Unsigned32(0..4294967295)
        MAX-ACCESS   read-only
        STATUS   current
        DESCRIPTION
           "  the link count of this Router Link Lsa ,
              this field is only valid for Router Link Lsa（type 1 LSA)"
       ::= { myOspfLsdbEntry 9 }         

myOspfLsdbPacketLength   OBJECT-TYPE
        SYNTAX   Unsigned32(0..65535)
        MAX-ACCESS   read-only
        STATUS   current
        DESCRIPTION
           "the  lsa packet  length   ."
       ::= { myOspfLsdbEntry 10 }  
      
myOspfSummaryLsaNetworkMask  OBJECT-TYPE
        SYNTAX   IpAddress
        MAX-ACCESS   read-only
        STATUS   current
        DESCRIPTION
           "this field is only useful when  ospfLsdbType is type-3 or 
           type-4 or type-7,it's the Lsa's network mask  ."
       ::= { myOspfLsdbEntry 11 } 

myOspfSummaryLsaTos0Metric OBJECT-TYPE
        SYNTAX   Unsigned32(0..65535)
        MAX-ACCESS   read-only
        STATUS   current
        DESCRIPTION
           "this field is only useful when  ospfLsdbType is type-3 or 
           type-4 or type-7,it's the  Lsa's tos0 metric  ."
       ::= { myOspfLsdbEntry 12 } 
       
myOspfNssaLsaDetailMetricType   OBJECT-TYPE
        SYNTAX   INTEGER
                       { type1(1),
                         type2(2)
                        }
        MAX-ACCESS   read-only
        STATUS   current
        DESCRIPTION
           "    this field is valid when Lsa is a type-7 LSA.
	        The type of Nssa ernal metric.  If bit E is set, the metric
	        specified is a Type 2 external metric.  This means the metric is
	        considered larger than any link state path.  If bit E is zero,
	        the specified metric is a Type 1 external metric.  This means
	        that it is expressed in the same units as the link state metric
	        (i.e., the same units as interface cost).  "
       ::= { myOspfLsdbEntry 13 }  
       
 myOspfNssaLsaDetailForwardAddr   OBJECT-TYPE  
        SYNTAX   IpAddress
        MAX-ACCESS   read-only
        STATUS   current
        DESCRIPTION
           "this field is valid when Lsa is a type-7 LSA. 
            Data traffic for the advertised destination will be forwarded to
            this address.  If the Forwarding address is set to 0.0.0.0, data
            traffic will be forwarded instead to the LSA's originator (i.e.,
            the responsible AS boundary router)  ."            
       ::= { myOspfLsdbEntry 14 }         
       
 myOspfNssaLsaDetailRouteTag   OBJECT-TYPE
        SYNTAX   Unsigned32
        MAX-ACCESS   read-only
        STATUS   current
        DESCRIPTION
           " this field is valid when Lsa is a type-7 LSA.
             A 32-bit field attached to each external route.  This is not
             used by the OSPF protocol itself.  It may be used to communicate
             information between AS boundary routers; the precise nature of
             such information is outside the scope of this specification."
       ::= { myOspfLsdbEntry 15 }          

 myOspfLsdbOption   OBJECT-TYPE
        SYNTAX   Unsigned32
        MAX-ACCESS   read-only
        STATUS   current
        DESCRIPTION
           "the option field indicate which optional capabilities
            area associated with the LSA. "
        REFERENCE
          "OSPF Version 2, Appendix A.2, the Options Field"
       ::= { myOspfLsdbEntry 16 }           

--  OSPF Link State Database, External

--      The Link State Database contains the Link State
--      Advertisements from throughout the areas that the
--      device is attached to.

--             This table is identical to the OSPF LSDB Table in
--      format, but contains only External Link State
--             Advertisements.  The purpose is to allow external
--      LSAs to be displayed once for the router rather
--      than once in each non-stub area.

myOspfExtLsdbTable OBJECT-TYPE
        SYNTAX   SEQUENCE OF MyOspfExtLsdbEntry
        MAX-ACCESS   not-accessible
        STATUS   current
        DESCRIPTION
           "The OSPF Process's Links State Database."
        REFERENCE
          "OSPF Version 2, Section 12  Link  State  Adver-
          tisements"
       ::= { myOspfLsaDetailInfoMibsGroup  2 }

myOspfExtLsdbEntry OBJECT-TYPE
       SYNTAX   MyOspfExtLsdbEntry
       MAX-ACCESS   not-accessible
       STATUS   current        
       DESCRIPTION
           "A single Link State Advertisement."
       INDEX { myOspfExtLsdbType, myOspfExtLsdbLsid, myOspfExtLsdbRouterId }    
      ::= { myOspfExtLsdbTable 1 }
      
MyOspfExtLsdbEntry ::=
     SEQUENCE{
        myOspfExtLsdbType
            INTEGER,
        myOspfExtLsdbLsid
            IpAddress,
        myOspfExtLsdbRouterId
            RouterID,
        myOspfExtLsdbSequence
            Unsigned32,
        myOspfExtLsdbAge
            Unsigned32,
        myOspfExtLsdbChecksum
            Unsigned32,
        myOspfExtLsdbAdvertisement
            OCTET STRING,     
        myOspfExtLsdbNetworkMask
            IpAddress,
        myOspfExtLsdbMetricType   
            INTEGER,
        myOspfExtLsdbForwardAddr
            IpAddress,
        myOspfExtLsdbRouteTag
            IpAddress,
        myOspfExtLsdbMetric   
            INTEGER,
        myOspfExtLsdbOption
            Unsigned32,
        myOspfExtLsdbPacketLength 
            Unsigned32   
              }          

 myOspfExtLsdbType OBJECT-TYPE
        SYNTAX   INTEGER    {
                    asExternalLink (5)
                  }
        MAX-ACCESS   read-only
        STATUS   current
        DESCRIPTION
           "The type  of  the  link  state  advertisement.
           Each  link state type has a separate advertise-
           ment format."
       REFERENCE
          "OSPF Version 2, Appendix A.4.1 The  Link  State
          Advertisement header"
      ::= { myOspfExtLsdbEntry 1 }


 myOspfExtLsdbLsid OBJECT-TYPE
        SYNTAX   IpAddress
        MAX-ACCESS   read-only
        STATUS   current
        DESCRIPTION
           "The Link State ID is an LS Type Specific field
           containing either a Router ID or an IP Address;
           it identifies the piece of the  routing  domain
           that is being described by the advertisement."
       REFERENCE
          "OSPF Version 2, Section 12.1.4 Link State ID"
      ::= { myOspfExtLsdbEntry 2 }


 myOspfExtLsdbRouterId OBJECT-TYPE
        SYNTAX   RouterID
        MAX-ACCESS   read-only
        STATUS   current
        DESCRIPTION
           "The 32 bit number that uniquely identifies the
           originating router in the Autonomous System."
       REFERENCE
          "OSPF Version 2, Appendix C.1 Global parameters"
      ::= { myOspfExtLsdbEntry 3 }

--  Note that the OSPF Sequence Number is a 32 bit signed
--  integer.  It mys with the value '80000001'h,
--  or -'7FFFFFFF'h, and increments until '7FFFFFFF'h
--  Thus, a typical sequence number will be very negative.

 myOspfExtLsdbSequence OBJECT-TYPE
        SYNTAX   Unsigned32
        MAX-ACCESS   read-only
        STATUS   current
        DESCRIPTION
           "The sequence number field is a  signed  32-bit
           integer.   It  is used to detect old and dupli-
           cate link state advertisements.  The  space  of
           sequence  numbers  is  linearly  ordered.   The
           larger the sequence number the more recent  the
           advertisement."
       REFERENCE
          "OSPF Version  2,  Section  12.1.6  LS  sequence
          number"
      ::= { myOspfExtLsdbEntry 4 }


 myOspfExtLsdbAge OBJECT-TYPE
        SYNTAX   Unsigned32    -- Should be 0..MaxAge
        MAX-ACCESS   read-only
        STATUS   current
        DESCRIPTION
           "This field is the age of the link state adver-
           tisement in seconds."
       REFERENCE
          "OSPF Version 2, Section 12.1.1 LS age"
      ::= { myOspfExtLsdbEntry 5 }


 myOspfExtLsdbChecksum OBJECT-TYPE
        SYNTAX   Unsigned32
        MAX-ACCESS   read-only
        STATUS   current
        DESCRIPTION
           "This field is the  checksum  of  the  complete
           contents  of  the  advertisement, excepting the
           age field.  The age field is excepted  so  that
           an   advertisement's  age  can  be  incremented
           without updating the  checksum.   The  checksum
           used  is  the same that is used for ISO connec-
           tionless datagrams; it is commonly referred  to
           as the Fletcher checksum."
       REFERENCE
          "OSPF Version 2, Section 12.1.7 LS checksum"
      ::= { myOspfExtLsdbEntry 6 }


 myOspfExtLsdbAdvertisement OBJECT-TYPE
        SYNTAX   OCTET STRING (SIZE(36))
        MAX-ACCESS   read-only
        STATUS   current
        DESCRIPTION
           "The entire Link State Advertisement, including
           its header."
       REFERENCE
          "OSPF Version 2, Section 12  Link  State  Adver-
          tisements"
      ::= { myOspfExtLsdbEntry 7 }
                  
 myOspfExtLsdbNetworkMask   OBJECT-TYPE
        SYNTAX   IpAddress
        MAX-ACCESS   read-only
        STATUS   current
        DESCRIPTION
           "The IP address mask for the advertised destination.  For
            example, when advertising a class A network the mask 0xff000000
            would be used."
       ::= { myOspfExtLsdbEntry 8 }   

 myOspfExtLsdbMetric   OBJECT-TYPE
        SYNTAX   INTEGER                       
        MAX-ACCESS   read-only
        STATUS   current
        DESCRIPTION
           " The cost of this route.  Interpretation depends on the external
             type indication.  "
       ::= { myOspfExtLsdbEntry 9 } 
               
 myOspfExtLsdbMetricType   OBJECT-TYPE
        SYNTAX   INTEGER
                       { type1(1),
                         type2(2)
                        }
        MAX-ACCESS   read-only
        STATUS   current
        DESCRIPTION
           " The type of external metric.  If bit E is set, the metric
            specified is a Type 2 external metric.  This means the metric is
            considered larger than any link state path.  If bit E is zero,
            the specified metric is a Type 1 external metric.  This means
            that it is expressed in the same units as the link state metric
            (i.e., the same units as interface cost).  "
       ::= { myOspfExtLsdbEntry 10 }  
       
 myOspfExtLsdbForwardAddr   OBJECT-TYPE  
        SYNTAX   IpAddress
        MAX-ACCESS   read-only
        STATUS   current
        DESCRIPTION
           "  Data traffic for the advertised destination will be forwarded to
              this address.  If the Forwarding address is set to 0.0.0.0, data
              traffic will be forwarded instead to the LSA's originator (i.e.,
              the responsible AS boundary router)  ."
       ::= { myOspfExtLsdbEntry 11 }      
          
 myOspfExtLsdbRouteTag   OBJECT-TYPE
        SYNTAX   Unsigned32
        MAX-ACCESS   read-only
        STATUS   current
        DESCRIPTION
           "A 32-bit field attached to each external route.  This is not
           used by the OSPF protocol itself.  It may be used to communicate
           information between AS boundary routers; the precise nature of
           such information is outside the scope of this specification."
       ::= { myOspfExtLsdbEntry 12 }    
       
 
              
 myOspfExtLsdbOption   OBJECT-TYPE
        SYNTAX   Unsigned32
        MAX-ACCESS   read-only
        STATUS   current
        DESCRIPTION
           "the option field indicate which optional capabilities
            area associated with the LSA. "
        REFERENCE
          "OSPF Version 2, Appendix A.2, the Options Field"
       ::= { myOspfExtLsdbEntry 13 } 
       
myOspfExtLsdbPacketLength   OBJECT-TYPE
        SYNTAX   Unsigned32(0..65535)
        MAX-ACCESS   read-only
        STATUS   current
        DESCRIPTION
           "the  lsa packet  length   ."
       ::= { myOspfExtLsdbEntry 14 }       

--Router Lsa's detail information table  

myOspfRouterLsaDetailTable OBJECT-TYPE
        SYNTAX   SEQUENCE OF MyOspfRouterLsaDetailEntry
        MAX-ACCESS   not-accessible
        STATUS   current
        DESCRIPTION
           "the router Lsa's detail Infromtion."
       ::= { myOspfLsaDetailInfoMibsGroup  3 }

myOspfRouterLsaDetailEntry OBJECT-TYPE
       SYNTAX   MyOspfRouterLsaDetailEntry
       MAX-ACCESS   not-accessible
       STATUS   current
       DESCRIPTION
          "the entry of this table."
      INDEX {myOspfLsdbAreaId, myOspfLsdbType,
             myOspfLsdbLsid, myOspfLsdbRouterId,
             myOspfRouterLsaDetailLinkID
             }
      ::= { myOspfRouterLsaDetailTable 1 }
      
MyOspfRouterLsaDetailEntry ::=
     SEQUENCE{
        myOspfRouterLsaDetailLinkID
            IpAddress,
        myOspfRouterLsaDetailLinkType
            INTEGER,
        myOspfRouterLsaDetailLinkData
            IpAddress,
        myOspfRouterLsaDetailTos0Metric  
            INTEGER
              }   

 myOspfRouterLsaDetailLinkID   OBJECT-TYPE
        SYNTAX   IpAddress
        MAX-ACCESS   read-only
        STATUS   current
        DESCRIPTION
           "router lsa's link ID Identifies the object that this router
            link connects to.  Value  depends on the link's Type.  
            When connecting to an object that  also originates an 
            LSA (i.e., another router or a transit  network) the 
            Link ID is equal to the neighboring LSA's Link
           State ID.  This provides the key for looking up the neighboring
           LSA in the link state database during the routing table
           calculation. See Section 12.2 for more details.
                       Type   Link ID
                       ________________________________________
                       1      Neighboring router's Router ID
                       2      IP address of Designated Router
                       3      IP network/subnet number
                       4      Neighboring router's Router ID
           "
       ::= { myOspfRouterLsaDetailEntry 1 }  
                     
 myOspfRouterLsaDetailLinkType   OBJECT-TYPE
        SYNTAX   INTEGER{
                         pointtopointConnectionToAnotherRouter(1),
                         connectionToaTransitNetwork(2),
                         connectionToaStubNetwork(3),
                         virtualLink(4)
                        }
        MAX-ACCESS   read-only
        STATUS   current
        DESCRIPTION
           "router lsa's link type
            A quick description of the router link.  One of the following.
           Note that host routes are classified as links to stub networks
           with network mask of 0xffffffff."
       ::= { myOspfRouterLsaDetailEntry 2 }    
              
 myOspfRouterLsaDetailLinkData   OBJECT-TYPE
        SYNTAX   IpAddress
        MAX-ACCESS   read-only
        STATUS   current
        DESCRIPTION
           " Value again depends on the link's Type field. For connections to
             stub networks, Link Data specifies the network's IP address
             mask. For unnumbered point-to-point connections, it specifies
             the interface's MIB-II  ifIndex value. For the other link
             types it specifies the router interface's IP address. This
            latter piece of information is needed during the routing table
            build process, when calculating the IP address of the next hop.            "
       ::= { myOspfRouterLsaDetailEntry 3 } 
              
myOspfRouterLsaDetailTos0Metric   OBJECT-TYPE  
        SYNTAX   Unsigned32
        MAX-ACCESS   read-only
        STATUS   current
        DESCRIPTION
           "TOS0-specific metric information."
       ::= { myOspfRouterLsaDetailEntry 4 }    
        
        
--NetWork Lsa's detail information table  

myOspfNetWorkLsaDetailTable OBJECT-TYPE
        SYNTAX   SEQUENCE OF MyOspfNetWorkLsaDetailEntry
        MAX-ACCESS   not-accessible
        STATUS   current
        DESCRIPTION
           "the NetWork Lsa's detail Infromtion."
       ::= { myOspfLsaDetailInfoMibsGroup  4 }

myOspfNetWorkLsaDetailEntry OBJECT-TYPE
       SYNTAX   MyOspfNetWorkLsaDetailEntry
       MAX-ACCESS   not-accessible
       STATUS   current
       DESCRIPTION
          "the entry of this table."
      INDEX {myOspfLsdbAreaId, myOspfLsdbType,
             myOspfLsdbLsid, myOspfLsdbRouterId,
             myOspfNetWorkLsaDetailAttachedRouter
             }
      ::= { myOspfNetWorkLsaDetailTable 1 }
      
MyOspfNetWorkLsaDetailEntry ::=
     SEQUENCE{
        myOspfNetWorkLsaDetailAttachedRouter   
            IpAddress,     
        myOspfNetWorkLsaDetailNetworkMask 
            IpAddress        
              }                 
 myOspfNetWorkLsaDetailAttachedRouter   OBJECT-TYPE
        SYNTAX   IpAddress
        MAX-ACCESS   read-only
        STATUS   current
        DESCRIPTION
           " The Router IDs of each of the routers attached to the network.
             Actually, only those routers that are fully adjacent to the
             Designated Router are listed.  The Designated Router includes
             itself in this list.  The number of routers included can be
             deduced from the LSA header's length field.  "
       ::= { myOspfNetWorkLsaDetailEntry 1 }   
                         
 myOspfNetWorkLsaDetailNetworkMask   OBJECT-TYPE
        SYNTAX   IpAddress
        MAX-ACCESS   read-only
        STATUS   current
        DESCRIPTION
           "The IP address mask for the network.  For example, a class A
            network would have the mask 0xff000000."
       ::= { myOspfNetWorkLsaDetailEntry 2 }    
       

--my Ospf Area Lsa Database Summary Table 

myOspfAreaLsaDBSumTable OBJECT-TYPE
        SYNTAX   SEQUENCE OF MyOspfAreaLsaDBSumEntry
        MAX-ACCESS   not-accessible
        STATUS   current
        DESCRIPTION
           "The OSPF Area LSA database summary Infromtion."
       ::= { myOspfLsaDetailInfoMibsGroup  5 }

myOspfAreaLsaDBSumEntry OBJECT-TYPE
       SYNTAX   MyOspfAreaLsaDBSumEntry
       MAX-ACCESS   not-accessible
       STATUS   current
       DESCRIPTION
          "the entry of this table."
      INDEX {myOspfAreaLsaDBSumAreaId, 
             myOspfAreaLsaDBSumLsaType
             }
      ::= { myOspfAreaLsaDBSumTable 1 }
      
MyOspfAreaLsaDBSumEntry ::=
     SEQUENCE{
        myOspfAreaLsaDBSumAreaId
            IpAddress,
        myOspfAreaLsaDBSumLsaType
            INTEGER,
        myOspfAreaLsaDBSumCounts   
            Counter32,
        myOspfAreaLsaDBSumDeletes
            Counter32,
        myOspfAreaLsaDBSumMaxage
            Counter32 
            }   
 myOspfAreaLsaDBSumAreaId   OBJECT-TYPE  
        SYNTAX   IpAddress
        MAX-ACCESS   read-only
        STATUS   current
        DESCRIPTION
           "The area Id."
       ::= { myOspfAreaLsaDBSumEntry 1 }  
              
 myOspfAreaLsaDBSumLsaType   OBJECT-TYPE
        SYNTAX   INTEGER 
        	{ routerLink (1),
           networkLink (2),
           summaryLink (3),
           asSummaryLink (4),
           --asExternalLink (5), because in each area,type 5 lsa is no meaning
                                 --it's only meaning in one router
           -- multicastLink (6),  not implement
           nssaExternalLink (7),
           subtotal(8)
           --subtotal is use for total counter for all type LSA in this area.
           }
        MAX-ACCESS   read-only
        STATUS   current
        DESCRIPTION
           "the entry's entry type."
       ::= { myOspfAreaLsaDBSumEntry 2 }    
       
 myOspfAreaLsaDBSumCounts   OBJECT-TYPE
        SYNTAX   Counter32
        MAX-ACCESS   read-only
        STATUS   current
        DESCRIPTION
           " number os this type Lsa in this area ,
             if this type Lsa does not exist,this field is 0."
       ::= { myOspfAreaLsaDBSumEntry 3 } 
       
myOspfAreaLsaDBSumDeletes    OBJECT-TYPE
        SYNTAX   Counter32
        MAX-ACCESS   read-only
        STATUS   current
        DESCRIPTION
           " number os this type Lsa which has been delete in this area ,
             if this type Lsa is not been deleted,this field is 0"
       ::= { myOspfAreaLsaDBSumEntry 4 }   
       
 myOspfAreaLsaDBSumMaxage   OBJECT-TYPE
        SYNTAX   Counter32
        MAX-ACCESS   read-only
        STATUS   current
        DESCRIPTION
           " number of this type Lsa which has up to Maxage,
             if this type Lsa which has up to Maxage does not exist,
             this field is 0"
       ::= { myOspfAreaLsaDBSumEntry 5 }  
 

--my Ospf Lsa Database total summary table 

myOspfLsaDBSumTable OBJECT-TYPE
        SYNTAX   SEQUENCE OF MyOspfLsaDBSumEntry
        MAX-ACCESS   not-accessible
        STATUS   current
        DESCRIPTION
           "LSA database total summary infromtion in the all areas ."
       ::= { myOspfLsaDetailInfoMibsGroup  6 }

myOspfLsaDBSumEntry OBJECT-TYPE
       SYNTAX   MyOspfLsaDBSumEntry
       MAX-ACCESS   not-accessible
       STATUS   current
       DESCRIPTION
          "the entry of this table."
      INDEX {   
               myOspfLsaDBSumLsaType
            }
      ::= { myOspfLsaDBSumTable 1 }
      
MyOspfLsaDBSumEntry ::=
     SEQUENCE{
        myOspfLsaDBSumLsaType
            INTEGER,
        myOspfLsaDBSumCounts   
            Counter32,
        myOspfLsaDBSumDeletes
            Counter32,
        myOspfLsaDBSumMaxage
            Counter32
              }   
     
 myOspfLsaDBSumLsaType   OBJECT-TYPE
        SYNTAX   INTEGER 
        	{ routerLink (1),
           networkLink (2),
           summaryTotalLink (3),
           asSummaryTotalLink (4),
           asExternalLink (5), 
           -- multicastLink (6),  not implement
           nssaExternalLink (7),
           total(8)
           --subtotal is use for total counter for all type LSA in this router. 
                 }
        MAX-ACCESS   read-only
        STATUS   current
        DESCRIPTION
           "the table's entry type."
       ::= { myOspfLsaDBSumEntry 1 }   
        
 myOspfLsaDBSumCounts   OBJECT-TYPE
        SYNTAX   Counter32
        MAX-ACCESS   read-only
        STATUS   current
        DESCRIPTION
           "total number of this type Lsa in all area ."
       ::= { myOspfLsaDBSumEntry 2 } 
       
myOspfLsaDBSumDeletes    OBJECT-TYPE
        SYNTAX   Counter32
        MAX-ACCESS   read-only
        STATUS   current
        DESCRIPTION
           " total number of this type Lsa deleted in all area ."
       ::= { myOspfLsaDBSumEntry 3 }  
        
myOspfLsaDBSumMaxage   OBJECT-TYPE
        SYNTAX   Counter32
        MAX-ACCESS   read-only
        STATUS   current
        DESCRIPTION
           "total number of this type Lsa which has been up to max age in all area "
       ::= { myOspfLsaDBSumEntry 4 } 
       

--      The OSPF Neighbor Table describes all neighbors in
--      the locality of the subject router.

myOspfNeighborTable OBJECT-TYPE
        SYNTAX   SEQUENCE OF MyOspfNeighborEntry
        MAX-ACCESS   not-accessible
        STATUS   current
        DESCRIPTION
           "the neighbor detail infomation ."
       REFERENCE
          "ospfNbrTable in rfc1850"           
       ::= { myOspfMIBObjects  9 }

myOspfNeighborEntry OBJECT-TYPE
       SYNTAX   MyOspfNeighborEntry
       MAX-ACCESS   not-accessible
       STATUS   current
       DESCRIPTION
          "the entry of this table."
      INDEX {   myOspfNbrIpAddr, 
                myOspfNbrAddressLessIndex
             }
      ::= { myOspfNeighborTable 1 }
      
MyOspfNeighborEntry ::=
     SEQUENCE{
        myOspfNbrIpAddr
            IpAddress,
        myOspfNbrAddressLessIndex
            Unsigned32,
        myOspfNbrRtrId
            RouterID,
        myOspfNbrOptions
            Unsigned32,
        myOspfNbrPriority
            DesignatedRouterPriority,
        myOspfNbrState
            INTEGER,
        myOspfNbrEvents
            Counter32,
        myOspfNbrLsRetransQLen
            Gauge32,
        myOspfNbmaNbrStatus
            RowStatus,
        myOspfNbmaNbrPermanence
            INTEGER,
        myOspfNbrHelloSuppressed
            TruthValue,     
        myOspfNbrDeadTimeDueIn   
            TimeTicks,
        myOspfNbrNeighborUpTime
            TimeTicks,
        myOspfNbrDR
            IpAddress,
        myOspfNbrBDR
            IpAddress,
        myOspfNbrArea
            IpAddress,
        myOspfNbrRetransmissionNum
            Counter32,
        myOspfNbrIfState
            INTEGER
              }   
myOspfNbrIpAddr OBJECT-TYPE
        SYNTAX   IpAddress
        MAX-ACCESS   read-only
        STATUS   current
        DESCRIPTION
           "The IP address this neighbor(neighbor's interface IP address) 
           is using  in  its IP  Source  Address.  Note that, on addressless
           links, this will not be 0.0.0.0,  but  the  ad-
           dress of another of the neighbor's interfaces."
       ::= { myOspfNeighborEntry 1 }


myOspfNbrAddressLessIndex OBJECT-TYPE
        SYNTAX   Unsigned32
        MAX-ACCESS   read-only
        STATUS   current
        DESCRIPTION
           "On an interface having an  IP  Address,  zero.
           On  addressless  interfaces,  the corresponding
           value of ifIndex in the Internet Standard  MIB.
           On  row  creation, this can be derived from the
           instance."
       ::= { myOspfNeighborEntry 2 }


myOspfNbrRtrId OBJECT-TYPE
        SYNTAX   RouterID
        MAX-ACCESS   read-only
        STATUS   current
        DESCRIPTION
           "A 32-bit integer (represented as a type  IpAd-
           dress)  uniquely  identifying  the  neighboring
           router in the Autonomous System."
       ::= { myOspfNeighborEntry 3 }


myOspfNbrOptions OBJECT-TYPE
        SYNTAX   Unsigned32
        MAX-ACCESS   read-only
        STATUS   current
        DESCRIPTION
           "A Bit Mask corresponding to the neighbor's op-
           tions field.

           Bit 0, if set, indicates that the  system  will
           operate  on  Type of Service metrics other than
           TOS 0.  If zero, the neighbor will  ignore  all
           metrics except the TOS 0 metric.

           Bit 1, if set, indicates  that  the  associated
           area  accepts and operates on external informa-
           tion; if zero, it is a stub area.

           Bit 2, if set, indicates that the system is ca-
           pable  of routing IP Multicast datagrams; i.e.,
           that it implements the Multicast Extensions  to
           OSPF.

           Bit 3, if set, indicates  that  the  associated
           area  is  an  NSSA.  These areas are capable of
           carrying type 7 external advertisements,  which
           are  translated into type 5 external advertise-
           ments at NSSA borders."
       REFERENCE
          "OSPF Version 2, Section 12.1.2 Options"
      ::= { myOspfNeighborEntry 4 }


myOspfNbrPriority OBJECT-TYPE
        SYNTAX   DesignatedRouterPriority
        MAX-ACCESS   read-only
        STATUS   current
        DESCRIPTION
           "The priority of this neighbor in the designat-
           ed router election algorithm.  The value 0 sig-
           nifies that the neighbor is not eligible to be-
           come  the  designated router on this particular
           network."
       ::= { myOspfNeighborEntry 5 }


myOspfNbrState OBJECT-TYPE
        SYNTAX   INTEGER    {
                    down (1),
                    attempt (2),
                    init (3),
                    twoWay (4),
                    exchangeMy (5),
                    exchange (6),
                    loading (7),
                    full (8)
                  }
        MAX-ACCESS   read-only
        STATUS   current
        DESCRIPTION
           "The State of the relationship with this Neigh-
           bor."
       REFERENCE
          "OSPF Version 2, Section 10.1 Neighbor States"
      ::= { myOspfNeighborEntry 6 }


myOspfNbrEvents OBJECT-TYPE
        SYNTAX   Counter32
        MAX-ACCESS   read-only
        STATUS   current
        DESCRIPTION
           "The number of times this neighbor relationship
           has changed state, or an error has occurred."
       ::= { myOspfNeighborEntry 7 }


myOspfNbrLsRetransQLen OBJECT-TYPE
        SYNTAX   Gauge32
        MAX-ACCESS   read-only
        STATUS   current
        DESCRIPTION
           "The  current  length  of  the   retransmission
           queue."
       ::= { myOspfNeighborEntry 8 }


myOspfNbmaNbrStatus OBJECT-TYPE
        SYNTAX   RowStatus
        MAX-ACCESS   read-only
        STATUS   current
        DESCRIPTION
           "This variable displays the status of  the  en-
           try.  Setting it to 'invalid' has the effect of
           rendering it inoperative.  The internal  effect
           (row removal) is implementation dependent."
       ::= { myOspfNeighborEntry 9 }


myOspfNbmaNbrPermanence OBJECT-TYPE
        SYNTAX   INTEGER    {
                    dynamic (1),        -- learned through protocol
                    permanent (2)       -- configured address
                  }
        MAX-ACCESS   read-only
        STATUS   current
        DESCRIPTION
           "This variable displays the status of  the  en-
           try.   'dynamic'  and  'permanent' refer to how
           the neighbor became known."
       ::= { myOspfNeighborEntry 10 }


myOspfNbrHelloSuppressed OBJECT-TYPE
        SYNTAX   TruthValue
        MAX-ACCESS   read-only
        STATUS   current
        DESCRIPTION
           "Indicates whether Hellos are being  suppressed
           to the neighbor"
       ::= { myOspfNeighborEntry 11 }
                     
myOspfNbrDeadTimeDueIn OBJECT-TYPE 
        SYNTAX   TimeTicks
        MAX-ACCESS   read-only
        STATUS   current
        DESCRIPTION
           "if in this interval ,hello packet is not been received ,
            the neighbor is recognized dead.if received,it 
            will recovery the dead time which has been setted."
       ::= { myOspfNeighborEntry 12 }
       
myOspfNbrNeighborUpTime OBJECT-TYPE 
        SYNTAX   TimeTicks
        MAX-ACCESS   read-only
        STATUS   current
        DESCRIPTION
           "the time that the neighbor has been up."
       ::= { myOspfNeighborEntry 13 }
       
myOspfNbrDR OBJECT-TYPE 
        SYNTAX   IpAddress
        MAX-ACCESS   read-only
        STATUS   current
        DESCRIPTION
           "the Designated Router of this neighbor."
       ::= { myOspfNeighborEntry 14 }
       
myOspfNbrBDR OBJECT-TYPE 
        SYNTAX   IpAddress
        MAX-ACCESS   read-only
        STATUS   current
        DESCRIPTION
           "the Backup Designated Router of this neighbor."
       ::= { myOspfNeighborEntry 15 }
       
myOspfNbrArea  OBJECT-TYPE	
	SYNTAX   IpAddress
        MAX-ACCESS   read-only
        STATUS   current
        DESCRIPTION
           "the area where the neighbor is in."
       ::= { myOspfNeighborEntry 16 }
       
myOspfNbrRetransmissionNum  OBJECT-TYPE 
        SYNTAX   Counter32
        MAX-ACCESS   read-only
        STATUS   current
        DESCRIPTION
           "the Retransmission times."
       ::= { myOspfNeighborEntry 17 }

myOspfNbrIfState OBJECT-TYPE
        SYNTAX   INTEGER    {
                    other(0),
                    designatedRouter (1),
                    backupDesignatedRouter (2),
                    otherDesignatedRouter (3)
                  }
        MAX-ACCESS   read-only
        STATUS   current
        DESCRIPTION
           "The neighbor's interface State which connected to local router."
        ::= { myOspfNeighborEntry 18 }

--OSPF border routing information
myOspfRouteTable OBJECT-TYPE
    SYNTAX   SEQUENCE OF MyOspfRouteEntry
    MAX-ACCESS not-accessible
    STATUS   current
    DESCRIPTION
       "This entity's OSPF border routing table."
    ::= { myOspfMIBObjects  10 }

myOspfRouteEntry OBJECT-TYPE
    SYNTAX   MyOspfRouteEntry
    MAX-ACCESS not-accessible
    STATUS   current
    DESCRIPTION
       "A  route to  a  destination."
    INDEX {
        myOspfRouteDest,
        myOspfRouteArea,        
        myOspfRouteNextHop        
        }
    ::= { myOspfRouteTable 1 }

MyOspfRouteEntry ::=
    SEQUENCE {
        myOspfRouteDest
            IpAddress,
        myOspfRouteArea
            IpAddress,            
        myOspfRouteNextHop
             IpAddress,
        myOspfRouteCost
            Unsigned32,
        myOspfRouteType
            INTEGER,            
        myOspfRouteDRType
            INTEGER,
        myOspfRouteSpfNo
            Counter32
   }
                 
myOspfRouteDest OBJECT-TYPE
    SYNTAX   IpAddress
    MAX-ACCESS read-only
    STATUS   current
    DESCRIPTION
       "Router ID of the destination."
    ::= { myOspfRouteEntry 1 }

myOspfRouteArea OBJECT-TYPE
    SYNTAX   IpAddress
    MAX-ACCESS read-only
    STATUS   current
    DESCRIPTION
       "The area ID of the area from which this route is learned."
    ::= { myOspfRouteEntry 2 }

myOspfRouteNextHop OBJECT-TYPE
    SYNTAX   IpAddress
    MAX-ACCESS read-only
    STATUS   current
    DESCRIPTION
       "Next hop toward the destination."
    ::= { myOspfRouteEntry 3 }

myOspfRouteCost OBJECT-TYPE
    SYNTAX   Unsigned32
    MAX-ACCESS read-only
    STATUS   current
    DESCRIPTION
       " Cost of using this route."

    ::= { myOspfRouteEntry 4 }
    
myOspfRouteDRType OBJECT-TYPE
    SYNTAX   INTEGER {
                      abr(1),
                      asbr(2),
                      both(3) --abr and asbr
                     }
    MAX-ACCESS read-only
    STATUS   current
    DESCRIPTION
       "The router type of the destination;
        it is either an ABR or ASBR or both."
    ::= { myOspfRouteEntry 5 }

myOspfRouteType  OBJECT-TYPE
    SYNTAX   INTEGER {
                       intral-area-route(1),
                       inter-area-route(2)
                       } 
    MAX-ACCESS read-only
    STATUS   current
    DESCRIPTION 
              "this field indicate this route is an intral area route 
               or inter area route."
      ::= { myOspfRouteEntry 6 } 
          
myOspfRouteSpfNo OBJECT-TYPE
    SYNTAX   Counter32
    MAX-ACCESS read-only
    STATUS   current
    DESCRIPTION
       " The internal number of the shortest path first (SPF) calculation that
         installs this route."
    ::= { myOspfRouteEntry 7 }
                             
-- conformance information

myOspfMIBConformance OBJECT IDENTIFIER ::= { myOspfMIB 2 }
myOspfMIBCompliances OBJECT IDENTIFIER ::= { myOspfMIBConformance 1 }
myOspfMIBGroups      OBJECT IDENTIFIER ::= { myOspfMIBConformance 2 }


-- compliance statements

myOspfMIBCompliance MODULE-COMPLIANCE
        STATUS  current
        DESCRIPTION
                "The compliance statement for entities which implement
                the My OSPF MIB"
        MODULE  -- this module
                MANDATORY-GROUPS {
                     myOspfBaseMIBGroup,
                     myOspfAreaMIBGroup,
                     myOspfLsaMIBGroup,
                     myOspfIfMIBGroup,
                     myOspfVirtMIBGroup,
                     myOspfNeighborMIBGroup,
                     myOspfRouteInfoMIBGroup
                 }
        ::= { myOspfMIBCompliances 1 }
                
-- units of conformance

myOspfBaseMIBGroup OBJECT-GROUP
        OBJECTS {
               myOspfMiniLsaInterval         ,
               myOspfMiniLsaArrival          , 
               myOspfAreasNum                ,        
               myOspfNormalAreasNum          ,   
               myOspfStubAreasNum            ,   
               myOspfNssaAreasNum            ,   
               myOspfSpfDelay                ,            
               myOspfSpfHoldTime             ,   
               myOspfAutoCostRefBandWidthRef ,         
               myOspfLsaGroupPacing          ,           
               myOspfInterDistance           ,
               myOspfIntraDistance           ,      
               myOspfExternDistance          ,
               myOspfLogAdjChangeNotify      ,
               myOspfPassiveStatus           ,
               myOspfRFC1583Compatibility    ,
               myOspfRouteRedisDefMetricVal
   
        }
        STATUS  current
        DESCRIPTION
                "A collection of general objects providing OSPF managment."
        ::= { myOspfMIBGroups 1 }

myOspfAreaMIBGroup OBJECT-GROUP
        OBJECTS {
               myOspfAreaId,
               myOspfAuthType,
               myOspfImportAsExtern,
               myOspfSpfRuns,
               myOspfAreaBdrRtrCount,
               myOspfAsBdrRtrCount,
               myOspfAreaLsaCount,
               myOspfAreaLsaCksumSum,
               myOspfAreaSummary,
               myOspfAreaStatus,        
               myOspfAreaInterfaceNum,
               myOspfAreaNssaIsRedistribution,
               myOspfAreaNssaIsDefInfoOriginate,
               myOspfNetWorkAreaID,
               myOspfNetWorkAddress,
               myOspfNetWorkMask,
               myOspfNetWorkStatus
        }
        STATUS  current
        DESCRIPTION
                "A collection of area objects providing OSPF managment."
        ::= { myOspfMIBGroups 2 }
                
myOspfLsaMIBGroup OBJECT-GROUP
        OBJECTS {
           myOspfLsdbAreaId,
           myOspfLsdbType,
           myOspfLsdbLsid,
           myOspfLsdbRouterId,
           myOspfLsdbSequence,
           myOspfLsdbAge,
           myOspfLsdbChecksum,
           myOspfLsdbAdvertisement,
           myOspfLsdbLinkNum,
           myOspfLsdbPacketLength,
           myOspfSummaryLsaNetworkMask,
           myOspfSummaryLsaTos0Metric,
           myOspfNssaLsaDetailMetricType,
           myOspfNssaLsaDetailForwardAddr ,
           myOspfNssaLsaDetailRouteTag ,
           myOspfLsdbOption,
           
           myOspfExtLsdbType,
           myOspfExtLsdbLsid,
           myOspfExtLsdbRouterId,
           myOspfExtLsdbSequence,
           myOspfExtLsdbAge,
           myOspfExtLsdbChecksum,
           myOspfExtLsdbAdvertisement,  
           myOspfExtLsdbNetworkMask,
           myOspfExtLsdbMetricType,
           myOspfExtLsdbForwardAddr,
           myOspfExtLsdbRouteTag,
           myOspfExtLsdbMetric,
           myOspfExtLsdbOption,
           myOspfExtLsdbPacketLength,
                      
           myOspfRouterLsaDetailLinkID,
           myOspfRouterLsaDetailLinkType,
           myOspfRouterLsaDetailLinkData,
           myOspfRouterLsaDetailTos0Metric,
           
           myOspfNetWorkLsaDetailAttachedRouter,     
           myOspfNetWorkLsaDetailNetworkMask,  
           
           myOspfAreaLsaDBSumAreaId,
           myOspfAreaLsaDBSumLsaType,
           myOspfAreaLsaDBSumCounts   ,
           myOspfAreaLsaDBSumDeletes,
           myOspfAreaLsaDBSumMaxage,
            
           myOspfLsaDBSumLsaType,
           myOspfLsaDBSumCounts,
           myOspfLsaDBSumDeletes,
           myOspfLsaDBSumMaxage
           
        }
        STATUS  current
        DESCRIPTION
                "A collection of OSPF Link State Database objects providing OSPF managment."
        ::= { myOspfMIBGroups 3 }

myOspfIfMIBGroup OBJECT-GROUP
        OBJECTS {
         myOspfIfIpAddress,
         myOspfAddressLessIf,
         myOspfIfAreaId,
         myOspfIfType,
         myOspfIfAdminStat,
         myOspfIfRtrPriority,
         myOspfIfTransitDelay,
         myOspfIfRetransInterval,
         myOspfIfHelloInterval,
         myOspfIfRtrDeadInterval,
         myOspfIfPollInterval,
         myOspfIfState,
         myOspfIfDesignatedRouter,
         myOspfIfBackupDesignatedRouter,
         myOspfIfEvents,
         myOspfIfAuthType,
         myOspfIfAuthKey,
         myOspfIfStatus,
         myOspfIfMulticastForwarding,
         myOspfIfDemand,  
         myOspfIfDatabaseFilterAllOut,
         myOspfIfDesignateRouterId     ,
         myOspfIfBackupDesignateRouterId ,
--         myOspfIfMd5AuthKeyId,
         myOspfIfWaitInternal,
         myOspfIfPassiveStatus,
         myOspfIfCurrentUsedMd5AuthKeyId,
         
         myOspfIfMd5AuthKeyIf,
         myOspfIfMd5AuthKeyId,
         myOspfIfMd5AuthKey,
         myOspfIfMd5AuthKeySt
                
        }
        STATUS  current
        DESCRIPTION
                "A collection of OSPF interface managment."
        ::= { myOspfMIBGroups 4 }


myOspfVirtMIBGroup OBJECT-GROUP
        OBJECTS {
        myOspfVirtIfAreaId,
        myOspfVirtIfNeighbor,
        myOspfVirtIfTransitDelay,
        myOspfVirtIfRetransInterval,
        myOspfVirtIfHelloInterval,
        myOspfVirtIfRtrDeadInterval,
        myOspfVirtIfState,
        myOspfVirtIfEvents,
        myOspfVirtIfAuthType,
        myOspfVirtIfAuthKey,
        myOspfVirtIfStatus,
        myOspfVirtCost,
        myOspfVirtNativeIfIndex,
        myOspfVirtLinkState,     
        myOspfVirtHelloDueIn,
        
        myOspfVirtIfMd5AuthKeyAreaId,
        myOspfVirtIfMd5AuthKeyNeighbor,
        myOspfVirtIfMd5AuthKeyId,
        myOspfVirtIfMd5AuthKey,
        myOspfVirtIfMd5AuthKeySt,
        myOspfVirtCurrentUsedMd5AuthKeyId
        }
        STATUS  current
        DESCRIPTION
                "A collection of OSPF Virtual Link managment."
        ::= { myOspfMIBGroups 5 }

myOspfNeighborMIBGroup OBJECT-GROUP
        OBJECTS {
        myOspfNbrIpAddr,
        myOspfNbrAddressLessIndex,
        myOspfNbrRtrId,
        myOspfNbrOptions,
        myOspfNbrPriority,
        myOspfNbrState,
        myOspfNbrEvents,
        myOspfNbrLsRetransQLen,
        myOspfNbmaNbrStatus,
        myOspfNbmaNbrPermanence,
        myOspfNbrHelloSuppressed,     
        myOspfNbrDeadTimeDueIn,
        myOspfNbrNeighborUpTime,
        myOspfNbrDR,
        myOspfNbrBDR,
        myOspfNbrArea,
        myOspfNbrRetransmissionNum
        }
        STATUS  current
        DESCRIPTION
                "A collection of OSPF Neighbor information."
        ::= { myOspfMIBGroups 6 }

myOspfRouteInfoMIBGroup OBJECT-GROUP
        OBJECTS {
        myOspfRouteType,
        myOspfRouteDest,
        myOspfRouteNextHop,
        myOspfRouteCost,
        myOspfRouteDRType,
        myOspfRouteArea,
        myOspfRouteSpfNo
        }
        STATUS  current
        DESCRIPTION
                "A collection of OSPF route information."
        ::= { myOspfMIBGroups 7 }
                
-- -------------------------------------------------------------
-- Compliance statements
-- -------------------------------------------------------------
ospfMIBConformance OBJECT IDENTIFIER ::= { myOspfMIB 3 }
ospfMIBCompliances OBJECT IDENTIFIER ::= { ospfMIBConformance 1 }

ospfExternCompliance MODULE-COMPLIANCE
    STATUS      current
    DESCRIPTION
        "The compliance statement for device support of OSPF
         services."
         
    MODULE
--        OBJECT           ospfASBdrRtrStatus
--        MIN-ACCESS       read-only
--        DESCRIPTION     "Write access is not required."
--            
--        OBJECT           ospfTOSSupport
--        MIN-ACCESS       read-only
--        DESCRIPTION     "Write access is not required."
--                    
--        OBJECT           ospfExtLsdbLimit
--        MIN-ACCESS       read-only
--        DESCRIPTION     "Write access is not required."
--                            
--        OBJECT           ospfMulticastExtensions
--        MIN-ACCESS       read-only
--        DESCRIPTION     "Write access is not required."
--                                    
--        OBJECT           ospfExitOverflowInterval
--        MIN-ACCESS       read-only
--        DESCRIPTION     "Write access is not required."
--        
--        OBJECT           ospfDemandExtensions
--        MIN-ACCESS       read-only
--        DESCRIPTION     "Write access is not required."
--
--        OBJECT           ospfIfAreaId
--        MIN-ACCESS       read-only
--        DESCRIPTION     "Write access is not required."
--
--        OBJECT           ospfIfStatus
--        MIN-ACCESS       read-only
--        DESCRIPTION     "Create access is not required."
--
--                
--        OBJECT           ospfStubMetric
--        MIN-ACCESS       read-write
--        DESCRIPTION     "Create access is not required."                
--                                                    
--        OBJECT           ospfStubStatus
--        MIN-ACCESS       read-only
--        DESCRIPTION     "Write access is not required."
--         
--        OBJECT           ospfStubMetricType
--        MIN-ACCESS       read-write
--        DESCRIPTION     "Create access is not required."         
--        
--        OBJECT           ospfIfAdminStat
--        MIN-ACCESS       read-only
--        DESCRIPTION     "Write access is not required."                 
--         
--        OBJECT           ospfNbmaNbrStatus
--        MIN-ACCESS       read-only
--        DESCRIPTION     "Read-create access is not required."                 
--        
--        OBJECT           ospfNbrPriority
--        MIN-ACCESS       read-only
--        DESCRIPTION     "Read-create access is not required."  
--
--        OBJECT           ospfIfPollInterval
--        MIN-ACCESS       read-only
--        DESCRIPTION     "Read-create access is not required."                  
--        
--        OBJECT           ospfIfTransitDelay
--        SYNTAX           Unsigned32 (1..65535)
--        DESCRIPTION     "Range of value is changed."  
--        
--        OBJECT           ospfIfRetransInterval
--        SYNTAX           Unsigned32 (1..65535)
--        DESCRIPTION     "Range of value is changed."          
--        
--        OBJECT           ospfVirtIfTransitDelay
--        SYNTAX           Unsigned32 (1..65535)
--        DESCRIPTION     "Range of value is changed."          
--
--        OBJECT           ospfIfType
--        SYNTAX           INTEGER    {
--                             broadcast (1),
--                             nbma (2),
--                             pointToPoint (3),
--                             pointToMultipoint (5),
--                             loopback(6)
--                         }
--        DESCRIPTION     "add type 'loopback'."          
--                
--        OBJECT           ospfVirtIfRetransInterval
--        SYNTAX           Unsigned32 (1..65535)
--        DESCRIPTION     "Range of value is changed."       
        
        OBJECT           myOspfVirtIfRtrDeadInterval
        SYNTAX           PositiveInteger
        DESCRIPTION     "default value change from 60 to 40."                           
                                   
    ::= { ospfMIBCompliances 1 }

        
END

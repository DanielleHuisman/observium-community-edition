-- Module Name: HMS113R6.MIB (SCTE 85-2)
-- SCTE Status: Adopted

SCTE-HMS-HE-OPTICAL-RECEIVER-MIB DEFINITIONS ::= BEGIN

IMPORTS
    Unsigned32, MODULE-IDENTITY, OBJECT-TYPE
        FROM SNMPv2-SMI
    MODULE-COMPLIANCE, OBJECT-GROUP
        FROM SNMPv2-CONF
    entPhysicalIndex
         FROM ENTITY-MIB     
    HeTenthdB, HeTenthdBm, HeHundredthNanoMeter,
    HeOnOffControl, HeFaultStatus
        FROM SCTE-HMS-HEADENDIDENT-MIB  -- see SCTE 38-11 (formerly HMS114)
    heOpticalReceiverGroup
        FROM SCTE-HMS-HE-OPTICS-MIB;  -- see SCTE 83-1 (formerly HMS108)

heOpticalReceiverMIB MODULE-IDENTITY
    LAST-UPDATED "200302170000Z" -- February 17, 2003
    ORGANIZATION "SCTE HMS Working Group"
    CONTACT-INFO
            "   SCTE HMS Subcommittee, Chairman                
                mailto:standards@scte.org
            "
    DESCRIPTION
            "The MIB module is for representing an optical receiver
            present in the headend (or indoor) and is supported by a 
            SNMP agent."
             
        ::= { heOpticalReceiverGroup 1 }

heOpRxMIBObjects OBJECT IDENTIFIER ::= { heOpticalReceiverMIB 1 }

--          The Optical Receiver Input Table
heOpRxInputTable OBJECT-TYPE
    SYNTAX      SEQUENCE OF HeOpRxInputEntry
    MAX-ACCESS  not-accessible
    STATUS      current
    DESCRIPTION
            "A table containing information about the input (optical) section 
            in optical receivers in a subsystem."
    ::= { heOpRxMIBObjects 1 }

heOpRxInputEntry OBJECT-TYPE
    SYNTAX      HeOpRxInputEntry
    MAX-ACCESS  not-accessible
    STATUS      current
    DESCRIPTION
            "A list of information about each optical section in an 
            optical receiver."
    INDEX       { entPhysicalIndex, heOpRxInputIndex }
    ::= { heOpRxInputTable 1 }

HeOpRxInputEntry ::= SEQUENCE
{
    heOpRxInputIndex                    Unsigned32,
    heOpRxInputPower                    HeTenthdBm,
    heOpRxInputWavelengthControl        HeHundredthNanoMeter,
    heOpRxInputStatus                   HeFaultStatus
}

heOpRxInputIndex OBJECT-TYPE
    SYNTAX      Unsigned32
    MAX-ACCESS  not-accessible
    STATUS      current
    DESCRIPTION
            "An arbitrary value which uniquely identifies 
            the receiver input."
    ::= { heOpRxInputEntry 1 }

heOpRxInputPower OBJECT-TYPE
    SYNTAX      HeTenthdBm
    UNITS       "0.1 dBm"
    MAX-ACCESS  read-only
    STATUS      current
    DESCRIPTION
            "Receiver input power.

            This object must provide for the alarm management capabilities
            with a corresponding entry in the propertyTable of
            SCTE-HMS-PROPERTY-MIB (HMS026).

            An alarm shall be recorded as an entry in the currentAlarmTable
            of SCTE-HMS-PROPERTY-MIB (HMS026).  

            A log record shall be added as an entry in the heCommonLogTable.

            An heCommonAlarmEvent notification shall be sent."
    ::= { heOpRxInputEntry 2 }

heOpRxInputWavelengthControl OBJECT-TYPE
    SYNTAX      HeHundredthNanoMeter
    UNITS       "0.01 nm"
    MAX-ACCESS  read-write
    STATUS      current
    DESCRIPTION
            "Wavelength feeding the particular input of the receiver.
            Typical values might be 131000 (1310 nm) and 155000 (1550 nm).

            This object is used to calibrate the optical power reading
            and has no affect on the wavelength of light received."
    ::= { heOpRxInputEntry 3 }

heOpRxInputStatus OBJECT-TYPE
    SYNTAX      HeFaultStatus
    MAX-ACCESS  read-only
    STATUS      current
    DESCRIPTION
            "The laser detector status. 

            The value is normal(1) if the optical input is at normal levels.

            The value is fault(2) if the optical level is not at
            the normal level. 

            This object must provide for the alarm management capabilities
            with a corresponding entry in the discretePropertyTable of
            SCTE-HMS-PROPERTY-MIB (HMS026).

            An alarm shall be recorded as an entry in the currentAlarmTable
            of SCTE-HMS-PROPERTY-MIB (HMS026).  

            A log record shall be added as an entry in the heCommonLogTable.

            An heCommonAlarmEvent notification shall be sent."
    ::= { heOpRxInputEntry 4 }

--              The Optical Receiver Output Table
heOpRxOutputTable OBJECT-TYPE
    SYNTAX      SEQUENCE OF HeOpRxOutputEntry
    MAX-ACCESS  not-accessible
    STATUS      current
    DESCRIPTION
            "A table containing information about the output (RF) section 
            in optical receivers in a subsystem."
    ::= { heOpRxMIBObjects 2 }

heOpRxOutputEntry OBJECT-TYPE
    SYNTAX      HeOpRxOutputEntry
    MAX-ACCESS  not-accessible
    STATUS      current
    DESCRIPTION
            "A list of information about each RF section in an 
            optical receiver."
    INDEX       { entPhysicalIndex, heOpRxOutputIndex }
    ::= { heOpRxOutputTable 1 }

HeOpRxOutputEntry ::= SEQUENCE
{
    heOpRxOutputIndex           Unsigned32,
    heOpRxOutputControl         HeOnOffControl,
    heOpRxOutputGainType        INTEGER, 
    heOpRxOutputPower           HeTenthdBm,
    heOpRxOutputRFPadLevel      HeTenthdB
}

heOpRxOutputIndex OBJECT-TYPE
    SYNTAX      Unsigned32
    MAX-ACCESS  not-accessible
    STATUS      current
    DESCRIPTION
            "An arbitrary value which uniquely identifies
            the receiver output."
    ::= { heOpRxOutputEntry 1 }

heOpRxOutputControl OBJECT-TYPE
    SYNTAX      HeOnOffControl
    MAX-ACCESS  read-write
    STATUS      current
    DESCRIPTION
            "Switches a particular receiver output either off(1) or on(2).

            A GET request shall return the current control state that is
            either off(1) or on(2)."
    ::= { heOpRxOutputEntry 2 }

heOpRxOutputGainType OBJECT-TYPE
    SYNTAX      INTEGER {
        constantPower(1),
        constantGain(2)
    }
    MAX-ACCESS  read-write
    STATUS      current
    DESCRIPTION
            "Controls the output gain type, which is either constant
            power or constant gain."
    ::= { heOpRxOutputEntry 3 }

heOpRxOutputPower OBJECT-TYPE
    SYNTAX      HeTenthdBm
    UNITS       "0.1 dBm"
    MAX-ACCESS  read-only
    STATUS      current
    DESCRIPTION
            "RF output power."
    ::= { heOpRxOutputEntry 4 }     
    
heOpRxOutputRFPadLevel OBJECT-TYPE
    SYNTAX      HeTenthdB
    UNITS       "0.1 dB"
    MAX-ACCESS  read-write
    STATUS      current
    DESCRIPTION
            "RF Pad Attenuation Level."
    ::= { heOpRxOutputEntry 5 }

-- conformance information
heOpRxMIBConformance 
        OBJECT IDENTIFIER ::= { heOpticalReceiverMIB 2 }

heOpRxMIBCompliances
        OBJECT IDENTIFIER ::= { heOpRxMIBConformance 1 }

heOpRxMIBGroups  
        OBJECT IDENTIFIER ::= { heOpRxMIBConformance 2 }

-- compliance statements
heOpRxCompliance MODULE-COMPLIANCE
    STATUS  current
    DESCRIPTION
            "The minimum compliance statement for indoor optical receivers."
    MODULE  
        MANDATORY-GROUPS { heOpRxInputMandatoryGroup
                         }
    ::= { heOpRxMIBCompliances 1 }

heOpRxInputMandatoryGroup OBJECT-GROUP
    OBJECTS {
              heOpRxInputStatus,
              heOpRxInputWavelengthControl
            }
    STATUS  current
    DESCRIPTION
            "The main group defines objects which are common to all
            indoor optical receiver modules."
    ::= { heOpRxMIBGroups 1 }

heOpRxInputTableGroup OBJECT-GROUP
    OBJECTS {
              heOpRxInputPower,
              heOpRxInputWavelengthControl,
              heOpRxInputStatus
            }
    STATUS  current
    DESCRIPTION
            "This group defines all the objects which are defined
            in the input section of SCTE-HMS-HE-OPTICAL-RECEIVER-MIB
            MIB module."
    ::= { heOpRxMIBGroups 2 }
    
heOpRxOutputTableGroup OBJECT-GROUP
    OBJECTS {
              heOpRxOutputControl,
              heOpRxOutputGainType,
              heOpRxOutputPower,
              heOpRxOutputRFPadLevel
            }
    STATUS  current
    DESCRIPTION
            "This group defines all the objects which are defined
            in the output section of SCTE-HMS-HE-OPTICAL-RECEIVER-MIB
            MIB module."
    ::= { heOpRxMIBGroups 3 }

END

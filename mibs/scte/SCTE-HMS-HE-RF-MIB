SCTE-HMS-HE-RF-MIB DEFINITIONS ::= BEGIN

IMPORTS
    OBJECT-IDENTITY, MODULE-IDENTITY
        FROM SNMPv2-SMI
    heRF
        FROM SCTE-HMS-HEADENDIDENT-MIB;

heRFMib MODULE-IDENTITY
    LAST-UPDATED "200310090000Z" -- Oct 9, 2003
    ORGANIZATION "SCTE HMS Working Group"
    CONTACT-INFO
            "
                SCTE HMS Subcommittee, Chairman
                mailto:standards@scte.org "

    DESCRIPTION
            "The MIB module provides the branch object identifiers for the
            headend RF MIBs within the SCTE HMS Headend subtree."

    ::= { heRF 0 }

-- Registration subtree for headend RF equipment

heRFAmplifierGroup   OBJECT-IDENTITY
    STATUS  current
    DESCRIPTION
            "Defines the base OID for the inside plant
            rf amplifiers (see HMS131; SCTE 94-1)."
    ::= { heRF 1 }

heRFSwitchGroup      OBJECT-IDENTITY
    STATUS  current
    DESCRIPTION
            "Defines the base OID for the inside plant
            rf switches (see HMS132; SCTE 94-2)."
    ::= { heRF 2 }

END

-- ****************************************************************************
-- *
-- * Module Name: HMS050R5.MIB (SCTE 38-7)
-- *
-- * SCTE Status: ADOPTED JANUARY 11, 2002
-- *  
-- * This MIB contains information about the communications state of
-- * devices connected to the transponder, as well as indicating what
-- * device-specific MIB each device supports.  These devices are typically
-- * connected to the transponder via a serial communications link (bus).
-- *
-- ****************************************************************************

SCTE-HMS-TIB-MIB DEFINITIONS ::= BEGIN

IMPORTS
     OBJECT-TYPE
          FROM RFC-1212
     transponderInterfaceBusIdent
          FROM SCTE-HMS-ROOTS
     ;

tibAttachedDevices OBJECT-TYPE
     SYNTAX INTEGER
     ACCESS read-only
     STATUS mandatory
     DESCRIPTION
          "Bit Map that indicates addresses of attached devices. Bit set means a device using that address
           is attached to NE.
            Bits    Addresses
             0         Not used
             1         1
             2         2
             3         3
             4         4
             5         5
             6         6
             7         7
             8         8
             9         9
             10       10
             11       11
             12       12
             13       13
             14       14
             15       15
             16       16
             17       17
             18       18
             19       19
             20       20
             21       21
             22       22
             23       23
             24       24
             25       25
             26       26
             27       27
             28       28
             29       29
             30       30
             31       31
             "
     ::= { transponderInterfaceBusIdent 1 }

tibCommStatus OBJECT-TYPE
     SYNTAX INTEGER
     ACCESS read-only
     STATUS mandatory
     DESCRIPTION
          "Bit Map that indicates attached devices that are not communicating. Bit set means a device using that address
           is not communicating. This only applies to addresses whose bit is set in tibAttachedDevices.
            Bits    Addresses
             0         Not used
             1         1
             2         2
             3         3
             4         4
             5         5
             6         6
             7         7
             8         8
             9         9
             10       10
             11       11
             12       12
             13       13
             14       14
             15       15
             16       16
             17       17
             18       18
             19       19
             20       20
             21       21
             22       22
             23       23
             24       24
             25       25
             26       26
             27       27
             28       28
             29       29
             30       30
             31       31
             "
     ::= { transponderInterfaceBusIdent 2 }
    
tibDevicesAddressedTable OBJECT-TYPE
     SYNTAX SEQUENCE OF  TibDevicesAddressedEntry
     ACCESS not-accessible
     STATUS mandatory
     DESCRIPTION
          "Table containing identity of devices addressed by this NE.
          This table should contain entries ONLY for devices that are physically
          connected to the NE.  If a device is not connected, no entry should be
          created in the table for that address/index."
     ::= { transponderInterfaceBusIdent 3 }
     
tibDevicesAddressedEntry OBJECT-TYPE
     SYNTAX TibDevicesAddressedEntry
     ACCESS not-accessible
     STATUS mandatory
     DESCRIPTION         
             "Entry containing information about individual devices"
     INDEX { tibDeviceAddress }
     ::= { tibDevicesAddressedTable 1 }     
     
TibDevicesAddressedEntry ::=
     SEQUENCE
     {
          tibDeviceAddress
               INTEGER,
          tibDeviceIdentity
               OBJECT IDENTIFIER, 
          tibControlMode
               INTEGER

     }

tibDeviceAddress OBJECT-TYPE
     SYNTAX INTEGER ( 1..31 )
     ACCESS read-only
     STATUS mandatory
     DESCRIPTION
          "Index into tibDevicesAddressedTable."
     ::= { tibDevicesAddressedEntry 1 }

tibDeviceIdentity OBJECT-TYPE
     SYNTAX      OBJECT IDENTIFIER
     ACCESS     read-only
     STATUS     mandatory
     DESCRIPTION 
          "Device identification. root OID for MIB that this device supports.
               For Power Supply use psIdent from SCTE-HMS-ROOTS (1.3.6.1.4.1.5591.1.4)
               For Fiber Node use fnIdent from SCTE-HMS-ROOTS   (1.3.6.1.4.1.5591.1.5)
               For Generator use genIdent from SCTE-HMS-ROOTS   (1.3.6.1.4.1.5591.1.6)"
     ::= { tibDevicesAddressedEntry 2 }

tibControlMode OBJECT-TYPE
     SYNTAX INTEGER { remote(1), local(2), notCommunicating(3) }
     ACCESS read-only              
     STATUS optional
     DESCRIPTION
          "Control mode for this device
                 1 = Remote device will respond to commands from master NE
                 2 = Local device is under local control and will not respond
                            to commands from master NE
                 3 = This device is not responding.
                 
                 This item requires entries in the discrete property table"

     ::= { tibDevicesAddressedEntry 3 }   

END

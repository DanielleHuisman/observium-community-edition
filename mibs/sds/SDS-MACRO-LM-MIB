SDS-MACRO-LM-MIB DEFINITIONS ::= BEGIN

IMPORTS
     MODULE-IDENTITY, OBJECT-TYPE,
     Counter32, Integer32, Gauge32,
     TimeTicks, IpAddress,
     enterprises
    FROM SNMPv2-SMI;
 

mib-AN-Dcz-SDS MODULE-IDENTITY
    LAST-UPDATED "202010281256Z"
    ORGANIZATION "AN-D.cz"
    CONTACT-INFO
            "   Adam Nemcek
                AN-D.cz
                -
                -
                CZ EUROPE

                -
                adam.nemcek@an-d.cz"
    DESCRIPTION
            "The MIB module to describe generic objects for AN-D.cz
            devices - SDS MACRO, firmware of November 2012 and newer. Updates by 2019 and 2020."


    REVISION      "202010280000Z"
    DESCRIPTION
            "Third revision. By AN."
    ::= { enterprises 33283 }


--
-- MIB file definition for SDS - MACRO LM
--
-- note. older firmware versions for SDS MACRO LM might have not some OIDs implemented
-- always update to the newest firmware (it is available at wiki.merenienergie.cz for free)
--


sdsxpublic OBJECT IDENTIFIER ::= { mib-AN-Dcz-SDS 1 }

sdsMACROLM   OBJECT IDENTIFIER ::= { sdsxpublic 5 }


-- ****************************************************************************

sdsIPWatchdog OBJECT IDENTIFIER ::= { sdsMACROLM 1 }

ipwActive OBJECT-TYPE
    SYNTAX  INTEGER {
                disabled(0),
                active(255)
            }
    MAX-ACCESS  read-only
    STATUS      current
    DESCRIPTION
            "The current IP watchdog status."
    ::= { sdsIPWatchdog 1 }

ipwPingIP OBJECT-TYPE
    SYNTAX      IpAddress
    MAX-ACCESS  read-only
    STATUS      current
    DESCRIPTION
            "IP address of the wdg-monitored object."
    ::= { sdsIPWatchdog 2 }

ipwPauseAfterPwOn OBJECT-TYPE
    SYNTAX Integer32
    MAX-ACCESS  read-only
    STATUS      current
    DESCRIPTION
            "Amount of time in [sec]. 
             Duration of the IP watchdog disable period, 
             applied when watchdog device itself is first powered on."
    ::= { sdsIPWatchdog 3 }

ipwPingTimeout OBJECT-TYPE
    SYNTAX Integer32
    MAX-ACCESS  read-only
    STATUS      current
    DESCRIPTION
            "Config value - the RTT timeout."
    ::= { sdsIPWatchdog 4 }

ipwRepeatPingPer OBJECT-TYPE
    SYNTAX Integer32
    MAX-ACCESS  read-only
    STATUS      current
    DESCRIPTION
            "PING REQUEST packet sending:
             the configured send repeat period, in [miliseconds]."
    ::= { sdsIPWatchdog 5 }

ipwIgnoreLostCnt OBJECT-TYPE
    SYNTAX Gauge32
    MAX-ACCESS  read-only
    STATUS      current
    DESCRIPTION
            "How many lost PING REPLY packets should get ignored,
             before activating the relay."
    ::= { sdsIPWatchdog 6 }

ipwPauseWdAfterAct OBJECT-TYPE
    SYNTAX Integer32
    MAX-ACCESS  read-only
    STATUS      current
    DESCRIPTION
            "Delay of the IP watchdog pause, 
             applied when the output relay is activated 
             (e.g. the time for controlled device recovery)."
    ::= { sdsIPWatchdog 7 }

ipwRelayActTime OBJECT-TYPE
    SYNTAX Integer32
    MAX-ACCESS  read-only
    STATUS      current
    DESCRIPTION
            "How many [seconds] should be the output relay activated."
    ::= { sdsIPWatchdog 8 }

ipwActualFailed OBJECT-TYPE
    SYNTAX Gauge32
    MAX-ACCESS  read-only
    STATUS      current
    DESCRIPTION
            "How many unreceived PING REPLY packets are detected so far."
    ::= { sdsIPWatchdog 9 }

ipwLastRTT OBJECT-TYPE
    SYNTAX Gauge32
    MAX-ACCESS  read-only
    STATUS      current
    DESCRIPTION
            "Round Trip Time for the last ping echo."
    ::= { sdsIPWatchdog 10 }

ipwActualRelayState OBJECT-TYPE
    SYNTAX Integer32
    MAX-ACCESS  read-only
    STATUS      current
    DESCRIPTION
            "Actual (virtual) output relay status 
            (before mapping this status to the selected hardware)."
    ::= { sdsIPWatchdog 11 }

-- ****************************************************************************

sdsOptoInput OBJECT IDENTIFIER ::= { sdsMACROLM 2 }

opto1 OBJECT-TYPE
    SYNTAX  INTEGER {
                activeSignalPresent(0),
                noSignal(4)
            }
    MAX-ACCESS  read-only
    STATUS      current
    DESCRIPTION
            "Current OPTO1 binary input status."
    ::= { sdsOptoInput 1 }

opto2 OBJECT-TYPE
    SYNTAX  INTEGER {
                activeSignalPresent(0),
                noSignal(8)
            }
    MAX-ACCESS  read-only
    STATUS      current
    DESCRIPTION
            "Current OPTO2 binary input status."
    ::= { sdsOptoInput 2 }

opto3 OBJECT-TYPE
    SYNTAX  INTEGER {
                activeSignalPresent(0),
                noSignal(2)
            }
    MAX-ACCESS  read-only
    STATUS      current
    DESCRIPTION
            "Current OPTO3 binary input status."
    ::= { sdsOptoInput 3 }

opto4 OBJECT-TYPE
    SYNTAX  INTEGER {
                activeSignalPresent(0),
                noSignal(1)
            }
    MAX-ACCESS  read-only
    STATUS      current
    DESCRIPTION
            "Current OPTO4 binary input status."
    ::= { sdsOptoInput 4 }

opto5 OBJECT-TYPE
    SYNTAX  INTEGER {
                activeSignalPresent(0),
                noSignal(8)
            }
    MAX-ACCESS  read-only
    STATUS      current
    DESCRIPTION
            "Current OPTO5 binary input status."
    ::= { sdsOptoInput 5 }

opto6 OBJECT-TYPE
    SYNTAX  INTEGER {
                activeSignalPresent(0),
                noSignal(4)
            }
    MAX-ACCESS  read-only
    STATUS      current
    DESCRIPTION
            "Current OPTO6 binary input status."
    ::= { sdsOptoInput 6 }

opto7 OBJECT-TYPE
    SYNTAX  INTEGER {
                activeSignalPresent(0),
                noSignal(2)
            }
    MAX-ACCESS  read-only
    STATUS      current
    DESCRIPTION
            "Current OPTO7 binary input status."
    ::= { sdsOptoInput 7 }

opto8 OBJECT-TYPE
    SYNTAX  INTEGER {
                activeSignalPresent(0),
                noSignal(1)
            }
    MAX-ACCESS  read-only
    STATUS      current
    DESCRIPTION
            "Current OPTO8 binary input status."
    ::= { sdsOptoInput 8 }

-- ****************************************************************************

sdsOutputRelay OBJECT IDENTIFIER ::= { sdsMACROLM 3 }

sdsRE1state OBJECT-TYPE
    SYNTAX  INTEGER {
                off(0),
                activated(255)
            }
    MAX-ACCESS  read-write
    STATUS      current
    DESCRIPTION
            "Current RELAY 1 output status."
    ::= { sdsOutputRelay 1 }

sdsRE1cby OBJECT-TYPE
    SYNTAX  INTEGER {
                manualControl(0),
                sdscControl(2),
                ipwControl(4),
                oneShotReset(8)
            }
    MAX-ACCESS  read-write
    STATUS      current
    DESCRIPTION
            "RELAY 1 controled by ..."
    ::= { sdsOutputRelay 2 }

sdsRE1name OBJECT-TYPE
    SYNTAX  OCTET STRING
    MAX-ACCESS  read-only
    STATUS      current
    DESCRIPTION
            "User name for RELAY 1."
    ::= { sdsOutputRelay 3 }

sdsRE2state OBJECT-TYPE
    SYNTAX  INTEGER {
                off(0),
                activated(255)
            }
    MAX-ACCESS  read-write
    STATUS      current
    DESCRIPTION
            "Current RELAY 2 output status."
    ::= { sdsOutputRelay 4 }

sdsRE2cby OBJECT-TYPE
    SYNTAX  INTEGER {
                manualControl(0),
                sdscControl(2),
                ipwControl(4),
                oneShotReset(8)
            }
    MAX-ACCESS  read-write
    STATUS      current
    DESCRIPTION
            "RELAY 2 controled by ..."
    ::= { sdsOutputRelay 5 }

sdsRE2name OBJECT-TYPE
    SYNTAX  OCTET STRING
    MAX-ACCESS  read-only
    STATUS      current
    DESCRIPTION
            "User name for RELAY 2."
    ::= { sdsOutputRelay 6 }

sdsRE3state OBJECT-TYPE
    SYNTAX  INTEGER {
                off(0),
                activated(255)
            }
    MAX-ACCESS  read-write
    STATUS      current
    DESCRIPTION
            "Current RELAY 3 output status."
    ::= { sdsOutputRelay 7 }

sdsRE3cby OBJECT-TYPE
    SYNTAX  INTEGER {
                manualControl(0),
                sdscControl(2),
                ipwControl(4),
                oneShotReset(8)
            }
    MAX-ACCESS  read-write
    STATUS      current
    DESCRIPTION
            "RELAY 3 controled by ..."
    ::= { sdsOutputRelay 8 }

sdsRE3name OBJECT-TYPE
    SYNTAX  OCTET STRING
    MAX-ACCESS  read-only
    STATUS      current
    DESCRIPTION
            "User name for RELAY 3."
    ::= { sdsOutputRelay 9 }

sdsRE4state OBJECT-TYPE
    SYNTAX  INTEGER {
                off(0),
                activated(255)
            }
    MAX-ACCESS  read-write
    STATUS      current
    DESCRIPTION
            "Current RELAY 4 output status."
    ::= { sdsOutputRelay 10 }

sdsRE4cby OBJECT-TYPE
    SYNTAX  INTEGER {
                manualControl(0),
                sdscControl(2),
                ipwControl(4),
                oneShotReset(8)
            }
    MAX-ACCESS  read-write
    STATUS      current
    DESCRIPTION
            "RELAY 4 controled by ..."
    ::= { sdsOutputRelay 11 }

sdsRE4name OBJECT-TYPE
    SYNTAX  OCTET STRING
    MAX-ACCESS  read-only
    STATUS      current
    DESCRIPTION
            "User name for RELAY 4."
    ::= { sdsOutputRelay 12 }

-- ****************************************************************************

sdsPWMoutput OBJECT IDENTIFIER ::= { sdsMACROLM 4 }

sdsPWM1freq OBJECT-TYPE
    SYNTAX  Gauge32
    MAX-ACCESS  read-write
    STATUS      current
    DESCRIPTION
            "Actual PWM1 frequency [Hz]."
    ::= { sdsPWMoutput 1 }

sdsPWM1duty OBJECT-TYPE
    SYNTAX  Gauge32
    MAX-ACCESS  read-write
    STATUS      current
    DESCRIPTION
            "Actual PWM1 duty control setting."
    ::= { sdsPWMoutput 2 }

-- ****************************************************************************

sdsADCinput OBJECT IDENTIFIER ::= { sdsMACROLM 5 }

sdsInADC1 OBJECT-TYPE
    SYNTAX  Gauge32
    MAX-ACCESS  read-only
    STATUS      current
    DESCRIPTION
            "Actual analog AD1 input value [raw value 0..1023]."
    ::= { sdsADCinput 1 }

sdsInADC2 OBJECT-TYPE
    SYNTAX  Gauge32
    MAX-ACCESS  read-only
    STATUS      current
    DESCRIPTION
            "Actual analog AD1 input value [raw value 0..1023]."
    ::= { sdsADCinput 2 }

sdsInADC3 OBJECT-TYPE
    SYNTAX  Gauge32
    MAX-ACCESS  read-only
    STATUS      current
    DESCRIPTION
            "Actual analog AD3 input value [raw value 0..1023]."
    ::= { sdsADCinput 3 }

sdsInADC4 OBJECT-TYPE
    SYNTAX  Gauge32
    MAX-ACCESS  read-only
    STATUS      current
    DESCRIPTION
            "Actual analog AD4 input value [raw value 0..1023]."
    ::= { sdsADCinput 4 }

sdsSItextADC1 OBJECT-TYPE
    SYNTAX  OCTET STRING
    MAX-ACCESS  read-only
    STATUS      current
    DESCRIPTION
            "SI textual value for AD1."
    ::= { sdsADCinput 5 }

sdsSItextADC2 OBJECT-TYPE
    SYNTAX  OCTET STRING
    MAX-ACCESS  read-only
    STATUS      current
    DESCRIPTION
            "SI textual value for AD2."
    ::= { sdsADCinput 6 }

sdsSItextADC3 OBJECT-TYPE
    SYNTAX  OCTET STRING
    MAX-ACCESS  read-only
    STATUS      current
    DESCRIPTION
            "SI textual value for AD3."
    ::= { sdsADCinput 7 }

sdsSItextADC4 OBJECT-TYPE
    SYNTAX  OCTET STRING
    MAX-ACCESS  read-only
    STATUS      current
    DESCRIPTION
            "SI textual value for AD4."
    ::= { sdsADCinput 8 }

sdsNameADC1 OBJECT-TYPE
    SYNTAX  OCTET STRING
    MAX-ACCESS  read-only
    STATUS      current
    DESCRIPTION
            "User name for AD1."
    ::= { sdsADCinput 9 }

sdsNameADC2 OBJECT-TYPE
    SYNTAX  OCTET STRING
    MAX-ACCESS  read-only
    STATUS      current
    DESCRIPTION
            "User name for AD2."
    ::= { sdsADCinput 10 }

sdsNameADC3 OBJECT-TYPE
    SYNTAX  OCTET STRING
    MAX-ACCESS  read-only
    STATUS      current
    DESCRIPTION
            "User name for AD3."
    ::= { sdsADCinput 11 }

sdsNameADC4 OBJECT-TYPE
    SYNTAX  OCTET STRING
    MAX-ACCESS  read-only
    STATUS      current
    DESCRIPTION
            "User name for AD4."
    ::= { sdsADCinput 12 }

sdsUnitADC1 OBJECT-TYPE
    SYNTAX      OCTET STRING
    MAX-ACCESS  read-only
    STATUS      current
    DESCRIPTION
            "User unit for AD1."
    ::= { sdsADCinput 13 }

sdsUnitADC2 OBJECT-TYPE
    SYNTAX      OCTET STRING
    MAX-ACCESS  read-only
    STATUS      current
    DESCRIPTION
            "User unit for AD2."
    ::= { sdsADCinput 14 }

sdsUnitADC3 OBJECT-TYPE
    SYNTAX      OCTET STRING
    MAX-ACCESS  read-only
    STATUS      current
    DESCRIPTION
            "User unit for AD3."
    ::= { sdsADCinput 15 }

sdsUnitADC4 OBJECT-TYPE
    SYNTAX      OCTET STRING
    MAX-ACCESS  read-only
    STATUS      current
    DESCRIPTION
            "User unit for AD4."
    ::= { sdsADCinput 16 }

-- ****************************************************************************

-- the ONEWIRE table (MACRO-LM: BUS A and BUS B combined together in here)

-- The ONEWIRE table contains information on the OneWire devices (like DS18B20 or SDS-T-RH)

sdsONEWIRETable OBJECT-TYPE
    SYNTAX      SEQUENCE OF SdsONEWIREEntry
    MAX-ACCESS  not-accessible
    STATUS      current
    DESCRIPTION
            "A list of all (1-Wire) devices."
    ::= { sdsMACROLM 6 }

sdsONEWIREEntry OBJECT-TYPE
    SYNTAX      SdsONEWIREEntry
    MAX-ACCESS  not-accessible
    STATUS      current
    DESCRIPTION
            "An entry containing information applicable to a
            particular ONEWIRE device."
    INDEX   { sdsONEWIREtableRowIndex }
    ::= { sdsONEWIRETable 1 }

SdsONEWIREEntry ::=
    SEQUENCE {  
        sdsONEWIREdeviceROMcode            OCTET STRING,     
        sdsONEWIREactualTempInteger        Integer32,
        sdsONEWIREactualTempFrac           Integer32,
        sdsONEWIREuserName                 OCTET STRING,
        sdsONEWIREactualTempCompleteMul100 Integer32,
        sdsONEWIREtableRowIndex            Integer32,
        sdsONEWIREactualRHpercent          Integer32
    }

sdsONEWIREdeviceROMcode OBJECT-TYPE
    SYNTAX      OCTET STRING
    MAX-ACCESS  read-only
    STATUS      current
    DESCRIPTION
            "Internal ONEWIRE device ROM unique identification code."
    ::= { sdsONEWIREEntry 1 }

sdsONEWIREactualTempInteger OBJECT-TYPE
    SYNTAX      Integer32
    MAX-ACCESS  read-only
    STATUS      current
    DESCRIPTION
            "Actual temperature for this ONEWIRE sensor, 
             an integral part."
    ::= { sdsONEWIREEntry 2 }

sdsONEWIREactualTempFrac OBJECT-TYPE
    SYNTAX      Integer32
    MAX-ACCESS  read-only
    STATUS      current
    DESCRIPTION
            "Actual temperature for this ONEWIRE sensor, 
             a fractional part."
    ::= { sdsONEWIREEntry 3 }

sdsONEWIREuserName OBJECT-TYPE
    SYNTAX      OCTET STRING
    MAX-ACCESS  read-only
    STATUS      current
    DESCRIPTION
            "User name for the actual ONEWIRE device."
    ::= { sdsONEWIREEntry 4 } 

sdsONEWIREactualTempCompleteMul100 OBJECT-TYPE
    SYNTAX      Integer32
    MAX-ACCESS  read-only
    STATUS      current
    DESCRIPTION
            "Actual temperature for this ONEWIRE sensor: 
             the complete value multiplied by 100 
             (target precision: two post-zero digits)."
    ::= { sdsONEWIREEntry 5 }

sdsONEWIREtableRowIndex OBJECT-TYPE
    SYNTAX      Integer32
    MAX-ACCESS  not-accessible
    STATUS      current
    DESCRIPTION
            "ONEWIRE device index in this table."
    ::= { sdsONEWIREEntry 6 }

sdsONEWIREactualRHpercent OBJECT-TYPE
    SYNTAX      Integer32
    MAX-ACCESS  read-only
    STATUS      current
    DESCRIPTION
            "Actual RH value for this ONEWIRE sensor"
    ::= { sdsONEWIREEntry 7 }

-- ****************************************************************************

sdsVersionEntry OBJECT IDENTIFIER ::= { sdsMACROLM 7 }

sdsVersionText OBJECT-TYPE
    SYNTAX    OCTET STRING
    MAX-ACCESS  read-only
    STATUS      current
    DESCRIPTION
            "SDS device version text."
    ::= { sdsVersionEntry 1 }

sdsCustomTrap1 OBJECT-TYPE
    SYNTAX    Integer32
    MAX-ACCESS  read-only
    STATUS      current
    DESCRIPTION
            "SDS-C custom int32 TRAP."
    ::= { sdsVersionEntry 2 }


-- ****************************************************************************

sdsGeneralInfoEntry OBJECT IDENTIFIER ::= { sdsMACROLM 8 }

sdsNTPvalue OBJECT-TYPE
    SYNTAX    Counter32
    MAX-ACCESS  read-only
    STATUS      current
    DESCRIPTION
            "Actual NTP UTC time value (SDS device is NTP client)."
    ::= { sdsGeneralInfoEntry 1 }

sdsSoCtempValue OBJECT-TYPE
    SYNTAX    Integer32
    MAX-ACCESS  read-only
    STATUS      current
    DESCRIPTION
            "Actual SoC chip internal temperature, 
             represented in a special units [0..1023]. 
             This needs to be recalculated to get a degC value."
    ::= { sdsGeneralInfoEntry 2 }

sdsOneWireBUSAcountValue OBJECT-TYPE
    SYNTAX    Integer32
    MAX-ACCESS  read-only
    STATUS      current
    DESCRIPTION
            "Number of discovered 1-Wire devices on BUS A."
    ::= { sdsGeneralInfoEntry 3 }

sdsOneWireBUSBcountValue OBJECT-TYPE
    SYNTAX    Integer32
    MAX-ACCESS  read-only
    STATUS      current
    DESCRIPTION
            "Number of discovered 1-Wire devices on BUS B."
    ::= { sdsGeneralInfoEntry 4 }

sdsPD0outputState OBJECT-TYPE
    SYNTAX  Integer32
    MAX-ACCESS  read-write
    STATUS      current
    DESCRIPTION
            "Pin PD0 actual output status."
    ::= { sdsGeneralInfoEntry 5 }

sdsPD0Direction OBJECT-TYPE
    SYNTAX  Integer32
    MAX-ACCESS  read-only
    STATUS      current
    DESCRIPTION
            "Pin PD0 actual port-pin direction (MACROLM:output only) status."
    ::= { sdsGeneralInfoEntry 6 }

sdsBackUpCoinBatteryVoltageValue OBJECT-TYPE
    SYNTAX    Integer32
    MAX-ACCESS  read-only
    STATUS      current
    DESCRIPTION
            "This is not used for SDS MACRO LM."
    ::= { sdsGeneralInfoEntry 7 }

sdsLOCALTIMEvalue OBJECT-TYPE
    SYNTAX    Counter32
    MAX-ACCESS  read-only
    STATUS      current
    DESCRIPTION
            "Actual LOCAL time value (SDS device is NTP client)."
    ::= { sdsGeneralInfoEntry 10 }


-- ****************************************************************************

-- the S0 INPUT table

-- The S0 INPUT contains information from the S0 impulse input

sdsS0Table OBJECT-TYPE
    SYNTAX      SEQUENCE OF SdsS0Entry
    MAX-ACCESS  not-accessible
    STATUS      current
    DESCRIPTION
            "A list of S0 impulse inputs."
    ::= { sdsMACROLM 9 }

sdsS0Entry OBJECT-TYPE
    SYNTAX      SdsS0Entry
    MAX-ACCESS  not-accessible
    STATUS      current
    DESCRIPTION
            "An entry containing information applicable to a
            particular S0 input."
    INDEX   { sdsS0tableRowIndex }
    ::= { sdsS0Table 1 }

SdsS0Entry ::=
    SEQUENCE {       
        sdsS0impCountT0       Counter32,
        sdsS0impCountT1       Counter32,
        sdsS0impMoneyOffsetT0 Gauge32,
        sdsS0impMoneyOffsetT1 Gauge32,
        sdsS0constant         Gauge32,
        sdsS0translatedUnitT0 OCTET STRING,
        sdsS0translatedUnitT1 OCTET STRING,
        sdsS0translatedCashT0 OCTET STRING,
        sdsS0translatedCashT1 OCTET STRING,
        sdsS0actualEnergyFlow OCTET STRING,
        sdsS0constantMTD      Gauge32,
        sdsS0tableRowIndex    Integer32
    }

sdsS0impCountT0 OBJECT-TYPE
    SYNTAX  Counter32
    MAX-ACCESS  read-only
    STATUS      current
    DESCRIPTION
            "Actual S0 impulse counter value 
             for the tarif state T0 (no tarif signal)."
    ::= { sdsS0Entry 1 }

sdsS0impCountT1 OBJECT-TYPE
    SYNTAX  Counter32
    MAX-ACCESS  read-only
    STATUS      current
    DESCRIPTION
            "Actual S0 impulse counter value
            for the tarif state T1 (active tarif signal)."
    ::= { sdsS0Entry 2 }

sdsS0impMoneyOffsetT0 OBJECT-TYPE
    SYNTAX  Gauge32
    MAX-ACCESS  read-only
    STATUS      current
    DESCRIPTION
            "Offset (impulse count) for cash calculation.
             Cash value is calculated relatively starting 
             at this offset, for the T0 counter."
    ::= { sdsS0Entry 3 }

sdsS0impMoneyOffsetT1 OBJECT-TYPE
    SYNTAX  Gauge32
    MAX-ACCESS  read-only
    STATUS      current
    DESCRIPTION
            "Offset (impulse count) for cash calculation.
             Cash value is calculated relatively starting 
             at this offset, for the T1 counter."
    ::= { sdsS0Entry 4 }

sdsS0constant OBJECT-TYPE
    SYNTAX  Gauge32
    MAX-ACCESS  read-only
    STATUS      current
    DESCRIPTION
            "S0 output constant (number of impulses for 1 energy unit)."
    ::= { sdsS0Entry 5 }

sdsS0translatedUnitT0 OBJECT-TYPE
    SYNTAX  OCTET STRING
    MAX-ACCESS  read-only
    STATUS      current
    DESCRIPTION
            "T0 related S0 impulse count value, 
             recalculated into energy units, 
             in a textual representation."
    ::= { sdsS0Entry 6 }

sdsS0translatedUnitT1 OBJECT-TYPE
    SYNTAX  OCTET STRING
    MAX-ACCESS  read-only
    STATUS      current
    DESCRIPTION
            "T1 related S0 impulse count value, 
             recalculated into energy units, 
             in a textual representation."
    ::= { sdsS0Entry 7 }

sdsS0translatedCashT0 OBJECT-TYPE
    SYNTAX  OCTET STRING
    MAX-ACCESS  read-only
    STATUS      current
    DESCRIPTION
            "T0 related S0 counter value recalculated into cash
             (total T0 impulse count minus a T0 custom offset),
             in a textual representation."
    ::= { sdsS0Entry 8 }

sdsS0translatedCashT1 OBJECT-TYPE
    SYNTAX  OCTET STRING
    MAX-ACCESS  read-only
    STATUS      current
    DESCRIPTION
            "T1 related S0 counter value recalculated into cash
             (total T1 impulse count minus a T1 custom offset),
             in a textual representation."
    ::= { sdsS0Entry 9 }

sdsS0actualEnergyFlow OBJECT-TYPE
    SYNTAX  OCTET STRING
    MAX-ACCESS  read-only
    STATUS      current
    DESCRIPTION
            "S0: the actual energy flow value."
    ::= { sdsS0Entry 10 }

sdsS0constantMTD OBJECT-TYPE
    SYNTAX  Gauge32
    MAX-ACCESS  read-only
    STATUS      current
    DESCRIPTION
            "Configuration: the MTD constant."
    ::= { sdsS0Entry 11 }

sdsS0tableRowIndex OBJECT-TYPE
    SYNTAX  Integer32
    MAX-ACCESS  not-accessible
    STATUS      current
    DESCRIPTION
            "S0 table row index."
    ::= { sdsS0Entry 12 }


-- ****************************************************************************

-- the SDSCEP table

-- The SDSCEP contains values from SDS-C sys[140] to sys[147] (user data)

sdsSDSCEPTable OBJECT-TYPE
    SYNTAX      SEQUENCE OF SdsSDSCEPEntry 
    MAX-ACCESS  not-accessible
    STATUS      current
    DESCRIPTION
            "A list of SDS-C SDSCEP user values. 
             Equals to sys[140] thru sys[147]."
    ::= { sdsMACROLM 10 }

sdsSDSCEPEntry OBJECT-TYPE
    SYNTAX      SdsSDSCEPEntry 
    MAX-ACCESS  not-accessible
    STATUS      current
    DESCRIPTION
            "An entry containing the values 
             for SDS-C SDSCEP items."
    INDEX   { sdsSDSCEPtableRowIndex }
    ::= { sdsSDSCEPTable 1 }

SdsSDSCEPEntry ::=
    SEQUENCE {        
        sdsSDSCEPvalue          Integer32,
        sdsSDSCEPtableRowIndex  Integer32
    }

sdsSDSCEPvalue OBJECT-TYPE
    SYNTAX  Integer32
    MAX-ACCESS  read-write
    STATUS      current
    DESCRIPTION
            "Actual value for the particular SDS-C SDSCEP value. 
             First index is starting at sys[140]."
    ::= { sdsSDSCEPEntry 1 }

sdsSDSCEPtableRowIndex OBJECT-TYPE
    SYNTAX  Integer32
    MAX-ACCESS  not-accessible
    STATUS      current
    DESCRIPTION
            "Index of the particular SDS-C SDSCEP value.
             Add a number of 139 to this item value, 
             to get the exact sys[] location.
             Example: value == 1 -> sys[140]."
    ::= { sdsSDSCEPEntry 2 }

-- ****************************************************************************

sdsEthToSerialEntry OBJECT IDENTIFIER ::= { sdsMACROLM 11 }

sdsETStelnetConnected OBJECT-TYPE
    SYNTAX    Integer32
    MAX-ACCESS  read-only
    STATUS      current
    DESCRIPTION
            "Is there any Ethernet client connected 
             and using the Eth-to-Serial converter, 
             at this moment."
    ::= { sdsEthToSerialEntry 1 }

sdsETSbaudrate OBJECT-TYPE
    SYNTAX    Integer32
    MAX-ACCESS  read-write
    STATUS      current
    DESCRIPTION
            "Actual configured UART baud rate in [bps]."
    ::= { sdsEthToSerialEntry 2 }

sdsETSdataSize OBJECT-TYPE
    SYNTAX    Integer32
    MAX-ACCESS  read-write
    STATUS      current
    DESCRIPTION
            "Actual configured UART char data size 
            [number of bits per char]."
    ::= { sdsEthToSerialEntry 3 }

sdsETSstopBits OBJECT-TYPE
    SYNTAX    Integer32
    MAX-ACCESS  read-write
    STATUS      current
    DESCRIPTION
            "Actual configured UART number of stop bits 
             [0, 1 or 2 stop bits]"
    ::= { sdsEthToSerialEntry 4 }

sdsETSparity OBJECT-TYPE
    SYNTAX  INTEGER { 
                noParity(1),
                oddParity(2),
                evenParity(3),
                mark(4),
                space(5)
            }
    MAX-ACCESS  read-write
    STATUS      current
    DESCRIPTION
            "Actual configured UART parity."
    ::= { sdsEthToSerialEntry 5 }

sdsETSuartInBytes OBJECT-TYPE
    SYNTAX    Counter32
    MAX-ACCESS  read-only
    STATUS      current
    DESCRIPTION
            "Total number of UART IN bytes."
    ::= { sdsEthToSerialEntry 6 }

sdsETSuartOutBytes OBJECT-TYPE
    SYNTAX    Counter32
    MAX-ACCESS  read-only
    STATUS      current
    DESCRIPTION
            "Total number of UART OUT bytes."
    ::= { sdsEthToSerialEntry 7 }

-- ****************************************************************************




-- ****************************************************************************
-- TRAP-SDS-MACROLM-MIB DEFINITIONS 
-- ****************************************************************************


ipwActive-trap TRAP-TYPE
	STATUS current
	ENTERPRISE mib-AN-Dcz-SDS
	VARIABLES { ipwActive }
    	DESCRIPTION "TRAP: The current IP watchdog status."
    ::= 70

ipwPingIP-trap TRAP-TYPE
	STATUS current
	ENTERPRISE mib-AN-Dcz-SDS
	VARIABLES { ipwPingIP }
    	DESCRIPTION "TRAP: IP address of the wdg monitored object."
    ::= 71

ipwPauseAfterPwOn-trap TRAP-TYPE
	STATUS current
	ENTERPRISE mib-AN-Dcz-SDS
	VARIABLES { ipwPauseAfterPwOn }
    	DESCRIPTION "TRAP: Duration of the IP watchdog disable period."
    ::= 72

ipwPingTimeout-trap TRAP-TYPE
	STATUS current
	ENTERPRISE mib-AN-Dcz-SDS
	VARIABLES { ipwPingTimeout }
    	DESCRIPTION "TRAP: IP watchdog RTT timeout."
    ::= 73

ipwRepeatPingPer-trap TRAP-TYPE
	STATUS current
	ENTERPRISE mib-AN-Dcz-SDS
	VARIABLES { ipwRepeatPingPer }
    	DESCRIPTION "TRAP: IP watchdog send repeat period."
    ::= 74

ipwIgnoreLostCnt-trap TRAP-TYPE
	STATUS current
	ENTERPRISE mib-AN-Dcz-SDS
	VARIABLES { ipwIgnoreLostCnt }
    	DESCRIPTION "TRAP: IP watchdog: number of missing packets to ignore."
    ::= 75

ipwPauseWdAfterAct-trap TRAP-TYPE
	STATUS current
	ENTERPRISE mib-AN-Dcz-SDS
	VARIABLES { ipwPauseWdAfterAct }
    	DESCRIPTION "TRAP: IP watchog pause applied after output activation."
    ::= 76

ipwRelayActTime-trap TRAP-TYPE
	STATUS current
	ENTERPRISE mib-AN-Dcz-SDS
	VARIABLES { ipwRelayActTime }
    	DESCRIPTION "TRAP: Length of IP watchdog notification output active state."
    ::= 77

ipwActualFailed-trap TRAP-TYPE
	STATUS current
	ENTERPRISE mib-AN-Dcz-SDS
	VARIABLES { ipwActualFailed }
    	DESCRIPTION "TRAP: number of missing IP watchdog ping responses."
    ::= 78

ipwLastRTT-trap TRAP-TYPE
	STATUS current
	ENTERPRISE mib-AN-Dcz-SDS
	VARIABLES { ipwLastRTT }
    	DESCRIPTION "TRAP: IP watchdog Round Trip Time for the last ping echo."
    ::= 79

ipwActualRelayState-trap TRAP-TYPE
	STATUS current
	ENTERPRISE mib-AN-Dcz-SDS
	VARIABLES { ipwActualRelayState }
    	DESCRIPTION "TRAP: Actual (virtual) output relay status of IP watchdog."
    ::= 80

-- next

opto1-trap TRAP-TYPE
	STATUS current
	ENTERPRISE mib-AN-Dcz-SDS
	VARIABLES { opto1 }
	DESCRIPTION "TRAP: optical input 1 status."
	::= 100

opto2-trap TRAP-TYPE
	STATUS current
	ENTERPRISE mib-AN-Dcz-SDS
	VARIABLES { opto2 }
	DESCRIPTION "TRAP: optical input 2 status."
	::= 101

opto3-trap TRAP-TYPE
	STATUS current
	ENTERPRISE mib-AN-Dcz-SDS
	VARIABLES { opto3 }
	DESCRIPTION "TRAP: optical input 3 status."
	::= 102

opto4-trap TRAP-TYPE
	STATUS current
	ENTERPRISE mib-AN-Dcz-SDS
	VARIABLES { opto4 }
	DESCRIPTION "TRAP: optical input 4 status."
	::= 103

opto5-trap TRAP-TYPE
	STATUS current
	ENTERPRISE mib-AN-Dcz-SDS
	VARIABLES { opto5 }
	DESCRIPTION "TRAP: optical input 5 status."
	::= 104

opto6-trap TRAP-TYPE
	STATUS current
	ENTERPRISE mib-AN-Dcz-SDS
	VARIABLES { opto6 }
	DESCRIPTION "TRAP: optical input 6 status."
	::= 105

opto7-trap TRAP-TYPE
	STATUS current
	ENTERPRISE mib-AN-Dcz-SDS
	VARIABLES { opto7 }
	DESCRIPTION "TRAP: optical input 7 status."
	::= 106

opto8-trap TRAP-TYPE
	STATUS current
	ENTERPRISE mib-AN-Dcz-SDS
	VARIABLES { opto3 }
	DESCRIPTION "TRAP: optical input 8 status."
	::= 107

-- next

sdsRE1state-trap TRAP-TYPE
	STATUS current
	ENTERPRISE mib-AN-Dcz-SDS
	VARIABLES { sdsRE1state }
	DESCRIPTION "TRAP: Current RELAY 1 output status."
    ::= 150

sdsRE1cby-trap TRAP-TYPE
	STATUS current
	ENTERPRISE mib-AN-Dcz-SDS
	VARIABLES { sdsRE1cby }
	DESCRIPTION "TRAP: RELAY 1 controled by ..."
    ::= 151

sdsRE1name-trap TRAP-TYPE
	STATUS current
	ENTERPRISE mib-AN-Dcz-SDS
	VARIABLES { sdsRE1name }
	DESCRIPTION "TRAP: User name for RELAY 1."
    ::= 152

sdsRE2state-trap TRAP-TYPE
	STATUS current
	ENTERPRISE mib-AN-Dcz-SDS
	VARIABLES { sdsRE2state }
	DESCRIPTION "TRAP: Current RELAY 2 output status."
    ::= 153

sdsRE2cby-trap TRAP-TYPE
	STATUS current
	ENTERPRISE mib-AN-Dcz-SDS
	VARIABLES { sdsRE2cby }
	DESCRIPTION "TRAP: RELAY 2 controled by ..."
    ::= 154

sdsRE2name-trap TRAP-TYPE
	STATUS current
	ENTERPRISE mib-AN-Dcz-SDS
	VARIABLES { sdsRE2name }
	DESCRIPTION "TRAP: User name for RELAY 2."
    ::= 155

sdsRE3state-trap TRAP-TYPE
	STATUS current
	ENTERPRISE mib-AN-Dcz-SDS
	VARIABLES { sdsRE3state }
	DESCRIPTION "TRAP: Current RELAY 3 output status."
    ::= 156

sdsRE3cby-trap TRAP-TYPE
	STATUS current
	ENTERPRISE mib-AN-Dcz-SDS
	VARIABLES { sdsRE3cby }
	DESCRIPTION "TRAP: RELAY 3 controled by ..."
    ::= 157

sdsRE3name-trap TRAP-TYPE
	STATUS current
	ENTERPRISE mib-AN-Dcz-SDS
	VARIABLES { sdsRE3name }
	DESCRIPTION "TRAP: User name for RELAY 3."
    ::= 158

sdsRE4state-trap TRAP-TYPE
	STATUS current
	ENTERPRISE mib-AN-Dcz-SDS
	VARIABLES { sdsRE4state }
	DESCRIPTION "TRAP: Current RELAY 4 output status."
    ::= 159

sdsRE4cby-trap TRAP-TYPE
	STATUS current
	ENTERPRISE mib-AN-Dcz-SDS
	VARIABLES { sdsRE4cby }
	DESCRIPTION "TRAP: RELAY 4 controled by ..."
    ::= 160

sdsRE4name-trap TRAP-TYPE
	STATUS current
	ENTERPRISE mib-AN-Dcz-SDS
	VARIABLES { sdsRE4name }
	DESCRIPTION "TRAP: User name for RELAY 4."
    ::= 161

-- next


sdsPWM1freq-trap TRAP-TYPE
	STATUS current
	ENTERPRISE mib-AN-Dcz-SDS
	VARIABLES { sdsPWM1freq }
	DESCRIPTION "TRAP: Actual PWM1 generator frequency [Hz]."
    ::= 200

sdsPWM1duty-trap TRAP-TYPE
	STATUS current
	ENTERPRISE mib-AN-Dcz-SDS
	VARIABLES { sdsPWM1duty }
	DESCRIPTION "TRAP: Actual PWM1 duty control setting."
    ::= 201

-- next

sdsInADC1-trap TRAP-TYPE
	STATUS current
	ENTERPRISE mib-AN-Dcz-SDS
	VARIABLES { sdsInADC1 }
	DESCRIPTION "TRAP: Actual analog AD1 input value [raw]."
    ::= 250

sdsInADC2-trap TRAP-TYPE
	STATUS current
	ENTERPRISE mib-AN-Dcz-SDS
	VARIABLES { sdsInADC2 }
	DESCRIPTION "TRAP: Actual analog AD1 input value [raw]."
    ::= 251

sdsInADC3-trap TRAP-TYPE
	STATUS current
	ENTERPRISE mib-AN-Dcz-SDS
	VARIABLES { sdsInADC3 }
	DESCRIPTION "TRAP: Actual analog AD3 input value [raw]."
    ::= 252

sdsInADC4-trap TRAP-TYPE
	STATUS current
	ENTERPRISE mib-AN-Dcz-SDS
	VARIABLES { sdsInADC4 }
	DESCRIPTION "TRAP: Actual analog AD4 input value [raw]."
    ::= 253

sdsSItextADC1-trap TRAP-TYPE
	STATUS current
	ENTERPRISE mib-AN-Dcz-SDS
	VARIABLES { sdsSItextADC1 }
	DESCRIPTION "TRAP: SI textual value for AD1."
    ::= 254

sdsSItextADC2-trap TRAP-TYPE
	STATUS current
	ENTERPRISE mib-AN-Dcz-SDS
	VARIABLES { sdsSItextADC2 }
	DESCRIPTION "TRAP: SI textual value for AD2."
    ::= 255

sdsSItextADC3-trap TRAP-TYPE
	STATUS current
	ENTERPRISE mib-AN-Dcz-SDS
	VARIABLES { sdsSItextADC3 }
	DESCRIPTION "TRAP: SI textual value for AD3."
    ::= 256

sdsSItextADC4-trap TRAP-TYPE
	STATUS current
	ENTERPRISE mib-AN-Dcz-SDS
	VARIABLES { sdsSItextADC4 }
	DESCRIPTION "TRAP: SI textual value for AD4."
    ::= 257

sdsNameADC1-trap TRAP-TYPE
	STATUS current
	ENTERPRISE mib-AN-Dcz-SDS
	VARIABLES { sdsNameADC1 }
	DESCRIPTION "TRAP: User name for AD1."
    ::= 258

sdsNameADC2-trap TRAP-TYPE
	STATUS current
	ENTERPRISE mib-AN-Dcz-SDS
	VARIABLES { sdsNameADC2 }
	DESCRIPTION "TRAP: User name for AD2."
    ::= 259

sdsNameADC3-trap TRAP-TYPE
	STATUS current
	ENTERPRISE mib-AN-Dcz-SDS
	VARIABLES { sdsNameADC3 }
	DESCRIPTION "TRAP: User name for AD3."
    ::= 260

sdsNameADC4-trap TRAP-TYPE
	STATUS current
	ENTERPRISE mib-AN-Dcz-SDS
	VARIABLES { sdsNameADC4 }
	DESCRIPTION "TRAP: User name for AD4."
    ::= 261

sdsUnitADC1-trap TRAP-TYPE
	STATUS current
	ENTERPRISE mib-AN-Dcz-SDS
	VARIABLES { sdsUnitADC1 }
	DESCRIPTION "TRAP: User unit for AD1."
    ::= 262

sdsUnitADC2-trap TRAP-TYPE
	STATUS current
	ENTERPRISE mib-AN-Dcz-SDS
	VARIABLES { sdsUnitADC2 }
	DESCRIPTION "TRAP: User unit for AD2."
    ::= 263

sdsUnitADC3-trap TRAP-TYPE
	STATUS current
	ENTERPRISE mib-AN-Dcz-SDS
	VARIABLES { sdsUnitADC3 }
	DESCRIPTION "TRAP: User unit for AD3."
    ::= 264

sdsUnitADC4-trap TRAP-TYPE
	STATUS current
	ENTERPRISE mib-AN-Dcz-SDS
	VARIABLES { sdsUnitADC4 }
	DESCRIPTION "TRAP: User unit for AD4."
    ::= 265

-- next

sdsONEWIREactualTempInteger-trap TRAP-TYPE
	STATUS current
	ENTERPRISE mib-AN-Dcz-SDS
	VARIABLES { sdsONEWIREactualTempInteger }
	DESCRIPTION "TRAP: Actual temperature [integral part] for this DS18B20 sensor. 
                     INFO: USE INDEX OID TO ACCESS THE TABLE ITEMS."
    ::= 300

sdsONEWIREactualTempFrac-trap TRAP-TYPE
	STATUS current
	ENTERPRISE mib-AN-Dcz-SDS
	VARIABLES { sdsONEWIREactualTempFrac }
	DESCRIPTION "TRAP: Actual temperature [a fractional part] for this DS18B20 sensor. 
                     INFO: USE INDEX OID TO ACCESS THE TABLE ITEMS."
    ::= 301

sdsONEWIREdeviceROMcode-trap TRAP-TYPE
	STATUS current
	ENTERPRISE mib-AN-Dcz-SDS
	VARIABLES { sdsONEWIREdeviceROMcode }
	DESCRIPTION "TRAP: DS18B20 device ROM code. 
                     INFO: USE INDEX OID TO ACCESS THE TABLE ITEMS."
    ::= 302

sdsONEWIREuserName-trap TRAP-TYPE
	STATUS current
	ENTERPRISE mib-AN-Dcz-SDS
	VARIABLES { sdsONEWIREuserName }
	DESCRIPTION "TRAP: User name for this DS18B20 device. 
                     INFO: USE INDEX OID TO ACCESS THE TABLE ITEMS."
    ::= 303

sdsONEWIREactualTempCompleteMul100-trap TRAP-TYPE
	STATUS current
	ENTERPRISE mib-AN-Dcz-SDS
	VARIABLES { sdsONEWIREactualTempCompleteMul100 }
	DESCRIPTION "TRAP: Actual temperature [a complete value, multiplied by 100]. 
                     INFO: USE INDEX OID TO ACCESS THE TABLE ITEMS."
    ::= 304

sdsONEWIREactualRHpercent-trap TRAP-TYPE
	STATUS current
	ENTERPRISE mib-AN-Dcz-SDS
	VARIABLES { sdsONEWIREactualRHpercent }
	DESCRIPTION "TRAP: Actual RH value for SDS-T-RH sensor on this position.
                     INFO: USE INDEX OID TO ACCESS THE TABLE ITEMS."
    ::= 306
 
-- next

sdsVersionText-trap TRAP-TYPE
	STATUS current
	ENTERPRISE mib-AN-Dcz-SDS
	VARIABLES { sdsVersionText }
        DESCRIPTION "TRAP: SDS device version text."
    ::= 400

sdsCustomTrap1-trap TRAP-TYPE
	STATUS current
	ENTERPRISE mib-AN-Dcz-SDS
	VARIABLES { sdsCustomTrap1 }
        DESCRIPTION "TRAP: SDS-C custom int32 trap."
    ::= 401

-- next

sdsNTPvalue-trap TRAP-TYPE
	STATUS current
	ENTERPRISE mib-AN-Dcz-SDS
	VARIABLES { sdsNTPvalue }
        DESCRIPTION "TRAP: Actual NTP UTC time value (SDS device is NTP client)."
    ::= 600

sdsSoCtempValue-trap TRAP-TYPE
	STATUS current
	ENTERPRISE mib-AN-Dcz-SDS
	VARIABLES { sdsSoCtempValue }
        DESCRIPTION "TRAP: Actual SoC chip internal temperature, in special units."
    ::= 601

sdsOneWireBUSAcountValue-trap TRAP-TYPE
	STATUS current
	ENTERPRISE mib-AN-Dcz-SDS
	VARIABLES { sdsOneWireBUSAcountValue }
        DESCRIPTION "TRAP: Number of discovered 1-Wire devices on BUS A."
    ::= 602

sdsOneWireBUSBcountValue-trap TRAP-TYPE
	STATUS current
	ENTERPRISE mib-AN-Dcz-SDS
	VARIABLES { sdsOneWireBUSBcountValue }
        DESCRIPTION "TRAP: Number of discovered 1-Wire devices on BUS B."
    ::= 603

sdsPD0outputState-trap TRAP-TYPE
	STATUS current
	ENTERPRISE mib-AN-Dcz-SDS
	VARIABLES { sdsPD0outputState }
        DESCRIPTION "TRAP: PD0 actual port-pin bit (log1-log0) status."
    ::= 604

sdsPD0Direction-trap TRAP-TYPE
	STATUS current
	ENTERPRISE mib-AN-Dcz-SDS
	VARIABLES { sdsPD0Direction }
        DESCRIPTION "TRAP: PD0 actual port-pin direction (in-out) status."
    ::= 605

sdsLOCALTIMEvalue-trap TRAP-TYPE
	STATUS current
	ENTERPRISE mib-AN-Dcz-SDS
	VARIABLES { sdsLOCALTIMEvalue }
        DESCRIPTION "TRAP: Actual LOCAL time value (SDS device is NTP client)."
    ::= 610

-- next

sdsS0impCountT0-trap TRAP-TYPE
	STATUS current
	ENTERPRISE mib-AN-Dcz-SDS
	VARIABLES { sdsS0impCountT0 }
	DESCRIPTION "TRAP: Actual S0 impulse counter value for T0 tarif. 
                     INFO: USE INDEX OID TO ACCESS THE TABLE ITEMS."
    ::= 501

sdsS0impCountT1-trap TRAP-TYPE
	STATUS current
	ENTERPRISE mib-AN-Dcz-SDS
	VARIABLES { sdsS0impCountT1 }
	DESCRIPTION "TRAP: Actual S0 impulse counter value for T1 tarif. 
                     INFO: USE INDEX OID TO ACCESS THE TABLE ITEMS."
    ::= 502

sdsS0impMoneyOffsetT0-trap TRAP-TYPE
	STATUS current
	ENTERPRISE mib-AN-Dcz-SDS
	VARIABLES { sdsS0impMoneyOffsetT0 }
	DESCRIPTION "TRAP: Offset (impulse count) for cash calculation for T0. 
                     INFO: USE INDEX OID TO ACCESS THE TABLE ITEMS."
    ::= 503

sdsS0impMoneyOffsetT1-trap TRAP-TYPE
	STATUS current
	ENTERPRISE mib-AN-Dcz-SDS
	VARIABLES { sdsS0impMoneyOffsetT1 }
	DESCRIPTION "TRAP: Offset (impulse count) for cash calculation for T1. 
                     INFO: USE INDEX OID TO ACCESS THE TABLE ITEMS."
    ::= 504

sdsS0constant-trap TRAP-TYPE
	STATUS current
	ENTERPRISE mib-AN-Dcz-SDS
	VARIABLES { sdsS0constant }
	DESCRIPTION "TRAP: S0 output constant (number of impulses for 1 energy unit). 
                     INFO: USE INDEX OID TO ACCESS THE TABLE ITEMS."
    ::= 505

sdsS0translatedUnitT0-trap TRAP-TYPE
	STATUS current
	ENTERPRISE mib-AN-Dcz-SDS
	VARIABLES { sdsS0translatedUnitT0 }
	DESCRIPTION "TRAP: T0 related S0 impulse count value as textual energy unit. 
                     INFO: USE INDEX OID TO ACCESS THE TABLE ITEMS."
    ::= 506

sdsS0translatedUnitT1-trap TRAP-TYPE
	STATUS current
	ENTERPRISE mib-AN-Dcz-SDS
	VARIABLES { sdsS0translatedUnitT1 }
	DESCRIPTION "TRAP: T1 related S0 impulse count value as textual energy unit. 
                     INFO: USE INDEX OID TO ACCESS THE TABLE ITEMS."
     ::= 507

sdsS0translatedCashT0-trap TRAP-TYPE
	STATUS current
	ENTERPRISE mib-AN-Dcz-SDS
	VARIABLES { sdsS0translatedCashT0 }
	DESCRIPTION "TRAP: T0 related S0 counter value as textual cash value. 
                     INFO: USE INDEX OID TO ACCESS THE TABLE ITEMS."
    ::= 508

sdsS0translatedCashT1-trap TRAP-TYPE
	STATUS current
	ENTERPRISE mib-AN-Dcz-SDS
	VARIABLES { sdsS0translatedCashT1 }
	DESCRIPTION "TRAP: T1 related S0 counter value as textual cash value. 
                     INFO: USE INDEX OID TO ACCESS THE TABLE ITEMS."
    ::= 509

sdsS0actualEnergyFlow-trap TRAP-TYPE
	STATUS current
	ENTERPRISE mib-AN-Dcz-SDS
	VARIABLES { sdsS0actualEnergyFlow }
	DESCRIPTION "TRAP: S0: the actual energy flow value. 
                     INFO: USE INDEX OID TO ACCESS THE TABLE ITEMS."
    ::= 510
    
sdsS0constantMTD-trap TRAP-TYPE
	STATUS current
	ENTERPRISE mib-AN-Dcz-SDS
	VARIABLES { sdsS0constantMTD }
	DESCRIPTION "TRAP: S0: configuration - the MTD constant. 
                     INFO: USE INDEX OID TO ACCESS THE TABLE ITEMS."
    ::= 511

-- next

sdsSDSCEPvalue-trap TRAP-TYPE
	STATUS current
	ENTERPRISE mib-AN-Dcz-SDS
	VARIABLES { sdsSDSCEPvalue }
	DESCRIPTION "TRAP: Actual value for the particular SDS-C SDSCEP value. 
                     INFO: USE INDEX OID TO ACCESS THE TABLE ITEMS."
    ::= 700

-- next

sdsETStelnetConnected-trap TRAP-TYPE
	STATUS current
	ENTERPRISE mib-AN-Dcz-SDS
	VARIABLES { sdsETStelnetConnected }
        DESCRIPTION "TRAP: Is any Ethernet client connected to Eth-to-Serial converter."
    ::= 800

sdsETSbaudrate-trap TRAP-TYPE
	STATUS current
	ENTERPRISE mib-AN-Dcz-SDS
	VARIABLES { sdsETSbaudrate }
        DESCRIPTION "TRAP: Actual configured UART baud rate in [bps]."
    ::= 801

sdsETSdataSize-trap TRAP-TYPE
	STATUS current
	ENTERPRISE mib-AN-Dcz-SDS
	VARIABLES { sdsETSdataSize }
        DESCRIPTION "TRAP: Actual configured UART char data size [num of bits]."
    ::= 802

sdsETSstopBits-trap TRAP-TYPE
	STATUS current
	ENTERPRISE mib-AN-Dcz-SDS
	VARIABLES { sdsETSstopBits }
        DESCRIPTION "TRAP: Actual configured UART number of stop bits."
    ::= 803

sdsETSparity-trap TRAP-TYPE
	STATUS current
	ENTERPRISE mib-AN-Dcz-SDS
	VARIABLES { sdsETSparity }
        DESCRIPTION "TRAP: Actual configured UART parity."
    ::= 804

sdsETSuartInBytes-trap TRAP-TYPE
	STATUS current
	ENTERPRISE mib-AN-Dcz-SDS
	VARIABLES { sdsETSuartInBytes }
        DESCRIPTION "TRAP: Total number of UART IN bytes."
    ::= 805

sdsETSuartOutBytes-trap TRAP-TYPE
	STATUS current
	ENTERPRISE mib-AN-Dcz-SDS
	VARIABLES { sdsETSuartOutBytes }
        DESCRIPTION "TRAP: Total number of UART OUT bytes."
    ::= 806


-- end

END

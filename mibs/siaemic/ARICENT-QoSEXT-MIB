-- Copyright (C) 2006-2012 Aricent Group . All Rights Reserved

-- $Id: smqosxtdext.mib,v 1.9 2018/3/27 09:51:44 Gaurav Srivastav $

ARICENT-QoSEXT-MIB DEFINITIONS ::= BEGIN

IMPORTS
       fsQoSClassMapEntry
	   FROM ARICENT-DIFFSERV-MIB
	   MODULE-IDENTITY, OBJECT-TYPE,
       enterprises, Unsigned32, Integer32, Counter32, Counter64 
       FROM SNMPv2-SMI
       TEXTUAL-CONVENTION 
       FROM SNMPv2-TC;

smfutqos  MODULE-IDENTITY
        LAST-UPDATED "201209050000Z"
        ORGANIZATION "ARICENT COMMUNICATIONS SOFTWARE"
        CONTACT-INFO "|||||"
        DESCRIPTION  "This MIB defines the objects. OID assign for siae
                     is (29601.100.1)"

        ::=  { enterprises aricent-communication-holding-ltd(29601) 100 1 3}

-- Class Table
smQoSClass         OBJECT IDENTIFIER ::= { smfutqos 1 }

smQoSClassMapExtTable OBJECT-TYPE
    SYNTAX       SEQUENCE OF SmQoSClassMapExtEntry
    MAX-ACCESS   not-accessible
    STATUS       current
    DESCRIPTION
       "This table contains the Multifield Classifier details. It takes input
        from the ACL or priority-map table and outputs a CLASS for the 
        traffic-class pattern/match.This is an extended table."
    ::= { smQoSClass 1 }

smQoSClassMapExtEntry OBJECT-TYPE
    SYNTAX       SmQoSClassMapExtEntry
    MAX-ACCESS   not-accessible
    STATUS   current
    DESCRIPTION
       "A Multi-field Classifier entry maps an ACL entry or a priority-map 
        to a CLASS of Service."
    AUGMENTS { fsQoSClassMapEntry }
    ::= { smQoSClassMapExtTable 1 }

SmQoSClassMapExtEntry ::= SEQUENCE {
    smQoSExtClassMapYpDeiBit INTEGER
    }

smQoSExtClassMapYpDeiBit OBJECT-TYPE
    SYNTAX      INTEGER { reset(0), set(1), None(2) }
    MAX-ACCESS  read-write
    STATUS      current
    DESCRIPTION
        "This object is used to set the CFI/DEI bit on the external VLAN on all the packets pre-colored with yellow color.
         This object should be used with mac-access list with OUT direction."
    DEFVAL  { 2 }
    ::=  { smQoSClassMapExtEntry 1}
	
END

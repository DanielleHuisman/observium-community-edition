-- Copyright (C) 2006-2012 Aricent Group . All Rights Reserved

-- $Id: fsrmon.mib,v 1.9 2013/10/28 09:51:44 siva Exp $

ARICENT-RMON-MIB DEFINITIONS ::= BEGIN
                   --  Remote Network Monitoring MIB

-- Enterprises MIB for RMON product (for Trace).

IMPORTS 
    etherStatsEntry, historyControlEntry, etherHistoryEntry 
  FROM RMON-MIB
    MODULE-IDENTITY, OBJECT-TYPE,
    enterprises, Unsigned32, Integer32, Counter32, Counter64 
  FROM SNMPv2-SMI
    TEXTUAL-CONVENTION 
  FROM SNMPv2-TC;


futrmon MODULE-IDENTITY
     LAST-UPDATED "201406190000Z"
     ORGANIZATION "ARICENT COMMUNICATIONS SOFTWARE"
     CONTACT-INFO "support@aricent.com" 
     DESCRIPTION
           " This MIB module is for managing RMON implementations."
           
-- revision history

     REVISION "201406190000Z"
     DESCRIPTION
           " This MIB module is for managing RMON implementations. 
        Ether Statistics group supports the monitoring of different statistics on
        ethernet interfaces, which is enhanced to support statistics per VLAN.
        The etherStatsDatasource of etherStats table identifies the source of data 
        that is configured to analyze. Now Ether Statistics group supports the 
        monitoring of further statistics and they can be collected per service."
           
     REVISION "201209050000Z"
     DESCRIPTION
           " This MIB module is for managing RMON implementations. 
        Ether Statistics group supports the monitoring of different statistics on
        ethernet interfaces, which is enhanced to support statistics per VLAN
        The etherStatsDatasource of etherStats table identifies the source of data 
        that is configured to analyze. Now this source can be set to either
        interface OID or VLAN OID. If configured for interface OID the statistics
        collection is set to be on Interface and if the source is set to VLAN OID 
        the statistics collection is set to be on any of the VLAN configured in the
        device."

                  ::= { enterprises futuresoftware (2076) 44 }
                  
-- -------------------------------------------------------------
-- Textual Conventions
-- -------------------------------------------------------------

VIDOrZero  ::= TEXTUAL-CONVENTION
    DISPLAY-HINT "d"
    STATUS        current
    DESCRIPTION   "The VLAN ID that uniquely identifies a VLAN. 
                  The value zero is NOT a valid VLAN ID.                  
                  When this value is set, the displayed 
                  statistics are not differentiated for VLAN."
    SYNTAX        Unsigned32 (0 | 1..4094)
    
PriorityOrNegative   ::= TEXTUAL-CONVENTION
    DISPLAY-HINT  "d"
    STATUS        current
    DESCRIPTION   "The VLAN priority. 
                  The value -1 is NOT a valid priority.                  
                  When this value is set, the displayed 
                  statistics are not differentiated for priority."
    SYNTAX        Integer32 (-1 | 0..7)    

    
-- FutreRmon Trace enable/disable object
 
         rmonDebugType OBJECT-TYPE
              SYNTAX  Unsigned32 
              MAX-ACCESS read-write
              STATUS current
              DESCRIPTION
          "This object defines the enabled debug flag for rmon"

         ::=  { futrmon  1 }
        
-- FutreRmon enable/disable status object
 
         rmonEnableStatus OBJECT-TYPE
              SYNTAX  INTEGER { rmonenabled(1), rmondisabled(2) } 
              MAX-ACCESS read-write
              STATUS current
              DESCRIPTION
          "This object defines the rmonenable flag for rmon" 

         ::=  { futrmon  2 }
         
-- FutreRmon  stats supported object
 
      rmonHwStatsSupp OBJECT-TYPE

              SYNTAX  INTEGER { notsupported(0), supported(1)}
              MAX-ACCESS read-write
              STATUS current
              DESCRIPTION
          "This object defines the flag for whether HW supports
                   Etherstatistics or not   "

         ::=  { futrmon  3 }

-- FutreRmon  HW history supported object

 
         rmonHwHistorySupp OBJECT-TYPE
              SYNTAX  INTEGER { notsupported(0), supported(1)}
              MAX-ACCESS read-write
              STATUS current
              DESCRIPTION
          "This object defines the enabled HWhistorysupp flag for rmon"

         ::=  { futrmon  4 }

-- FutreRmon HWalarmsupported object
 
         rmonHwAlarmSupp OBJECT-TYPE
              SYNTAX  INTEGER { notsupported(0), supported(1)}
              MAX-ACCESS read-write
              STATUS current
              DESCRIPTION
          "This object defines the enabled HWAlarmsupp flag for rmon"

         ::=  { futrmon  5 }

-- FutreRmon  HWHostsupported object
 
         rmonHwHostSupp OBJECT-TYPE

              SYNTAX  INTEGER { notsupported(0), supported(1)}
              MAX-ACCESS read-write
              STATUS current
              DESCRIPTION
          "This object defines the enabled HWhostsupp flag for rmon"

         ::=  { futrmon  6 }

-- FutreRmon  HW hosttopN supported object
 
         rmonHwHostTopNSupp OBJECT-TYPE
              SYNTAX  INTEGER { notsupported(0), supported(1)}
              MAX-ACCESS read-write
              STATUS current
              DESCRIPTION
          "This object defines the enabled HWHostTopN flag for rmon"

         ::=  { futrmon  7 }

-- FutreRmon  HW matrix supported object
 
         rmonHwMatrixSupp OBJECT-TYPE
              SYNTAX  INTEGER { notsupported(0), supported(1)}
              MAX-ACCESS read-write
              STATUS current
              DESCRIPTION
          "This object defines the enabled HWMatrix flag for rmon"

         ::=  { futrmon  8 }

-- FutreRmon  HW Event supported object
 
         rmonHwEventSupp OBJECT-TYPE
              SYNTAX  INTEGER { notsupported(0), supported(1)}
              MAX-ACCESS read-write
              STATUS current
              DESCRIPTION
          "This object defines the enabled HWEvent flag for rmon"

         ::=  { futrmon  9 }


-- Tabular Objects

 -- rmonStatsTable 

    rmonStatsTable OBJECT-TYPE
        SYNTAX     SEQUENCE OF RmonStatsEntry
        MAX-ACCESS not-accessible
        STATUS     current
        DESCRIPTION "The table is a enhancement of etherStatsTable in stdrmon.mib."

    ::= {futrmon 10}

    rmonStatsEntry  OBJECT-TYPE
        SYNTAX      RmonStatsEntry
        MAX-ACCESS not-accessible
        STATUS     current
        DESCRIPTION "An Entry containing Statistics information (e.g., OutFCSError)."
        AUGMENTS {etherStatsEntry}
    ::= {rmonStatsTable 1}

    RmonStatsEntry  ::= SEQUENCE {
     rmonStatsOutFCSErrors              Counter32,
     rmonStatsPkts1519to1522Octets      Counter32
                                }
    rmonStatsOutFCSErrors OBJECT-TYPE
        SYNTAX      Counter32
        MAX-ACCESS  read-only
        STATUS      current
        DESCRIPTION
        "The number of frames transmitted with an invalid FCS.
        Whenever a frame is modified during transmission
        (e.g., to add or remove a tag) the frame's original FCS
        is inspected before a new FCS is added to a modified
        frame. If the original FCS is invalid, the new FCS is
        made invalid too and this counter is incremented."

    ::={rmonStatsEntry 1}
	
    rmonStatsPkts1519to1522Octets OBJECT-TYPE
     SYNTAX     Counter32
     UNITS      "Packets"
     MAX-ACCESS read-only
     STATUS     current
     DESCRIPTION
         "The total number of packets (including bad
         packets) received that were between
         1519 and 1522 octets in length inclusive
         (excluding framing bits but including FCS octets)."

    ::={rmonStatsEntry 2}

 -- sEtherStatsTable 

    sEtherStatsTable OBJECT-TYPE
          SYNTAX     SEQUENCE OF SEtherStatsEntry
        MAX-ACCESS not-accessible
        STATUS     current
        DESCRIPTION 
        "The table is a further enhancement of etherStatsTable in stdrmon.mib 
         to allow a collection of statistics kept for Ethernet 
         interface and service."
    ::= {futrmon 11}

    sEtherStatsEntry  OBJECT-TYPE
        SYNTAX      SEtherStatsEntry
        MAX-ACCESS not-accessible
        STATUS     current
        DESCRIPTION "An Entry containing Statistics information (e.g. InUCastPkts)."
        AUGMENTS {etherStatsEntry}        
    ::= {sEtherStatsTable 1}

    SEtherStatsEntry  ::= SEQUENCE {
            sEtherStatsInPkts                 Counter32,
            sEtherStatsInOverflowPkts         Counter32,
            sEtherStatsInHCPkts               Counter64,
            sEtherStatsOutPkts                Counter32,
            sEtherStatsOutOverflowPkts        Counter32,
            sEtherStatsOutHCPkts              Counter64,
            sEtherStatsInOctets               Counter32,
            sEtherStatsInOverflowOctets       Counter32,
            sEtherStatsInHCOctets             Counter64,
            sEtherStatsOutOctets              Counter32,
            sEtherStatsOutOverflowOctets      Counter32,
            sEtherStatsOutHCOctets            Counter64,
            sEtherStatsInDiscard              Counter32,
            sEtherStatsInOverflowDiscard      Counter32,
            sEtherStatsInHCDiscard            Counter64,
            sEtherStatsOutDiscard             Counter32,
            sEtherStatsOutOverflowDiscard     Counter32,
            sEtherStatsOutHCDiscard           Counter64,
            sEtherStatsInUCastPkts            Counter32,
            sEtherStatsInUCastOverflowPkts    Counter32,
            sEtherStatsInUCastHCPkts          Counter64,
            sEtherStatsOutUCastPkts           Counter32,
            sEtherStatsOutUCastOverflowPkts   Counter32,
            sEtherStatsOutUCastHCPkts         Counter64,
            sEtherStatsInNUCastPkts           Counter32,
            sEtherStatsInNUCastOverflowPkts   Counter32,
            sEtherStatsInNUCastHCPkts         Counter64,
            sEtherStatsOutNUCastPkts          Counter32,
            sEtherStatsOutNUCastOverflowPkts  Counter32,
            sEtherStatsOutNUCastHCPkts        Counter64,
            sEtherStatsOuterVid               VIDOrZero,
            sEtherStatsOuterPriority          PriorityOrNegative,
            sEtherStatsInnerVid               VIDOrZero
    }
                                
    sEtherStatsInPkts OBJECT-TYPE
        SYNTAX      Counter32
        MAX-ACCESS  read-only
        STATUS      current
        DESCRIPTION
        "The total number of received packets."

    ::={sEtherStatsEntry 1}
    
    
    sEtherStatsInOverflowPkts OBJECT-TYPE
        SYNTAX      Counter32
        MAX-ACCESS  read-only
        STATUS      current
        DESCRIPTION
        "The number of times the associated
        sEtherStatsInPkts counter has overflowed."

    ::={sEtherStatsEntry 2}
    
    
    sEtherStatsInHCPkts OBJECT-TYPE
        SYNTAX      Counter64
        MAX-ACCESS  read-only
        STATUS      current
        DESCRIPTION
        "The high capacity counter for the total
        number of received packets."

    ::={sEtherStatsEntry 3}
    

    sEtherStatsOutPkts OBJECT-TYPE
        SYNTAX      Counter32
        MAX-ACCESS  read-only
        STATUS      current
        DESCRIPTION
        "The total number of transmitted packets."

    ::={sEtherStatsEntry 4}
    
    
   sEtherStatsOutOverflowPkts OBJECT-TYPE
        SYNTAX      Counter32
        MAX-ACCESS  read-only
        STATUS      current
        DESCRIPTION
        "The number of times the associated
        sEtherStatsOutPkts counter has overflowed."

    ::={sEtherStatsEntry 5}    


    sEtherStatsOutHCPkts OBJECT-TYPE
        SYNTAX      Counter64
        MAX-ACCESS  read-only
        STATUS      current
        DESCRIPTION
        "The high capacity counter for the total
        number of transmitted packets."

    ::={sEtherStatsEntry 6}
                                

    sEtherStatsInOctets OBJECT-TYPE
        SYNTAX      Counter32
        MAX-ACCESS  read-only
        STATUS      current
        DESCRIPTION
        "The total number of received octets."

    ::={sEtherStatsEntry 7}
    
    
   sEtherStatsInOverflowOctets OBJECT-TYPE
        SYNTAX      Counter32
        MAX-ACCESS  read-only
        STATUS      current
        DESCRIPTION
        "The number of times the associated
        sEtherStatsInOctets counter has overflowed."

    ::={sEtherStatsEntry 8}
                          

    sEtherStatsInHCOctets OBJECT-TYPE
        SYNTAX      Counter64
        MAX-ACCESS  read-only
        STATUS      current
        DESCRIPTION
        "The high capacity counter for the total
        number of received octets."

    ::={sEtherStatsEntry 9}                     


    sEtherStatsOutOctets OBJECT-TYPE
        SYNTAX      Counter32
        MAX-ACCESS  read-only
        STATUS      current
        DESCRIPTION
        "The total number of transmitted octets."

    ::={sEtherStatsEntry 10}
    
    
   sEtherStatsOutOverflowOctets OBJECT-TYPE
        SYNTAX      Counter32
        MAX-ACCESS  read-only
        STATUS      current
        DESCRIPTION
        "The number of times the associated
        sEtherStatsOutOctets counter has overflowed."

    ::={sEtherStatsEntry 11}
                          

    sEtherStatsOutHCOctets OBJECT-TYPE
        SYNTAX      Counter64
        MAX-ACCESS  read-only
        STATUS      current
        DESCRIPTION
        "The high capacity counter for the total
        number of transmitted octets."

    ::={sEtherStatsEntry 12}                   
                        

    sEtherStatsInDiscard OBJECT-TYPE
        SYNTAX      Counter32
        MAX-ACCESS  read-only
        STATUS      current
        DESCRIPTION
        "The number of received packets which were
        discarded."

    ::={sEtherStatsEntry 13}
    
    
   sEtherStatsInOverflowDiscard OBJECT-TYPE
        SYNTAX      Counter32
        MAX-ACCESS  read-only
        STATUS      current
        DESCRIPTION
        "The number of times the associated
        sEtherStatsInDiscard counter has overflowed."

    ::={sEtherStatsEntry 14}
                          

    sEtherStatsInHCDiscard OBJECT-TYPE
        SYNTAX      Counter64
        MAX-ACCESS  read-only
        STATUS      current
        DESCRIPTION
        "The high capacity counter for the number of
        received packets which were discarded."

    ::={sEtherStatsEntry 15}
                            
    
    sEtherStatsOutDiscard OBJECT-TYPE
        SYNTAX      Counter32
        MAX-ACCESS  read-only
        STATUS      current
        DESCRIPTION
        "The number of packets to be transmitted which
        were discarded."

    ::={sEtherStatsEntry 16}
    
    
   sEtherStatsOutOverflowDiscard OBJECT-TYPE
        SYNTAX      Counter32
        MAX-ACCESS  read-only
        STATUS      current
        DESCRIPTION
        "The number of times the associated
        sEtherStatsOutDiscard counter has overflowed."

    ::={sEtherStatsEntry 17}
                          

    sEtherStatsOutHCDiscard OBJECT-TYPE
        SYNTAX      Counter64
        MAX-ACCESS  read-only
        STATUS      current
        DESCRIPTION
        "The high capacity counter for the number of
        packets to be transmitted which were
        discarded."

    ::={sEtherStatsEntry 18}
    
    
    sEtherStatsInUCastPkts OBJECT-TYPE
        SYNTAX      Counter32
        MAX-ACCESS  read-only
        STATUS      current
        DESCRIPTION
        "The number of received unicast packets."

    ::={sEtherStatsEntry 19}
    
    
   sEtherStatsInUCastOverflowPkts OBJECT-TYPE
        SYNTAX      Counter32
        MAX-ACCESS  read-only
        STATUS      current
        DESCRIPTION
        "The number of times the associated
        sEtherStatsInUCastPkts counter has overflowed."

    ::={sEtherStatsEntry 20}
                          

    sEtherStatsInUCastHCPkts OBJECT-TYPE
        SYNTAX      Counter64
        MAX-ACCESS  read-only
        STATUS      current
        DESCRIPTION
        "The high capacity counter for the number of
        received unicast packets."

    ::={sEtherStatsEntry 21}        


    sEtherStatsOutUCastPkts OBJECT-TYPE
        SYNTAX      Counter32
        MAX-ACCESS  read-only
        STATUS      current
        DESCRIPTION
        "The number of transmitted unicast packets."

    ::={sEtherStatsEntry 22}
    
    
   sEtherStatsOutUCastOverflowPkts OBJECT-TYPE
        SYNTAX      Counter32
        MAX-ACCESS  read-only
        STATUS      current
        DESCRIPTION
        "The number of times the associated
        sEtherStatsOutUCastPkts counter has overflowed."

    ::={sEtherStatsEntry 23}
                          

    sEtherStatsOutUCastHCPkts OBJECT-TYPE
        SYNTAX      Counter64
        MAX-ACCESS  read-only
        STATUS      current
        DESCRIPTION
        "The high capacity counter for the number of
        transmitted unicast packets."

    ::={sEtherStatsEntry 24}    


    sEtherStatsInNUCastPkts OBJECT-TYPE
        SYNTAX      Counter32
        MAX-ACCESS  read-only
        STATUS      current
        DESCRIPTION
        "The number of received not unicast packets."

    ::={sEtherStatsEntry 25}
    
    
   sEtherStatsInNUCastOverflowPkts OBJECT-TYPE
        SYNTAX      Counter32
        MAX-ACCESS  read-only
        STATUS      current
        DESCRIPTION
        "The number of times the associated
        sEtherStatsInNUCastPkts counter has overflowed."

    ::={sEtherStatsEntry 26}
                          

    sEtherStatsInNUCastHCPkts OBJECT-TYPE
        SYNTAX      Counter64
        MAX-ACCESS  read-only
        STATUS      current
        DESCRIPTION
        "The high capacity counter for the number of
        received not unicast packets."

    ::={sEtherStatsEntry 27}        


    sEtherStatsOutNUCastPkts OBJECT-TYPE
        SYNTAX      Counter32
        MAX-ACCESS  read-only
        STATUS      current
        DESCRIPTION
        "The number of transmitted not unicast packets."

    ::={sEtherStatsEntry 28}
    
    
   sEtherStatsOutNUCastOverflowPkts OBJECT-TYPE
        SYNTAX      Counter32
        MAX-ACCESS  read-only
        STATUS      current
        DESCRIPTION
        "The number of times the associated
        sEtherStatsOutNUCastPkts counter has overflowed."

    ::={sEtherStatsEntry 29}
                          

    sEtherStatsOutNUCastHCPkts OBJECT-TYPE
        SYNTAX      Counter64
        MAX-ACCESS  read-only
        STATUS      current
        DESCRIPTION
        "The high capacity counter for the number of
        transmitted not unicast packets."

    ::={sEtherStatsEntry 30}
                       

    sEtherStatsOuterVid OBJECT-TYPE
        SYNTAX      VIDOrZero
        MAX-ACCESS  read-create
        STATUS      current
        DESCRIPTION
        "The outer vlan identifier."
        DEFVAL      { 0 }

    ::={sEtherStatsEntry 31}                    


    sEtherStatsOuterPriority OBJECT-TYPE
        SYNTAX      PriorityOrNegative
        MAX-ACCESS  read-create
        STATUS      current
        DESCRIPTION
        "The priority code point."
        DEFVAL      { -1 }

    ::={sEtherStatsEntry 32}                                          
 

    sEtherStatsInnerVid OBJECT-TYPE
        SYNTAX      VIDOrZero
        MAX-ACCESS  read-create
        STATUS      current
        DESCRIPTION
        "The inner vlan identifier."
        DEFVAL      { 0 }

    ::={sEtherStatsEntry 33}
                               

 -- sHistoryControlTable 

    sHistoryControlTable OBJECT-TYPE
        SYNTAX     SEQUENCE OF SHistoryControlEntry
        MAX-ACCESS not-accessible
        STATUS     current
        DESCRIPTION 
        "The table is an enhancement of historyTable in stdrmon.mib."
    ::= {futrmon 12}

    sHistoryControlEntry  OBJECT-TYPE
        SYNTAX      SHistoryControlEntry
        MAX-ACCESS not-accessible
        STATUS     current
        DESCRIPTION "A list of parameters that set up a periodic 
                    sampling of statistic."
        AUGMENTS {historyControlEntry}        
    ::= {sHistoryControlTable 1}

    SHistoryControlEntry  ::= SEQUENCE {
            sHistoryControlOuterVid               VIDOrZero,
            sHistoryControlOuterPriority          PriorityOrNegative,
            sHistoryControlInnerVid               VIDOrZero,
            sHistoryControlPersistence            INTEGER
    }
                                
    sHistoryControlOuterVid OBJECT-TYPE
        SYNTAX      VIDOrZero
        MAX-ACCESS  read-create
        STATUS      current
        DESCRIPTION
        "The outer vlan identifier."
        DEFVAL      { 0 }

    ::={sHistoryControlEntry 1}                    


    sHistoryControlOuterPriority OBJECT-TYPE
        SYNTAX      PriorityOrNegative
        MAX-ACCESS  read-create
        STATUS      current
        DESCRIPTION
        "The priority code point."
        DEFVAL      { -1 }

    ::={sHistoryControlEntry 2}                                          
 

    sHistoryControlInnerVid OBJECT-TYPE
        SYNTAX      VIDOrZero
        MAX-ACCESS  read-create
        STATUS      current
        DESCRIPTION
        "The inner vlan identifier."
        DEFVAL      { 0 }

    ::={sHistoryControlEntry 3}                 


    sHistoryControlPersistence OBJECT-TYPE
        SYNTAX      INTEGER {
                             disable  (0),
                             enable   (2)
                            }
        MAX-ACCESS  read-create
        STATUS      current
        DESCRIPTION
        "This object defines the persistence flag for history collections."
        DEFVAL      { disable }

    ::={sHistoryControlEntry 4}                 
                        
 -- sEtherHistoryTable 

    sEtherHistoryTable OBJECT-TYPE
        SYNTAX     SEQUENCE OF SEtherHistoryEntry
        MAX-ACCESS not-accessible
        STATUS     current
        DESCRIPTION 
        "The table is an enhancement of etherHistoryTable in stdrmon.mib."
    ::= {futrmon 13}

    sEtherHistoryEntry  OBJECT-TYPE
        SYNTAX      SEtherHistoryEntry
        MAX-ACCESS not-accessible
        STATUS     current
        DESCRIPTION "An historical sample of Ethernet statistics on a
                     specific history control pattern
                     (e.g. historyControlDataSource - sHistoryControlOuterVid)."
        AUGMENTS {etherHistoryEntry}        
    ::= {sEtherHistoryTable 1}

    SEtherHistoryEntry  ::= SEQUENCE {
            sEtherHistoryInPkts                 Counter32,
            sEtherHistoryInOverflowPkts         Counter32,
            sEtherHistoryInHCPkts               Counter64,
            sEtherHistoryOutPkts                Counter32,
            sEtherHistoryOutOverflowPkts        Counter32,
            sEtherHistoryOutHCPkts              Counter64,
            sEtherHistoryInOctets               Counter32,
            sEtherHistoryInOverflowOctets       Counter32,
            sEtherHistoryInHCOctets             Counter64,
            sEtherHistoryOutOctets              Counter32,
            sEtherHistoryOutOverflowOctets      Counter32,
            sEtherHistoryOutHCOctets            Counter64,
            sEtherHistoryInDiscard              Counter32,
            sEtherHistoryInOverflowDiscard      Counter32,
            sEtherHistoryInHCDiscard            Counter64,
            sEtherHistoryOutDiscard             Counter32,
            sEtherHistoryOutOverflowDiscard     Counter32,
            sEtherHistoryOutHCDiscard           Counter64,
            sEtherHistoryInUCastPkts            Counter32,
            sEtherHistoryInUCastOverflowPkts    Counter32,
            sEtherHistoryInUCastHCPkts          Counter64,
            sEtherHistoryOutUCastPkts           Counter32,
            sEtherHistoryOutUCastOverflowPkts   Counter32,
            sEtherHistoryOutUCastHCPkts         Counter64,
            sEtherHistoryInNUCastPkts           Counter32,
            sEtherHistoryInNUCastOverflowPkts   Counter32,
            sEtherHistoryInNUCastHCPkts         Counter64,
            sEtherHistoryOutNUCastPkts          Counter32,
            sEtherHistoryOutNUCastOverflowPkts  Counter32,
            sEtherHistoryOutNUCastHCPkts        Counter64,
            sEtherHistoryTimestamp              Unsigned32

    }
                                
    sEtherHistoryInPkts OBJECT-TYPE
        SYNTAX      Counter32
        MAX-ACCESS  read-only
        STATUS      current
        DESCRIPTION
        "The total number of received packets."

    ::={sEtherHistoryEntry 1}
    
    
    sEtherHistoryInOverflowPkts OBJECT-TYPE
        SYNTAX      Counter32
        MAX-ACCESS  read-only
        STATUS      current
        DESCRIPTION
        "The number of times the associated
        sEtherHistoryInPkts counter has overflowed."

    ::={sEtherHistoryEntry 2}
    
    
    sEtherHistoryInHCPkts OBJECT-TYPE
        SYNTAX      Counter64
        MAX-ACCESS  read-only
        STATUS      current
        DESCRIPTION
        "The high capacity counter for the total
        number of received packets."

    ::={sEtherHistoryEntry 3}
    

    sEtherHistoryOutPkts OBJECT-TYPE
        SYNTAX      Counter32
        MAX-ACCESS  read-only
        STATUS      current
        DESCRIPTION
        "The total number of transmitted packets."

    ::={sEtherHistoryEntry 4}
    
    
   sEtherHistoryOutOverflowPkts OBJECT-TYPE
        SYNTAX      Counter32
        MAX-ACCESS  read-only
        STATUS      current
        DESCRIPTION
        "The number of times the associated
        sEtherHistoryOutPkts counter has overflowed."

    ::={sEtherHistoryEntry 5}    


    sEtherHistoryOutHCPkts OBJECT-TYPE
        SYNTAX      Counter64
        MAX-ACCESS  read-only
        STATUS      current
        DESCRIPTION
        "The high capacity counter for the total
        number of transmitted packets."

    ::={sEtherHistoryEntry 6}
                                

    sEtherHistoryInOctets OBJECT-TYPE
        SYNTAX      Counter32
        MAX-ACCESS  read-only
        STATUS      current
        DESCRIPTION
        "The total number of received octets."

    ::={sEtherHistoryEntry 7}
    
    
   sEtherHistoryInOverflowOctets OBJECT-TYPE
        SYNTAX      Counter32
        MAX-ACCESS  read-only
        STATUS      current
        DESCRIPTION
        "The number of times the associated
        sEtherHistoryInOctets counter has overflowed."

    ::={sEtherHistoryEntry 8}
                          

    sEtherHistoryInHCOctets OBJECT-TYPE
        SYNTAX      Counter64
        MAX-ACCESS  read-only
        STATUS      current
        DESCRIPTION
        "The high capacity counter for the total
        number of received octets."

    ::={sEtherHistoryEntry 9}                     


    sEtherHistoryOutOctets OBJECT-TYPE
        SYNTAX      Counter32
        MAX-ACCESS  read-only
        STATUS      current
        DESCRIPTION
        "The total number of transmitted octets."

    ::={sEtherHistoryEntry 10}
    
    
   sEtherHistoryOutOverflowOctets OBJECT-TYPE
        SYNTAX      Counter32
        MAX-ACCESS  read-only
        STATUS      current
        DESCRIPTION
        "The number of times the associated
        sEtherHistoryOutOctets counter has overflowed."

    ::={sEtherHistoryEntry 11}
                          

    sEtherHistoryOutHCOctets OBJECT-TYPE
        SYNTAX      Counter64
        MAX-ACCESS  read-only
        STATUS      current
        DESCRIPTION
        "The high capacity counter for the total
        number of transmitted octets."

    ::={sEtherHistoryEntry 12}                   
                        

    sEtherHistoryInDiscard OBJECT-TYPE
        SYNTAX      Counter32
        MAX-ACCESS  read-only
        STATUS      current
        DESCRIPTION
        "The number of received packets which were
        discarded."

    ::={sEtherHistoryEntry 13}
    
    
   sEtherHistoryInOverflowDiscard OBJECT-TYPE
        SYNTAX      Counter32
        MAX-ACCESS  read-only
        STATUS      current
        DESCRIPTION
        "The number of times the associated
        sEtherHistoryInDiscard counter has overflowed."

    ::={sEtherHistoryEntry 14}
                          

    sEtherHistoryInHCDiscard OBJECT-TYPE
        SYNTAX      Counter64
        MAX-ACCESS  read-only
        STATUS      current
        DESCRIPTION
        "The high capacity counter for the number of
        received packets which were discarded."

    ::={sEtherHistoryEntry 15}                         
    
    sEtherHistoryOutDiscard OBJECT-TYPE
        SYNTAX      Counter32
        MAX-ACCESS  read-only
        STATUS      current
        DESCRIPTION
        "The number of packets to be transmitted which
        were discarded."

    ::={sEtherHistoryEntry 16}
    
    
   sEtherHistoryOutOverflowDiscard OBJECT-TYPE
        SYNTAX      Counter32
        MAX-ACCESS  read-only
        STATUS      current
        DESCRIPTION
        "The number of times the associated
        sEtherHistoryOutDiscard counter has overflowed."

    ::={sEtherHistoryEntry 17}
                          

    sEtherHistoryOutHCDiscard OBJECT-TYPE
        SYNTAX      Counter64
        MAX-ACCESS  read-only
        STATUS      current
        DESCRIPTION
        "The high capacity counter for the number of
        packets to be transmitted which were
        discarded."

    ::={sEtherHistoryEntry 18}
    
    
    sEtherHistoryInUCastPkts OBJECT-TYPE
        SYNTAX      Counter32
        MAX-ACCESS  read-only
        STATUS      current
        DESCRIPTION
        "The number of received unicast packets."

    ::={sEtherHistoryEntry 19}
    
    
   sEtherHistoryInUCastOverflowPkts OBJECT-TYPE
        SYNTAX      Counter32
        MAX-ACCESS  read-only
        STATUS      current
        DESCRIPTION
        "The number of times the associated
        sEtherHistoryInUCastPkts counter has overflowed."

    ::={sEtherHistoryEntry 20}
                          

    sEtherHistoryInUCastHCPkts OBJECT-TYPE
        SYNTAX      Counter64
        MAX-ACCESS  read-only
        STATUS      current
        DESCRIPTION
        "The high capacity counter for the number of
        received unicast packets."

    ::={sEtherHistoryEntry 21}        


    sEtherHistoryOutUCastPkts OBJECT-TYPE
        SYNTAX      Counter32
        MAX-ACCESS  read-only
        STATUS      current
        DESCRIPTION
        "The number of transmitted unicast packets."

    ::={sEtherHistoryEntry 22}
    
    
   sEtherHistoryOutUCastOverflowPkts OBJECT-TYPE
        SYNTAX      Counter32
        MAX-ACCESS  read-only
        STATUS      current
        DESCRIPTION
        "The number of times the associated
        sEtherHistoryOutUCastPkts counter has overflowed."

    ::={sEtherHistoryEntry 23}
                          

    sEtherHistoryOutUCastHCPkts OBJECT-TYPE
        SYNTAX      Counter64
        MAX-ACCESS  read-only
        STATUS      current
        DESCRIPTION
        "The high capacity counter for the number of
        transmitted unicast packets."

    ::={sEtherHistoryEntry 24}    


    sEtherHistoryInNUCastPkts OBJECT-TYPE
        SYNTAX      Counter32
        MAX-ACCESS  read-only
        STATUS      current
        DESCRIPTION
        "The number of received not unicast packets."

    ::={sEtherHistoryEntry 25}
    
    
   sEtherHistoryInNUCastOverflowPkts OBJECT-TYPE
        SYNTAX      Counter32
        MAX-ACCESS  read-only
        STATUS      current
        DESCRIPTION
        "The number of times the associated
        sEtherHistoryInNUCastPkts counter has overflowed."

    ::={sEtherHistoryEntry 26}
                          

    sEtherHistoryInNUCastHCPkts OBJECT-TYPE
        SYNTAX      Counter64
        MAX-ACCESS  read-only
        STATUS      current
        DESCRIPTION
        "The high capacity counter for the number of
        received not unicast packets."

    ::={sEtherHistoryEntry 27}        


    sEtherHistoryOutNUCastPkts OBJECT-TYPE
        SYNTAX      Counter32
        MAX-ACCESS  read-only
        STATUS      current
        DESCRIPTION
        "The number of transmitted not unicast packets."

    ::={sEtherHistoryEntry 28}
    
    
   sEtherHistoryOutNUCastOverflowPkts OBJECT-TYPE
        SYNTAX      Counter32
        MAX-ACCESS  read-only
        STATUS      current
        DESCRIPTION
        "The number of times the associated
        sEtherHistoryOutNUCastPkts counter has overflowed."

    ::={sEtherHistoryEntry 29}
                          

    sEtherHistoryOutNUCastHCPkts OBJECT-TYPE
        SYNTAX      Counter64
        MAX-ACCESS  read-only
        STATUS      current
        DESCRIPTION
        "The high capacity counter for the number of
        transmitted not unicast packets."

    ::={sEtherHistoryEntry 30}
   
    sEtherHistoryTimestamp OBJECT-TYPE
        SYNTAX      Unsigned32
        MAX-ACCESS  read-only
        STATUS      current
        DESCRIPTION
        "The time (in secs) since 01-Gen-1970 when this sample was closed."

    ::={sEtherHistoryEntry 31} 


    rmonGlobalClearCounters OBJECT-TYPE
        SYNTAX          TruthValue
        MAX-ACCESS      read-write
        STATUS          current
        DESCRIPTION
        "This object is used to clear all the rmon counters.
        Setting this object to true will cause the statistics to be reset
        and setting this object to false will have no effect.
        A Get operation on this object will always return a value of
        false."
        DEFVAL { false }

    ::=  { futrmon  14 }


    rmonInterfaceClearCountersTable OBJECT-TYPE
        SYNTAX       SEQUENCE OF RmonInterfaceClearCountersEntry
        MAX-ACCESS   not-accessible
        STATUS       current
        DESCRIPTION
        "A table to clear the interface rmon counters."

    ::= { futrmon 15}

    rmonInterfaceClearCountersEntry OBJECT-TYPE
        SYNTAX       RmonInterfaceClearCountersEntry
        MAX-ACCESS   not-accessible
        STATUS       current
        DESCRIPTION
        "An entry appears in this table to clear the interface rmon counters.
         Index to the table is the interface index of the port."
        INDEX { rmonIfindex }

    ::= { rmonInterfaceClearCountersTable 1}


    RmonInterfaceClearCountersEntry  ::= SEQUENCE {
           rmonIfindex                Integer32,
           rmonInterfaceClearCounters TruthValue
        }

    rmonIfindex OBJECT-TYPE
        SYNTAX      Integer32 (1..65535)
        MAX-ACCESS  not-accessible
        STATUS      current
        DESCRIPTION
            "Interface index of the port for which the counters are to be cleared."

    ::= { rmonInterfaceClearCountersEntry 1}


    rmonInterfaceClearCounters OBJECT-TYPE
         SYNTAX      TruthValue
         MAX-ACCESS  read-write
         STATUS      current
         DESCRIPTION
         "This object is used to clear all the rmon interface counters.
         Setting this object to true will cause the statistics to be reset
         and setting this object to false will have no effect.
         A Get operation on this object will always return a value of
         false."
         DEFVAL { false }

    ::= {rmonInterfaceClearCountersEntry 2 }

      -- Extension of the etherStatsTable

    etherStatsTxTable OBJECT-TYPE
        SYNTAX     SEQUENCE OF EtherStatsTxEntry
        MAX-ACCESS not-accessible
        STATUS     current
        DESCRIPTION
        "The table is a further enhancement of etherStatsTable in stdrmon.mib
        to allow a collection of statistics kept for particular Ethernet interface."
    ::= { futrmon 16 }

    etherStatsTxEntry  OBJECT-TYPE
        SYNTAX      EtherStatsTxEntry
        MAX-ACCESS  not-accessible
        STATUS      current
        DESCRIPTION "An Entry containing Statistics information (e.g. OutUCastPkts)."
        AUGMENTS { etherStatsEntry }
    ::= { etherStatsTxTable 1 }

    EtherStatsTxEntry  ::= SEQUENCE {
         etherStatsTxOverflowOctets              Counter32,
         etherStatsTxOctets                      Counter64,
         etherStatsTxOverflowPkts                Counter32,
         etherStatsTxPkts                        Counter64,
         etherStatsTxBroadcastPkts               Counter64,
         etherStatsTxMulticastPkts               Counter64,
         etherStatsTxDiscardPkts                 Counter64
    }

    etherStatsTxOverflowOctets OBJECT-TYPE
        SYNTAX      Counter32
        MAX-ACCESS  read-only
        STATUS      current
        DESCRIPTION
        "The number of times the associated etherStatsOctets
        counter has overflowed."

    ::= { etherStatsTxEntry 1 }

    etherStatsTxOctets OBJECT-TYPE
        SYNTAX      Counter64
        MAX-ACCESS  read-only
        STATUS      current
        DESCRIPTION
        "The total number of octets of data (including
        bad packets) transmitted from the network."

    ::= { etherStatsTxEntry 2 }

    etherStatsTxOverflowPkts OBJECT-TYPE
        SYNTAX      Counter32
        MAX-ACCESS  read-only
        STATUS      current
        DESCRIPTION
        "The number of times the associated etherStatsPkts
        counter has overflowed."

    ::= { etherStatsTxEntry 3 }

    etherStatsTxPkts OBJECT-TYPE
        SYNTAX      Counter64
        MAX-ACCESS  read-only
        STATUS      current
        DESCRIPTION
        "The total number of packets (including bad
        packets) transmitted from the network."

    ::= { etherStatsTxEntry 4 }

    etherStatsTxBroadcastPkts OBJECT-TYPE
        SYNTAX      Counter64
        MAX-ACCESS  read-only
        STATUS      current
        DESCRIPTION
        "The total number of broadcast packets transmitted from the
        network. Note that this does not include multicast packets."

    ::= { etherStatsTxEntry 5 }

    etherStatsTxMulticastPkts OBJECT-TYPE
        SYNTAX      Counter64
        MAX-ACCESS  read-only
        STATUS      current
        DESCRIPTION
        "The total number of multicast packets transmitted
        from the network."

    ::= { etherStatsTxEntry 6 }

    etherStatsTxDiscardPkts OBJECT-TYPE
        SYNTAX      Counter64
        MAX-ACCESS  read-only
        STATUS      current
        DESCRIPTION
        "The number of packets to be transmitted which
        were discarded from the network."

    ::= { etherStatsTxEntry 7 }

 -- Extension for the etherHistoryTable

    etherHistoryTxTable OBJECT-TYPE
        SYNTAX      SEQUENCE OF EtherHistoryTxEntry
        MAX-ACCESS  not-accessible
        STATUS      current
        DESCRIPTION
        "The table is an enhancement of etherHistoryTable in stdrmon.mib."
    ::= { futrmon 17 }

    etherHistoryTxEntry  OBJECT-TYPE
        SYNTAX      EtherHistoryTxEntry
        MAX-ACCESS  not-accessible
        STATUS      current
        DESCRIPTION "An historical sample of Ethernet statistics on a
                    specific history control pattern."
    ::= { etherHistoryTxTable 1 }

    EtherHistoryTxEntry  ::= SEQUENCE {
         etherHistoryTxOverflowOctets             Counter32,
         etherHistoryTxOctets                     Counter64,
         etherHistoryTxOverflowPkts               Counter32,
         etherHistoryTxPkts                       Counter64,
         etherHistoryTxBroadcastPkts              Counter64,
         etherHistoryTxMulticastPkts              Counter64,
         etherHistoryTxUtilization                Integer32,
         etherHistoryTxDiscardPkts                Counter64
    }

    etherHistoryTxOverflowOctets OBJECT-TYPE
        SYNTAX      Counter32
        MAX-ACCESS  read-only
        STATUS      current
        DESCRIPTION
        "The number of times the associated etherHistoryOctets
        counter has overflowed during sampling interval."

    ::= { etherHistoryTxEntry 1 }

    etherHistoryTxOctets OBJECT-TYPE
        SYNTAX      Counter64
        MAX-ACCESS  read-only
        STATUS      current
        DESCRIPTION
        "The number of transmitted octets from the network
        during sampling interval."

    ::= { etherHistoryTxEntry 2 }

    etherHistoryTxOverflowPkts OBJECT-TYPE
        SYNTAX      Counter32
        MAX-ACCESS  read-only
        STATUS      current
        DESCRIPTION
        "The number of times the associated etherHistoryPkts
        overflowed during this sampling interval."

    ::= { etherHistoryTxEntry 3 }

    etherHistoryTxPkts OBJECT-TYPE
        SYNTAX      Counter64
        MAX-ACCESS  read-only
        STATUS      current
        DESCRIPTION
        "The number of packets transmitted during
        this sampling interval."

    ::= { etherHistoryTxEntry 4 }

    etherHistoryTxBroadcastPkts OBJECT-TYPE
        SYNTAX      Counter64
        MAX-ACCESS  read-only
        STATUS      current
        DESCRIPTION
        "The number of broadcast packets received during this
        sampling interval."

    ::= { etherHistoryTxEntry 5 }

    etherHistoryTxMulticastPkts OBJECT-TYPE
        SYNTAX      Counter64
        MAX-ACCESS  read-only
        STATUS      current
        DESCRIPTION
        "The number of good packets received during this
        sampling interval."

    ::= { etherHistoryTxEntry 6 }

    etherHistoryTxUtilization OBJECT-TYPE
        SYNTAX      Integer32 (0..10000)
        MAX-ACCESS  read-only
        STATUS      current
        DESCRIPTION
        "The best estimate of the mean physical layer
        network utilization on this interface during
        sampling interval, in hundredths of a percent."

    ::= { etherHistoryTxEntry 7 }

    etherHistoryTxDiscardPkts OBJECT-TYPE
        SYNTAX      Counter64
        MAX-ACCESS  read-only
        STATUS      current
        DESCRIPTION
        "The number of packets discarded during
        this sampling interval."

    ::= { etherHistoryTxEntry 8}
END

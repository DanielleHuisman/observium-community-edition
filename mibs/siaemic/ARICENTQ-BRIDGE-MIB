-- Copyright (C) 2015 Aricent. All Rights Reserved

-- $Id: fsmsvlan.mib,v 1.11 2016/02/18 09:47:31 siva Exp $

ARICENTQ-BRIDGE-MIB DEFINITIONS ::= BEGIN

-- -------------------------------------------------------------
-- MIB for IEEE 802.1Q Devices
-- -------------------------------------------------------------

IMPORTS
    MODULE-IDENTITY, OBJECT-TYPE,
    Counter32, Counter64, Unsigned32, TimeTicks, Integer32
        FROM SNMPv2-SMI
    RowStatus, TruthValue, TEXTUAL-CONVENTION, MacAddress
        FROM SNMPv2-TC
    SnmpAdminString
        FROM SNMP-FRAMEWORK-MIB
    fsDot1dBridge, fsDot1dBasePort
        FROM ARICENT-MIStdBRIDGE-MIB
    EnabledStatus
        FROM ARICENTP-BRIDGE-MIB
    TimeFilter
        FROM RMON2-MIB;

fsQBridgeMIB MODULE-IDENTITY
    LAST-UPDATED "201209050000Z"
    ORGANIZATION "ARICENT COMMUNICATIONS SOFTWARE"
    CONTACT-INFO "support@aricent.com"
    DESCRIPTION
        "The VLAN Bridge MIB module for managing Virtual Bridged
        Local Area Networks, with multiple instance capability."
    REVISION "201209050000Z"
    DESCRIPTION
        "The VLAN Bridge MIB module for managing Virtual Bridged
        Local Area Networks, with multiple instance capability."

    ::= { fsDot1dBridge 7 }

fsQBridgeMIBObjects OBJECT IDENTIFIER ::= { fsQBridgeMIB 1 }

-- -------------------------------------------------------------
-- Textual Conventions
-- -------------------------------------------------------------

VlanIndex ::= TEXTUAL-CONVENTION
    DISPLAY-HINT "d"
    STATUS      current
    DESCRIPTION
        "A value used to index per-VLAN tables: values of 0 and
        4095 are not permitted; if the value is between 1 and
        4094 inclusive, it represents an IEEE 802.1Q VLAN-ID with
        global scope within a given bridged domain (see VlanId
        textual convention). If the value is greater than 4095
        then it represents a VLAN with scope local to the
        particular agent, i.e. one without a global VLAN-ID
        assigned to it. Such VLANs are outside the scope of
        IEEE 802.1Q but it is convenient to be able to manage them
        in the same way using this MIB."
    SYNTAX      Unsigned32

VlanId ::= TEXTUAL-CONVENTION
    DISPLAY-HINT "d"
    STATUS      current
    DESCRIPTION
        "A 12-bit VLAN ID used in the VLAN Tag header."
    SYNTAX      Integer32 (1..4094)

-- -------------------------------------------------------------
-- groups in the Q-BRIDGE MIB
-- -------------------------------------------------------------

fsDot1qBase       OBJECT IDENTIFIER ::= { fsQBridgeMIBObjects 1 }
fsDot1qTp         OBJECT IDENTIFIER ::= { fsQBridgeMIBObjects 2 }
fsDot1qStatic     OBJECT IDENTIFIER ::= { fsQBridgeMIBObjects 3 }
fsDot1qVlan       OBJECT IDENTIFIER ::= { fsQBridgeMIBObjects 4 }
fsDot1vProtocol   OBJECT IDENTIFIER ::= { fsQBridgeMIBObjects 5 }

-- -------------------------------------------------------------
-- fsDot1qBase group
-- -------------------------------------------------------------

fsDot1qBaseTable OBJECT-TYPE
   SYNTAX        SEQUENCE OF FsDot1qBaseEntry
   MAX-ACCESS    not-accessible
   STATUS        current
   DESCRIPTION
      "List of fsDot1qBase objects that can be configured per 
      virtual context in the system."
   ::= { fsDot1qBase 1 }

fsDot1qBaseEntry OBJECT-TYPE
   SYNTAX        FsDot1qBaseEntry
   MAX-ACCESS    not-accessible
   STATUS        current
   DESCRIPTION
      "Virtual context fsDot1qBase objects."
   INDEX { fsDot1qVlanContextId }
   ::= { fsDot1qBaseTable 1 }

FsDot1qBaseEntry ::=
    SEQUENCE {
        fsDot1qVlanContextId
           Integer32,
        fsDot1qVlanVersionNumber
           INTEGER,
        fsDot1qMaxVlanId 
           VlanId,
        fsDot1qMaxSupportedVlans 
           Unsigned32,
        fsDot1qNumVlans 
           Unsigned32,
        fsDot1qGvrpStatus 
           EnabledStatus
}

fsDot1qVlanContextId OBJECT-TYPE
   SYNTAX       Integer32 (0..65535)
   MAX-ACCESS   not-accessible
   STATUS       current
   DESCRIPTION
      "Identifies a virtual context."
   ::= { fsDot1qBaseEntry 1 }

fsDot1qVlanVersionNumber OBJECT-TYPE
    SYNTAX      INTEGER {
                    version1(1)
                }
    MAX-ACCESS  read-only
    STATUS      current
    DESCRIPTION
        "The version number of IEEE 802.1Q that this device
        supports."
    REFERENCE
        "IEEE 802.1Q/D11 Section 12.10.1.1"
    ::= { fsDot1qBaseEntry 2 }

fsDot1qMaxVlanId OBJECT-TYPE
    SYNTAX      VlanId
    MAX-ACCESS  read-only
    STATUS      current
    DESCRIPTION
        "The maximum IEEE 802.1Q VLAN ID that this device
        supports."
    REFERENCE
        "IEEE 802.1Q/D11 Section 9.3.2.3"
    ::= { fsDot1qBaseEntry 3 }

fsDot1qMaxSupportedVlans OBJECT-TYPE
    SYNTAX      Unsigned32
    MAX-ACCESS  read-only
    STATUS      current
    DESCRIPTION
        "The maximum number of IEEE 802.1Q VLANs that this
        device supports."
    REFERENCE
        "IEEE 802.1Q/D11 Section 12.10.1.1"
    ::= { fsDot1qBaseEntry 4 }

fsDot1qNumVlans OBJECT-TYPE
    SYNTAX      Unsigned32
    MAX-ACCESS  read-only
    STATUS      current
    DESCRIPTION
        "The current number of IEEE 802.1Q VLANs that are
        configured in this device."
    REFERENCE
        "IEEE 802.1Q/D11 Section 12.7.1.1"
    ::= { fsDot1qBaseEntry 5 }

fsDot1qGvrpStatus OBJECT-TYPE
    SYNTAX      EnabledStatus
    MAX-ACCESS  read-write
    STATUS      current
    DESCRIPTION
        "The administrative status requested by management for
        GVRP. The value enabled(1) indicates that GVRP should
        be enabled on this device, on all ports for which it has
        not been specifically disabled. When disabled(2), GVRP
        is disabled on all ports and all GVRP packets will be
        forwarded transparently. This object affects all GVRP
        Applicant and Registrar state machines. A transition
        from disabled(2) to enabled(1) will cause a reset of all
        GVRP state machines on all ports. By default, this will be enabled for 
        default context and it will be disabled for other contexts."
    ::= { fsDot1qBaseEntry 6 }

-- -------------------------------------------------------------
-- the fsDot1qTp group
-- -------------------------------------------------------------

fsDot1qFdbTable OBJECT-TYPE
    SYNTAX      SEQUENCE OF FsDot1qFdbEntry
    MAX-ACCESS  not-accessible
    STATUS      current
    DESCRIPTION
        "A table that contains configuration and control
        information for each Filtering Database currently
        operating on this device. Entries in this table appear
        automatically when VLANs are assigned FDB IDs in the
        fsDot1qVlanCurrentTable. This table maintains context ID
        as one more index to support Multiple Instances."
    ::= { fsDot1qTp 1 }

fsDot1qFdbEntry OBJECT-TYPE
    SYNTAX      FsDot1qFdbEntry
    MAX-ACCESS  not-accessible
    STATUS      current
    DESCRIPTION
        "Information about a specific Filtering Database."
    INDEX   { fsDot1qVlanContextId, fsDot1qFdbId }
    ::= { fsDot1qFdbTable 1 }

FsDot1qFdbEntry ::=
    SEQUENCE {
        fsDot1qFdbId
            Unsigned32,
        fsDot1qFdbDynamicCount
            Counter32
    }

fsDot1qFdbId OBJECT-TYPE
    SYNTAX       Unsigned32
    MAX-ACCESS   not-accessible
    STATUS       current
    DESCRIPTION
        "The identity of this Filtering Database."
    ::= { fsDot1qFdbEntry 1 }

fsDot1qFdbDynamicCount OBJECT-TYPE
    SYNTAX       Counter32
    MAX-ACCESS   read-only
    STATUS       current
    DESCRIPTION
        "The current number of dynamic entries in this
        Filtering Database."
    REFERENCE
        "IEEE 802.1Q/D11 Section 12.7.1.1.3"
    ::= { fsDot1qFdbEntry 2 }

-- -------------------------------------------------------------
-- Multiple Forwarding Databases for 802.1Q Transparent devices
-- This table is an alternative to the fsDot1dTpFdbTable,
-- previously defined for 802.1D devices which only support a
-- single Forwarding Database.
-- -------------------------------------------------------------

fsDot1qTpFdbTable OBJECT-TYPE
    SYNTAX      SEQUENCE OF FsDot1qTpFdbEntry
    MAX-ACCESS  not-accessible
    STATUS      current
    DESCRIPTION
        "A table that contains information about unicast entries
        for which the device has forwarding and/or filtering
        information. This information is used by the
        transparent bridging function in determining how to
        propagate a received frame. This table maintains context ID
        as one more index to support Multiple Instances."
    REFERENCE
        "IEEE 802.1Q/D11 Section 12.7.7"
    ::= { fsDot1qTp 2 }

fsDot1qTpFdbEntry OBJECT-TYPE
    SYNTAX      FsDot1qTpFdbEntry
    MAX-ACCESS  not-accessible
    STATUS      current
    DESCRIPTION
        "Information about a specific unicast MAC address for
        which the device has some forwarding and/or filtering
        information."
    INDEX   { fsDot1qVlanContextId, fsDot1qFdbId, fsDot1qTpFdbAddress }
    ::= { fsDot1qTpFdbTable 1 }

FsDot1qTpFdbEntry ::=
    SEQUENCE {
        fsDot1qTpFdbAddress
            MacAddress,
        fsDot1qTpFdbPort
            Integer32,
        fsDot1qTpFdbStatus
            INTEGER,
        fsDot1qTpFdbPw
            Unsigned32
    }

fsDot1qTpFdbAddress OBJECT-TYPE
    SYNTAX      MacAddress
    MAX-ACCESS  not-accessible
    STATUS      current
    DESCRIPTION
        "A unicast MAC address for which the device has
        forwarding and/or filtering information."
    ::= { fsDot1qTpFdbEntry 1 }

fsDot1qTpFdbPort OBJECT-TYPE
    SYNTAX      Integer32 (0..65535)
    MAX-ACCESS  read-only
    STATUS      current
    DESCRIPTION
        "Either the value '0', or the port number of the port on
        which a frame having a source address equal to the value
        of the corresponding instance of fsDot1qTpFdbAddress has
        been seen. A value of '0' indicates that the port
        number has not been learned but that the device does
        have some forwarding/filtering information about this
        address (e.g. in the fsDot1qStaticUnicastTable).
        Implementers are encouraged to assign the port value to
        this object whenever it is learned even for addresses
        for which the corresponding value of fsDot1qTpFdbStatus is
        not learned(3)."
    ::= { fsDot1qTpFdbEntry 2 }

fsDot1qTpFdbStatus OBJECT-TYPE
    SYNTAX      INTEGER {
                    other(1),
                    invalid(2),
                    learned(3),
                    self(4),
                    mgmt(5)
                }
    MAX-ACCESS  read-only
    STATUS      current
    DESCRIPTION
        "The object specifies the status of this entry. The meanings of the
         values are:
            other(1) - none of the following. This may include
                the case where some other MIB object (not the
                corresponding instance of fsDot1qTpFdbPort, nor an
                entry in the fsDot1qStaticUnicastTable) is being
                used to determine if and how frames addressed to
                the value of the corresponding instance of
                fsDot1qTpFdbAddress are being forwarded.
            invalid(2) - this entry is no longer valid (e.g., it
                was learned but has since aged out), but has not
                yet been flushed from the table.
            learned(3) - the value of the corresponding instance
                of fsDot1qTpFdbPort was learned and is being used.
            self(4) - the value of the corresponding instance of
                fsDot1qTpFdbAddress represents one of the device's
                addresses. The corresponding instance of
                fsDot1qTpFdbPort indicates which of the device's
                ports has this address.
            mgmt(5) - the value of the corresponding instance of
                fsDot1qTpFdbAddress is also the value of an
                existing instance of fsDot1qStaticAddress."
    ::= { fsDot1qTpFdbEntry 3 }

fsDot1qTpFdbPw OBJECT-TYPE
    SYNTAX      Unsigned32
    MAX-ACCESS  read-only
    STATUS      current
    DESCRIPTION
        "Either the value '0', or the pseudowire number on
        which a frame having a source address equal to the value
        of the corresponding instance of dot1qTpFdbAddress has
        been seen. A value of '0' indicates that the entry was
        learned via the layer2 port. Non-zero value indicates
        that this value must be used for forwarding irrespective
        of dot1qTpFdbPort."
    ::= { fsDot1qTpFdbEntry 4 }

-- -------------------------------------------------------------
-- Dynamic Group Registration Table
-- -------------------------------------------------------------

fsDot1qTpGroupTable OBJECT-TYPE
    SYNTAX      SEQUENCE OF FsDot1qTpGroupEntry
    MAX-ACCESS  not-accessible
    STATUS      current
    DESCRIPTION
        "A table containing filtering information for VLANs
        configured into the bridge by (local or network)
        management, or learnt dynamically, specifying the set of
        ports to which frames received on a VLAN for this FDB
        and containing a specific Group destination address are
        allowed to be forwarded. This table maintains context ID 
	as one more index to support Multiple Instances."
    ::= { fsDot1qTp 3 }

fsDot1qTpGroupEntry OBJECT-TYPE
    SYNTAX      FsDot1qTpGroupEntry
    MAX-ACCESS  not-accessible
    STATUS      current
    DESCRIPTION
        "Filtering information configured into the bridge by
        management, or learnt dynamically, specifying the set of
        ports to which frames received on a VLAN and containing
        a specific Group destination address, are allowed to be
        forwarded. The subset of these ports learnt dynamically
        is also provided."
    INDEX   { fsDot1qVlanContextId, 
              fsDot1qVlanIndex, fsDot1qTpGroupAddress, fsDot1qTpPort }
    ::= { fsDot1qTpGroupTable 1 }

FsDot1qTpGroupEntry ::=
    SEQUENCE {
        fsDot1qVlanIndex
	    VlanIndex,
        fsDot1qTpGroupAddress
            MacAddress,
	fsDot1qTpPort
	    Integer32,
        fsDot1qTpGroupIsLearnt
            TruthValue
    }
    
fsDot1qVlanIndex OBJECT-TYPE
    SYNTAX      VlanIndex
    MAX-ACCESS  not-accessible
    STATUS      current
    DESCRIPTION
        "The VLAN-ID or other identifier referring to this VLAN."
    ::= { fsDot1qTpGroupEntry 1 }

fsDot1qTpGroupAddress OBJECT-TYPE
    SYNTAX      MacAddress
    MAX-ACCESS  not-accessible
    STATUS      current
    DESCRIPTION
        "The destination Group MAC address in a frame to which
        this entry's filtering information applies."
    ::= { fsDot1qTpGroupEntry 2 }

fsDot1qTpPort OBJECT-TYPE 
    SYNTAX      Integer32 (1..65535) 
    MAX-ACCESS  not-accessible 
    STATUS      current 
    DESCRIPTION 
       "The port number of the port for which this entry applies." 
    ::= { fsDot1qTpGroupEntry 3 }

fsDot1qTpGroupIsLearnt OBJECT-TYPE
    SYNTAX      TruthValue
    MAX-ACCESS  read-only
    STATUS      current
    DESCRIPTION
        "Indicates whether the port is statically configured or a 
	dynamic member of the Group address learnt through GMRP."  
    ::= { fsDot1qTpGroupEntry 4 }


-- -------------------------------------------------------------
-- Service Requirements Group
-- -------------------------------------------------------------

fsDot1qForwardAllLearntPortTable OBJECT-TYPE
    SYNTAX      SEQUENCE OF FsDot1qForwardAllLearntPortEntry
    MAX-ACCESS  not-accessible
    STATUS      current
    DESCRIPTION
        "A table containing the Learnt-Port details of the 
	forwarding information for each VLAN. This table 
	maintains context ID as one more index to support 
	Multiple Instances." 
    REFERENCE
        "IEEE 802.1Q/D11 Section 12.7.2, 12.7.7"
    ::= { fsDot1qTp 4 }

fsDot1qForwardAllLearntPortEntry OBJECT-TYPE
    SYNTAX      FsDot1qForwardAllLearntPortEntry
    MAX-ACCESS  not-accessible
    STATUS      current
    DESCRIPTION
        "Information about a forwardall port, Whether the port 
	is learnt dynamically by GMRP."
    INDEX   { fsDot1qVlanContextId, fsDot1qVlanIndex, fsDot1qTpPort }
    ::= { fsDot1qForwardAllLearntPortTable 1 }

FsDot1qForwardAllLearntPortEntry ::=
    SEQUENCE {
        fsDot1qForwardAllIsLearnt
            TruthValue
    }

fsDot1qForwardAllIsLearnt OBJECT-TYPE
    SYNTAX      TruthValue
    MAX-ACCESS  read-only
    STATUS      current
    DESCRIPTION
        "Indicates whether the forwardall port is learnt 
	dynamically using GMRP."
    ::= { fsDot1qForwardAllLearntPortEntry 1 }


fsDot1qForwardAllStatusTable OBJECT-TYPE
    SYNTAX      SEQUENCE OF FsDot1qForwardAllStatusEntry
    MAX-ACCESS  not-accessible
    STATUS      current
    DESCRIPTION
        "This table is used to maintain the status of static 
	and forbidden portlist required in ForwardAll table 
	for VLAN. This table maintains context ID as one more 
	index to support Multiple Instances."
    ::= { fsDot1qTp 5 }

fsDot1qForwardAllStatusEntry OBJECT-TYPE
    SYNTAX      FsDot1qForwardAllStatusEntry
    MAX-ACCESS  not-accessible
    STATUS      current
    DESCRIPTION
        "An entry to specify the status of static and 
	forbidden portlist in ForwardAll Table."
    INDEX   { fsDot1qVlanContextId, fsDot1qVlanIndex }
    ::= { fsDot1qForwardAllStatusTable 1 }

FsDot1qForwardAllStatusEntry ::=
    SEQUENCE {
        fsDot1qForwardAllRowStatus
            RowStatus
    }

fsDot1qForwardAllRowStatus OBJECT-TYPE
    SYNTAX      RowStatus
    MAX-ACCESS  read-create
    STATUS      current
    DESCRIPTION
        "This object indicates the status of the PortLists
	(Static, Forbidden) used in the forwarding 
	information of a VLAN (ForwardAll). To fill the
        static and forbidden portlist, we have to set the
        rowstatus as 'NOT_IN_SERVICE' and set the appropriate
        port in the fsDot1qForwardUnregPortConfigTable and
        set the rowstatus as 'ACTIVE' to make the portlist
        available."
    ::= { fsDot1qForwardAllStatusEntry 1 }


fsDot1qForwardAllPortConfigTable OBJECT-TYPE
    SYNTAX      SEQUENCE OF FsDot1qForwardAllPortConfigEntry
    MAX-ACCESS  not-accessible
    STATUS      current
    DESCRIPTION
        "A table containing the	forwarding information of static 
	ports and forbidden ports for each VLAN. This table
	maintains context ID as one more index to support
	Multiple Instances." 
    REFERENCE
        "IEEE 802.1Q/D11 Section 12.7.2, 12.7.7"
    ::= { fsDot1qTp 6 }

fsDot1qForwardAllPortConfigEntry OBJECT-TYPE
    SYNTAX      FsDot1qForwardAllPortConfigEntry
    MAX-ACCESS  not-accessible
    STATUS      current
    DESCRIPTION
        "Forwarding information about a port, Whether it is a 
	member or a forbidden member."
    INDEX   { fsDot1qVlanContextId, fsDot1qVlanIndex, fsDot1qTpPort }
    ::= { fsDot1qForwardAllPortConfigTable 1 }

FsDot1qForwardAllPortConfigEntry ::=
    SEQUENCE {
        fsDot1qForwardAllPort
            INTEGER
    }

fsDot1qForwardAllPort OBJECT-TYPE
    SYNTAX      INTEGER  {
                    addMember(1),
                    addForbidden(2),
                    delMember(3),
		    delForbidden(4)
                }
    MAX-ACCESS  read-write
    STATUS      current
    DESCRIPTION
        "Indicates whether the port is a member or a forbidden 
	member in the forwarding information for this VLAN.
	  'addMember'    - to add the port in the static 
	                   member-list.
	  'addForbidden' - to add the port in the forbidden 
	                   member-list.
	  'delMember'    - to remove the port from the static 
	                   member-list.
	  'delForbidden' - to remove the port from the forbidden
	                   member-list."
    ::= { fsDot1qForwardAllPortConfigEntry 1 }


fsDot1qForwardUnregLearntPortTable OBJECT-TYPE
    SYNTAX      SEQUENCE OF FsDot1qForwardUnregLearntPortEntry
    MAX-ACCESS  not-accessible
    STATUS      current
    DESCRIPTION
        "A table containing the Learnt-Port details to which 
	forwarding of multicast group-addressed	frames for 
	which there is no more specific forwarding information 
	applies (per VLAN). This table maintains context ID as 
	one more index to support Multiple Instances." 
    REFERENCE
        "IEEE 802.1Q/D11 Section 12.7.2, 12.7.7"
    ::= { fsDot1qTp 7 }

fsDot1qForwardUnregLearntPortEntry OBJECT-TYPE
    SYNTAX      FsDot1qForwardUnregLearntPortEntry
    MAX-ACCESS  not-accessible
    STATUS      current
    DESCRIPTION
        "Information about a forwardUnreg port, Whether the port 
	is learnt dynamically by GMRP."
    INDEX   { fsDot1qVlanContextId, fsDot1qVlanIndex, fsDot1qTpPort }
    ::= { fsDot1qForwardUnregLearntPortTable 1 }

FsDot1qForwardUnregLearntPortEntry ::=
    SEQUENCE {
        fsDot1qForwardUnregIsLearnt
            TruthValue
    }

fsDot1qForwardUnregIsLearnt OBJECT-TYPE
    SYNTAX      TruthValue
    MAX-ACCESS  read-only
    STATUS      current
    DESCRIPTION
        "Indicates whether the ForwardUnreg port is learnt 
	dynamically using GMRP."
    ::= { fsDot1qForwardUnregLearntPortEntry 1 }


fsDot1qForwardUnregStatusTable OBJECT-TYPE
    SYNTAX      SEQUENCE OF FsDot1qForwardUnregStatusEntry
    MAX-ACCESS  not-accessible
    STATUS      current
    DESCRIPTION
        "This table is used to maintain the status of static 
	and forbidden portlist required in ForwardUnreg table 
	for VLAN. This table maintains context ID as one more 
	index to support Multiple Instances."
    ::= { fsDot1qTp 8 }

fsDot1qForwardUnregStatusEntry OBJECT-TYPE
    SYNTAX      FsDot1qForwardUnregStatusEntry
    MAX-ACCESS  not-accessible
    STATUS      current
    DESCRIPTION
        "An entry to specify the status of static and 
	forbidden portlist in ForwardUnreg table."
    INDEX   { fsDot1qVlanContextId, fsDot1qVlanIndex }
    ::= { fsDot1qForwardUnregStatusTable 1 }

FsDot1qForwardUnregStatusEntry ::=
    SEQUENCE {
        fsDot1qForwardUnregRowStatus
            RowStatus
    }

fsDot1qForwardUnregRowStatus OBJECT-TYPE
    SYNTAX      RowStatus
    MAX-ACCESS  read-create
    STATUS      current
    DESCRIPTION
        "This object indicates the status of the PortLists
	(Static, Forbidden) used in the forwarding 
	information of a VLAN (ForwardUnreg). To fill the 
	static and forbidden portlist, we have to set the 
	rowstatus as 'NOT_IN_SERVICE' and set the appropriate
	port in the fsDot1qForwardUnregPortConfigTable and 
	set the rowstatus as 'ACTIVE' to make the portlist 
	available."
    ::= { fsDot1qForwardUnregStatusEntry 1 }


fsDot1qForwardUnregPortConfigTable OBJECT-TYPE
    SYNTAX      SEQUENCE OF FsDot1qForwardUnregPortConfigEntry
    MAX-ACCESS  not-accessible
    STATUS      current
    DESCRIPTION
        "A table containing the	information of static ports 
	and forbidden ports to which forwarding of multicast 
	group-addressed frames for which there is no more 
	specific forwarding information applies (per VLAN). 
	This table maintains context ID as one more index to 
	support Multiple Instances." 
    REFERENCE
        "IEEE 802.1Q/D11 Section 12.7.2, 12.7.7"
    ::= { fsDot1qTp 9 }

fsDot1qForwardUnregPortConfigEntry OBJECT-TYPE
    SYNTAX      FsDot1qForwardUnregPortConfigEntry
    MAX-ACCESS  not-accessible
    STATUS      current
    DESCRIPTION
        "Forwarding information about a port, Whether it is a 
	member or a forbidden member."
    INDEX   { fsDot1qVlanContextId, fsDot1qVlanIndex, fsDot1qTpPort }
    ::= { fsDot1qForwardUnregPortConfigTable 1 }

FsDot1qForwardUnregPortConfigEntry ::=
    SEQUENCE {
        fsDot1qForwardUnregPort
            INTEGER
    }

fsDot1qForwardUnregPort OBJECT-TYPE
    SYNTAX      INTEGER  {
                    addMember(1),
                    addForbidden(2),
                    delMember(3),
		    delForbidden(4)
                }
    MAX-ACCESS  read-write
    STATUS      current
    DESCRIPTION
        "Indicates whether the port is a member or a forbidden 
	member in the forwarding information for this VLAN.
	  'addMember'    - to add the port in the static 
	                   member-list.
	  'addForbidden' - to add the port in the forbidden 
	                   member-list.
	  'delMember'    - to remove the port from the static 
	                   member-list.
	  'delForbidden' - to remove the port from the forbidden
	                   member-list."
    ::= { fsDot1qForwardUnregPortConfigEntry 1 }


-- -------------------------------------------------------------
-- The Static (Destination-Address Filtering) Database
-- -------------------------------------------------------------

fsDot1qStaticUnicastTable OBJECT-TYPE
    SYNTAX      SEQUENCE OF FsDot1qStaticUnicastEntry
    MAX-ACCESS  not-accessible
    STATUS      current
    DESCRIPTION
        "A table containing filtering information for Unicast
        MAC addresses for each Filtering Database, configured
        into the device by (local or network) management
        specifying the set of ports to which frames received
        from specific ports and containing specific unicast
        destination addresses are allowed to be forwarded. A
        value of zero in this table as the port number from
        which frames with a specific destination address are
        received, is used to specify all ports for which there
        is no specific entry in this table for that particular
        destination address. Entries are valid for unicast
        addresses only. This table maintains context ID as 
	one more index to support Multiple Instances."
    REFERENCE
        "IEEE 802.1Q/D11 Section 12.7.7,
        ISO/IEC 15802-3 Section 7.9.1"
    ::= { fsDot1qStatic 1 }

fsDot1qStaticUnicastEntry OBJECT-TYPE
    SYNTAX      FsDot1qStaticUnicastEntry
    MAX-ACCESS  not-accessible
    STATUS      current
    DESCRIPTION
        "Filtering information configured into the device by
        (local or network) management specifying the set of
        ports to which frames received from a specific port and
        containing a specific unicast destination address are
        allowed to be forwarded."
    INDEX   {
        fsDot1qVlanContextId, 
	fsDot1qFdbId,
        fsDot1qStaticUnicastAddress,
        fsDot1qStaticUnicastReceivePort
    }
    ::= { fsDot1qStaticUnicastTable 1 }

FsDot1qStaticUnicastEntry ::=
    SEQUENCE {
        fsDot1qStaticUnicastAddress
            MacAddress,
        fsDot1qStaticUnicastReceivePort
            Integer32,
        fsDot1qStaticUnicastRowStatus
            RowStatus,
        fsDot1qStaticUnicastStatus
            INTEGER
    }

fsDot1qStaticUnicastAddress OBJECT-TYPE
    SYNTAX      MacAddress
    MAX-ACCESS  not-accessible
    STATUS      current
    DESCRIPTION
        "The destination MAC address in a frame to which this
        entry's filtering information applies. This object must
        take the value of a unicast address."
    ::= { fsDot1qStaticUnicastEntry 1 }

fsDot1qStaticUnicastReceivePort OBJECT-TYPE
    SYNTAX      Integer32 (0..65535)
    MAX-ACCESS  not-accessible
    STATUS      current
    DESCRIPTION
        "Either the value '0', or the port number of the port
        from which a frame must be received in order for this
        entry's filtering information to apply. A value of zero
        indicates that this entry applies on all ports of the
        device for which there is no other applicable entry."
    ::= { fsDot1qStaticUnicastEntry 2 }

fsDot1qStaticUnicastRowStatus OBJECT-TYPE
    SYNTAX      RowStatus
    MAX-ACCESS  read-create
    STATUS      current
    DESCRIPTION
        "This object indicates the status of the AllowedToGoTo
	PortList to which a frame with a specific unicast 
	address will be flooded in the event that it has not 
	been learned. To fill the AllowedToGoTo portlist, 
	we have to set the rowstatus as 'NOT_IN_SERVICE' and 
	set the appropriate port in the 
	fsDot1qStaticAllowedToGoTable and set the rowstatus as 
	'ACTIVE' to make the portlist available."
    ::= { fsDot1qStaticUnicastEntry 3 }

fsDot1qStaticUnicastStatus OBJECT-TYPE
    SYNTAX      INTEGER {
                    other(1),
                    invalid(2),
                    permanent(3),
                    deleteOnReset(4),
                    deleteOnTimeout(5)
                }
    MAX-ACCESS  read-write
    STATUS      current
    DESCRIPTION
        "This object indicates the status of this entry.
            other(1) - this entry is currently in use but
                the conditions under which it will remain
                so differ from the following values.
            invalid(2) - writing this value to the object
                removes the corresponding entry.
            permanent(3) - this entry is currently in use
                and will remain so after the next reset of
                the bridge.
            deleteOnReset(4) - this entry is currently in
                use and will remain so until the next
                reset of the bridge.
            deleteOnTimeout(5) - this entry is currently in
                use and will remain so until it is aged out."
    DEFVAL      { permanent }
    ::= { fsDot1qStaticUnicastEntry 4 }

fsDot1qStaticAllowedToGoTable OBJECT-TYPE
    SYNTAX      SEQUENCE OF FsDot1qStaticAllowedToGoEntry
    MAX-ACCESS  not-accessible
    STATUS      current
    DESCRIPTION
        "A table containing the information of AllowedToGoTo
        ports for each static unicast entry. This table
        maintains context ID as one more index to support
        Multiple Instances."
    REFERENCE
        "IEEE 802.1Q/D11 Table 8-5, ISO/IEC 15802-3 Table 7-5"
    ::= { fsDot1qStatic 2 }

fsDot1qStaticAllowedToGoEntry OBJECT-TYPE
    SYNTAX      FsDot1qStaticAllowedToGoEntry
    MAX-ACCESS  not-accessible
    STATUS      current
    DESCRIPTION
        "Information about a port, Whether it is an AllowedToGoTo
        member or not."
    INDEX   {
        fsDot1qVlanContextId,
        fsDot1qFdbId,
        fsDot1qStaticUnicastAddress,
        fsDot1qStaticUnicastReceivePort,
        fsDot1qTpPort
    }
    ::= { fsDot1qStaticAllowedToGoTable 1 }

FsDot1qStaticAllowedToGoEntry ::=
    SEQUENCE {
        fsDot1qStaticAllowedIsMember
            TruthValue
    }

fsDot1qStaticAllowedIsMember OBJECT-TYPE
    SYNTAX      TruthValue
    MAX-ACCESS  read-write
    STATUS      current
    DESCRIPTION
        "Indicates whether the port is an allowedToGoTo member."
    REFERENCE
        "IEEE 802.1Q/D11 Table 8-5, ISO/IEC 15802-3 Table 7-5"
    ::= { fsDot1qStaticAllowedToGoEntry 1 }


fsDot1qStaticMulticastTable OBJECT-TYPE
    SYNTAX      SEQUENCE OF FsDot1qStaticMulticastEntry
    MAX-ACCESS  not-accessible
    STATUS      current
    DESCRIPTION
        "A table containing filtering information for Multicast
        and Broadcast MAC addresses for each VLAN, configured
        into the device by (local or network) management
        specifying the set of ports to which frames received
        from specific ports and containing specific Multicast
        and Broadcast destination addresses are allowed to be
        forwarded. A value of zero in this table as the port
        number from which frames with a specific destination
        address are received, is used to specify all ports for
        which there is no specific entry in this table for that
        particular destination address. Entries are valid for
        Multicast and Broadcast addresses only. This table
        maintains context ID as one more index to support
        Multiple Instances." 
    REFERENCE
        "IEEE 802.1Q/D11 Section 12.7.7,
        ISO/IEC 15802-3 Section 7.9.1"
    ::= { fsDot1qStatic 3 }

fsDot1qStaticMulticastEntry OBJECT-TYPE
    SYNTAX      FsDot1qStaticMulticastEntry
    MAX-ACCESS  not-accessible
    STATUS      current
    DESCRIPTION
        "Filtering information configured into the device by
        (local or network) management specifying the set of
        ports to which frames received from this specific port
        for this VLAN and containing this Multicast or Broadcast
        destination address are allowed to be forwarded."
    INDEX   {
        fsDot1qVlanContextId,
        fsDot1qVlanIndex,
        fsDot1qStaticMulticastAddress,
        fsDot1qStaticMulticastReceivePort
    }
    ::= { fsDot1qStaticMulticastTable 1 }

FsDot1qStaticMulticastEntry ::=
    SEQUENCE {
        fsDot1qStaticMulticastAddress
            MacAddress,
        fsDot1qStaticMulticastReceivePort
            Integer32,
        fsDot1qStaticMulticastRowStatus
            RowStatus,
        fsDot1qStaticMulticastStatus
            INTEGER
    }

fsDot1qStaticMulticastAddress OBJECT-TYPE
    SYNTAX      MacAddress
    MAX-ACCESS  not-accessible
    STATUS      current
    DESCRIPTION
        "The destination MAC address in a frame to which this
        entry's filtering information applies. This object must
        take the value of a Multicast or Broadcast address."
    ::= { fsDot1qStaticMulticastEntry 1 }

fsDot1qStaticMulticastReceivePort OBJECT-TYPE
    SYNTAX      Integer32 (0..65535)
    MAX-ACCESS  not-accessible
    STATUS      current
    DESCRIPTION
        "Either the value '0', or the port number of the port
        from which a frame must be received in order for this
        entry's filtering information to apply. A value of zero
        indicates that this entry applies on all ports of the
        device for which there is no other applicable entry."
    ::= { fsDot1qStaticMulticastEntry 2 }

fsDot1qStaticMulticastRowStatus OBJECT-TYPE
    SYNTAX      RowStatus
    MAX-ACCESS  read-create
    STATUS      current
    DESCRIPTION
        "This object indicates the status of the PortLists
        (Eggress, Forbidden) used in the static multicast 
        table. To fill the eggress and forbidden portlist, 
	we have to set the rowstatus as 'NOT_IN_SERVICE' 
	and set the appropriate port in the 
	fsDot1qForwardUnregPortConfigTable and set the 
	rowstatus as 'ACTIVE' to make the portlist available."
    ::= { fsDot1qStaticMulticastEntry 3 }

fsDot1qStaticMulticastStatus OBJECT-TYPE
    SYNTAX      INTEGER {
                    other(1),
                    invalid(2),
                    permanent(3),
                    deleteOnReset(4),
                    deleteOnTimeout(5)
                }
    MAX-ACCESS  read-write
    STATUS      current
    DESCRIPTION
        "This object indicates the status of this entry.
            other(1) - this entry is currently in use but
                the conditions under which it will remain
                so differ from the following values.
            invalid(2) - writing this value to the object
                removes the corresponding entry.
            permanent(3) - this entry is currently in use
                and will remain so after the next reset of
                the bridge.
            deleteOnReset(4) - this entry is currently in
                use and will remain so until the next
                reset of the bridge.
            deleteOnTimeout(5) - this entry is currently in
                use and will remain so until it is aged out."
    DEFVAL      { permanent }
    ::= { fsDot1qStaticMulticastEntry 4 }

fsDot1qStaticMcastPortTable OBJECT-TYPE
    SYNTAX      SEQUENCE OF FsDot1qStaticMcastPortEntry
    MAX-ACCESS  not-accessible
    STATUS      current
    DESCRIPTION
        "A table containing egress and forbidden ports for 
        static multicast entry. This table maintains context 
        ID as one more index to support Multiple Instance."
    ::= { fsDot1qStatic 4 }

fsDot1qStaticMcastPortEntry OBJECT-TYPE
    SYNTAX      FsDot1qStaticMcastPortEntry
    MAX-ACCESS  not-accessible
    STATUS      current
    DESCRIPTION
        "Information about a port, Whether it is a member or 
        a forbidden member."
    INDEX   {
        fsDot1qVlanContextId,
        fsDot1qVlanIndex,
        fsDot1qStaticMulticastAddress,
        fsDot1qStaticMulticastReceivePort,
        fsDot1qTpPort
    }
    ::= { fsDot1qStaticMcastPortTable 1 }

FsDot1qStaticMcastPortEntry ::=
    SEQUENCE {
        fsDot1qStaticMcastPort
            INTEGER
    }

fsDot1qStaticMcastPort OBJECT-TYPE
    SYNTAX      INTEGER  {
                    addMember(1),
                    addForbidden(2),
                    delMember(3),
		    delForbidden(4)
                }
    MAX-ACCESS  read-write
    STATUS      current
    DESCRIPTION
        "Indicates whether the port is a member or a forbidden
        member in the static multicast entry.
          'addMember'    - to add the port in the egress
                           member-list.
          'addForbidden' - to add the port in the forbidden
                           member-list.
          'delMember'    - to remove the port from the egress
                           member-list.
          'delForbidden' - to remove the port from the forbidden
                           member-list."
    ::= { fsDot1qStaticMcastPortEntry 1 }


-- -------------------------------------------------------------
-- The Current VLAN Database
-- -------------------------------------------------------------

fsDot1qVlanNumDeletesTable OBJECT-TYPE
   SYNTAX      SEQUENCE OF FsDot1qVlanNumDeletesEntry
   MAX-ACCESS  not-accessible
   STATUS      current
   DESCRIPTION
      "Table containing number of VLAN deletions in the VLAN 
      current database. This table maintains context ID as index 
      to support Multiple Instances."
   ::= { fsDot1qVlan 1 }

fsDot1qVlanNumDeletesEntry OBJECT-TYPE
   SYNTAX        FsDot1qVlanNumDeletesEntry
   MAX-ACCESS    not-accessible
   STATUS        current
   DESCRIPTION
      "Entry for a virtual context."
   INDEX { fsDot1qVlanContextId }
   ::= { fsDot1qVlanNumDeletesTable 1 }

FsDot1qVlanNumDeletesEntry ::=
   SEQUENCE {
       fsDot1qVlanNumDeletes
          Counter32
   }

fsDot1qVlanNumDeletes OBJECT-TYPE
    SYNTAX     Counter32
    MAX-ACCESS read-only
    STATUS     current
    DESCRIPTION
        "The number of times a VLAN entry has been deleted from
        the fsDot1qVlanCurrentTable (for any reason). If an entry
        is deleted, then inserted, and then deleted, this
        counter will be incremented by 2."
    ::= { fsDot1qVlanNumDeletesEntry 1 }


fsDot1qVlanCurrentTable OBJECT-TYPE
    SYNTAX      SEQUENCE OF FsDot1qVlanCurrentEntry
    MAX-ACCESS  not-accessible
    STATUS      current
    DESCRIPTION
        "A table containing current configuration information
        for each VLAN currently configured into the device by
        (local or network) management, or dynamically created
        as a result of GVRP requests received. This table
        maintains context ID as one more index to support
        Multiple Instances."
    ::= { fsDot1qVlan 2 }

fsDot1qVlanCurrentEntry OBJECT-TYPE
    SYNTAX      FsDot1qVlanCurrentEntry
    MAX-ACCESS  not-accessible
    STATUS      current
    DESCRIPTION
        "Information for a VLAN configured into the device by
        (local or network) management, or dynamically created
        as a result of GVRP requests received."
    INDEX   { fsDot1qVlanContextId, fsDot1qVlanTimeMark, fsDot1qVlanIndex }
    ::= { fsDot1qVlanCurrentTable 1 }

FsDot1qVlanCurrentEntry ::=
    SEQUENCE {
        fsDot1qVlanTimeMark
            TimeFilter,
        fsDot1qVlanFdbId
            Unsigned32,
        fsDot1qVlanStatus
            INTEGER,
        fsDot1qVlanCreationTime
            TimeTicks
    }

fsDot1qVlanTimeMark OBJECT-TYPE
    SYNTAX      TimeFilter
    MAX-ACCESS  not-accessible
    STATUS      current
    DESCRIPTION
        "A TimeFilter for this entry. See the TimeFilter
        textual convention to see how this works."
    ::= { fsDot1qVlanCurrentEntry 1 }

fsDot1qVlanFdbId OBJECT-TYPE
    SYNTAX      Unsigned32
    MAX-ACCESS  read-only
    STATUS      current
    DESCRIPTION
        "The Filtering Database used by this VLAN. This is one
        of the fsDot1qFdbId values in the fsDot1qFdbTable. This
        value is allocated automatically by the device whenever
        the VLAN is created: either dynamically by GVRP, or by
        management, in fsDot1qVlanStaticTable. Allocation of this
        value follows the learning constraints defined for this
        VLAN in fsDot1qLearningConstraintsTable."
    ::= { fsDot1qVlanCurrentEntry 2 }

fsDot1qVlanStatus OBJECT-TYPE
    SYNTAX      INTEGER {
                    other(1),
                    permanent(2),
                    dynamicGvrp(3)
                }
    MAX-ACCESS  read-only
    STATUS      current
    DESCRIPTION
        "This object indicates the status of this entry.
            other(1) - this entry is currently in use but the
                conditions under which it will remain so differ
                from the following values.
            permanent(2) - this entry, corresponding to an entry
                in fsDot1qVlanStaticTable, is currently in use and
                will remain so after the next reset of the
                device. The port lists for this entry include
                ports from the equivalent fsDot1qVlanStaticTable
                entry and ports learnt dynamically.
            dynamicGvrp(3) - this entry is currently in use
                and will remain so until removed by GVRP. There
                is no static entry for this VLAN and it will be
                removed when the last port leaves the VLAN."
    ::= { fsDot1qVlanCurrentEntry 3 }

fsDot1qVlanCreationTime OBJECT-TYPE
    SYNTAX      TimeTicks
    MAX-ACCESS  read-only
    STATUS      current
    DESCRIPTION
        "The value of sysUpTime when this VLAN was created."
    ::= { fsDot1qVlanCurrentEntry 4 }


fsDot1qVlanEgressPortTable OBJECT-TYPE
    SYNTAX      SEQUENCE OF FsDot1qVlanEgressPortEntry
    MAX-ACCESS  not-accessible
    STATUS      current
    DESCRIPTION
        "A table containing the information of egress ports 
        for each VLAN. This table maintains context ID as 
        one more index to support Multiple Instance."
    ::= { fsDot1qVlan 3 }

fsDot1qVlanEgressPortEntry OBJECT-TYPE
    SYNTAX      FsDot1qVlanEgressPortEntry
    MAX-ACCESS  not-accessible
    STATUS      current
    DESCRIPTION
        "Information about a port, Whether it is a tagged 
        or an untagged member."
    INDEX   { fsDot1qVlanContextId, fsDot1qVlanTimeMark, fsDot1qVlanIndex,
                fsDot1qTpPort}
    ::= { fsDot1qVlanEgressPortTable 1 }

FsDot1qVlanEgressPortEntry ::=
    SEQUENCE {
        fsDot1qVlanCurrentEgressPort INTEGER
    }

fsDot1qVlanCurrentEgressPort OBJECT-TYPE
    SYNTAX      INTEGER {
                    tagged(1),
                    untagged(2)
                }
    MAX-ACCESS  read-only
    STATUS      current
    DESCRIPTION
        "Indicates whether the port is a tagged or a untagged
        member in the VLAN.
          'tagged'   - to add the port in the tagged portlist.
          'untagged' - to add the port in the untagged portlist."
    ::= { fsDot1qVlanEgressPortEntry 1 }


-- -------------------------------------------------------------
-- The Static VLAN Database
-- -------------------------------------------------------------

fsDot1qVlanStaticTable OBJECT-TYPE
    SYNTAX      SEQUENCE OF FsDot1qVlanStaticEntry
    MAX-ACCESS  not-accessible
    STATUS      current
    DESCRIPTION
        "A table containing static configuration information for
        each VLAN configured into the device by (local or
        network) management. All entries are permanent and will
        be restored after the device is reset. This table
        maintains context ID as one more index to support
        Multiple Instance."
    ::= { fsDot1qVlan 4 }

fsDot1qVlanStaticEntry OBJECT-TYPE
    SYNTAX      FsDot1qVlanStaticEntry
    MAX-ACCESS  not-accessible
    STATUS      current
    DESCRIPTION
        "Static information for a VLAN configured into the
        device by (local or network) management."
    INDEX   { fsDot1qVlanContextId, fsDot1qVlanIndex }
    ::= { fsDot1qVlanStaticTable 1 }

FsDot1qVlanStaticEntry ::=
    SEQUENCE {
        fsDot1qVlanStaticName
            SnmpAdminString,
        fsDot1qVlanStaticRowStatus
            RowStatus
    }

fsDot1qVlanStaticName OBJECT-TYPE
    SYNTAX      SnmpAdminString (SIZE (0..32))
    MAX-ACCESS  read-create
    STATUS      current
    DESCRIPTION
        "An administratively assigned string, which may be used
        to identify the VLAN."
    REFERENCE
        "IEEE 802.1Q/D11 Section 12.10.2.1"
    ::= { fsDot1qVlanStaticEntry 1 }

fsDot1qVlanStaticRowStatus OBJECT-TYPE
    SYNTAX      RowStatus
    MAX-ACCESS  read-create
    STATUS      current
    DESCRIPTION
        "This object is used to set/indicate the status of the
        static vlan entry. Setting the status as NOT_IN_SERVICE stops
        the data flow for this Vlan.

        This table will only create/delete a Vlan. To set the member ports
        for the Vlan configure the table - fsDot1qVlanStaticPortConfigTable.

        To create a new VLAN and assign member ports to it set the rowstatus
        object in this table as 'CREATE_AND_WAIT', set the appropriate port
        in the fsDot1qVlanStaticPortConfigTable and finally set the rowstatus
        in this table as 'ACTIVE'.

        To update the member ports of an existing Vlan
            - EITHER set the rowstatus object in this table as
              'NOT_IN_SERVICE', add/delete the appropriate ports in the
              fsDot1qVlanStaticPortConfigTable and finally 'apply' the
              changes by setting the rowstatus in this table as 'ACTIVE'.
            - OR directly add/delete the ports in the
              fsDot1qVlanStaticPortConfigTable on the fly without changing
              the Vlan status."
    ::= { fsDot1qVlanStaticEntry 2 }


fsDot1qVlanStaticPortConfigTable OBJECT-TYPE
    SYNTAX      SEQUENCE OF FsDot1qVlanStaticPortConfigEntry
    MAX-ACCESS  not-accessible
    STATUS      current
    DESCRIPTION
        "A table containing the information of tagged, untagged
        and forbidden ports for each VLAN. This table
        maintains context ID as one more index to support
        Multiple Instance."
    ::= { fsDot1qVlan 5 }

fsDot1qVlanStaticPortConfigEntry OBJECT-TYPE
    SYNTAX      FsDot1qVlanStaticPortConfigEntry
    MAX-ACCESS  not-accessible
    STATUS      current
    DESCRIPTION
        "Forwarding information about a port, Whether it is a
        member or a forbidden member."
    INDEX   { fsDot1qVlanContextId, fsDot1qVlanIndex, fsDot1qTpPort }
    ::= { fsDot1qVlanStaticPortConfigTable 1 }

FsDot1qVlanStaticPortConfigEntry ::=
    SEQUENCE {
        fsDot1qVlanStaticPort
            INTEGER
    }

fsDot1qVlanStaticPort OBJECT-TYPE
    SYNTAX      INTEGER {
                    addTagged(1),
                    addUntagged(2),
                    addForbidden(3),
                    delTagged(4),
                    delUntagged(5),
                    delForbidden(6)
                }
    MAX-ACCESS  read-write
    STATUS      current
    DESCRIPTION
        "Indicates whether the port is a member or a forbidden
        member in the forwarding information for this VLAN.
          'addTagged'    - to add the port in the tagged portlist.
          'addUntagged'  - to add the port in the untagged portlist.
          'addForbidden' - to add the port in the forbidden portlist.
          'delTagged'    - to delete the port from the tagged portlist.
          'delUntagged'  - to delete the port from the untagged portlist.
          'delForbidden' - to delete the port from the forbidden portlist."
    REFERENCE
        "IEEE 802.1Q/D11 Section 12.10.2.1"
    ::= { fsDot1qVlanStaticPortConfigEntry 1 }


fsDot1qNextFreeLocalVlanIndexTable OBJECT-TYPE
   SYNTAX       SEQUENCE OF FsDot1qNextFreeLocalVlanIndexEntry
   MAX-ACCESS   not-accessible
   STATUS       current
   DESCRIPTION
      "Table containing Next FreeLocalVlanIndex per virtual context."
   ::= { fsDot1qVlan 6 }

fsDot1qNextFreeLocalVlanIndexEntry OBJECT-TYPE
   SYNTAX      FsDot1qNextFreeLocalVlanIndexEntry
   MAX-ACCESS  not-accessible
   STATUS      current
   DESCRIPTION
      "Entry for a particular virtual context."
   INDEX { fsDot1qVlanContextId }
   ::= { fsDot1qNextFreeLocalVlanIndexTable 1 }

FsDot1qNextFreeLocalVlanIndexEntry ::=
        SEQUENCE {
          fsDot1qNextFreeLocalVlanIndex
             Integer32
        }

fsDot1qNextFreeLocalVlanIndex OBJECT-TYPE
    SYNTAX      Integer32 (0|4096..2147483647)
    MAX-ACCESS  read-only
    STATUS      current
    DESCRIPTION
        "The next available value for fsDot1qVlanIndex of a local
        VLAN entry in fsDot1qVlanStaticTable. This will report
        values >=4096 if a new Local VLAN may be created or else
        the value 0 if this is not possible.
        A row creation operation in this table for an entry with a local
        VlanIndex value may fail if the current value of this object
        is not used as the index. Even if the value read is used,
        there is no guarantee that it will still be the valid index
        when the create operation is attempted - one more manager may
        have already got in during the intervening time interval.
        In this case, fsDot1qNextFreeLocalVlanIndex should be re-read
        and the creation re-tried with the new value.

        This value will automatically change when the current value is
        used to create a new row."
    ::= { fsDot1qNextFreeLocalVlanIndexEntry 1 }

-- -------------------------------------------------------------
-- The VLAN Port Configuration Table
-- -------------------------------------------------------------

fsDot1qPortVlanTable OBJECT-TYPE
    SYNTAX      SEQUENCE OF FsDot1qPortVlanEntry
    MAX-ACCESS  not-accessible
    STATUS      current
    DESCRIPTION
        "A table containing per port control and status
        information for VLAN configuration in the device."
    ::= { fsDot1qVlan 7 }

fsDot1qPortVlanEntry OBJECT-TYPE
    SYNTAX      FsDot1qPortVlanEntry
    MAX-ACCESS  not-accessible
    STATUS      current
    DESCRIPTION
        "Information controlling VLAN configuration for a port
        on the device. This is indexed by fsDot1dBasePort."
    INDEX  { fsDot1dBasePort }
    ::= { fsDot1qPortVlanTable 1 }

FsDot1qPortVlanEntry ::=
    SEQUENCE {
        fsDot1qPvid
            VlanIndex,
        fsDot1qPortAcceptableFrameTypes
            INTEGER,
        fsDot1qPortIngressFiltering
            TruthValue,
        fsDot1qPortGvrpStatus
            EnabledStatus,
        fsDot1qPortGvrpFailedRegistrations
            Counter32,
        fsDot1qPortGvrpLastPduOrigin
            MacAddress,
        fsDot1qPortRestrictedVlanRegistration
            TruthValue
    }

fsDot1qPvid OBJECT-TYPE
    SYNTAX      VlanIndex
    MAX-ACCESS  read-write
    STATUS      current
    DESCRIPTION
        "The PVID, the VLAN ID assigned to untagged frames or
        Priority-Tagged frames received on this port."
    REFERENCE
        "IEEE 802.1Q/D11 Section 12.10.1.1"
    DEFVAL      { 1 }
    ::= { fsDot1qPortVlanEntry 1 }

fsDot1qPortAcceptableFrameTypes OBJECT-TYPE
    SYNTAX      INTEGER {
                    admitAll(1),
                    admitOnlyVlanTagged(2),
                    admitOnlyUntaggedAndPriorityTagged(3)
                }
    MAX-ACCESS  read-write
    STATUS      current
    DESCRIPTION
        "When this is admitOnlyVlanTagged(2), the device will
        discard untagged frames or Priority-Tagged frames
        received on this port. When admitAll(1), untagged
        frames or Priority-Tagged frames received on this port
        will be accepted and assigned to the PVID for this port.

        When this is admitOnlyUntaggedAndPriorityTagged the device 
        will receive only untagged and priority tagged frames on 
        this port.

        This control does not affect VLAN independent BPDU
        frames, such as GVRP and STP. It does affect VLAN
        dependent BPDU frames, such as GMRP."
    REFERENCE
        "IEEE 802.1Q/D11 Section 12.10.1.3"
    DEFVAL      { admitAll }
    ::= { fsDot1qPortVlanEntry 2 }

fsDot1qPortIngressFiltering OBJECT-TYPE
    SYNTAX      TruthValue
    MAX-ACCESS  read-write
    STATUS      current
    DESCRIPTION
        "When this is true(1) the device will discard incoming
        frames for VLANs which do not include this Port in its
        Member set. When false(2), the port will accept all
        incoming frames.

        This control does not affect VLAN independent BPDU
        frames, such as GVRP and STP. It does affect VLAN
        dependent BPDU frames, such as GMRP."
    REFERENCE
        "IEEE 802.1Q/D11 Section 12.10.1.4"
    DEFVAL      { false }
    ::= { fsDot1qPortVlanEntry 3 }

fsDot1qPortGvrpStatus OBJECT-TYPE
    SYNTAX      EnabledStatus
    MAX-ACCESS  read-write
    STATUS      current
    DESCRIPTION
        "The state of GVRP operation on this port. The value
        enabled(1) indicates that GVRP is enabled on this port,
        as long as fsDot1qGvrpStatus is also enabled for this
        device. When disabled(2) but fsDot1qGvrpStatus is still
        enabled for the device, GVRP is disabled on this port:
        any GVRP packets received will be silently discarded and
        no GVRP registrations will be propagated from other
        ports. This object affects all GVRP Applicant and
        Registrar state machines on this port. A transition
        from disabled(2) to enabled(1) will cause a reset of all
        GVRP state machines on this port."
    DEFVAL      { enabled }
    ::= { fsDot1qPortVlanEntry 4 }

fsDot1qPortGvrpFailedRegistrations OBJECT-TYPE
    SYNTAX      Counter32
    MAX-ACCESS  read-only
    STATUS      current
    DESCRIPTION
        "The total number of failed GVRP registrations, for any
        reason, on this port."
    ::= { fsDot1qPortVlanEntry 5 }

fsDot1qPortGvrpLastPduOrigin OBJECT-TYPE
    SYNTAX      MacAddress
    MAX-ACCESS  read-only
    STATUS      current
    DESCRIPTION
        "The Source MAC Address of the last GVRP message
        received on this port."
    ::= { fsDot1qPortVlanEntry 6 }

fsDot1qPortRestrictedVlanRegistration OBJECT-TYPE
    SYNTAX      TruthValue
    MAX-ACCESS  read-write
    STATUS      current
    DESCRIPTION
        "The state of Restricted VLAN Registration on this port.
         If the value of this control is true(1), then creation
         of a new dynamic VLAN entry is permitted only if there
         is a Static VLAN Registration Entry for the VLAN concerned,
         in which the Registrar Administrative Control value for
         this port is Normal Registration."
    REFERENCE
        "IEEE 802.1u clause 11.2.3.2.3, 12.10.1.7."
    DEFVAL      { false }
    ::= { fsDot1qPortVlanEntry 7 }

-- -------------------------------------------------------------
-- Per port VLAN Statistics Table
-- -------------------------------------------------------------

fsDot1qPortVlanStatisticsTable OBJECT-TYPE
    SYNTAX      SEQUENCE OF FsDot1qPortVlanStatisticsEntry
    MAX-ACCESS  not-accessible
    STATUS      current
    DESCRIPTION
        "A table containing per-port, per-VLAN statistics for
        traffic received. Separate objects are provided for both the
        most-significant and least-significant bits of statistics
        counters for ports that are associated with this transparent
        bridge. The most-significant bit objects are only required on
        high capacity interfaces, as defined in the conformance clauses
        for these objects. This mechanism is provided as a way to read
        64-bit counters for agents which support only SNMPv1.

        Note that the reporting of most-significant and least-
        significant counter bits separately runs the risk of missing
        an overflow of the lower bits in the interval between sampling.
        The manager must be aware of this possibility, even within the
        same varbindlist, when interpreting the results of a request or
        asynchronous notification."
    ::= { fsDot1qVlan 8 }

fsDot1qPortVlanStatisticsEntry OBJECT-TYPE
    SYNTAX      FsDot1qPortVlanStatisticsEntry
    MAX-ACCESS  not-accessible
    STATUS      current
    DESCRIPTION
        "Traffic statistics for a VLAN on an interface."
    INDEX   { fsDot1dBasePort, fsDot1qVlanIndex }
    ::= { fsDot1qPortVlanStatisticsTable 1 }

FsDot1qPortVlanStatisticsEntry ::=
    SEQUENCE {
        fsDot1qTpVlanPortInFrames
            Counter32,
        fsDot1qTpVlanPortOutFrames
            Counter32,
        fsDot1qTpVlanPortInDiscards
            Counter32,
        fsDot1qTpVlanPortInOverflowFrames
            Counter32,
        fsDot1qTpVlanPortOutOverflowFrames
            Counter32,
        fsDot1qTpVlanPortInOverflowDiscards
            Counter32
    }

fsDot1qTpVlanPortInFrames OBJECT-TYPE
    SYNTAX      Counter32
    MAX-ACCESS  read-only
    STATUS      current
    DESCRIPTION
        "The number of valid frames received by this port from
        its segment which were classified as belonging to this
        VLAN. Note that a frame received on this port is
        counted by this object if and only if it is for a
        protocol being processed by the local forwarding process
        for this VLAN. This object includes received bridge
        management frames classified as belonging to this VLAN
        (e.g. GMRP, but not GVRP or STP)."
    REFERENCE
        "IEEE 802.1Q/D11 Section 12.6.1.1.3(a)"
    ::= { fsDot1qPortVlanStatisticsEntry 1 }

fsDot1qTpVlanPortOutFrames OBJECT-TYPE
    SYNTAX      Counter32
    MAX-ACCESS  read-only
    STATUS      current
    DESCRIPTION
        "The number of valid frames transmitted by this port to
        its segment from the local forwarding process for this
        VLAN. This includes bridge management frames originated
        by this device which are classified as belonging to this
        VLAN (e.g. GMRP, but not GVRP or STP)."
    REFERENCE
        "IEEE 802.1Q/D11 Section 12.6.1.1.3(d)"
    ::= { fsDot1qPortVlanStatisticsEntry 2 }

fsDot1qTpVlanPortInDiscards OBJECT-TYPE
    SYNTAX      Counter32
    MAX-ACCESS  read-only
    STATUS      current
    DESCRIPTION
        "The number of valid frames received by this port from
        its segment which were classified as belonging to this
        VLAN which were discarded due to VLAN related reasons.
        Specifically, the IEEE 802.1Q counters for Discard
        Inbound and Discard on Ingress Filtering."
    REFERENCE
        "IEEE 802.1Q/D11 Section 12.6.1.1.3"
    ::= { fsDot1qPortVlanStatisticsEntry 3 }

fsDot1qTpVlanPortInOverflowFrames OBJECT-TYPE
    SYNTAX      Counter32
    MAX-ACCESS  read-only
    STATUS      current
    DESCRIPTION
        "The number of times the associated
        fsDot1qTpVlanPortInFrames counter has overflowed."
    REFERENCE
        "ISO/IEC 15802-3 Section 14.6.1.1.3"
    ::= { fsDot1qPortVlanStatisticsEntry 4 }

fsDot1qTpVlanPortOutOverflowFrames OBJECT-TYPE
    SYNTAX      Counter32
    MAX-ACCESS  read-only
    STATUS      current
    DESCRIPTION
        "The number of times the associated
        fsDot1qTpVlanPortOutFrames counter has overflowed."
    REFERENCE
        "ISO/IEC 15802-3 Section 14.6.1.1.3"
    ::= { fsDot1qPortVlanStatisticsEntry 5 }

fsDot1qTpVlanPortInOverflowDiscards OBJECT-TYPE
    SYNTAX      Counter32
    MAX-ACCESS  read-only
    STATUS      current
    DESCRIPTION
        "The number of times the associated
        fsDot1qTpVlanPortInDiscards counter has overflowed."
    REFERENCE
        "ISO/IEC 15802-3 Section 14.6.1.1.3"
    ::= { fsDot1qPortVlanStatisticsEntry 6 }

fsDot1qPortVlanHCStatisticsTable OBJECT-TYPE
    SYNTAX      SEQUENCE OF FsDot1qPortVlanHCStatisticsEntry
    MAX-ACCESS  not-accessible
    STATUS      current
    DESCRIPTION
        "A table containing per port, per VLAN statistics for
        traffic on high capacity interfaces."
    ::= { fsDot1qVlan 9 }

fsDot1qPortVlanHCStatisticsEntry OBJECT-TYPE
    SYNTAX      FsDot1qPortVlanHCStatisticsEntry
    MAX-ACCESS  not-accessible
    STATUS      current
    DESCRIPTION
        "Traffic statistics for a VLAN on a high capacity
        interface."
    INDEX   { fsDot1dBasePort, fsDot1qVlanIndex }
    ::= { fsDot1qPortVlanHCStatisticsTable 1 }

FsDot1qPortVlanHCStatisticsEntry ::=
    SEQUENCE {
        fsDot1qTpVlanPortHCInFrames
            Counter64,
        fsDot1qTpVlanPortHCOutFrames
            Counter64,
        fsDot1qTpVlanPortHCInDiscards
            Counter64
    }

fsDot1qTpVlanPortHCInFrames OBJECT-TYPE
    SYNTAX      Counter64
    MAX-ACCESS  read-only
    STATUS      current
    DESCRIPTION
        "The number of valid frames received by this port from
        its segment which were classified as belonging to this
        VLAN. Note that a frame received on this port is
        counted by this object if and only if it is for a
        protocol being processed by the local forwarding process
        for this VLAN. This object includes received bridge
        management frames classified as belonging to this VLAN
        (e.g. GMRP, but not GVRP or STP)."
    REFERENCE
        "IEEE 802.1Q/D11 Section 12.6.1.1.3(a)"
    ::= { fsDot1qPortVlanHCStatisticsEntry 1 }

fsDot1qTpVlanPortHCOutFrames OBJECT-TYPE
    SYNTAX      Counter64
    MAX-ACCESS  read-only
    STATUS      current
    DESCRIPTION
        "The number of valid frames transmitted by this port to
        its segment from the local forwarding process for this
        VLAN. This includes bridge management frames originated
        by this device which are classified as belonging to this
        VLAN (e.g. GMRP, but not GVRP or STP)."
    REFERENCE
        "IEEE 802.1Q/D11 Section 12.6.1.1.3(d)"
    ::= { fsDot1qPortVlanHCStatisticsEntry 2 }

fsDot1qTpVlanPortHCInDiscards OBJECT-TYPE
    SYNTAX      Counter64
    MAX-ACCESS  read-only
    STATUS      current
    DESCRIPTION
        "The number of valid frames received by this port from
        its segment which were classified as belonging to this
        VLAN which were discarded due to VLAN related reasons.
        Specifically, the IEEE 802.1Q counters for Discard
        Inbound and Discard on Ingress Filtering."
    REFERENCE
        "IEEE 802.1Q/D11 Section 12.6.1.1.3"
    ::= { fsDot1qPortVlanHCStatisticsEntry 3 }

-- -------------------------------------------------------------
-- The VLAN Learning Constraints Table
-- -------------------------------------------------------------

fsDot1qLearningConstraintsTable OBJECT-TYPE
    SYNTAX      SEQUENCE OF FsDot1qLearningConstraintsEntry
    MAX-ACCESS  not-accessible
    STATUS      current
    DESCRIPTION
        "A table containing learning constraints for sets of
        Shared and Independent VLANs. This table maintains 
	context ID as one more index to support Multiple Instances."
    REFERENCE
        "IEEE 802.1Q/D11 Section 12.10.3.1"
    ::= { fsDot1qVlan 10 }

fsDot1qLearningConstraintsEntry OBJECT-TYPE
    SYNTAX      FsDot1qLearningConstraintsEntry
    MAX-ACCESS  not-accessible
    STATUS      current
    DESCRIPTION
        "A learning constraint defined for a VLAN."
    INDEX   { fsDot1qVlanContextId, fsDot1qConstraintVlan, 
              fsDot1qConstraintSet }
    ::= { fsDot1qLearningConstraintsTable 1 }

FsDot1qLearningConstraintsEntry ::=
    SEQUENCE {
        fsDot1qConstraintVlan
            VlanIndex,
        fsDot1qConstraintSet
            Integer32,
        fsDot1qConstraintType
            INTEGER,
        fsDot1qConstraintStatus
            RowStatus
    }

fsDot1qConstraintVlan OBJECT-TYPE
    SYNTAX      VlanIndex
    MAX-ACCESS  not-accessible
    STATUS      current
    DESCRIPTION
        "The index of the row in fsDot1qVlanCurrentTable for the
        VLAN constrained by this entry."
    ::= { fsDot1qLearningConstraintsEntry 1 }

fsDot1qConstraintSet OBJECT-TYPE
    SYNTAX      Integer32 (0..65535)
    MAX-ACCESS  not-accessible
    STATUS      current
    DESCRIPTION
        "The identity of the constraint set to which
        fsDot1qConstraintVlan belongs. These values may be chosen
        by the management station."
    ::= { fsDot1qLearningConstraintsEntry 2 }

fsDot1qConstraintType OBJECT-TYPE
    SYNTAX      INTEGER {
                    independent(1),
                    shared(2)
                }
    MAX-ACCESS  read-create
    STATUS      current
    DESCRIPTION
        "The type of constraint this entry defines.
            independent(1) - the VLAN, fsDot1qConstraintVlan,
                uses an independent filtering database from all
                other VLANs in the same set, defined by
                fsDot1qConstraintSet.
            shared(2) - the VLAN, fsDot1qConstraintVlan, shares
                the same filtering database as all other VLANs
                in the same set, defined by fsDot1qConstraintSet."
    ::= { fsDot1qLearningConstraintsEntry 3 }

fsDot1qConstraintStatus OBJECT-TYPE
    SYNTAX      RowStatus
    MAX-ACCESS  read-create
    STATUS      current
    DESCRIPTION
        "The status of this entry."
    ::= { fsDot1qLearningConstraintsEntry 4 }


fsDot1qConstraintDefaultTable OBJECT-TYPE
   SYNTAX       SEQUENCE OF FsDot1qConstraintDefaultEntry
   MAX-ACCESS   not-accessible
   STATUS       current
   DESCRIPTION
      "Table containing fsDot1q default constraints per
      virtual bridge context."
   ::= { fsDot1qVlan 11 }
fsDot1qConstraintDefaultEntry OBJECT-TYPE
   SYNTAX       FsDot1qConstraintDefaultEntry
   MAX-ACCESS   not-accessible
   STATUS       current
   DESCRIPTION
      "Per virtual bridge fsDot1q default constraints."
   INDEX { fsDot1qVlanContextId }
   ::= { fsDot1qConstraintDefaultTable  1 }

FsDot1qConstraintDefaultEntry ::=
    SEQUENCE {
      fsDot1qConstraintSetDefault
         Integer32,
      fsDot1qConstraintTypeDefault
         INTEGER
    }

fsDot1qConstraintSetDefault OBJECT-TYPE
    SYNTAX      Integer32 (0..65535)
    MAX-ACCESS  read-write
    STATUS      current
    DESCRIPTION
        "The identity of the constraint set to which a VLAN
        belongs, if there is not an explicit entry for that VLAN
        in fsDot1qLearningConstraintsTable."
    ::= { fsDot1qConstraintDefaultEntry 1 }

fsDot1qConstraintTypeDefault OBJECT-TYPE
    SYNTAX      INTEGER {
                    independent(1),
                    shared(2)
                }
    MAX-ACCESS  read-write
    STATUS      current
    DESCRIPTION
        "The type of constraint set to which a VLAN belongs, if
        there is not an explicit entry for that VLAN in
        fsDot1qLearningConstraintsTable. The types are as defined
        for fsDot1qConstraintType."
    ::= { fsDot1qConstraintDefaultEntry 2 }

-- -------------------------------------------------------------
-- fsDot1vProtocol group
-- -------------------------------------------------------------

fsDot1vProtocolGroupTable OBJECT-TYPE
    SYNTAX      SEQUENCE OF FsDot1vProtocolGroupEntry
    MAX-ACCESS  not-accessible
    STATUS      current
    DESCRIPTION
        "A table that contains mappings from Protocol
         Templates to Protocol Group Identifiers used for
         Port-and-Protocol-based VLAN Classification. This 
	 table maintains context ID as one more index to 
	 support Multiple Instance."
    REFERENCE
        "IEEE 802.1v clause 8.6.4"
    ::= { fsDot1vProtocol 1 }

fsDot1vProtocolGroupEntry OBJECT-TYPE
    SYNTAX      FsDot1vProtocolGroupEntry
    MAX-ACCESS  not-accessible
    STATUS      current
    DESCRIPTION
        "A mapping from a Protocol Template to a Protocol
         Group Identifier."
    INDEX       { fsDot1qVlanContextId, fsDot1vProtocolTemplateFrameType,
                  fsDot1vProtocolTemplateProtocolValue }
    ::= { fsDot1vProtocolGroupTable 1 }

FsDot1vProtocolGroupEntry ::=
    SEQUENCE {
        fsDot1vProtocolTemplateFrameType
            INTEGER,
        fsDot1vProtocolTemplateProtocolValue
            OCTET STRING,
        fsDot1vProtocolGroupId
            Integer32,
        fsDot1vProtocolGroupRowStatus
            RowStatus
    }

fsDot1vProtocolTemplateFrameType OBJECT-TYPE
    SYNTAX      INTEGER {
                  ethernet  (1),
                  rfc1042   (2),
                  snap8021H (3),
                  snapOther (4),
                  llcOther  (5)
                }
    MAX-ACCESS  not-accessible
    STATUS      current
    DESCRIPTION
        "The data-link encapsulation format or the
         'detagged_frame_type' in a Protocol Template."
    REFERENCE
        "IEEE 802.1v clause 8.6.2"
    ::= { fsDot1vProtocolGroupEntry 1 }

fsDot1vProtocolTemplateProtocolValue OBJECT-TYPE
    SYNTAX      OCTET STRING (SIZE (2 | 5))
    MAX-ACCESS  not-accessible
    STATUS      current
    DESCRIPTION
        "The identification of the protocol above the data-link
         layer in a Protocol Template.  Depending on the
         frame type, the octet string will have one of the
         following values:

         For 'ethernet', 'rfc1042' and 'snap8021H',
             this is the 16-bit (2-octet) IEEE 802.3 Type Field.
         For 'snapOther',
             this is the 40-bit (5-octet) PID.
         For 'llcOther',
             this is the 2-octet IEEE 802.2 LSAP pair:
             first octet for DSAP and second octet for SSAP."
    REFERENCE
        "IEEE 802.1v clause 8.6.2"
    ::= { fsDot1vProtocolGroupEntry 2 }

fsDot1vProtocolGroupId OBJECT-TYPE
    SYNTAX      Integer32 (0..2147483647)
    MAX-ACCESS  read-create
    STATUS      current
    DESCRIPTION
        "Represents a group of protocols that are associated
         together when assigning a VID to a frame."
    REFERENCE
        "IEEE 802.1v clause 8.6.3, 12.10.2.1"
    ::= { fsDot1vProtocolGroupEntry 3 }

fsDot1vProtocolGroupRowStatus OBJECT-TYPE
    SYNTAX      RowStatus
    MAX-ACCESS  read-create
    STATUS      current
    DESCRIPTION
        "This object indicates the status of this entry."
    ::= { fsDot1vProtocolGroupEntry 4 }

fsDot1vProtocolPortTable OBJECT-TYPE
    SYNTAX      SEQUENCE OF FsDot1vProtocolPortEntry
    MAX-ACCESS  not-accessible
    STATUS      current
    DESCRIPTION
        "A table that contains VID sets used for
         Port-and-Protocol-based VLAN Classification."
    REFERENCE
        "IEEE 802.1v clause 8.4.4"
    ::= { fsDot1vProtocol 2 }

fsDot1vProtocolPortEntry OBJECT-TYPE
    SYNTAX      FsDot1vProtocolPortEntry
    MAX-ACCESS  not-accessible
    STATUS      current
    DESCRIPTION
        "A VID set for a port."
    INDEX       { fsDot1dBasePort,
                  fsDot1vProtocolPortGroupId }
    ::= { fsDot1vProtocolPortTable 1 }

FsDot1vProtocolPortEntry ::=
    SEQUENCE {
        fsDot1vProtocolPortGroupId
            Integer32,
        fsDot1vProtocolPortGroupVid
            Integer32,
        fsDot1vProtocolPortRowStatus
            RowStatus
    }

fsDot1vProtocolPortGroupId OBJECT-TYPE
    SYNTAX      Integer32 (1..2147483647)
    MAX-ACCESS  not-accessible
    STATUS      current
    DESCRIPTION
        "Designates a group of protocols in the Protocol
         Group Database."
    REFERENCE
        "IEEE 802.1v clause 8.6.3, 12.10.1.2"
    ::= { fsDot1vProtocolPortEntry 1 }

fsDot1vProtocolPortGroupVid OBJECT-TYPE
    SYNTAX      Integer32 (1..4094)
    MAX-ACCESS  read-create
    STATUS      current
    DESCRIPTION
        "The VID associated with a group of protocols for
         each port."
    REFERENCE
        "IEEE 802.1v clause 8.4.4, 12.10.1.2"
    ::= { fsDot1vProtocolPortEntry 2 }

fsDot1vProtocolPortRowStatus OBJECT-TYPE
    SYNTAX      RowStatus
    MAX-ACCESS  read-create
    STATUS      current
    DESCRIPTION
        "This object indicates the status of this entry."
    ::= { fsDot1vProtocolPortEntry 3 }

END

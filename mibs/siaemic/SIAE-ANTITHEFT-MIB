-- ----------------------------------------------------------------------------
--
--  SIAE MICROELETTRONICA s.p.a.
--                 
--  Via Michelangelo Buonarroti, 21
--  20093 - Cologno Monzese
--  Milano 
--  ITALY
--
-- ----------------------------------------------------------------------------
-- ----------------------------------------------------------------------------

SIAE-ANTITHEFT-MIB
    DEFINITIONS ::= BEGIN

    IMPORTS
        MODULE-IDENTITY, OBJECT-TYPE
    FROM SNMPv2-SMI
        DisplayString,
        RowStatus
    FROM SNMPv2-TC
        InterfaceIndex
    FROM IF-MIB
        siaeMib
    FROM SIAE-TREE-MIB;

    antiTheft MODULE-IDENTITY
        LAST-UPDATED "201809140000Z" 
        ORGANIZATION "SIAE MICROELETTRONICA spa"
        CONTACT-INFO
        "SIAE MICROELETTONICA s.p.a.
        Via Michelangelo Buonarroti, 21
        20093 - Cologno Monzese
        Milano - ITALY
        Phone :  +39-02-27325-1
        E-mail: help@siaemic.com
        "
    DESCRIPTION
        "This feature is designed to prevent equipments theft.
        "
    REVISION "201903250000Z"
    DESCRIPTION
        "Added antiTheftReconnectionTimeout attribute.
        "
    REVISION "201809140000Z"
    DESCRIPTION
        "Removed unused imports.
        "
    REVISION "201803150000Z"
    DESCRIPTION
        "Added antitheftPortMgtTable.
        "
    REVISION "201701090000Z"
    DESCRIPTION
        "Initial version 01.00.00 of anti-theft feature.
        "
    ::= { siaeMib 105 }
        

------------------------------------------------------------------------------
--  antiTheft GROUP
------------------------------------------------------------------------------
--
--  This MIB defines the objects of the anti-theft feature.
--
------------------------------------------------------------------------------

------ Beginning -------------------------------------------------------------

    antiTheftMibVersion  OBJECT-TYPE
        SYNTAX      INTEGER
        MAX-ACCESS  read-only
        STATUS      current
        DESCRIPTION
            "Numerical version of this module. The string version of this MIB 
             have the following format: XX.YY.ZZ so, for example, the value 1 
             should be interpreted as 00.00.01 and the value 10001 should be 
             interpreted as 01.00.01.
            "
        DEFVAL {1}
    ::= {antiTheft 1}

    antiTheftEnable  OBJECT-TYPE
        SYNTAX       INTEGER {
                     enable(1),
                     disable(2)
                    }
        MAX-ACCESS  read-write
        STATUS      current
        DESCRIPTION
            "This object is for enabling or disabling anti-theft feature in 
            the system.
            "
        DEFVAL  { disable }
    ::= { antiTheft 2 }

    antiTheftLicense OBJECT-TYPE
        SYNTAX      OCTET STRING
        MAX-ACCESS  read-write
        STATUS      current
        DESCRIPTION
            "This object is for setting anti-theft license key.
            "
    ::= { antiTheft 3 }

    antiTheftStatus  OBJECT-TYPE
        SYNTAX       INTEGER {
          unlockedUnbound (1),
            unlockedBound (2),
                    locked (3),
              notAvailable (4)
                    }
        MAX-ACCESS  read-only
        STATUS      current
        DESCRIPTION
            "This object indicates the current binding status. When a valid 
            license key is set on the equipment, it binds to NMS and starts 
            working properly, otherwise it is locked.
            "
    ::= { antiTheft 4 }

    antiTheftTimeout  OBJECT-TYPE
        SYNTAX      INTEGER (0..43200)
        UNITS        "min"
        MAX-ACCESS  read-only
        STATUS      current
        DESCRIPTION
            "This object indicates the current bind timeout in minutes. Zero 
             timeout means no timeout.
            "
        DEFVAL  { 4320 }
    ::= { antiTheft 5 }
    
    antiTheftCountdown  OBJECT-TYPE
        SYNTAX      INTEGER (0..43200)
        UNITS        "min"
        MAX-ACCESS  read-only
        STATUS      current
        DESCRIPTION
            "This object shows remaining time (in minutes) before equipment 
             will be locked. 
            "
    ::= { antiTheft 6 }
    
    antiTheftCustomer  OBJECT-TYPE
        SYNTAX      DisplayString    (SIZE(1..7))
        MAX-ACCESS  read-only
        STATUS      current
        DESCRIPTION
            "This object shows customer that owns the equipment. 
            "
    ::= { antiTheft 7 }

-------  Begin of antitheftPortMgtTable
--
    antitheftPortMgtTable  OBJECT-TYPE
        SYNTAX      SEQUENCE OF     AntitheftPortMgtEntry
        MAX-ACCESS  not-accessible
        STATUS      current
        DESCRIPTION
            "Table with antitheft port management entries useful to 
             choose antitheft consequent actions on equipment ports."
    ::= {antiTheft 8}

    antitheftPortMgtEntry  OBJECT-TYPE
        SYNTAX      AntitheftPortMgtEntry
        MAX-ACCESS  not-accessible
        STATUS      current
        DESCRIPTION
            "Antitheft port management record."
        INDEX {antitheftPortIfIndex}
    ::= {antitheftPortMgtTable 1}

    AntitheftPortMgtEntry  ::=
        SEQUENCE {
            antitheftPortIfIndex           InterfaceIndex,
            antitheftPortLock              INTEGER,
            antitheftPortRowStatus         RowStatus
         }
     
    antitheftPortIfIndex  OBJECT-TYPE
        SYNTAX      InterfaceIndex
        MAX-ACCESS  not-accessible
        STATUS      current
        DESCRIPTION
            "A unique value, greater than zero, for each interface. This object is 
            identical to the ifIndex of the standard MIB-2 ifTable."
    ::= {antitheftPortMgtEntry 1}
   
    antitheftPortLock  OBJECT-TYPE
        SYNTAX      INTEGER  {
                               allow          (1),
                               deny           (2)                            
                             }
        MAX-ACCESS  read-create
        STATUS      current
        DESCRIPTION
            "Object used to allow or deny antitheft consequent actions on that port.
             When NE is bound with NMS, it is possible to choose which ports will be 
             disabled in case of equipment lock (only ports involved in management vlan
             are enabled by default to safeguard management)."
        DEFVAL  {deny} 
    ::= {antitheftPortMgtEntry 2}

    antitheftPortRowStatus   OBJECT-TYPE 
        SYNTAX      RowStatus
        MAX-ACCESS  read-create
        STATUS      current
        DESCRIPTION
            "Status of this row of antitheftPortMgtTable."
    ::= {antitheftPortMgtEntry 3}
    
    antiTheftReconnectionTimeout  OBJECT-TYPE
        SYNTAX      INTEGER (1440..43200)
        UNITS        "min"
        MAX-ACCESS  read-write
        STATUS      current
        DESCRIPTION
            "This object indicates the reconnection timeout in minutes.
            "
        DEFVAL  { 4320 }
    ::= { antiTheft 9 }
--
-------  End of antitheftPortMgtTable

------ End group -------------------------------------------------------------

END

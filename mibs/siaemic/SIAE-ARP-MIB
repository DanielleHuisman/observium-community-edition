-- ----------------------------------------------------------------------------
--
--  SIAE MICROELETTRONICA s.p.a.
--
--  Via Michelangelo Buonarroti, 21
--  20093 - Cologno Monzese
--  Milano
--  ITALY
--
-- ----------------------------------------------------------------------------
-- ----------------------------------------------------------------------------

SIAE-ARP-MIB DEFINITIONS ::= BEGIN
IMPORTS
    enterprises                 FROM SNMPv2-SMI
    MODULE-IDENTITY, OBJECT-TYPE, DisplayString,
    IpAddress, MacAddress,
    TEXTUAL-CONVENTION          FROM SNMPv2-TC
    IndexInteger                FROM DIFFSERV-MIB
    OBJECT-GROUP                FROM SNMPv2-CONF;

smArpMIB  MODULE-IDENTITY
    LAST-UPDATED "201802010000Z"
    ORGANIZATION "SIAE MICROELETTRONICA spa"
    CONTACT-INFO
        "SIAE MICROELETTONICA s.p.a.
        Via Michelangelo Buonarroti, 21
        20093 - Cologno Monzese
        Milano - ITALY
        Phone :  +39-02-27325-1
        E-mail: tbd@siaemic.com
        "
    DESCRIPTION
        "The MIB is designed for ARP related enhancements for SIAEMIC."

    ::= { enterprises aricent-communication-holding-ltd(29601) 100 1 12}

-- ---------------------------------
-- Subtree for this mib
-- ---------------------------------

smArpSecured                    OBJECT IDENTIFIER ::= { smArpMIB 1 }

----------------------------------------------------------------------------------
--  smSecuredArpTable
----------------------------------------------------------------------------------
--
--  This table is used to store secured MAC add with IP & VRF Name as Index.
--  This table is used for SM SECURED ARP FEATURE.
--
--  This used to prevent arp spooofing in network
--  If the user configures the IP & MAC in this table then the devices
--  will only accept packets from this MAC wrt to this IP
--
----------------------------------------------------------------------------------
smSecuredArpTable               OBJECT-TYPE
    SYNTAX                      SEQUENCE OF SmSecuredArpEntry
    MAX-ACCESS                  not-accessible
    STATUS                      current
    DESCRIPTION
        "A table to hold the IP-MAC mappings for the list of IPs that the user
        want to mark as secured.
        This table is used to store secured MAC add with IP & VRF Name as Index.
        This table is used for SM SECURED ARP FEATURE.

        This used to prevent arp spooofing in network
        If the used configure the an IP & ARP in this table then th devices will
        will only accept packets from this this MAC wrt to this IP
        "
    ::= { smArpSecured 1 }

smSecuredArpEntry               OBJECT-TYPE
    SYNTAX                      SmSecuredArpEntry
    MAX-ACCESS                  not-accessible
    STATUS                      current
    DESCRIPTION
        "An entry in the IP-MAC secured mappings table."

    INDEX   { smSecuredArpVrfName , smSecuredArpIp }

    ::= { smSecuredArpTable 1 }

SmSecuredArpEntry::=  SEQUENCE {
    smSecuredArpVrfName         DisplayString,
    smSecuredArpIp              IpAddress,
    smSecuredArpMac             MacAddress,
    smSecuredArpRowStatus       RowStatus
}

    smSecuredArpVrfName         OBJECT-TYPE
    SYNTAX                      DisplayString (SIZE (0..16))
    MAX-ACCESS                  not-accessible
    STATUS                      current
    DESCRIPTION
        "The VRF to which the IP address belongs."
    ::= { smSecuredArpEntry 1 }

    smSecuredArpIp              OBJECT-TYPE
    SYNTAX                      IpAddress
    MAX-ACCESS                  not-accessible
    STATUS                      current
    DESCRIPTION
        "The IP for which the secured MAC needs to be configured."
    ::= { smSecuredArpEntry 2 }

    smSecuredArpMac             OBJECT-TYPE
    SYNTAX                      MacAddress
    MAX-ACCESS                  read-create
    STATUS                      current
    DESCRIPTION
        "The secured MAC corresponding the IP configured by the above object."
    ::= { smSecuredArpEntry 3 }

    smSecuredArpRowStatus       OBJECT-TYPE
    SYNTAX                      RowStatus
    MAX-ACCESS                  read-create
    STATUS                      current
    DESCRIPTION
        " The status of this conceptual row.
         The value of this object has no effect on whether
         other objects in this conceptual row can be modified.
         A conceptual row can not be made active until the
         smSecuredArpIp object has been set."
    ::= { smSecuredArpEntry 4 }

END

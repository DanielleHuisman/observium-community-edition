-- Copyright (C) 2006-2012 Aricent Group . All Rights Reserved

-- ********************************************************************
-- $Id: smip.mib,v 1 2019/03/18  Gaurav Srivastav Exp $
-- ********************************************************************

SIAE-IP-MIB DEFINITIONS ::= BEGIN
IMPORTS

    MODULE-IDENTITY, OBJECT-TYPE,
    enterprises                 FROM SNMPv2-SMI
    TEXTUAL-CONVENTION          FROM SNMPv2-TC
    OBJECT-GROUP                FROM SNMPv2-CONF;

smIpMIB  MODULE-IDENTITY
       LAST-UPDATED "201802010000Z"
       ORGANIZATION "SIAE MICROELETTRONICA spa"
       CONTACT-INFO
            "SIAE MICROELETTONICA s.p.a.
             Via Michelangelo Buonarroti, 21
             20093 - Cologno Monzese
             Milano - ITALY
             Phone :  +39-02-27325-1
             E-mail: tbd@siaemic.com
            "
       DESCRIPTION  "The MIB is designed for IP related enhancements for SIAEMIC."

 ::=  { enterprises aricent-communication-holding-ltd(29601) 100 1 10}

-- ---------------------------------
-- Subtree for this mib
-- ---------------------------------

  smIpGlobal      OBJECT IDENTIFIER ::= { smIpMIB 1 }

-- *****************************************************************************
--                         smIpForwardingStatus Scalar objects
-- *****************************************************************************

smIpForwardingStatus OBJECT-TYPE
   SYNTAX      INTEGER { enable(1), disable(2) }
   MAX-ACCESS  read-write
   STATUS      current
   DESCRIPTION
     "This object is used to enable or disable IP forwarding. By default,
      it is enabled."
   DEFVAL { enable }
   ::= {smIpGlobal 1 }

END

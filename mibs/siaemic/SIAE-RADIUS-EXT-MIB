-- Copyright (C) 2009-2012 Aricent Group . All Rights Reserved

-- $Id: fsradext.mib,v 1.1 2015/04/28 12:25:01 siva Exp $

-- ****************************************************************************
-- *                         Document Version Info                            *
-- ****************************************************************************
-- *Version |    Date        |   Author             |        Changes          *
-- * ------------------------------------------------------------------------ *
-- * 1.1    |  4thAug 2009   | Private              |fsradius.mib, radauth.mib*
-- *        |                |                      |radacc.mib extended for  *
-- *        |                |                      |IPv6 support             *
-- *        |                |                      |	 		              *
-- ****************************************************************************

-- RADIUS-CLIENT-MIB DEFINITIONS ::= BEGIN


SIAE-RADIUS-EXT-MIB DEFINITIONS ::= BEGIN

 IMPORTS
     MODULE-IDENTITY, OBJECT-TYPE,
     Counter32, Gauge32, TimeTicks,
     Integer32, enterprises           FROM SNMPv2-SMI
     DisplayString, RowStatus         FROM SNMPv2-TC
     SnmpAdminString                  FROM SNMP-FRAMEWORK-MIB
     InetAddressType, InetAddress     FROM INET-ADDRESS-MIB
     fsRadExtServerEntry              FROM ARICENT-RADIUS-EXT-MIB;

 futureRADIUSEXTSIAEMIB MODULE-IDENTITY
    LAST-UPDATED "201209050000Z"
    ORGANIZATION "ARICENT COMMUNICATIONS SOFTWARE"
    CONTACT-INFO "support@aricent.com"
	DESCRIPTION "MIB for Radius. Extended for Ipv6 Support"
	REVISION "201209050000Z"
	DESCRIPTION "MIB for Radius. Extended for Ipv6 Support"
         ::= { enterprises  aricent-communication-holding-ltd(29601) 100 1 20 }

fsRadExtSiaeServer           OBJECT IDENTIFIER ::= { futureRADIUSEXTSIAEMIB 1 }


-- ---------------------------------------------------------- --
-- The Radius Siae Extended table
-- ---------------------------------------------------------- --
fsRadExtSiaeServerTable OBJECT-TYPE
    SYNTAX SEQUENCE OF FsRadExtSiaeServerEntry
    MAX-ACCESS not-accessible
    STATUS current
    DESCRIPTION
        "Siae extension of the (conceptual) table that lists the RADIUS 
         servers with which the client shares a secret."
    ::=  { fsRadExtSiaeServer 1 }

fsRadExtSiaeServerEntry OBJECT-TYPE
    SYNTAX FsRadExtSiaeServerEntry
    MAX-ACCESS not-accessible
    STATUS current
    DESCRIPTION
        "Siae extension of an entry (conceptual row) representing 
         a RADIUS server with which the client shares a secret."
    AUGMENTS { fsRadExtServerEntry }
    ::=  { fsRadExtSiaeServerTable 1 }

FsRadExtSiaeServerEntry ::= SEQUENCE {
    fsRadExtSiaeServerLabel    DisplayString
   }

fsRadExtSiaeServerLabel OBJECT-TYPE
    SYNTAX DisplayString (SIZE(1..32))
    MAX-ACCESS read-write
    STATUS current
    DEFVAL { "SiaeNAS" }
    DESCRIPTION
        "The label which is shared from the Client
         to the server"
    ::=  { fsRadExtSiaeServerEntry 1 }

END

-- ----------------------------------------------------------------------------
--
--  SIAE MICROELETTRONICA s.p.a.
--
--  Via Michelangelo Buonarroti, 21
--  20093 - Cologno Monzese
--  Milano
--  ITALY
--
-- ----------------------------------------------------------------------------
-- ----------------------------------------------------------------------------

SM-MEFEXT-MIB DEFINITIONS ::= BEGIN

IMPORTS
       fsUniCVlanEvcEntry  FROM ARICENT-MEF-MIB
       MODULE-IDENTITY, OBJECT-TYPE, enterprises, Unsigned32  FROM SNMPv2-SMI
       TEXTUAL-CONVENTION, DisplayString  FROM SNMPv2-TC;

smMefMibs  MODULE-IDENTITY
        LAST-UPDATED "201804090000Z"
        ORGANIZATION "SIAE MICROELETTRONICA spa"
        CONTACT-INFO
            "SIAE MICROELETTONICA s.p.a.
             Via Michelangelo Buonarroti, 21
             20093 - Cologno Monzese
             Milano - ITALY
             Phone : +39-02-27325-1
             E-mail: tbd@siaemic.com
            "
        DESCRIPTION  "This MIB defines the objects. OID assign for siae
                     is (29601.100.1)"

        ::=  { enterprises aricent-communication-holding-ltd(29601) 100 1 5}

-- -------------------------------------------------------------------------
           -- groups in the MIB
-- -------------------------------------------------------------------------

smUniCVlanEvc         OBJECT IDENTIFIER ::= { smMefMibs 1 }


-- -------------------------------------------------------------------------
           -- smUniCVlanEvcExtTable START
-- -------------------------------------------------------------------------

smUniCVlanEvcExtTable OBJECT-TYPE
    SYNTAX       SEQUENCE OF SmUniCVlanEvcExtEntry
    MAX-ACCESS   not-accessible
    STATUS       current
    DESCRIPTION
        "This table is an extension of fsUniCVlanEvcTable which contains list of the CE-VLAN ID UNI ID mapped with EVC."
    ::= { smUniCVlanEvc 1 }

smUniCVlanEvcExtEntry OBJECT-TYPE
    SYNTAX       SmUniCVlanEvcExtEntry
    MAX-ACCESS   not-accessible
    STATUS       current
    DESCRIPTION
        "This entry represents CE-VLAN and EVC label mapping."
--    AUGMENTS { fsUniCVlanEvcEntry }
    ::= { smUniCVlanEvcExtTable 1 }

SmUniCVlanEvcExtEntry ::= SEQUENCE {
    smUniCVlanCeLabel DisplayString
    }

smUniCVlanCeLabel OBJECT-TYPE
    SYNTAX      DisplayString (SIZE (0..32))
    MAX-ACCESS  read-write
    STATUS      current
    DESCRIPTION
        "This string value is used to identify CVLAN to SVLAN mappings."
--	DEFVAL { "" }
    ::=  { smUniCVlanEvcExtEntry 1}

END

-- ----------------------------------------------------------------------------
           -- smUniCVlanEvcExtTable END
-- ----------------------------------------------------------------------------

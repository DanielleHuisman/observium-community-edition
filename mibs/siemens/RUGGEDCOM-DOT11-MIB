RUGGEDCOM-DOT11-MIB DEFINITIONS ::= BEGIN

IMPORTS
    MODULE-IDENTITY, OBJECT-IDENTITY,  
    OBJECT-TYPE, IpAddress, Unsigned32,
    TimeTicks                       	FROM SNMPv2-SMI
    OBJECT-GROUP			       	    FROM SNMPv2-CONF    
    DisplayString, MacAddress,
    TruthValue							FROM SNMPv2-TC
    ruggedcomMgmt				        FROM RUGGEDCOM-MIB;
	
rcDot11 MODULE-IDENTITY
    LAST-UPDATED "200902271000Z"      -- Feb 27, 10:00 EST 2009
    ORGANIZATION "RuggedCom"
    CONTACT-INFO
       "Postal: RuggedCom Inc.
                300 Applewood Crescent
                Concord, Ontario, 
                L4K 5C7 Canada
        Tel:    1-905-856-5288
        E-Mail: support@ruggedcom.com"
    
    DESCRIPTION
        "RuggedCom MIB for Managing Wireless Interface on RuggedCom Devices."

    ::= { ruggedcomMgmt 4 }

-- ---------------------------------------------------------------------- --
--  rcDot11 subtrees
-- ---------------------------------------------------------------------- --

rcDot11GlobalParams OBJECT-IDENTITY
    STATUS      current
    DESCRIPTION
        "The main subtree for managing system wide parameters as applicable to 
        wireless interface."
    ::= { rcDot11  1 }    

rcDot11NetworkParams OBJECT-IDENTITY
    STATUS      current
    DESCRIPTION
        "The main subtree for managing Wireless Network related parameteres of 
        wireless interface."
    ::= { rcDot11  2 }    

rcDot11SecurityParams OBJECT-IDENTITY
    STATUS      current
    DESCRIPTION
        "The main subtree for managing Security parameteres on wireless
        interface."
    ::= { rcDot11  3 } 

rcDot11MacFiltering	OBJECT-IDENTITY
	STATUS		current
	DESCRIPTION	
		"The main subtree for managaing Mac Filtering options and entries
		for the wireless interface."
	::= { rcDot11 4 }              
	
rcDot11DhcpParams OBJECT-IDENTITY
    STATUS      current
    DESCRIPTION
        "The main subtree for managing DHCP client-server communication for
        wireless interfaces."
    ::= { rcDot11  5 } 

rcDot11AssociationInfo	OBJECT-IDENTITY
	STATUS 		current
	DESCRIPTION
		"The main subtree for managing information related to associated 
		stations on the wireless interface."
	::= { rcDot11  6 } 		
	
-- ---------------------------------------------------------------------- --
-- branches rcDot11 7,8 and 9 are reserved for future use
-- ---------------------------------------------------------------------- --
rcDot11Conformance	OBJECT IDENTIFIER ::= { rcDot11 10 }
-- rcDot11Compliances  OBJECT IDENTIFIER ::= { rcDot11Conformance 1 }
rcDot11Groups		OBJECT IDENTIFIER ::= { rcDot11Conformance 2 }


-- ---------------------------------------------------------------------- --
--  rcDot11GlobalParams Interface objects
-- ---------------------------------------------------------------------- --

rcDot11OpMode OBJECT-TYPE
    SYNTAX  	INTEGER  {
     			ap(1), 
     			clientBridge(2), 
     			clientIpBridge(3)
     		}
    MAX-ACCESS  read-write
    STATUS      current
    DESCRIPTION
		"The Operational mode of wireless interface."
    ::= { rcDot11GlobalParams 1}

rcDot11RFMAC OBJECT-TYPE
    SYNTAX  	MacAddress
    MAX-ACCESS  read-only
    STATUS      current
    DESCRIPTION
		"The MAC address assigned to the wireless interface side to operate
		in WLAN. Wired interface side is actually WLAN port of the switch 
		and it is represented as an interface entry of ifTable."
    ::= { rcDot11GlobalParams 2}

rcDot11IpAddress OBJECT-TYPE
    SYNTAX  	IpAddress
    MAX-ACCESS  read-only
    STATUS      current
    DESCRIPTION
		"The IP Address assigned to the wireless interface.
		
		Note that wireless interface resides on a daughter card and 
		is supported by separate IP stack."
    ::= { rcDot11GlobalParams 3}

rcDot11IpSubnet OBJECT-TYPE
    SYNTAX  	IpAddress
    MAX-ACCESS  read-only
    STATUS      current
    DESCRIPTION
		"The subnet mask associated with rcDot11SysIpAddress.
		The value of the mask is an IP address with all the network bits set 
		to 1 and all the hosts bits set to 0. 
		
		Note that wireless interface resides on a daughter card and is 
		supported by separate IP stack."
    ::= { rcDot11GlobalParams 4}

rcDot11DefaultGateway OBJECT-TYPE
    SYNTAX  	IpAddress
    MAX-ACCESS  read-only
    STATUS      current
    DESCRIPTION 
		"The default IP Gateway for the wireless interface. 
		
		Note that wireless interface resides on a daughter card and is
		supported by separate IP stack."
    ::= { rcDot11GlobalParams 5}
    
rcDot11Status OBJECT-TYPE
    SYNTAX  	INTEGER  {
    			unknown(1), 
    			booting(2), 
    			running(3), 
    			cmdProcessing(4), 
    			softwareUpgrade(5)
    		}
    MAX-ACCESS  read-only
    STATUS      current
    DESCRIPTION
		"The current status of the wireless interface."
    ::= { rcDot11GlobalParams   6}

rcDot11UpTime OBJECT-TYPE
    SYNTAX      DisplayString
    MAX-ACCESS  read-only
    STATUS      current
    DESCRIPTION
		"The time since the daughter card was last re-initialized."
    ::= { rcDot11GlobalParams 7}

rcDot11Version OBJECT-TYPE
    SYNTAX  	DisplayString 
    MAX-ACCESS  read-only
    STATUS      current
    DESCRIPTION
		"The version of the WLAN firmware residing on the wireless daughter 
		card."
    ::= { rcDot11GlobalParams   8}

rcDot11TftpServerIpAddress OBJECT-TYPE
    SYNTAX  	IpAddress
    MAX-ACCESS  read-write
    STATUS      current
    DESCRIPTION 
		"The IP address of the TFTP server where the WLAN firmware is located.
		
		Note that rcDot11IpAddress and rcDot11TftpServerIpAddress must be on
		the same IP subnet."
    ::= { rcDot11GlobalParams   9}  

rcDot11SwUpgrade OBJECT-TYPE    
    SYNTAX  	TruthValue
    MAX-ACCESS  read-write
    STATUS      current
    DESCRIPTION 
		"Setting the value of this object to 'true(1)' will start firmware
		upgrade procedure for the wireless daughter card.
		
		Note that this upgrade will take approximately 15 mintues to complete."
    ::= { rcDot11GlobalParams   10}  

rcDot11SwUpgradeStatus OBJECT-TYPE    
    SYNTAX  	DisplayString
    MAX-ACCESS  read-only
    STATUS      current
    DESCRIPTION 
		"The Current status of the software upgrade process for the wireless 
		daughter card."
    ::= { rcDot11GlobalParams   11}  

rcDot11WlanReset OBJECT-TYPE   
    SYNTAX  	INTEGER {
    			none(1), 
    			fullReset(2), 
    			quickReset(3)
    		}
    MAX-ACCESS  read-write
    STATUS      current
    DESCRIPTION 
		"The software controlled WLAN interface reset functionality. 
		
		Setting the value of this object to 'fullReset(2)' will reset to both,
		the RF and Ethernet interfaces of WLAN (duration is approx 70 seconds). 
		
		Setting the value of this object to 'quickReset(3)' will reset only the
		RF interface of WLAN (duration is approx 10 seconds).
		
		As a result of Read request the agent will return value 'none(1)'.
		
		NOTE: The daughter card must be reset, to activate any newly applied 
		WLAN parameter(s). Most WLAN parameters only require a 
		'quickReset(3)' to take effect, and it is also acceptable for the user 
		to issue a single reset command, even after several multiple WLAN 
		parameters may have been changed."
    ::= { rcDot11GlobalParams   12}  

-- ---------------------------------------------------------------------- --
--  rcDot11NetworkParams objects
-- ---------------------------------------------------------------------- --

rcDot11NetworkPhyMode OBJECT-TYPE
    SYNTAX  	INTEGER { 
    			auto(1), 
    			dot11b(2), 
    			dot11g(3)
    		}
    MAX-ACCESS  read-write
    STATUS      current
    DESCRIPTION
		"The wireless mode running on the wireless network.
		
		Setting the value of this object to 'auto(1)' will allow Access Point
		to select the wireless mode. 
		
		Setting the value of this object to 'dot11b(2) allows 802.11b mode only
		(up to 11 Mbps). 
		
		Setting the value of this object to 'dot11g(3) allows 802.11g mode with
		802.11b compatibility (up to 54 Mbps)"

    ::= { rcDot11NetworkParams 1}

rcDot11NetworkDesiredSsid OBJECT-TYPE
    SYNTAX  	OCTET STRING (SIZE(3..32))
    MAX-ACCESS  read-write
    STATUS      current
    DESCRIPTION
		"The Service Set ID (SSID). This value is a unique name which is used
		to identify the wireless network for an Access Point(AP)."
    ::= { rcDot11NetworkParams 2}  

rcDot11NetworkPrimarySsid	OBJECT-TYPE
	SYNTAX		OCTET STRING (SIZE(3..32))
	MAX-ACCESS	read-write
	STATUS		current
	DESCRIPTION
		"The Service Set ID (SSID). This value is a unique name which is used
		to identify the Primary Network for a ClientBridge or ClientIpBridge.	
		
		Note that for wireless clients upto three networks are supported, 
		identified by objects rcDot11PrimaryNetworkSsid, 
		rcDot11SecondaryNetwork1Ssid and rcDot11SecondaryNetwork2Ssid. 
		If the rcDot11PrimaryNetworkSsid network is unavailable then Client 
		will try to connect to rcDot11SecondaryNetwork1Ssid network and then 
		rcDot11SecondaryNetwork2Ssid if  rcDot11SecondaryNetwork1Ssid is also
		unavailable. In this way wireless network achieves simple redundancy
		through this technique."
	::= { rcDot11NetworkParams 3}  		
	
rcDot11NetworkSecondary1Ssid   OBJECT-TYPE
	SYNTAX		OCTET STRING (SIZE(3..32))
	MAX-ACCESS	read-write
	STATUS		current
	DESCRIPTION
		"The Service Set ID (SSID). This value is a unique name which is used
		to identify the First secondary network (Secondary 1) for a 
		ClientBridge or ClientIpBridge.
		
		Note that for wireless clients upto three networks are supported, 
		identified by objects rcDot11PrimaryNetworkSsid, 
		rcDot11SecondaryNetwork1Ssid and rcDot11SecondaryNetwork2Ssid. 
		If the rcDot11PrimaryNetworkSsid network is unavailable then Client 
		will try to connect to rcDot11SecondaryNetwork1Ssid network and then 
		rcDot11SecondaryNetwork2Ssid if  rcDot11SecondaryNetwork1Ssid is also
		unavailable. In this way wireless network achieves simple redundancy
		through this technique."
	::= { rcDot11NetworkParams 4}  		
	
rcDot11NetworkSecondary2Ssid   OBJECT-TYPE
	SYNTAX		OCTET STRING (SIZE(3..32))
	MAX-ACCESS	read-write
	STATUS		current
	DESCRIPTION
		"The Service Set ID (SSID). This value is a unique name which is used
		to identify the Second Secondary network (Secondary 2) for a 
		ClientBridge or ClientIpBridge. 
		
		Note that for wireless clients upto three networks are supported, 
		identified by objects rcDot11PrimaryNetworkSsid, 
		rcDot11SecondaryNetwork1Ssid and rcDot11SecondaryNetwork2Ssid. 
		If the rcDot11PrimaryNetworkSsid network is unavailable then Client 
		will try to connect to rcDot11SecondaryNetwork1Ssid network and then 
		rcDot11SecondaryNetwork2Ssid if  rcDot11SecondaryNetwork1Ssid is also
		unavailable. In this way wireless network achieves simple redundancy
		through this technique."
	::= { rcDot11NetworkParams 5}  
					
rcDot11NetworkRfChannel OBJECT-TYPE
    SYNTAX  	INTEGER (0..13)
    MAX-ACCESS  read-write
    STATUS      current
    DESCRIPTION
		"RF communication channel for the wireless interface. 
		
		All devices in the same Basic Service Set ID (BSSID) must be 
		communicating on the same channel in order to function correctly. 

		Settings this object value to 0 allows the device to scan and choose
		the best available channel, while a channel number (1 to 13) allows to
		select a specific channel. 

		Users are responsible for ensuring that the channel configuration 
		complies with the regulatory standards."
    ::= { rcDot11NetworkParams 6}

rcDot11NetworkSsidTxSuppress OBJECT-TYPE
    SYNTAX  	TruthValue
    MAX-ACCESS  read-write
    STATUS      current
    DESCRIPTION 
		"Setting the value of this object to 'true(1)' will suppress sending 
		SSID information by Wireless Access Point(AP). 
		
		Setting the value of this object to 'false(2)' will allow sending SSID 
		information by AP. "
    ::= { rcDot11NetworkParams 7}

rcDot11NetworkRfTxEnable OBJECT-TYPE
    SYNTAX  	TruthValue
    MAX-ACCESS  read-write
    STATUS      current
    DESCRIPTION 
		"Setting the value of this object to 'true(1)' enables the RF 
		transmitter of wireless interface.                                                 
		
		Setting the value of this object to 'false(2)' disables the RF 
		transmitter."
    ::= { rcDot11NetworkParams 8 }

rcDot11NetworkRate OBJECT-TYPE
    SYNTAX  	INTEGER {
				best(1),
				mbps1(2),
				mbps2(3),
				mbps11(4),
				mbps12(5),
				mbps18(6),
				mbps24(7),
				mbps36(8),
				mbps48(9),
				mbps54(10)
    		}
    MAX-ACCESS  read-write
    STATUS      current
    DESCRIPTION
        "Data link rate (in Mbps) of the wireless interface.
        
        'best(1)'		-	Choose the best data link rate for the interface.
		'mbps1(2)'	    -	1  Mbps
		'mbps2(3)'	    -	2  Mbps
		'mbps11(4)'	    -   11 Mbps
		'mbps12(5)'	    -   12 Mbps
		'mbps18(6)'	    -	18 Mbps
		'mbps24(7)'	    -   24 Mbps
		'mbps36(8)'	    -   26 Mbps
		'mbps48(9)'	    -   48 Mbps
		'mbps54(10)'	-	54 Mpbs."

    ::= { rcDot11NetworkParams 9 }

rcDot11NetworkTxPower OBJECT-TYPE
    SYNTAX  	INTEGER (1..20)
    MAX-ACCESS  read-write
    STATUS      current
    DESCRIPTION
        "Maximum RF transmission power of the wireless interface."
    ::= { rcDot11NetworkParams 10 }

rcDot11NetworkWdsEnable OBJECT-TYPE
    SYNTAX  	TruthValue
    MAX-ACCESS  read-write
    STATUS      current
    DESCRIPTION
        "The Wireless Distribution System (WDS) support. 
        WDS is simply a mechanism for constructing 802.11 frames using the 
        4-address format.
        
        Setting the value of this object to 'true(1)' enables WDS support.
        
        Setting the value of this object to 'false(2)' disbales this 
        functionality.
        
        Note that this object must have a 'true(1)' value if rcDot11OpMode 
        object value is 'ap(1)' to support station(s) with Client/Bridge 
        functionality in the network."
    ::= { rcDot11NetworkParams 11}

rcDot11NetworkWmmEnable OBJECT-TYPE
    SYNTAX  	TruthValue
    MAX-ACCESS  read-write
    STATUS      current
    DESCRIPTION 
		"The Wireless Multimedia Support (WMM) is, actually QoS support for the
		wireless interface.
		
		Setting the value of this object to 'true(1)' enables the QoS support.
		
		Setting this value of this object to 'false(2)' disables this 
		functionality.
		
		Note the mapping in the presence of DS (DiffServ) field: 
		
		DSCP 0x08 and 0x10 mapped to 'Background'. 
		DSCP 0x20 and 0x28 mapped to 'Video'. 
		DSCP 0x30 and 0x38 mapped to 'Voice'.
		All other DSCP(DiffServ Code Point) are mapped to 'Best Effort'."
    ::= { rcDot11NetworkParams 12}

rcDot11NetworkTxShortPreamble OBJECT-TYPE
    SYNTAX  	TruthValue
    MAX-ACCESS  read-write
    STATUS      current
    DESCRIPTION 
		"Setting the value of this object to 'true(1)' allows sending short
		preamble block in the frames during wireless communication.
		
		Setting the value of this object to 'false(2)' lets the device 
		communicate using long preamble.
				
		Note that the value of the object must be 'false(2)' when
		rcDot11NetworkPhyMode is set to 'dott11b(2)'."
    ::= { rcDot11NetworkParams 13}

rcDot11NetworkDistance OBJECT-TYPE
    SYNTAX  	INTEGER (300..15000)
    MAX-ACCESS  read-write
    STATUS      current
    DESCRIPTION 
		"The distance (in meters) between AP and the farthest station.
		It allows to optimize the wireless communication parameters, especially
		for running wireless links over long distances.
		
		Note that all WLAN devices on a network must have approximately the
		same distance parameters setting for optimal performance."
    ::= { rcDot11NetworkParams 14}
 
rcDot11NetworkAssociatedStations OBJECT-TYPE
    SYNTAX  	Unsigned32 (0..64)
    MAX-ACCESS  read-only
    STATUS      current
    DESCRIPTION 
         "Number of connected station(s) in the wireless network."
    ::= { rcDot11NetworkParams  15}

-- ---------------------------------------------------------------------- --
--  rcDot11SecurityParams objects
-- ---------------------------------------------------------------------- --
 
rcDot11SecurityAuthMode OBJECT-TYPE
    SYNTAX  	INTEGER {
				none(1), 
				wep(2), 
				dot1x(3), 
				wpa(4), 
				wpaPsk(5), 
				wpa2(6), 
				wpa2psk(7), 
				wpaAuto(8), 
				wpaAutoPsk(9)
			}
    MAX-ACCESS  read-write
    STATUS      current
    DESCRIPTION
		"Authentication mode to be used by the wireless interface in the 
		network. 
		
		'none(1)' 		- 	No authentication. 
		'wep(2)'  		- 	WEP as an authentication algorithm 
		'dot1X(3)'		-	802.1X based authentication with RADIUS client and 
							server running on backend.
		'wpa(4)'		-	WPAv1 authentication type (Enterprise). 
		'wpaPsk(5)'		- 	WPAv1-PSK authentication type(Personal). 
		'wpa2(6)'		- 	WPAv2 authentication type (Enterprise). 
		'wpa2Psk(7)'	- 	WPAv2-PSK authentication type (Personal). 
		'wpaAuto(8)'	- 	WPAv1 or WPAv2 authentication type (Enterprise). 
		'wpaAutoPsk(9)'	- 	WPAv1 or WPAv2 authentication type (Personal).
		
		Note that for the object value of 'wep(2)' value of object 
		rcDot11SecurityEncrypType must also be set to 'wep(2)'."
    ::= { rcDot11SecurityParams 1}

rcDot11SecurityEncrypType OBJECT-TYPE
    SYNTAX  	INTEGER {
				auto(1), 
				wep(2), 
				tkip(3), 
				aes(4)
	    	}
    MAX-ACCESS  read-write
    STATUS      current
    DESCRIPTION
		"Encryption algorithm to be used, in conjunction with the  
		rcDot11SecurityAuthMode object.
		
		Note that with rcDot11OpMode object value set to 'clientBridge(2)' 
		only 'none(0)', 'wpaPsk(5)' and 'wpa2Psk(7)' values are supported for
		this object.
		
		The value of 'aes(4)' is supported only when rcDot11SecurityAuthMode
		object value is set to 'wpa2(6)' or 'wpa2psk(7)'."
    ::= { rcDot11SecurityParams 2}

rcDot11SecurityPassPhrase OBJECT-TYPE
    SYNTAX  	OCTET STRING (SIZE(0..48))       
    MAX-ACCESS  read-write
    STATUS      current
    DESCRIPTION
        "Security Pass Phrase to be used on the wireless network."
    ::= { rcDot11SecurityParams 3}

rcDot11SecurityWepKey OBJECT-TYPE
    SYNTAX  	OCTET STRING (SIZE(10|26))
    MAX-ACCESS  read-write
    STATUS      current
    DESCRIPTION 
		"WEP key for the wireless network presented as an octet string
		containing ASCII presentation of hexadecimal digits. 
		
		This key is applicaple only when rcDot11SecurityAuthMode object value
		is set to 'wep(2)'."
    ::= { rcDot11SecurityParams 4}

rcDot11SecurityKeyRenewal OBJECT-TYPE
    SYNTAX  	TimeTicks
    MAX-ACCESS  read-write
    STATUS      current
    DESCRIPTION 
		"Time (in hundredths of second) within which group key for the wireless 
		network should be changed."
    ::= { rcDot11SecurityParams 5}

rcDot11SecurityRadiusIpAddress OBJECT-TYPE
    SYNTAX  	IpAddress
    MAX-ACCESS  read-write
    STATUS      current
    DESCRIPTION
		"The IP Address of RADIUS server used by wireless interface for 802.1x
		based authentication."
    ::= { rcDot11SecurityParams 6}

rcDot11SecurityRadiusPort OBJECT-TYPE
    SYNTAX  	INTEGER  (1..65535)
    MAX-ACCESS  read-write
    STATUS      current
    DESCRIPTION
		"The UDP port at which RADIUS server for the wireless interface is to 
		be contacted."
    ::= { rcDot11SecurityParams 7}

rcDot11SecurityRadiusSecret OBJECT-TYPE
    SYNTAX  	OCTET STRING  (SIZE(8..48))
    MAX-ACCESS  read-write
    STATUS      current
    DESCRIPTION
		"The secret shared with the RADIUS server for 802.1x based 
		authentication."
    ::= { rcDot11SecurityParams 8}


-- ---------------------------------------------------------------------- --
--  rcDot11MacFiltering objects
-- ---------------------------------------------------------------------- --

rcDot11MacFilteringControl OBJECT-TYPE
	SYNTAX		INTEGER	{
				open(1),
				allow(2),
				deny(3)
			}     
	MAX-ACCESS	read-write
	STATUS		current
	DESCRIPTION
		"MAC filtering policy in place for WLAN. 
		
		'open(1)'  - No MAC filtering is performed, any MAC address is allowed
		             to connect from the network. 
		'allow(2)' - Only allow MACs specified in rcDot11MacFilteringTable. 
		'deny(3)'  - Only deny MACs specified in rcDot11MacFilteringTable."
	::= { rcDot11MacFiltering  1}
		

rcDot11MacFilteringTable OBJECT-TYPE
    SYNTAX      SEQUENCE OF RcDot11MacFilteringEntry
    MAX-ACCESS  not-accessible
    STATUS      current
    DESCRIPTION
		"This table provides ability to configure wireless LAN MAC filtering 
		entries. MACs represented by entries in this table are controlled per  
		description of the object rcDot11MacFilteringControl."
    ::= { rcDot11MacFiltering 2 }

rcDot11MacFilteringEntry OBJECT-TYPE
    SYNTAX      RcDot11MacFilteringEntry
    MAX-ACCESS  not-accessible
    STATUS      current
    DESCRIPTION
		"Each entry contains one MAC address."
    INDEX   { rcDot11FilterMacAddress }
    ::= { rcDot11MacFilteringTable 1 }

RcDot11MacFilteringEntry ::= SEQUENCE {
        rcDot11FilterMacAddress  MacAddress,
        rcDot11RowStatus         INTEGER
        }

rcDot11FilterMacAddress OBJECT-TYPE
    SYNTAX      MacAddress
    MAX-ACCESS  not-accessible
    STATUS      current
    DESCRIPTION
		"The MAC address from the network controled per description of the 
		object rcDot11MacFilteringControl."
    ::= { rcDot11MacFilteringEntry 1 }    
    
rcDot11RowStatus OBJECT-TYPE
	SYNTAX		INTEGER {
				active(1),
				createAndGo(4),				
				delete(6)
			}
	MAX-ACCESS	read-create
	STATUS		current
	DESCRIPTION	
		"The status of this conceptual row.
		The syntax of this object represents restricted RowStatus
		functionality."
	REFERENCE
	    "Description of RowStatus in SNMPv2-TC."
	    	
	::= { rcDot11MacFilteringEntry 2 }

-- ---------------------------------------------------------------------- --
--  rcDot11DhcpParams objects
-- ---------------------------------------------------------------------- --

rcDot11DhcpServerEnable  OBJECT-TYPE
    SYNTAX  	TruthValue    
    MAX-ACCESS  read-write
    STATUS      current
    DESCRIPTION
		"Setting the value of this object to 'true(1)' enables the DHCP server 
		functionality on wireless daughter card.
		
		Setting the value of this object to 'false(2)' disables the DHCP server
		functionality on the wireless daughter card."
    ::= { rcDot11DhcpParams  1}

rcDot11DhcpStartOfPool  OBJECT-TYPE
    SYNTAX  	IpAddress
    MAX-ACCESS  read-write
    STATUS      current
    DESCRIPTION
		"Beginning of IP address pool in the DHCP server."
    ::= { rcDot11DhcpParams 2}

rcDot11DhcpIpPoolSize  OBJECT-TYPE
    SYNTAX  	INTEGER (1..64)
    MAX-ACCESS  read-write
    STATUS      current
    DESCRIPTION
		"Size of IP address pool in the DHCP server."
    ::= { rcDot11DhcpParams  3}

rcDot11DhcpSubnet  OBJECT-TYPE
    SYNTAX  	IpAddress
    MAX-ACCESS  read-write
    STATUS      current
    DESCRIPTION 
		"The subnet mask associated with the DHCP server.
		
		The value of the mask is an IP address with all the network bits set 
		to 1 and all the hosts bits set to 0. "
    ::= { rcDot11DhcpParams  4}

rcDot11DhcpGateway  OBJECT-TYPE
    SYNTAX  	IpAddress
    MAX-ACCESS  read-write
    STATUS      current
    DESCRIPTION 
		"The default gateway to be used by DHCP server."
    ::= { rcDot11DhcpParams  5}

rcDot11DhcpDnsIpAddress  OBJECT-TYPE
    SYNTAX  	IpAddress
    MAX-ACCESS  read-write
    STATUS      current
    DESCRIPTION 
		"The IP address of DNS server in the DHCP server."
    ::= { rcDot11DhcpParams  6}

rcDot11DhcpLeaseTime  OBJECT-TYPE
    SYNTAX  	TimeTicks 
    MAX-ACCESS  read-write
    STATUS      current
    DESCRIPTION 
		"Lease Time (in hundredths of second) to be used by DHCP server for the
		IpAddress assigned to other devices.                                          
		
		Note that valid lease time varies between 6000 - 259200000."
    ::= { rcDot11DhcpParams  7}
 
-- ---------------------------------------------------------------------- --
--  rcDot11AssociationInfo objects
-- ---------------------------------------------------------------------- --

rcDot11AssociationTable OBJECT-TYPE
    SYNTAX      SEQUENCE OF RcDot11AssociationEntry
    MAX-ACCESS  not-accessible
    STATUS      current
    DESCRIPTION
   		"This table provides detailed information on wireless links with 
		associated stations if rcDot11OpMode object value is set to 'ap(1)'. 
		
		If rcDot11OpMode object value is set to to 'clientBridge(2)' or 
		'clientIpBridge(3)' then this table reflects the link information to 
		the	associated AP."
    ::= { rcDot11AssociationInfo 1 }

rcDot11AssociationEntry OBJECT-TYPE
    SYNTAX      RcDot11AssociationEntry
    MAX-ACCESS  not-accessible
    STATUS      current
    DESCRIPTION
		"Each entry contains one MAC address with its associated network 
		settings on a wireless link."
    INDEX   { rcDot11AssociationMac }
    ::= { rcDot11AssociationTable 1 }
 
  
RcDot11AssociationEntry ::= SEQUENCE {
        rcDot11AssociationMac		MacAddress,
        rcDot11AssociationChannel	Unsigned32,
        rcDot11AssociationRate		Unsigned32,
        rcDot11AssociationRssi		Unsigned32,
        rcDot11AssociationTxSeq		Unsigned32,
        rcDot11AssociationRxSeq		Unsigned32,
        rcDot11AssociationSecurity  OCTET STRING
        }

rcDot11AssociationMac OBJECT-TYPE
    SYNTAX      MacAddress
    MAX-ACCESS  not-accessible
    STATUS      current
    DESCRIPTION
		"The MAC address of associated station on a wireless link."
    ::= { rcDot11AssociationEntry 1 }

rcDot11AssociationChannel OBJECT-TYPE
    SYNTAX      Unsigned32 
    MAX-ACCESS  read-only
    STATUS      current
    DESCRIPTION
		"The association channel in use for this wireless link."
    ::= { rcDot11AssociationEntry 2 }

rcDot11AssociationRate OBJECT-TYPE
    SYNTAX      Unsigned32 
    MAX-ACCESS  read-only
    STATUS      current
    DESCRIPTION
		"The current data rate for this wireless link."
    ::= { rcDot11AssociationEntry 3 }

rcDot11AssociationRssi OBJECT-TYPE
    SYNTAX      Unsigned32
    MAX-ACCESS  read-only
    STATUS      current
    DESCRIPTION
		"The RSSI(Received Signal Strength Indication) of the power present in 
		a received RF signal for this wireless link."
    ::= { rcDot11AssociationEntry 4 }

rcDot11AssociationTxSeq OBJECT-TYPE
    SYNTAX      Unsigned32
    MAX-ACCESS  read-only
    STATUS      current
    DESCRIPTION
		"The Transmitter sequence number for associated station on this 
		wireless link."
    ::= { rcDot11AssociationEntry 5 }

rcDot11AssociationRxSeq OBJECT-TYPE
    SYNTAX      Unsigned32
    MAX-ACCESS  read-only
    STATUS      current
    DESCRIPTION
		"The Receiver sequence number from the associated station on this 
		wireless link."           
    ::= { rcDot11AssociationEntry 6 }

rcDot11AssociationSecurity  OBJECT-TYPE
    SYNTAX      OCTET STRING
    MAX-ACCESS  read-only
    STATUS      current
    DESCRIPTION
		"The Security policy in place for this wireless link."
    ::= { rcDot11AssociationEntry 7 }

-- ---------------------------------------------------------------------- --
--  Object Groups
-- ---------------------------------------------------------------------- --

-- ---------------------------------------------------------------------- --
--  rcDot11Groups Interface objects
-- ---------------------------------------------------------------------- --

rcDot11GlobalParamsGroup OBJECT-GROUP
	OBJECTS		{
				rcDot11OpMode,
				rcDot11RFMAC,
				rcDot11IpAddress,
				rcDot11IpSubnet, 
				rcDot11DefaultGateway,
				rcDot11Status,
				rcDot11UpTime,
				rcDot11Version,
				rcDot11TftpServerIpAddress,
				rcDot11SwUpgrade,
				rcDot11SwUpgradeStatus,
				rcDot11WlanReset 
				} 
	STATUS      current
    DESCRIPTION 
		"Objects related to global settings for wireless daughter card."
    ::= { rcDot11Groups 1 }   			
                    
rcDot11NetworkParamsGroup	OBJECT-GROUP
	OBJECTS     {
				rcDot11NetworkPhyMode,
				rcDot11NetworkDesiredSsid,
				rcDot11NetworkPrimarySsid,
				rcDot11NetworkSecondary1Ssid,
				rcDot11NetworkSecondary2Ssid,
				rcDot11NetworkRfChannel,
				rcDot11NetworkSsidTxSuppress,
				rcDot11NetworkAssociatedStations,
				rcDot11NetworkRfTxEnable,
				rcDot11NetworkRate,
				rcDot11NetworkTxPower,
				rcDot11NetworkWdsEnable,
				rcDot11NetworkWmmEnable,
				rcDot11NetworkTxShortPreamble,
				rcDot11NetworkDistance
	           }
    STATUS      current
    DESCRIPTION 
		"Objects related to managing Network related settings on wireless 
		daughter card."
    ::= { rcDot11Groups 2 }    

rcDot11SecurityParamsGroup	OBJECT-GROUP
	OBJECTS    {
				rcDot11SecurityAuthMode,				
				rcDot11SecurityEncrypType ,
				rcDot11SecurityPassPhrase,
				rcDot11SecurityWepKey,
				rcDot11SecurityKeyRenewal,
				rcDot11SecurityRadiusIpAddress,
				rcDot11SecurityRadiusPort,
				rcDot11SecurityRadiusSecret
	           }
    STATUS      current
    DESCRIPTION 
		"Objects related to managing Security attributes on wireless daughter
		card."
    ::= { rcDot11Groups 3 }    

rcDot11DhcpParamsGroup	OBJECT-GROUP
	OBJECTS		{
				rcDot11DhcpServerEnable,
				rcDot11DhcpStartOfPool,
				rcDot11DhcpIpPoolSize,
				rcDot11DhcpSubnet,
				rcDot11DhcpGateway,
				rcDot11DhcpDnsIpAddress,
				rcDot11DhcpLeaseTime
				}
	STATUS		current
	DESCRIPTION
		"Objects related to managing DHCP server on wirless	daughter card."
	::= { rcDot11Groups 4 } 			

rcDot11MacFilteringTableGroup	OBJECT-GROUP
	OBJECTS		{               
				rcDot11MacFilteringControl,
				rcDot11RowStatus 				
				}
	STATUS		current
	DESCRIPTION	
		"This group includes objects related to Mac Filter control."
	::= { rcDot11Groups 5 } 
	
rcDot11AssociationTableGroup	OBJECT-GROUP
	OBJECTS		{ 
				rcDot11AssociationChannel,
				rcDot11AssociationRate,
				rcDot11AssociationRssi,
				rcDot11AssociationTxSeq,
				rcDot11AssociationRxSeq,
				rcDot11AssociationSecurity
				}
	STATUS		current
	DESCRIPTION
		"Objects related to associated station(s) on their respective
		wireless link."
	::= { rcDot11Groups 6 }
END

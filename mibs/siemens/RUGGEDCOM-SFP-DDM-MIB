-- --------------------------------------------------------------------- --
-- RuggedCom Private SFP DDM MIB
-- --------------------------------------------------------------------- --
RUGGEDCOM-SFP-DDM-MIB DEFINITIONS ::= BEGIN

IMPORTS
    MODULE-IDENTITY,
    OBJECT-TYPE, Integer32              FROM SNMPv2-SMI
    DisplayString, TEXTUAL-CONVENTION,
    TruthValue                          FROM SNMPv2-TC
    OBJECT-GROUP                        FROM SNMPv2-CONF 
    ruggedcomMgmt, ruggedcomTraps       FROM RUGGEDCOM-MIB;

rcSfpDdm                MODULE-IDENTITY
    LAST-UPDATED "202107211620Z"      -- Jul 21, 16:20 EST 2021;
    ORGANIZATION "Siemens Canada Ltd., Process Industries and Drives"
    CONTACT-INFO
       "Postal: Siemens Canada Ltd.
                300 Applewood Crescent
                Concord, Ontario, 
                L4K 5C7 Canada
        Tel:    1-905-856-5288
        E-Mail: support.canada.automation@siemens.com"
    DESCRIPTION
        "RuggedCom proprietary to monitor SFP DDM information."

    ::= { ruggedcomMgmt 17 }

-- --------------------------------------------------------------------- --
-- Textual Conventions
-- --------------------------------------------------------------------- --
RcSfpDdmAlarmWarnStatus ::= TEXTUAL-CONVENTION
    STATUS                      current
    DESCRIPTION
        "DDM alarm and warning status of an SFP transceiver."
    SYNTAX INTEGER {
                        notAvailable(1), -- DDM information is not available
                        ok(2),           -- no alarm or warning flag is set
                        warning(3),      -- at least one warning flag is set
                        alarm(4)         -- at least one alarm flag is set
                   }

-- --------------------------------------------------------------------- --
-- rcSfpDdm subtrees
-- --------------------------------------------------------------------- --
rcSfpDdmGlobalConfig            OBJECT IDENTIFIER ::= { rcSfpDdm 1 }
rcSfpDdmTables                  OBJECT IDENTIFIER ::= { rcSfpDdm 2 }
rcSfpDdmConformance             OBJECT IDENTIFIER ::= { rcSfpDdm 3 }
rcSfpDdmGroups                  OBJECT IDENTIFIER ::= { rcSfpDdmConformance 2 }
ruggedcomSfpDdmTraps            OBJECT IDENTIFIER ::= { ruggedcomTraps 52 }

-- --------------------------------------------------------------------- --
-- rcSfpDdm Global Configuration subtree
-- --------------------------------------------------------------------- --
rcSfpDdmPollingInterval         OBJECT-TYPE
    SYNTAX                      Integer32(0..30)
    UNITS                       "minutes"
    MAX-ACCESS                  read-write
    STATUS                      current
    DESCRIPTION
        "The time interval in minutes to wait between two consecutive readings
         from SFP/SFP+ transceivers installed. When this interval is set to 0,
         the SFP DDM feature will be disabled on the system."
    ::= { rcSfpDdmGlobalConfig 1 }

-- --------------------------------------------------------------------- --
-- Tables subtree
-- --------------------------------------------------------------------- --
rcSfpDdmPortTable               OBJECT-TYPE
    SYNTAX                      SEQUENCE OF RcSfpDdmPortEntry
    MAX-ACCESS                  not-accessible
    STATUS                      current
    DESCRIPTION
        "A list of SFP DDM port entries."
    ::= { rcSfpDdmTables 1 }

rcSfpDdmPortEntry               OBJECT-TYPE
    SYNTAX                      RcSfpDdmPortEntry
    MAX-ACCESS                  not-accessible
    STATUS                      current
    DESCRIPTION
        "SFP DDM parameters for an SFP port."
    INDEX { rcSfpPortId }
    ::= { rcSfpDdmPortTable 1 }

RcSfpDdmPortEntry ::=           SEQUENCE {
        rcSfpPortId                         Integer32,
        rcSfpPlugged                        TruthValue,
        rcSfpDdmVendorName                  DisplayString,
        rcSfpDdmVendorPartNumber            DisplayString,
        rcSfpDdmVendorRevision              DisplayString,
        rcSfpDdmVendorSerialNumber          DisplayString,
        rcSfpDdmEncoding                    DisplayString,
        rcSfpDdmNominalBitrate              DisplayString,
        rcSfpDdmConnectorType               DisplayString,
        rcSfpDdmWavelength                  DisplayString,
        rcSfpDdmLinkLength                  DisplayString,

        rcSfpDdmImplemented                 TruthValue,
        rcSfpDdmCurrentStatus               RcSfpDdmAlarmWarnStatus,
        rcSfpDdmCurrentTemperature          Integer32,
        rcSfpDdmThreshTempAlarmLow          Integer32,
        rcSfpDdmThreshTempWarnLow           Integer32,
        rcSfpDdmThreshTempWarnHigh          Integer32,
        rcSfpDdmThreshTempAlarmHigh         Integer32,
        rcSfpDdmCurrentVoltage              Integer32,
        rcSfpDdmThreshVoltageAlarmLow       Integer32,
        rcSfpDdmThreshVoltageWarnLow        Integer32,
        rcSfpDdmThreshVoltageWarnHigh       Integer32,
        rcSfpDdmThreshVoltageAlarmHigh      Integer32,
        rcSfpDdmCurrentTxBiasCurrent        Integer32,
        rcSfpDdmThreshTxBiasAlarmLow        Integer32,
        rcSfpDdmThreshTxBiasWarnLow         Integer32,
        rcSfpDdmThreshTxBiasWarnHigh        Integer32,
        rcSfpDdmThreshTxBiasAlarmHigh       Integer32,
        rcSfpDdmCurrentRxPower              Integer32,
        rcSfpDdmThreshRxPowerAlarmLow       Integer32,
        rcSfpDdmThreshRxPowerWarnLow        Integer32,
        rcSfpDdmThreshRxPowerWarnHigh       Integer32,
        rcSfpDdmThreshRxPowerAlarmHigh      Integer32,
        rcSfpDdmCurrentTxPower              Integer32,
        rcSfpDdmThreshTxPowerAlarmLow       Integer32,
        rcSfpDdmThreshTxPowerWarnLow        Integer32,
        rcSfpDdmThreshTxPowerWarnHigh       Integer32,
        rcSfpDdmThreshTxPowerAlarmHigh      Integer32,
        rcSfpDdmWarningFlags                BITS,
        rcSfpDdmAlarmFlags                  BITS
    }

rcSfpPortId                     OBJECT-TYPE 
    SYNTAX                      Integer32(1..65535)
    MAX-ACCESS                  not-accessible
    STATUS                      current
    DESCRIPTION
        "The SFP port identifier for which this entry contains information.
         The value is limited by number of SFP ports on the device."
    ::= { rcSfpDdmPortEntry 1 }

rcSfpPlugged                    OBJECT-TYPE
    SYNTAX                      TruthValue
    MAX-ACCESS                  read-only
    STATUS                      current
    DESCRIPTION
        "SFP transceiver is plugged or not. true(1) is plugged and
         false(2) is unplugged."
    ::= { rcSfpDdmPortEntry 2 }

rcSfpDdmVendorName              OBJECT-TYPE
    SYNTAX                      DisplayString
    MAX-ACCESS                  read-only
    STATUS                      current
    DESCRIPTION
        "The vendor's name of the SFP transceiver."
    ::= { rcSfpDdmPortEntry 3 }

rcSfpDdmVendorPartNumber        OBJECT-TYPE
    SYNTAX                      DisplayString
    MAX-ACCESS                  read-only
    STATUS                      current
    DESCRIPTION
        "The vendor's part number of the SFP transceiver."
    ::= { rcSfpDdmPortEntry 4 }

rcSfpDdmVendorRevision          OBJECT-TYPE
    SYNTAX                      DisplayString
    MAX-ACCESS                  read-only
    STATUS                      current
    DESCRIPTION
        "The vendor's revision of the SFP transceiver."
    ::= { rcSfpDdmPortEntry 5 }

rcSfpDdmVendorSerialNumber      OBJECT-TYPE
    SYNTAX                      DisplayString
    MAX-ACCESS                  read-only
    STATUS                      current
    DESCRIPTION
        "The vendor's serial number of the SFP transceiver."
    ::= { rcSfpDdmPortEntry 6 }

rcSfpDdmEncoding                OBJECT-TYPE
    SYNTAX                      DisplayString
    MAX-ACCESS                  read-only
    STATUS                      current
    DESCRIPTION
        "The encoding mechanism of the SFP transceiver."
    ::= { rcSfpDdmPortEntry 7 }

rcSfpDdmNominalBitrate          OBJECT-TYPE
    SYNTAX                      DisplayString
    MAX-ACCESS                  read-only
    STATUS                      current
    DESCRIPTION
        "The nominal bit rate of the SFP transceiver."
    ::= { rcSfpDdmPortEntry 8 }

rcSfpDdmConnectorType           OBJECT-TYPE
    SYNTAX                      DisplayString
    MAX-ACCESS                  read-only
    STATUS                      current
    DESCRIPTION
        "The connector type of the SFP transceiver."
    ::= { rcSfpDdmPortEntry 9 }

rcSfpDdmWavelength              OBJECT-TYPE
    SYNTAX                      DisplayString
    MAX-ACCESS                  read-only
    STATUS                      current
    DESCRIPTION
        "The laser wavelength of the SFP transceiver."
    ::= { rcSfpDdmPortEntry 10 }

rcSfpDdmLinkLength              OBJECT-TYPE
    SYNTAX                      DisplayString
    MAX-ACCESS                  read-only
    STATUS                      current
    DESCRIPTION
        "The link length of the SFP transceiver."
    ::= { rcSfpDdmPortEntry 11 }

rcSfpDdmImplemented             OBJECT-TYPE
    SYNTAX                      TruthValue
    MAX-ACCESS                  read-only
    STATUS                      current
    DESCRIPTION
        "SFP DDM is implemented on the SFP transceiver or not.
         true(1) is implemented and false(2) is not implemented."
    ::= { rcSfpDdmPortEntry 12 }

rcSfpDdmCurrentStatus           OBJECT-TYPE
    SYNTAX                      RcSfpDdmAlarmWarnStatus
    MAX-ACCESS                  read-only
    STATUS                      current
    DESCRIPTION
        "The current alarm and warning status of the SFP transceiver."
    ::= { rcSfpDdmPortEntry 13 }

rcSfpDdmCurrentTemperature      OBJECT-TYPE
    SYNTAX                      Integer32(-128000..128000)
    MAX-ACCESS                  read-only
    STATUS                      current
    DESCRIPTION
        "The current temperature (in units of 0.001 degrees Celsius)
         of the SFP transceiver."
    ::= { rcSfpDdmPortEntry 14 }

rcSfpDdmThreshTempAlarmLow      OBJECT-TYPE
    SYNTAX                      Integer32(-128000..128000)
    MAX-ACCESS                  read-only
    STATUS                      current
    DESCRIPTION
        "The threshold of low temperature alarm (in units of 0.001 degrees
         Celsius) of the SFP transceiver."
    ::= { rcSfpDdmPortEntry 15 }

rcSfpDdmThreshTempWarnLow       OBJECT-TYPE
    SYNTAX                      Integer32(-128000..128000)
    MAX-ACCESS                  read-only
    STATUS                      current
    DESCRIPTION
        "The threshold of low temperature warning (in units of 0.001 degrees
         Celsius) of the SFP transceiver."
    ::= { rcSfpDdmPortEntry 16 }

rcSfpDdmThreshTempWarnHigh      OBJECT-TYPE
    SYNTAX                      Integer32(-128000..128000)
    MAX-ACCESS                  read-only
    STATUS                      current
    DESCRIPTION
        "The threshold of high temperature warning (in units of 0.001 degrees
         Celsius) of the SFP transceiver."
    ::= { rcSfpDdmPortEntry 17 }

rcSfpDdmThreshTempAlarmHigh     OBJECT-TYPE
    SYNTAX                      Integer32(-128000..128000)
    MAX-ACCESS                  read-only
    STATUS                      current
    DESCRIPTION
        "The threshold of high temperature alarm (in units of 0.001 degrees
         Celsius) of the SFP transceiver."
    ::= { rcSfpDdmPortEntry 18 }

rcSfpDdmCurrentVoltage          OBJECT-TYPE
    SYNTAX                      Integer32(0..6554)
    MAX-ACCESS                  read-only
    STATUS                      current
    DESCRIPTION
        "The current voltage (in millivolts) of the SFP transceiver."
    ::= { rcSfpDdmPortEntry 19 }

rcSfpDdmThreshVoltageAlarmLow   OBJECT-TYPE
    SYNTAX                      Integer32(0..6554)
    MAX-ACCESS                  read-only
    STATUS                      current
    DESCRIPTION
        "The threshold of low voltage alarm (in millivolts) of the SFP transceiver."
    ::= { rcSfpDdmPortEntry 20 }

rcSfpDdmThreshVoltageWarnLow    OBJECT-TYPE
    SYNTAX                      Integer32(0..6554)
    MAX-ACCESS                  read-only
    STATUS                      current
    DESCRIPTION
        "The threshold of low voltage warning (in millivolts) of the SFP transceiver."
    ::= { rcSfpDdmPortEntry 21 }

rcSfpDdmThreshVoltageWarnHigh   OBJECT-TYPE
    SYNTAX                      Integer32(0..6554)
    MAX-ACCESS                  read-only
    STATUS                      current
    DESCRIPTION
        "The threshold of high voltage warning (in millivolts) of the SFP transceiver."
    ::= { rcSfpDdmPortEntry 22 }

rcSfpDdmThreshVoltageAlarmHigh  OBJECT-TYPE
    SYNTAX                      Integer32(0..6554)
    MAX-ACCESS                  read-only
    STATUS                      current
    DESCRIPTION
        "The threshold of high voltage alarm (in millivolts) of the SFP transceiver."
    ::= { rcSfpDdmPortEntry 23 }

rcSfpDdmCurrentTxBiasCurrent    OBJECT-TYPE
    SYNTAX                      Integer32(0..131070)
    MAX-ACCESS                  read-only
    STATUS                      current
    DESCRIPTION
        "The current Tx bias current (in microamperes) of the SFP transceiver."
    ::= { rcSfpDdmPortEntry 24 }

rcSfpDdmThreshTxBiasAlarmLow    OBJECT-TYPE
    SYNTAX                      Integer32(0..131070)
    MAX-ACCESS                  read-only
    STATUS                      current
    DESCRIPTION
        "The threshold of low Tx bias current alarm (in microamperes)
         of the SFP transceiver."
    ::= { rcSfpDdmPortEntry 25 }

rcSfpDdmThreshTxBiasWarnLow     OBJECT-TYPE
    SYNTAX                      Integer32(0..131070)
    MAX-ACCESS                  read-only
    STATUS                      current
    DESCRIPTION
        "The threshold of low Tx bias current warning (in microamperes)
         of the SFP transceiver."
    ::= { rcSfpDdmPortEntry 26 }

rcSfpDdmThreshTxBiasWarnHigh    OBJECT-TYPE
    SYNTAX                      Integer32(0..131070)
    MAX-ACCESS                  read-only
    STATUS                      current
    DESCRIPTION
        "The threshold of high Tx bias current warning (in microamperes)
         of the SFP transceiver."
    ::= { rcSfpDdmPortEntry 27 }

rcSfpDdmThreshTxBiasAlarmHigh   OBJECT-TYPE
    SYNTAX                      Integer32(0..131070)
    MAX-ACCESS                  read-only
    STATUS                      current
    DESCRIPTION
        "The threshold of high Tx bias current alarm (in microamperes)
         of the SFP transceiver."
    ::= { rcSfpDdmPortEntry 28 }

rcSfpDdmCurrentRxPower          OBJECT-TYPE
    SYNTAX                      Integer32(0..6553500)
    MAX-ACCESS                  read-only
    STATUS                      current
    DESCRIPTION
        "The current Rx power (in nanowatts) of the SFP transceiver."
    ::= { rcSfpDdmPortEntry 29 }

rcSfpDdmThreshRxPowerAlarmLow   OBJECT-TYPE
    SYNTAX                      Integer32(0..6553500)
    MAX-ACCESS                  read-only
    STATUS                      current
    DESCRIPTION
        "The threshold of low Rx power alarm (in nanowatts) of the SFP transceiver."
    ::= { rcSfpDdmPortEntry 30 }

rcSfpDdmThreshRxPowerWarnLow    OBJECT-TYPE
    SYNTAX                      Integer32(0..6553500)
    MAX-ACCESS                  read-only
    STATUS                      current
    DESCRIPTION
        "The threshold of low Rx power warning (in nanowatts) of the SFP transceiver."
    ::= { rcSfpDdmPortEntry 31 }

rcSfpDdmThreshRxPowerWarnHigh   OBJECT-TYPE
    SYNTAX                      Integer32(0..6553500)
    MAX-ACCESS                  read-only
    STATUS                      current
    DESCRIPTION
        "The threshold of high Rx power warning (in nanowatts) of the SFP transceiver."
    ::= { rcSfpDdmPortEntry 32 }

rcSfpDdmThreshRxPowerAlarmHigh  OBJECT-TYPE
    SYNTAX                      Integer32(0..6553500)
    MAX-ACCESS                  read-only
    STATUS                      current
    DESCRIPTION
        "The threshold of high Rx power alarm (in nanowatts) of the SFP transceiver."
    ::= { rcSfpDdmPortEntry 33 }

rcSfpDdmCurrentTxPower          OBJECT-TYPE
    SYNTAX                      Integer32(0..6554)
    MAX-ACCESS                  read-only
    STATUS                      current
    DESCRIPTION
        "The current Tx power (in microwatts) of the SFP transceiver."
    ::= { rcSfpDdmPortEntry 34 }

rcSfpDdmThreshTxPowerAlarmLow   OBJECT-TYPE
    SYNTAX                      Integer32(0..6554)
    MAX-ACCESS                  read-only
    STATUS                      current
    DESCRIPTION
        "The threshold of low Tx power alarm (in microwatts) of the SFP transceiver."
    ::= { rcSfpDdmPortEntry 35 }

rcSfpDdmThreshTxPowerWarnLow    OBJECT-TYPE
    SYNTAX                      Integer32(0..6554)
    MAX-ACCESS                  read-only
    STATUS                      current
    DESCRIPTION
        "The threshold of low Tx power warning (in microwatts) of the SFP transceiver."
    ::= { rcSfpDdmPortEntry 36 }

rcSfpDdmThreshTxPowerWarnHigh   OBJECT-TYPE
    SYNTAX                      Integer32(0..6554)
    MAX-ACCESS                  read-only
    STATUS                      current
    DESCRIPTION
        "The threshold of high Tx power warning (in microwatts) of the SFP transceiver."
    ::= { rcSfpDdmPortEntry 37 }

rcSfpDdmThreshTxPowerAlarmHigh  OBJECT-TYPE
    SYNTAX                      Integer32(0..6554)
    MAX-ACCESS                  read-only
    STATUS                      current
    DESCRIPTION
        "The threshold of high Tx power alarm (in microwatts) of the SFP transceiver."
    ::= { rcSfpDdmPortEntry 38 }

rcSfpDdmWarningFlags            OBJECT-TYPE
    SYNTAX  BITS    {
                        tempHighWarning(0),
                        tempLowWarning(1),
                        vccHighWarning(2),
                        vccLowWarning(3),
                        txbiasHighWarning(4),
                        txbiasLowWarning(5),
                        rxpowerHighWarning(6),
                        rxpowerLowWarning(7),
                        txpowerHighWarning(8),
                        txpowerLowWarning(9)
                    } 
    MAX-ACCESS                  read-only
    STATUS                      current
    DESCRIPTION
        "Warning flags indicate if any of the monitored parameters
         exceeds its warning threshold or not. The change in the value
         of any of these bits will generate a warning trap."
    ::= { rcSfpDdmPortEntry 39 }

rcSfpDdmAlarmFlags              OBJECT-TYPE
    SYNTAX  BITS    {
                        tempHighAlarm(0),
                        tempLowAlarm(1),
                        vccHighAlarm(2),
                        vccLowAlarm(3),
                        txbiasHighAlarm(4),
                        txbiasLowAlarm(5),
                        rxpowerHighAlarm(6),
                        rxpowerLowAlarm(7),
                        txpowerHighAlarm(8),
                        txpowerLowAlarm(9)
                    } 
    MAX-ACCESS                  read-only
    STATUS                      current
    DESCRIPTION
        "Alarm flags indicate if any of the monitored parameters
         exceeds its alarm threshold or not. The change in the value
         of any of these bits will generate an alarm trap."
    ::= { rcSfpDdmPortEntry 40 }

-- --------------------------------------------------------------------- --
-- Traps
-- --------------------------------------------------------------------- --
rcSfpDdmWarningTrap             NOTIFICATION-TYPE
    OBJECTS         {
                        rcSfpPortId,
                        rcSfpDdmWarningFlags,
                        rcSfpDdmCurrentTemperature,
                        rcSfpDdmCurrentVoltage,
                        rcSfpDdmCurrentTxBiasCurrent,
                        rcSfpDdmCurrentRxPower,
                        rcSfpDdmCurrentTxPower
                    }
    STATUS                      current
    DESCRIPTION
        "An SFP DDM warning trap indicates that at least one of the
         warning flags is set or cleared on the SFP transceiver."
    ::= { ruggedcomSfpDdmTraps 1 }

rcSfpDdmAlarmTrap               NOTIFICATION-TYPE
    OBJECTS         {
                        rcSfpPortId,
                        rcSfpDdmAlarmFlags,
                        rcSfpDdmCurrentTemperature,
                        rcSfpDdmCurrentVoltage,
                        rcSfpDdmCurrentTxBiasCurrent,
                        rcSfpDdmCurrentRxPower,
                        rcSfpDdmCurrentTxPower
                    }
    STATUS                      current
    DESCRIPTION
        "An SFP DDM alarm trap indicates that at least one of the
         alarm flags is set or cleared on the SFP transceiver."
    ::= { ruggedcomSfpDdmTraps 2 }

-- --------------------------------------------------------------------- --
-- Object Groups
-- --------------------------------------------------------------------- --
rcSfpDdmCfgGroup                OBJECT-GROUP
    OBJECTS         {
                        rcSfpDdmPollingInterval
                    }
    STATUS                      current
    DESCRIPTION 
        "A group of objects of SFP DDM configurable parameters."
    ::= { rcSfpDdmGroups 1 }    

rcSfpDdmTableGroup              OBJECT-GROUP
    OBJECTS         {
                        rcSfpPortId,
                        rcSfpPlugged,
                        rcSfpDdmVendorName,
                        rcSfpDdmVendorPartNumber,
                        rcSfpDdmVendorRevision,
                        rcSfpDdmVendorSerialNumber,
                        rcSfpDdmEncoding,
                        rcSfpDdmNominalBitrate,
                        rcSfpDdmConnectorType,
                        rcSfpDdmWavelength,
                        rcSfpDdmLinkLength,
                        rcSfpDdmImplemented,
                        rcSfpDdmCurrentStatus,
                        rcSfpDdmCurrentTemperature,
                        rcSfpDdmThreshTempAlarmLow,
                        rcSfpDdmThreshTempWarnLow,
                        rcSfpDdmThreshTempWarnHigh,
                        rcSfpDdmThreshTempAlarmHigh,
                        rcSfpDdmCurrentVoltage,
                        rcSfpDdmThreshVoltageAlarmLow,
                        rcSfpDdmThreshVoltageWarnLow,
                        rcSfpDdmThreshVoltageWarnHigh,
                        rcSfpDdmThreshVoltageAlarmHigh,
                        rcSfpDdmCurrentTxBiasCurrent,
                        rcSfpDdmThreshTxBiasAlarmLow,
                        rcSfpDdmThreshTxBiasWarnLow,
                        rcSfpDdmThreshTxBiasWarnHigh,
                        rcSfpDdmThreshTxBiasAlarmHigh,
                        rcSfpDdmCurrentRxPower,
                        rcSfpDdmThreshRxPowerAlarmLow,
                        rcSfpDdmThreshRxPowerWarnLow,
                        rcSfpDdmThreshRxPowerWarnHigh,
                        rcSfpDdmThreshRxPowerAlarmHigh,
                        rcSfpDdmCurrentTxPower,
                        rcSfpDdmThreshTxPowerAlarmLow,
                        rcSfpDdmThreshTxPowerWarnLow,
                        rcSfpDdmThreshTxPowerWarnHigh,
                        rcSfpDdmThreshTxPowerAlarmHigh,
                        rcSfpDdmWarningFlags,
                        rcSfpDdmAlarmFlags
                    }
    STATUS                      current
    DESCRIPTION 
        "A group of objects providing information about SFP DDM."
    ::= { rcSfpDdmGroups 2 }    

rcSfpDdmNotifyGroup             OBJECT-GROUP
    OBJECTS         {
                        rcSfpDdmWarningTrap,
                        rcSfpDdmAlarmTrap
                    }
    STATUS                      current
    DESCRIPTION 
        "A group of objects that define SFP DDM traps."
    ::= { rcSfpDdmGroups 3 }

END

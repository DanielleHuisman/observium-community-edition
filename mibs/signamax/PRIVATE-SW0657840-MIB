PRIVATE-SW0657840-MIB DEFINITIONS ::= BEGIN

IMPORTS
    DisplayString FROM SNMPv2-TC
    MODULE-COMPLIANCE,OBJECT-GROUP, NOTIFICATION-GROUP       FROM SNMPv2-CONF
    enterprises,MODULE-IDENTITY,OBJECT-TYPE,NOTIFICATION-TYPE,Counter32,IpAddress        FROM SNMPv2-SMI
    ifIndex    FROM RFC1213-MIB;


privatetech MODULE-IDENTITY
        LAST-UPDATED "200607030000Z"
        ORGANIZATION "xxx Tech Corp."
        CONTACT-INFO
            "xxx"
        DESCRIPTION
            "The MIB module is for xxx Tech."
        ::= { enterprises 5205 }

switch                       OBJECT IDENTIFIER ::= { privatetech 2 }

sw0657840ProductID	        OBJECT IDENTIFIER ::= { switch 9 }

sw0657840Produces            OBJECT IDENTIFIER ::= { sw0657840ProductID 1 }

sw0657840System           	OBJECT IDENTIFIER ::= { sw0657840Produces 1 }

sw0657840CommonSys           	OBJECT IDENTIFIER ::= { sw0657840System 1 }

sw0657840Reboot OBJECT-TYPE
	SYNTAX		INTEGER(0|1|2)
	MAX-ACCESS	    read-write
	STATUS		current
	DESCRIPTION
		"Reboot the system. Get this OID always return zero.
            0 - do nothing
			1 - Reboot without saving start
			2 - Reboot with saving start"
	::= { sw0657840CommonSys 1 }

sw0657840BiosVsersion	OBJECT-TYPE
	SYNTAX		DisplayString
	MAX-ACCESS	    read-only
	STATUS		current
	DESCRIPTION
		"Get the BIOS version of the system."
	::= { sw0657840CommonSys 2 }

sw0657840FirmwareVersion	OBJECT-TYPE
	SYNTAX		DisplayString
	MAX-ACCESS	    read-only
	STATUS		current
	DESCRIPTION
		"Get the firmware version of the system."
	::= { sw0657840CommonSys 3 }

sw0657840HardwareVersion	OBJECT-TYPE
	SYNTAX		DisplayString
	MAX-ACCESS	    read-only
	STATUS		current
	DESCRIPTION
		"Get the hardware version of the system."
	::= { sw0657840CommonSys 4 }

sw0657840MechanicalVersion OBJECT-TYPE
	SYNTAX		DisplayString
	MAX-ACCESS 	    read-only
	STATUS		current
	DESCRIPTION
		"Get the mechanical version of the system."
	::= { sw0657840CommonSys 5 }

sw0657840SerialNumber	OBJECT-TYPE
	SYNTAX		DisplayString
	MAX-ACCESS	    read-only
	STATUS		current
	DESCRIPTION
		"Get the Serial number of the system."
	::= { sw0657840CommonSys 6 }

sw0657840HostMacAddress	OBJECT-TYPE
	SYNTAX		DisplayString
	MAX-ACCESS	    read-only
	STATUS		current
	DESCRIPTION
		"Get the MAC address of the system."
	::= { sw0657840CommonSys 7 }

sw0657840DevicePort	OBJECT-TYPE
	SYNTAX		DisplayString
	MAX-ACCESS  	read-only
	STATUS		current
	DESCRIPTION
		"Get the quantity of ports that this system owns now."
	::= { sw0657840CommonSys 8 }

sw0657840RamSize  OBJECT-TYPE
    SYNTAX      DisplayString
    MAX-ACCESS      read-only
    STATUS      current
    DESCRIPTION
        "Get the RAM size of the system."
	::= { sw0657840CommonSys 9 }

sw0657840FlashSize  OBJECT-TYPE
    SYNTAX      DisplayString
    MAX-ACCESS      read-only
    STATUS      current
    DESCRIPTION
        "Get the flash size of the system."
	::= { sw0657840CommonSys 10 }


sw0657840IP           	OBJECT IDENTIFIER ::= { sw0657840System 2 }

sw0657840DhcpSetting OBJECT-TYPE
	SYNTAX		    INTEGER(0|1)
	MAX-ACCESS	        read-write
	STATUS		    current
	DESCRIPTION
		"Get/Set DHCP status of the system.
			0 - DHCP disable
			1 - DHCP enable"
	::= { sw0657840IP 1 }

sw0657840IPAddress OBJECT-TYPE
	SYNTAX      IpAddress
	MAX-ACCESS	    read-write
	STATUS		current
	DESCRIPTION
		"Get/Set the IP address of the system.
		 You can't set this OID if DHCP status is enabled."
	::= { sw0657840IP 2 }

sw0657840NetMask OBJECT-TYPE
	SYNTAX      IpAddress
	MAX-ACCESS	    read-write
	STATUS		current
	DESCRIPTION
		"Get/Set the subnet mask of the system.
		 You can't set this OID if DHCP status is enabled."
	::= { sw0657840IP 3 }

sw0657840DefaultGateway OBJECT-TYPE
	SYNTAX      IpAddress
	MAX-ACCESS	    read-write
	STATUS		current
	DESCRIPTION
		"Get/Set the default gateway of the system.
		 You can't set this OID if DHCP status is enabled."
	::= { sw0657840IP 4 }

sw0657840DnsSetting OBJECT-TYPE
	SYNTAX      INTEGER(0|1)
	MAX-ACCESS	    read-write
	STATUS		current
	DESCRIPTION
		"Get/Set the source of DNS server.
		 You can't set this OID if DHCP status is disabled.
			0 - manual, the DNS server is from manual setting
            1 - auto, the DNS server is assigned by DHCP server."
	::= { sw0657840IP 5 }

sw0657840DnsServer OBJECT-TYPE
	SYNTAX      IpAddress
	MAX-ACCESS	    read-write
	STATUS		current
	DESCRIPTION
		"Get/Set the DNS server of the system."
	::= { sw0657840IP 6 }

sw0657840Time           	OBJECT IDENTIFIER ::= { sw0657840System 3 }

sw0657840SystemCurrentTime OBJECT-TYPE
	SYNTAX      DisplayString
	MAX-ACCESS	    read-only
	STATUS		current
	DESCRIPTION
		"Get the current time of the system."
	::= { sw0657840Time 1 }

sw0657840ManualTimeSetting OBJECT-TYPE
	SYNTAX      DisplayString
	MAX-ACCESS	    read-write
	STATUS		current
	DESCRIPTION
		"Get/Set the system time of the device.
        The input format is 'Year/Month/Day/Hour/Minute/Second'.
        ex: 2004/1/1/12/34/25  means 2004/1/1 - 12:24:25 .
        The value range:
        Year    : 2000 - 2036,
        Mouth   : 1 - 12,
        Day     : 1 - 31,
        Hour    : 0 - 23,
        Minute  : 0 - 59,
        Sec     : 0 - 59."
	::= { sw0657840Time 2 }

sw0657840NTPServer OBJECT-TYPE
	SYNTAX      DisplayString
	MAX-ACCESS	    read-write
	STATUS		current
	DESCRIPTION
		"Get/Set the NTP Time Server. You can use the IP address or domain name."
	::= { sw0657840Time 3 }

sw0657840NTPTimeZone OBJECT-TYPE
	SYNTAX      INTEGER(-12..13)
	MAX-ACCESS	    read-write
	STATUS		current
	DESCRIPTION
		"Get/Set the NTP Time Zone.
		The value range is between -12 and 13
		-12 - GMT -12:00,
		-11 - GMT -11:00,
		-10 - GMT -10:00,
		 -9 - GMT -09:00,
		 -8 - GMT -08:00,
		 -7 - GMT -07:00,
		 -6 - GMT -06:00,
		 -5 - GMT -05:00,
		 -4 - GMT -04:00,
		 -3 - GMT -03:00,
		 -2 - GMT -02:00,
		 -1 - GMT -01:00,
		  0 - GMT +00:00,
		  1 - GMT +01:00,
		  2 - GMT +02:00,
		  3 - GMT +03:00,
		  4 - GMT +04:00,
		  5 - GMT +05:00,
		  6 - GMT +06:00,
		  7 - GMT +07:00,
		  8 - GMT +08:00,
		  9 - GMT +09:00,
		 10 - GMT +10:00,
		 11 - GMT +11:00,
		 12 - GMT +12:00,
		 13 - GMT +13:00. "
	::= { sw0657840Time 4 }

sw0657840NTPTimeSync OBJECT-TYPE
	SYNTAX      INTEGER(0|1)
	MAX-ACCESS	    read-write
	STATUS		current
	DESCRIPTION
		"Sync time from NTP Server. Get this OID always return zero.
		Set the Time Server and Time Zone before doing time sync.
		Notice that time server must be correct!
		The value range (0|1):
		1 - sync.
        0 - do nothing."
	::= { sw0657840Time 5 }

sw0657840DaylightSavingTime OBJECT-TYPE
	SYNTAX      INTEGER(-5..5)
	MAX-ACCESS	    read-write
	STATUS		current
	DESCRIPTION
		"Get/Set the daylight saving time.
		The value range is between -5 and 5. (Unit: hour)"
	::= { sw0657840Time 6 }

sw0657840DaylightStartTime OBJECT-TYPE
	SYNTAX      DisplayString
	MAX-ACCESS	    read-write
	STATUS		current
	DESCRIPTION
		"Get/Set the Start time of Daylight Saving.
		The input format is 'MM/DD/HH',
		and daylight saving start month can't equal end month.
		example: month/day/hour   10/01/00
		month: 01~12, day: 01~31, hour: 00~23 ."
	::= { sw0657840Time 7 }

sw0657840DaylightEndTime OBJECT-TYPE
	SYNTAX      DisplayString
	MAX-ACCESS	    read-write
	STATUS		current
	DESCRIPTION
		"Get/Set the End time of Daylight Saving.
		The input format is 'MM/DD/HH',
		and daylight saving start month can't equal end month.
		example: month/day/hour   04/01/00
		month: 01~12, day: 01~31, hour: 00~23 ."
	::= { sw0657840Time 8 }


sw0657840Account           	OBJECT IDENTIFIER ::= { sw0657840System 4 }

sw0657840AccountNumber OBJECT-TYPE
	SYNTAX      INTEGER(1..5)
	MAX-ACCESS	    read-only
	STATUS		current
	DESCRIPTION
		"Get the current account number(s) of the system."
	::= { sw0657840Account 1 }

sw0657840AccountTable	OBJECT-TYPE
	SYNTAX		SEQUENCE OF SW0657840AccountEntry
	MAX-ACCESS	not-accessible
	STATUS		current
	DESCRIPTION
		"This is a list of SW0657840AccountEntry. The numbers of entries are given by
		the value of sw0657840AccountNumber."
	::= { sw0657840Account 2 }

SW0657840AccountEntry ::=
SEQUENCE {
    sw0657840AccountIndex		    INTEGER,
    sw0657840AccountAuthorization	DisplayString,
    sw0657840AccountName             DisplayString,
    sw0657840AccountPassword         DisplayString
}

sw0657840AccountEntry	OBJECT-TYPE
	SYNTAX		SW0657840AccountEntry
	MAX-ACCESS	    not-accessible
	STATUS		current
	DESCRIPTION
		"This is the Entry(s) for account information."
	INDEX {sw0657840AccountIndex}
	::= { sw0657840AccountTable 1 }

sw0657840AccountIndex	OBJECT-TYPE
	SYNTAX		INTEGER(1..5)
	MAX-ACCESS	    read-only
	STATUS		current
	DESCRIPTION
		"This is the index of the account entry."
	::= { sw0657840AccountEntry 1 }

sw0657840AccountAuthorization	OBJECT-TYPE
	SYNTAX		DisplayString
	MAX-ACCESS	    read-only
	STATUS		current
	DESCRIPTION
		"This is the authorization of the account entry."
	::= { sw0657840AccountEntry 2 }

sw0657840AccountName	OBJECT-TYPE
	SYNTAX		DisplayString
	MAX-ACCESS	    read-write
	STATUS		current
	DESCRIPTION
		"This is the username of the account entry."
	::= { sw0657840AccountEntry 3 }

sw0657840AccountPassword	OBJECT-TYPE
	SYNTAX		DisplayString
	MAX-ACCESS	    read-write
	STATUS		current
	DESCRIPTION
		"This is the password of the account entry. The return value is always '********'."
	::= { sw0657840AccountEntry 4 }

sw0657840AccountAddName OBJECT-TYPE
	SYNTAX      DisplayString
	MAX-ACCESS	    read-write
	STATUS		current
	DESCRIPTION
		"This is the account name for adding operation."
	::= { sw0657840Account 3 }

sw0657840AccountAddPassword OBJECT-TYPE
	SYNTAX      DisplayString
	MAX-ACCESS	    read-write
	STATUS		current
	DESCRIPTION
		"This is the account password for adding operation. The return value is always '********'."
	::= { sw0657840Account 4 }

sw0657840DoAccountAdd OBJECT-TYPE
	SYNTAX      INTEGER(0|1)
	MAX-ACCESS	    read-write
	STATUS		current
	DESCRIPTION
		"Add account name. OID sw0657840AccountAddName and sw0657840AccountAddPassword must be
        filled first. Get this OID always return zero.
            1 - add account.
            0 - do nothing."
	::= { sw0657840Account 5 }

sw0657840AccountDel	OBJECT-TYPE
	SYNTAX		INTEGER(2..5)
	MAX-ACCESS	    read-write
	STATUS		current
	DESCRIPTION
		"Delete account. The value is valid sw0657840AccountIndex(Can't delete administrator)."
	::= { sw0657840Account 6 }




sw0657840Snmp           	OBJECT IDENTIFIER ::= { sw0657840Produces 2 }

sw0657840GetCommunity OBJECT-TYPE
	SYNTAX      DisplayString
	MAX-ACCESS	    read-write
	STATUS		current
	DESCRIPTION
		"Get/Set the get-community of the SNMP."
	::= { sw0657840Snmp 1 }

sw0657840SetCommunity OBJECT-TYPE
	SYNTAX      DisplayString
	MAX-ACCESS	    read-write
	STATUS		current
	DESCRIPTION
		"Get/Set the set-community of the SNMP."
	::= { sw0657840Snmp 2 }

sw0657840TrapHostNumber OBJECT-TYPE
	SYNTAX      INTEGER(1..6)
	MAX-ACCESS	    read-only
	STATUS		current
	DESCRIPTION
		"Get the number of trap hosts."
	::= { sw0657840Snmp 3 }

sw0657840TrapHostTable	OBJECT-TYPE
	SYNTAX		SEQUENCE OF SW0657840TrapHostEntry
	MAX-ACCESS	not-accessible
	STATUS		current
	DESCRIPTION
		"A list of trap host entry. The numbers of entries are given by the value of sw0657840TrapHostNumber."
    ::= { sw0657840Snmp 4 }

SW0657840TrapHostEntry ::=
SEQUENCE {
    sw0657840TrapHostIndex		    INTEGER,
    sw0657840TrapHostIP          	IpAddress,
    sw0657840TrapHostPort            INTEGER,
    sw0657840TrapHostCommunity       DisplayString
}

sw0657840TrapHostEntry	OBJECT-TYPE
	SYNTAX		SW0657840TrapHostEntry
	MAX-ACCESS	    not-accessible
	STATUS		current
	DESCRIPTION
		"This is the entry information for trap host."
	INDEX {sw0657840TrapHostIndex}
	::= { sw0657840TrapHostTable 1 }

sw0657840TrapHostIndex	OBJECT-TYPE
	SYNTAX		INTEGER(1..6)
	MAX-ACCESS	    read-only
	STATUS		current
	DESCRIPTION
		"The index of the trap host entry."
	::= { sw0657840TrapHostEntry 1 }

sw0657840TrapHostIP	OBJECT-TYPE
	SYNTAX		IpAddress
	MAX-ACCESS	    read-write
	STATUS		current
	DESCRIPTION
		"This is the IP of the trap host."
	::= { sw0657840TrapHostEntry 2 }


sw0657840TrapHostPort	OBJECT-TYPE
	SYNTAX		INTEGER(1..65535)
	MAX-ACCESS	    read-write
	STATUS		current
	DESCRIPTION
		"This is the receiving-port number of the trap host."
	::= { sw0657840TrapHostEntry 3 }


sw0657840TrapHostCommunity	OBJECT-TYPE
	SYNTAX		DisplayString
	MAX-ACCESS	    read-write
	STATUS		current
	DESCRIPTION
		"The community name for the trap PDU."
	::= { sw0657840TrapHostEntry 4 }



sw0657840Alarm           	OBJECT IDENTIFIER ::= { sw0657840Produces 3 }

sw0657840Event           	OBJECT IDENTIFIER ::= { sw0657840Alarm 1 }

sw0657840EventNumber OBJECT-TYPE
	SYNTAX      INTEGER(1..2147483647)
	MAX-ACCESS	    read-only
	STATUS		current
	DESCRIPTION
		"Get the total number of alarm events."
	::= { sw0657840Event 1 }

sw0657840EventTable	OBJECT-TYPE
	SYNTAX		SEQUENCE OF SW0657840EventEntry
	MAX-ACCESS	not-accessible
	STATUS		current
    DESCRIPTION
        "This is a list of alarm event entry. The numbers of entries are given by the value of sw0657840EventNumber."
	::= { sw0657840Event 2 }

SW0657840EventEntry ::=
SEQUENCE {
    sw0657840EventIndex		    INTEGER,
    sw0657840EventName          	DisplayString,
    sw0657840EventSendEmail      INTEGER,
    sw0657840EventSendSMS        INTEGER,
    sw0657840EventSendTrap       INTEGER
}

sw0657840EventEntry	OBJECT-TYPE
	SYNTAX		SW0657840EventEntry
	MAX-ACCESS	    not-accessible
	STATUS		current
	DESCRIPTION
		"This is the entry information for alarm event."
	INDEX {sw0657840EventIndex}
	::= { sw0657840EventTable 1 }

sw0657840EventIndex	OBJECT-TYPE
	SYNTAX		INTEGER(1..2147483647)
	MAX-ACCESS	    read-only
	STATUS		current
	DESCRIPTION
		"This is the index of the alarm event entry."
	::= { sw0657840EventEntry 1 }

sw0657840EventName	OBJECT-TYPE
	SYNTAX		DisplayString
	MAX-ACCESS	    read-only
	STATUS		current
	DESCRIPTION
		"This is the alarm event name."
	::= { sw0657840EventEntry 2 }

sw0657840EventSendEmail	OBJECT-TYPE
	SYNTAX		INTEGER(0|1)
	MAX-ACCESS	    read-write
	STATUS		current
	DESCRIPTION
		"Send email when alarm event is triggered."
	::= { sw0657840EventEntry 3 }

sw0657840EventSendSMS	OBJECT-TYPE
	SYNTAX		INTEGER(0|1)
	MAX-ACCESS	    read-write
	STATUS		current
	DESCRIPTION
		"Send SMS when alarm event is triggered."
	::= { sw0657840EventEntry 4 }

sw0657840EventSendTrap	OBJECT-TYPE
	SYNTAX		INTEGER(0|1)
	MAX-ACCESS	    read-write
	STATUS		current
	DESCRIPTION
		"Send trap when alarm event is triggered."
	::= { sw0657840EventEntry 5 }




sw0657840Email           	OBJECT IDENTIFIER ::= { sw0657840Alarm 2 }

sw0657840EmailServer OBJECT-TYPE
	SYNTAX      DisplayString
	MAX-ACCESS	    read-write
	STATUS		current
	DESCRIPTION
		"This is the SMTP server for alarm event."
	::= { sw0657840Email 1 }

sw0657840EmailUsername OBJECT-TYPE
	SYNTAX      DisplayString
	MAX-ACCESS	    read-write
	STATUS		current
	DESCRIPTION
		"This is the Username of SMTP server."
	::= { sw0657840Email 2 }

sw0657840EmailPassword OBJECT-TYPE
	SYNTAX      DisplayString
	MAX-ACCESS	    read-write
	STATUS		current
	DESCRIPTION
		"This is the User Password of SMTP server."
	::= { sw0657840Email 3 }

sw0657840EmailUserNumber OBJECT-TYPE
	SYNTAX      INTEGER(1..6)
	MAX-ACCESS	    read-only
	STATUS		current
	DESCRIPTION
		"The number of the email users that you want to send the alarm notification."
	::= { sw0657840Email 4 }

sw0657840EmailUserTable	OBJECT-TYPE
	SYNTAX		SEQUENCE OF SW0657840EmailUserEntry
	MAX-ACCESS	not-accessible
	STATUS		current
    DESCRIPTION
        "This is a list of email user entry. The numbers of entries are given by the value of sw0657840EmailUserNumber."
	::= { sw0657840Email 5 }

SW0657840EmailUserEntry ::=
SEQUENCE {
    sw0657840EmailUserIndex		    INTEGER,
    sw0657840EmailUserAddress       	DisplayString
}

sw0657840EmailUserEntry	OBJECT-TYPE
	SYNTAX		SW0657840EmailUserEntry
	MAX-ACCESS	    not-accessible
	STATUS		current
	DESCRIPTION
		"This is the Entry information for email user entry."
	INDEX {sw0657840EmailUserIndex}
	::= { sw0657840EmailUserTable 1 }

sw0657840EmailUserIndex	OBJECT-TYPE
	SYNTAX		INTEGER(1..6)
	MAX-ACCESS	    read-only
	STATUS		current
	DESCRIPTION
		"This is the index of the email user entry."
	::= { sw0657840EmailUserEntry 1 }

sw0657840EmailUserAddress	OBJECT-TYPE
	SYNTAX		DisplayString
	MAX-ACCESS	    read-write
	STATUS		current
	DESCRIPTION
		"This is the email address of the email user entry."
	::= { sw0657840EmailUserEntry 2 }



sw0657840SMS           	OBJECT IDENTIFIER ::= { sw0657840Alarm 3 }

sw0657840SMSServer OBJECT-TYPE
	SYNTAX      DisplayString
	MAX-ACCESS	    read-write
	STATUS		current
	DESCRIPTION
		"This is the SMS server for alarm event."
	::= { sw0657840SMS 1 }

sw0657840SMSUsername OBJECT-TYPE
	SYNTAX      DisplayString
	MAX-ACCESS	    read-write
	STATUS		current
	DESCRIPTION
		"This is the Username of SMS server."
	::= { sw0657840SMS 2 }

sw0657840SMSPassword OBJECT-TYPE
	SYNTAX      DisplayString
	MAX-ACCESS	    read-write
	STATUS		current
	DESCRIPTION
		"This is the Password of SMS server."
	::= { sw0657840SMS 3 }

sw0657840SMSUserNumber OBJECT-TYPE
	SYNTAX      INTEGER(1..6)
	MAX-ACCESS	    read-only
	STATUS		current
	DESCRIPTION
		"The number of the SMS users that you want to send the alarm notification."
	::= { sw0657840SMS 4 }

sw0657840SMSUserTable	OBJECT-TYPE
	SYNTAX		SEQUENCE OF SW0657840SMSUserEntry
	MAX-ACCESS	not-accessible
	STATUS		current
    DESCRIPTION
        "This is a list of SMS user entry. The numbers of entries are given by the value of sw0657840SMSUserNumber."
    ::= { sw0657840SMS 5 }

SW0657840SMSUserEntry ::=
SEQUENCE {
    sw0657840SMSUserIndex		    INTEGER,
    sw0657840SMSUserMobilePhone       	DisplayString
}

sw0657840SMSUserEntry	OBJECT-TYPE
	SYNTAX		SW0657840SMSUserEntry
	MAX-ACCESS	    not-accessible
	STATUS		current
	DESCRIPTION
		"This is the Entry information for SMS user entry."
	INDEX {sw0657840SMSUserIndex}
	::= { sw0657840SMSUserTable 1 }

sw0657840SMSUserIndex	OBJECT-TYPE
	SYNTAX		INTEGER(1..6)
	MAX-ACCESS	    read-only
	STATUS		current
	DESCRIPTION
		"This is the index of the SMS user entry."
	::= { sw0657840SMSUserEntry 1 }

sw0657840SMSUserMobilePhone	OBJECT-TYPE
	SYNTAX		DisplayString
	MAX-ACCESS	    read-write
	STATUS		current
	DESCRIPTION
		"The SMS phone number of the SMS user entry."
	::= { sw0657840SMSUserEntry 2 }



sw0657840Tftp           	OBJECT IDENTIFIER ::= { sw0657840Produces 4 }

sw0657840TftpServer OBJECT-TYPE
	SYNTAX      IpAddress
	MAX-ACCESS	    read-write
	STATUS		current
	DESCRIPTION
		"Get/Set the tftp server."
	::= { sw0657840Tftp 1 }




sw0657840Configuration           	OBJECT IDENTIFIER ::= { sw0657840Produces 5 }

sw0657840SaveRestore           	OBJECT IDENTIFIER ::= { sw0657840Configuration 1 }

sw0657840SaveStart OBJECT-TYPE
	SYNTAX      INTEGER(0|1)
	MAX-ACCESS	    read-write
	STATUS		current
	DESCRIPTION
		"Save current configuration into flash memory (Save as Start Configuration).
        Get this OID always return zero.
            1 - save.
            0 - do nothing. "
	::= { sw0657840SaveRestore 1 }

sw0657840SaveUser OBJECT-TYPE
	SYNTAX      INTEGER(0|1)
	MAX-ACCESS	    read-write
	STATUS		current
	DESCRIPTION
		"Save current configuration into flash memory (Save as User Configuration).
        Get this OID always return zero.
            1 - save.
            0 - do nothing. "
	::= { sw0657840SaveRestore 2 }

sw0657840RestoreDefault OBJECT-TYPE
	SYNTAX      INTEGER(0|1|2)
	MAX-ACCESS	    read-write
	STATUS		current
	DESCRIPTION
		"Restore factory default configuration.
        Get this OID always return zero.
            2 - restore default included default ip address.
            1 - restore default without changing current ip address.
            0 - do nothing. "
	::= { sw0657840SaveRestore 3 }

sw0657840RestoreUser OBJECT-TYPE
	SYNTAX      INTEGER(0|1)
	MAX-ACCESS	    read-write
	STATUS		current
	DESCRIPTION
		"Restore user configuration.
        Get this OID always return zero.
            1 - restore.
            0 - do nothing. "
	::= { sw0657840SaveRestore 4 }




sw0657840ConfigFile           	OBJECT IDENTIFIER ::= { sw0657840Configuration 2 }

sw0657840ExportConfigName OBJECT-TYPE
	SYNTAX      DisplayString
	MAX-ACCESS	    read-write
	STATUS		current
	DESCRIPTION
		"Get/Set the export file path and name."
	::= { sw0657840ConfigFile 1 }

sw0657840DoExportConfig OBJECT-TYPE
	SYNTAX      INTEGER(1|2)
	MAX-ACCESS	    read-write
	STATUS		current
	DESCRIPTION
		"Do export-config.
        Get this OID always return zero.
			1	-	export start section.
			2	-	export user-conf section."
	::= { sw0657840ConfigFile 2 }

sw0657840ImportConfigName OBJECT-TYPE
	SYNTAX      DisplayString
	MAX-ACCESS	    read-write
	STATUS		current
	DESCRIPTION
        "Get/Set the import file path and name."
	::= { sw0657840ConfigFile 3 }

sw0657840DoImportConfig OBJECT-TYPE
	SYNTAX      INTEGER(1|2)
	MAX-ACCESS	    read-write
	STATUS		current
	DESCRIPTION
		"Do import-config.
        Get this OID always return zero.
			1	-	import start section.
			2	-	import user-conf section."
	::= { sw0657840ConfigFile 4 }



sw0657840Diagnostic           	OBJECT IDENTIFIER ::= { sw0657840Produces 6 }

sw0657840EEPROMTest OBJECT-TYPE
	SYNTAX      DisplayString
	MAX-ACCESS	    read-only
	STATUS		current
	DESCRIPTION
		"EEPROM access test."
	::= { sw0657840Diagnostic 1 }

sw0657840UartTest OBJECT-TYPE
	SYNTAX      DisplayString
	MAX-ACCESS	    read-only
	STATUS		current
	DESCRIPTION
		"UART access test."
	::= { sw0657840Diagnostic 2 }

sw0657840DramTest OBJECT-TYPE
	SYNTAX      DisplayString
	MAX-ACCESS	    read-only
	STATUS		current
	DESCRIPTION
		"DRAM access test."
	::= { sw0657840Diagnostic 3 }

sw0657840FlashTest OBJECT-TYPE
	SYNTAX      DisplayString
	MAX-ACCESS	    read-only
	STATUS		current
	DESCRIPTION
		"Flash memory access test."
	::= { sw0657840Diagnostic 4 }

sw0657840InternalLoopbackTest OBJECT-TYPE
	SYNTAX      DisplayString
	MAX-ACCESS	    read-only
	STATUS		current
	DESCRIPTION
		"Internal loopback test."
	::= { sw0657840Diagnostic 5 }

sw0657840ExternalLoopbackTest OBJECT-TYPE
	SYNTAX      DisplayString
	MAX-ACCESS	    read-only
	STATUS		current
	DESCRIPTION
		"External loopback test."
	::= { sw0657840Diagnostic 6 }

sw0657840PingTest OBJECT-TYPE
	SYNTAX      DisplayString
	MAX-ACCESS	    read-write
	STATUS		current
	DESCRIPTION
		"Set the host address that you want to ping and the system will return the test result."
	::= { sw0657840Diagnostic 7 }



sw0657840Log           	OBJECT IDENTIFIER ::= { sw0657840Produces 7 }

sw0657840ClearLog OBJECT-TYPE
	SYNTAX      INTEGER(0|1)
	MAX-ACCESS	    read-write
	STATUS		current
	DESCRIPTION
		"Clear system log.
        Get this OID always return zero.
            1 - clear log.
            0 - do nothing. "
	::= { sw0657840Log 1 }

sw0657840UploadLog OBJECT-TYPE
	SYNTAX      INTEGER(0|1)
	MAX-ACCESS	    read-write
	STATUS		current
	DESCRIPTION
		"Upload current system log. Set the correct tftp server first.
        The format of log file is 'ModelName_SerialNumbuer_YYMMDD_HHMM'.
        Get this OID always return zero.
            1 - upload log
            0 - do nothing. "
	::= { sw0657840Log 2 }

sw0657840AutoUploadLogState OBJECT-TYPE
	SYNTAX      INTEGER(0|1)
	MAX-ACCESS	    read-write
	STATUS		current
	DESCRIPTION
		"Enable auto-upload log function. Set the correct tftp server first.
        The format of log file is 'ModelName_SerialNumbuer_YYMMDD_HHMM'.
        Get this OID always return zero.
            1 - Enable auto-upload
            0 - do nothing. "
	::= { sw0657840Log 3 }

sw0657840LogNumber OBJECT-TYPE
	SYNTAX      INTEGER(0..120)
	MAX-ACCESS	    read-only
	STATUS		current
	DESCRIPTION
		"Get the number of current system log. "
	::= { sw0657840Log 4 }

sw0657840LogTable	OBJECT-TYPE
	SYNTAX		SEQUENCE OF SW0657840LogEntry
	MAX-ACCESS	not-accessible
	STATUS		current
    DESCRIPTION
        "This is a list of log entry. The numbers of entries are given by the value of sw0657840LogNumber."
	::= { sw0657840Log 5 }

SW0657840LogEntry ::=
SEQUENCE {
    sw0657840LogIndex		    INTEGER,
    sw0657840LogEvent           	DisplayString
}

sw0657840LogEntry	OBJECT-TYPE
	SYNTAX		SW0657840LogEntry
	MAX-ACCESS	    not-accessible
	STATUS		current
	DESCRIPTION
		"This is the Entry information for system log."
	INDEX {sw0657840LogIndex}
	::= { sw0657840LogTable 1 }

sw0657840LogIndex	OBJECT-TYPE
	SYNTAX		INTEGER(1..120)
	MAX-ACCESS	    read-only
	STATUS		current
	DESCRIPTION
		"This is the index of the log entry."
	::= { sw0657840LogEntry 1 }

sw0657840LogEvent	OBJECT-TYPE
	SYNTAX		DisplayString
	MAX-ACCESS	    read-only
	STATUS		current
	DESCRIPTION
		"This is the detail information of the log entry."
	::= { sw0657840LogEntry 2 }



sw0657840Firmware           	OBJECT IDENTIFIER ::= { sw0657840Produces 8 }

sw0657840FirmwareFileName OBJECT-TYPE
	SYNTAX      DisplayString
	MAX-ACCESS	    read-write
	STATUS		current
	DESCRIPTION
		"Get/Set the path and filename for firmware upgrading."
	::= { sw0657840Firmware 1 }

sw0657840DoFirmwareUpgrade OBJECT-TYPE
	SYNTAX      INTEGER(0|1)
	MAX-ACCESS	    read-write
	STATUS		current
	DESCRIPTION
		"Do firmware upgrade. Get this OID always return zero.
            1 - do firmware upgrade.
            0 - do nothing."
	::= { sw0657840Firmware 2 }



sw0657840Port           	OBJECT IDENTIFIER ::= { sw0657840Produces 9 }

sw0657840PortStatus           	OBJECT IDENTIFIER ::= { sw0657840Port 1 }

sw0657840PortStatusNumber OBJECT-TYPE
	SYNTAX      INTEGER(1..2147483647)
	MAX-ACCESS	    read-only
	STATUS		current
	DESCRIPTION
		"Get the number of port."
	::= { sw0657840PortStatus 1 }

sw0657840PortStatusTable	OBJECT-TYPE
	SYNTAX		SEQUENCE OF SW0657840PortStatusEntry
	MAX-ACCESS	not-accessible
	STATUS		current
    DESCRIPTION
        "This is a list of port status entry. The numbers of entries are given by the value of sw0657840PortStatusNumber."
	::= { sw0657840PortStatus 2 }

SW0657840PortStatusEntry ::=
SEQUENCE {
    sw0657840PortStatusIndex		    INTEGER,
    sw0657840PortStatusMedia          DisplayString,
    sw0657840PortStatusLink           DisplayString,
    sw0657840PortStatusPortState      DisplayString,
    sw0657840PortStatusAutoNego       DisplayString,
    sw0657840PortStatusSpdDpx         DisplayString,
    sw0657840PortStatusFlwCtrl        DisplayString,
    sw0657840PortStatuDescription     DisplayString
}

sw0657840PortStatusEntry	OBJECT-TYPE
	SYNTAX		SW0657840PortStatusEntry
	MAX-ACCESS	    not-accessible
	STATUS		current
	DESCRIPTION
		"This is the entry(s) for port status information."
	INDEX {sw0657840PortStatusIndex}
	::= { sw0657840PortStatusTable 1 }

sw0657840PortStatusIndex	OBJECT-TYPE
	SYNTAX		INTEGER(1..2147483647)
	MAX-ACCESS	    read-only
	STATUS		current
	DESCRIPTION
		"This is the index of the port status entry."
	::= { sw0657840PortStatusEntry 1 }

sw0657840PortStatusMedia	OBJECT-TYPE
	SYNTAX		DisplayString
	MAX-ACCESS	    read-only
	STATUS		current
	DESCRIPTION
		"The port media type of the port status entry."
	::= { sw0657840PortStatusEntry 2 }

sw0657840PortStatusLink	OBJECT-TYPE
	SYNTAX		DisplayString
	MAX-ACCESS	    read-only
	STATUS		current
	DESCRIPTION
		"This is the port link of the port status entry."
	::= { sw0657840PortStatusEntry 3 }

sw0657840PortStatusPortState	OBJECT-TYPE
	SYNTAX		DisplayString
	MAX-ACCESS	    read-only
	STATUS		current
	DESCRIPTION
		"This is the port state of the port status entry."
	::= { sw0657840PortStatusEntry 4 }

sw0657840PortStatusAutoNego	OBJECT-TYPE
	SYNTAX		DisplayString
	MAX-ACCESS	    read-only
	STATUS		current
	DESCRIPTION
		"This is the auto negotiation of the port status entry."
	::= { sw0657840PortStatusEntry 5 }

sw0657840PortStatusSpdDpx 	OBJECT-TYPE
	SYNTAX		DisplayString
	MAX-ACCESS	    read-only
	STATUS		current
	DESCRIPTION
		"This is the speed/duplex of the port status entry."
	::= { sw0657840PortStatusEntry 6 }

sw0657840PortStatusFlwCtrl 	OBJECT-TYPE
	SYNTAX		DisplayString
	MAX-ACCESS	    read-only
	STATUS		current
	DESCRIPTION
		"This is the flow control of the port status entry."
	::= { sw0657840PortStatusEntry 7 }

sw0657840PortStatuDescription	OBJECT-TYPE
	SYNTAX		DisplayString
	MAX-ACCESS	    read-only
	STATUS		current
	DESCRIPTION
		"This is the description of port."
	::= { sw0657840PortStatusEntry 8 }

sw0657840PortConf           	OBJECT IDENTIFIER ::= { sw0657840Port 2 }

sw0657840PortConfNumber OBJECT-TYPE
	SYNTAX      INTEGER(1..2147483647)
	MAX-ACCESS	    read-only
	STATUS		current
	DESCRIPTION
		"Get the number of port configuration."
	::= { sw0657840PortConf 1 }

sw0657840PortConfTable	OBJECT-TYPE
	SYNTAX		SEQUENCE OF SW0657840PortConfEntry
	MAX-ACCESS	not-accessible
	STATUS		current
    DESCRIPTION
        "This is a list of port configuration entry. The numbers of entries are given by the value of sw0657840PortConfNumber."
	::= { sw0657840PortConf 2 }

SW0657840PortConfEntry ::=
SEQUENCE {
    sw0657840PortConfIndex		    INTEGER,
    sw0657840PortConfPortState        INTEGER,
    sw0657840PortConfSpdDpx           INTEGER,
    sw0657840PortConfFlwCtrl          INTEGER,
    sw0657840PortConfDescription      DisplayString
}

sw0657840PortConfEntry	OBJECT-TYPE
	SYNTAX		SW0657840PortConfEntry
	MAX-ACCESS	    not-accessible
	STATUS		current
	DESCRIPTION
		"This is the Entry(s) for port configuration information."
	INDEX {sw0657840PortConfIndex}
	::= { sw0657840PortConfTable 1 }

sw0657840PortConfIndex	OBJECT-TYPE
	SYNTAX		INTEGER(1..2147483647)
	MAX-ACCESS	    read-only
	STATUS		current
	DESCRIPTION
		"This is the index of the port configuration entry."
	::= { sw0657840PortConfEntry 1 }

sw0657840PortConfPortState	OBJECT-TYPE
	SYNTAX		INTEGER(0|1)
	MAX-ACCESS	    read-write
	STATUS		current
	DESCRIPTION
		"This is the port state of the port configuration entry.
		 0 - disabled.
		 1 - enabled. "
	::= { sw0657840PortConfEntry 2 }

sw0657840PortConfSpdDpx	OBJECT-TYPE
	SYNTAX		INTEGER(0..5)
	MAX-ACCESS	    read-write
	STATUS		current
	DESCRIPTION
		"This is the speed/duplex of the port configuration entry.
		 0 - auto.
		 1 - 10M/Half.
		 2 - 10M/Full.
		 3 - 100M/Half.
		 4 - 100M/Full.
		 5 - 1G/Full.  "
	::= { sw0657840PortConfEntry 3 }

sw0657840PortConfFlwCtrl	OBJECT-TYPE
	SYNTAX		INTEGER(0|1)
	MAX-ACCESS	    read-write
	STATUS		current
	DESCRIPTION
		"This is the flow control of the port configuration entry.
		 0 - disabled.
		 1 - enabled.  "
	::= { sw0657840PortConfEntry 4 }

sw0657840PortConfDescription	OBJECT-TYPE
	SYNTAX		DisplayString
	MAX-ACCESS	    read-write
	STATUS		current
	DESCRIPTION
		"This is the description of port."
	::= { sw0657840PortConfEntry 5 }

sw0657840Mirror           	OBJECT IDENTIFIER ::= { sw0657840Produces 10 }

sw0657840MirrorMode OBJECT-TYPE
	SYNTAX      INTEGER(0|1)
	MAX-ACCESS	    read-write
	STATUS		current
	DESCRIPTION
		"Get/Set the Mirror mode.
		 0 - disabled.
		 1 - rx enable.  "
	::= { sw0657840Mirror 1 }

sw0657840MirroringPort OBJECT-TYPE
	SYNTAX      INTEGER(1..2147483647)
	MAX-ACCESS	    read-write
	STATUS		current
	DESCRIPTION
		"Get/Set the mirroring port.
		 The port range is from 1 to 24."
	::= { sw0657840Mirror 2 }

sw0657840MirroredPorts OBJECT-TYPE
	SYNTAX      DisplayString
	MAX-ACCESS	    read-write
	STATUS		current
	DESCRIPTION
		"Get/Set the monitored ports.
		 The port range is from 1 to 24, and the syntax is 1,5-7."
	::= { sw0657840Mirror 3 }



sw0657840MaxPktLen           	OBJECT IDENTIFIER ::= { sw0657840Produces 11 }

sw0657840MaxPktLen1           	OBJECT IDENTIFIER ::= { sw0657840MaxPktLen 1 }

sw0657840MaxPktLenPortNumber OBJECT-TYPE
	SYNTAX      INTEGER(1..2147483647)
	MAX-ACCESS	    read-only
	STATUS		current
	DESCRIPTION
		"Get the number of Max. packet length."
	::= { sw0657840MaxPktLen1 1 }

sw0657840MaxPktLenConfTable	OBJECT-TYPE
	SYNTAX		SEQUENCE OF SW0657840MaxPktLenConfEntry
	MAX-ACCESS	not-accessible
	STATUS		current
    DESCRIPTION
        "This is a list of Max. packet length entry. The numbers of entries are given by the value of sw0657840MaxPktLenPortNumber."
	::= { sw0657840MaxPktLen1 2 }

SW0657840MaxPktLenConfEntry ::=
SEQUENCE {
    sw0657840MaxPktLenConfIndex		    INTEGER,
    sw0657840MaxPktLenConfSetting         INTEGER
}

sw0657840MaxPktLenConfEntry	OBJECT-TYPE
	SYNTAX		SW0657840MaxPktLenConfEntry
	MAX-ACCESS	    not-accessible
	STATUS		current
	DESCRIPTION
		"Entry(s) for Max. packet length information."
	INDEX {sw0657840MaxPktLenConfIndex}
	::= { sw0657840MaxPktLenConfTable 1 }

sw0657840MaxPktLenConfIndex	OBJECT-TYPE
	SYNTAX		INTEGER(1..2147483647)
	MAX-ACCESS	    read-only
	STATUS		current
	DESCRIPTION
		"This is the index of the Max. packet length entry."
	::= { sw0657840MaxPktLenConfEntry 1 }

sw0657840MaxPktLenConfSetting	OBJECT-TYPE
	SYNTAX		INTEGER(1518|1532|9216)
	MAX-ACCESS	    read-write
	STATUS		current
	DESCRIPTION
		"Get/Set the Max. packet length.
		 The Max. packet length is 1518,1532,or 9216.  "
	::= { sw0657840MaxPktLenConfEntry 2 }


sw0657840Bandwidth           	OBJECT IDENTIFIER ::= { sw0657840Produces 12 }

sw0657840Bandwidth1           	OBJECT IDENTIFIER ::= { sw0657840Bandwidth 1 }

sw0657840BandwidthPortNumber OBJECT-TYPE
	SYNTAX      INTEGER(1..2147483647)
	MAX-ACCESS	    read-only
	STATUS		current
	DESCRIPTION
		"Get the number of bandwidth management configuration."
	::= { sw0657840Bandwidth1 1 }

sw0657840BandwidthConfTable	OBJECT-TYPE
	SYNTAX		SEQUENCE OF SW0657840BandwidthConfEntry
	MAX-ACCESS	not-accessible
	STATUS		current
    DESCRIPTION
        "This is a list of bandwidth management configuration entry. The numbers of entries are given by the value of sw0657840BandwidthPortNumber."
	::= { sw0657840Bandwidth1 2 }

SW0657840BandwidthConfEntry ::=
SEQUENCE {
    sw0657840BandwidthConfIndex		     INTEGER,
    sw0657840BandwidthConfIngressState      INTEGER,
    sw0657840BandwidthConfIngressBW         INTEGER,
    sw0657840BandwidthConfStormState       INTEGER,
    sw0657840BandwidthConfStormBW          INTEGER,
    sw0657840BandwidthConfEgressState      INTEGER,
    sw0657840BandwidthConfEgressBW         INTEGER
}

sw0657840BandwidthConfEntry	OBJECT-TYPE
	SYNTAX		SW0657840BandwidthConfEntry
	MAX-ACCESS	    not-accessible
	STATUS		current
	DESCRIPTION
		"This is the Entry(s) for bandwidth management configuration information."
	INDEX {sw0657840BandwidthConfIndex}
	::= { sw0657840BandwidthConfTable 1 }

sw0657840BandwidthConfIndex	OBJECT-TYPE
	SYNTAX		INTEGER(1..2147483647)
	MAX-ACCESS	    read-only
	STATUS		current
	DESCRIPTION
		"This is the index of the bandwidth management configuration entry."
	::= { sw0657840BandwidthConfEntry 1 }

sw0657840BandwidthConfIngressState	OBJECT-TYPE
	SYNTAX		INTEGER(0|1)
	MAX-ACCESS	    read-write
	STATUS		current
	DESCRIPTION
		"The ingress state of the bandwidth management configures entry.
		 0 - disabled.
		 1 - enabled. "
	::= { sw0657840BandwidthConfEntry 2 }

sw0657840BandwidthConfIngressBW	OBJECT-TYPE
	SYNTAX		INTEGER(0..1000)
	MAX-ACCESS	    read-write
	STATUS		current
	DESCRIPTION
		"Get/Set the ingress rate of the bandwidth management configuration.
		 The ingress rate is from 0 to 1000.  "
	::= { sw0657840BandwidthConfEntry 3 }

sw0657840BandwidthConfStormState	OBJECT-TYPE
	SYNTAX		INTEGER(0|1)
	MAX-ACCESS	    read-write
	STATUS		current
	DESCRIPTION
		"The storm state of the bandwidth management configuration entry.
		 0 - disabled.
		 1 - enabled. "
	::= { sw0657840BandwidthConfEntry 4 }

sw0657840BandwidthConfStormBW	OBJECT-TYPE
	SYNTAX		INTEGER(0..1000)
	MAX-ACCESS	    read-write
	STATUS		current
	DESCRIPTION
		"Get/Set the storm rate of the bandwidth management configuration.
		 The storm rate is from 0 to 1000.  "
	::= { sw0657840BandwidthConfEntry 5 }

sw0657840BandwidthConfEgressState	OBJECT-TYPE
	SYNTAX		INTEGER(0|1)
	MAX-ACCESS	    read-write
	STATUS		current
	DESCRIPTION
		"The egress state of the bandwidth management configuration entry.
		 0 - disabled.
		 1 - enabled. "
	::= { sw0657840BandwidthConfEntry 6 }

sw0657840BandwidthConfEgressBW	OBJECT-TYPE
	SYNTAX		INTEGER(0..1000)
	MAX-ACCESS	    read-write
	STATUS		current
	DESCRIPTION
		"Get/Set the egress rate of the bandwidth management configuration.
		 The egress rate is from 0 to 1000.  "
	::= { sw0657840BandwidthConfEntry 7 }

sw0657840LoopDetectedConf           	OBJECT IDENTIFIER ::= { sw0657840Produces 13 }

sw0657840LoopDetectedNumber OBJECT-TYPE
	SYNTAX      INTEGER(1..2147483647)
	MAX-ACCESS	    read-only
	STATUS		current
	DESCRIPTION
		"Get the number of loop detected entry."
	::= { sw0657840LoopDetectedConf 1 }

sw0657840LoopDetectedTable	OBJECT-TYPE
	SYNTAX		SEQUENCE OF SW0657840LoopDetectedEntry
	MAX-ACCESS	not-accessible
	STATUS		current
    DESCRIPTION
        "A list of loop detected entry. The numbers of entries are given by the value of sw0657840LoopDetectedNumber."
	::= { sw0657840LoopDetectedConf 2 }

SW0657840LoopDetectedEntry ::=
SEQUENCE {
    sw0657840LoopDetectedfIndex           INTEGER,
    sw0657840LoopDetectedStateEbl         INTEGER,
    sw0657840LoopDetectedCurrentStatus    INTEGER,
    sw0657840LoopDetectedResumed          INTEGER
}

sw0657840LoopDetectedEntry	OBJECT-TYPE
	SYNTAX		SW0657840LoopDetectedEntry
	MAX-ACCESS	    not-accessible
	STATUS		current
	DESCRIPTION
		"Entry(s) for loop detected information."
	INDEX {sw0657840LoopDetectedfIndex}
	::= { sw0657840LoopDetectedTable 1 }

sw0657840LoopDetectedfIndex	OBJECT-TYPE
	SYNTAX		INTEGER(1..2147483647)
	MAX-ACCESS	    read-only
	STATUS		current
	DESCRIPTION
		"The index of the loop detected entry."
	::= { sw0657840LoopDetectedEntry 1 }

sw0657840LoopDetectedStateEbl	OBJECT-TYPE
	SYNTAX		INTEGER(0|1)
	MAX-ACCESS	    read-write
	STATUS		current
	DESCRIPTION
		"The state of the loop detected entry.
		 0 - disabled.
		 1 - enabled. "
	::= { sw0657840LoopDetectedEntry 2 }

sw0657840LoopDetectedCurrentStatus	OBJECT-TYPE
	SYNTAX		INTEGER(0|1)
	MAX-ACCESS	    read-only
	STATUS		current
	DESCRIPTION
		"The current status of the loop detected port.
         0 - unlocked
         1 - locked due to the loop condition "
	::= { sw0657840LoopDetectedEntry 3 }

sw0657840LoopDetectedResumed	OBJECT-TYPE
	SYNTAX		INTEGER(0|1)
	MAX-ACCESS	    read-write
	STATUS		current
	DESCRIPTION
		"Unlock the port which is locked due to loop condition. Get this OID always return zero.
         1 - unlock the port,
         0 - do nothing."
	::= { sw0657840LoopDetectedEntry 4 }

sw0657840LoopDetectedAction OBJECT-TYPE
	SYNTAX      INTEGER(0|1)
	MAX-ACCESS	    read-write
	STATUS		current
	DESCRIPTION
		"Set the corresponding action while loop is detected.
         1 - lock the loop port,
         0 - do nothing."
	::= { sw0657840LoopDetectedConf 3 }

sw0657840SFPInfo           	OBJECT IDENTIFIER ::= { sw0657840Produces 14 }

sw0657840SFPInfoNumber OBJECT-TYPE
	SYNTAX      INTEGER(1..2147483647)
	MAX-ACCESS	    read-only
	STATUS		current
	DESCRIPTION
		"Get the number of sfp info entry."
	::= { sw0657840SFPInfo 1 }

sw0657840SFPInfoTable	OBJECT-TYPE
	SYNTAX		SEQUENCE OF SW0657840SFPInfoEntry
	MAX-ACCESS	not-accessible
	STATUS		current
    DESCRIPTION
        "A list of sfp info entry. The numbers of entries are given by the value of sw0657840SFPInfoNumber."
	::= { sw0657840SFPInfo 2 }

SW0657840SFPInfoEntry ::=
SEQUENCE {
    sw0657840SFPInfoIndex INTEGER,
    sw0657840SFPConnectorType DisplayString,
    sw0657840SFPFiberType DisplayString,
    sw0657840SFPWavelength DisplayString,
    sw0657840SFPBaudRate DisplayString,
    sw0657840SFPVendorOUI DisplayString,
    sw0657840SFPVendorName DisplayString,
    sw0657840SFPVendorPN DisplayString,
    sw0657840SFPVendorRev DisplayString,
    sw0657840SFPVendorSN DisplayString,
    sw0657840SFPDateCode DisplayString,
    sw0657840SFPTemperature DisplayString,
    sw0657840SFPVcc DisplayString,
    sw0657840SFPTxBias DisplayString,
    sw0657840SFPTxPWR DisplayString,
    sw0657840SFPRxPWR DisplayString
}

sw0657840SFPInfoEntry	OBJECT-TYPE
	SYNTAX		SW0657840SFPInfoEntry
	MAX-ACCESS	    not-accessible
	STATUS		current
	DESCRIPTION
		"Entry(s) for SFP information."
	INDEX {sw0657840SFPInfoIndex}
	::= { sw0657840SFPInfoTable 1 }

sw0657840SFPInfoIndex	OBJECT-TYPE
	SYNTAX		INTEGER(1..2147483647)
	MAX-ACCESS	    read-only
	STATUS		current
	DESCRIPTION
		"The index of the sfp info entry."
	::= { sw0657840SFPInfoEntry 1 }

sw0657840SFPConnectorType	OBJECT-TYPE
	SYNTAX		DisplayString
	MAX-ACCESS	    read-only
	STATUS		current
	DESCRIPTION
		"Get connector type of the sfp."
	::= { sw0657840SFPInfoEntry 2 }

sw0657840SFPFiberType	OBJECT-TYPE
	SYNTAX		DisplayString
	MAX-ACCESS	    read-only
	STATUS		current
	DESCRIPTION
		"Get fiber type of the sfp."
	::= { sw0657840SFPInfoEntry 3 }

sw0657840SFPWavelength	OBJECT-TYPE
	SYNTAX		DisplayString
	MAX-ACCESS	    read-only
	STATUS		current
	DESCRIPTION
		"Get tx central wavelength of the sfp."
	::= { sw0657840SFPInfoEntry 4 }

sw0657840SFPBaudRate	OBJECT-TYPE
	SYNTAX		DisplayString
	MAX-ACCESS	    read-only
	STATUS		current
	DESCRIPTION
		"Get baud rate of the sfp."
	::= { sw0657840SFPInfoEntry 5 }

sw0657840SFPVendorOUI	OBJECT-TYPE
	SYNTAX		DisplayString
	MAX-ACCESS	    read-only
	STATUS		current
	DESCRIPTION
		"Get vendor OUI of the sfp."
	::= { sw0657840SFPInfoEntry 6 }

sw0657840SFPVendorName	OBJECT-TYPE
	SYNTAX		DisplayString
	MAX-ACCESS	    read-only
	STATUS		current
	DESCRIPTION
		"Get vendor name of the sfp."
	::= { sw0657840SFPInfoEntry 7 }

sw0657840SFPVendorPN	OBJECT-TYPE
	SYNTAX		DisplayString
	MAX-ACCESS	    read-only
	STATUS		current
	DESCRIPTION
		"Get vendor part number of the sfp."
	::= { sw0657840SFPInfoEntry 8 }

sw0657840SFPVendorRev	OBJECT-TYPE
	SYNTAX		DisplayString
	MAX-ACCESS	    read-only
	STATUS		current
	DESCRIPTION
		"Get vendor revision number of the sfp."
	::= { sw0657840SFPInfoEntry 9 }

sw0657840SFPVendorSN	OBJECT-TYPE
	SYNTAX		DisplayString
	MAX-ACCESS	    read-only
	STATUS		current
	DESCRIPTION
		"Get vendor serial number of the sfp."
	::= { sw0657840SFPInfoEntry 10 }

sw0657840SFPDateCode	OBJECT-TYPE
	SYNTAX		DisplayString
	MAX-ACCESS	    read-only
	STATUS		current
	DESCRIPTION
		"Get data code of the sfp."
	::= { sw0657840SFPInfoEntry 11 }

sw0657840SFPTemperature	OBJECT-TYPE
	SYNTAX		DisplayString
	MAX-ACCESS	    read-only
	STATUS		current
	DESCRIPTION
		"Get current temperature of the sfp."
	::= { sw0657840SFPInfoEntry 12 }

sw0657840SFPVcc	OBJECT-TYPE
	SYNTAX		DisplayString
	MAX-ACCESS	    read-only
	STATUS		current
	DESCRIPTION
		"Get current internal supply voltage of the sfp."
	::= { sw0657840SFPInfoEntry 13 }

sw0657840SFPTxBias	OBJECT-TYPE
	SYNTAX		DisplayString
	MAX-ACCESS	    read-only
	STATUS		current
	DESCRIPTION
		"Get current TX Bias of the sfp."
	::= { sw0657840SFPInfoEntry 14 }

sw0657840SFPTxPWR	OBJECT-TYPE
	SYNTAX		DisplayString
	MAX-ACCESS	    read-only
	STATUS		current
	DESCRIPTION
		"Get current TX output power of the sfp."
	::= { sw0657840SFPInfoEntry 15 }

sw0657840SFPRxPWR	OBJECT-TYPE
	SYNTAX		DisplayString
	MAX-ACCESS	    read-only
	STATUS		current
	DESCRIPTION
		"Get current Received Power of the sfp."
	::= { sw0657840SFPInfoEntry 16 }

sw0657840TrapEntry	       OBJECT IDENTIFIER ::= { sw0657840Produces 20 }

sw0657840ModuleInserted NOTIFICATION-TYPE
    OBJECTS { ifIndex }
	STATUS    current
	DESCRIPTION
	    "Send the trap when a module is inserted to the system. The OID value means
	     the port number."
	::= { sw0657840TrapEntry 1 }

sw0657840ModuleRemoved NOTIFICATION-TYPE
    OBJECTS { ifIndex }
	STATUS    current
	DESCRIPTION
	    "Send the trap when a module is removed from the system. The OID value means
	     the port number."
	::= { sw0657840TrapEntry 2 }

sw0657840DualMediaSwapped NOTIFICATION-TYPE
    OBJECTS { ifIndex }
	STATUS    current
	DESCRIPTION
	    "Send the trap when the dual media port changed. The OID value means the port number."
	::= { sw0657840TrapEntry 3 }

sw0657840LoopDetected NOTIFICATION-TYPE
    OBJECTS { ifIndex }
	STATUS    current
	DESCRIPTION
	    "Send the trap when loop condition has been detected. The OID value means the port number."
	::= { sw0657840TrapEntry 5 }

sw0657840StpStateDisabled NOTIFICATION-TYPE
	STATUS		current
	DESCRIPTION
	   "Send the trap when the operational state of STP is from enabled to disabled. "
	::= { sw0657840TrapEntry 100 }

sw0657840StpStateEnabled NOTIFICATION-TYPE
	STATUS		current
	DESCRIPTION
	   "Send the trap when the operational state of STP is from disabled to enabled. "
	::= { sw0657840TrapEntry 101 }

sw0657840StpTopologyChanged NOTIFICATION-TYPE
    OBJECTS { ifIndex }
	STATUS		current
	DESCRIPTION
	   "Send the trap when RSTP determines a port should enter the FORWARDING state
	    (a topology change occurs). The OID value is the ifIndex of the port that
	    produces the topology change."
	::= { sw0657840TrapEntry 102 }

sw0657840LacpStateDisabled NOTIFICATION-TYPE
    OBJECTS {ifIndex, groupId}
	STATUS		current
	DESCRIPTION
	   "Send the trap when the operational state of LACP is from enabled to disabled.
	    The OID value means the disabled Group ID."
	::= { sw0657840TrapEntry 120 }

sw0657840LacpStateEnabled NOTIFICATION-TYPE
    OBJECTS {ifIndex, groupId}
	STATUS		current
	DESCRIPTION
	   "Send the trap when the operational state of LACP is from disabled to enabled.
	    The OID value means the disabled Group ID."
	::= { sw0657840TrapEntry 121 }

sw0657840LacpPortAdded NOTIFICATION-TYPE
    OBJECTS   { ifIndex, actorkey, partnerkey }
	STATUS		current
	DESCRIPTION
	   "Send the trap when the state of port is in 'trunk ready'."
	::= { sw0657840TrapEntry 123 }

sw0657840LacpPortTrunkFailure NOTIFICATION-TYPE
    OBJECTS   { ifIndex, actorkey, partnerkey}
	STATUS		current
	DESCRIPTION
	   "Send the trap when one port is not able to be aggregated
	    due to duplex-mode of the port. "
	::= { sw0657840TrapEntry 124 }

sw0657840GvrpStateDisabled NOTIFICATION-TYPE
	STATUS		current
	DESCRIPTION
	   "Send the trap when the operational state of GVRP is from enabled to disabled. "
	::= { sw0657840TrapEntry 140 }

sw0657840GvrpStateEnabled NOTIFICATION-TYPE
	STATUS		current
	DESCRIPTION
	   "Send the trap when the operational state of LACP is from disabled to enabled. "
	::= { sw0657840TrapEntry 141 }

sw0657840VlanStateDisabled NOTIFICATION-TYPE
	STATUS		current
	DESCRIPTION
	   "Send the trap when the operational state of vlan is from enabled to disabled.
	    The OID value means the enabled Group ID. "
	::= { sw0657840TrapEntry 150 }

sw0657840VlanPortBaseEnabled NOTIFICATION-TYPE
	STATUS		current
	DESCRIPTION
	   "Send the trap when the operational state of vlan is changed to port-based vlan."
	::= { sw0657840TrapEntry 151 }

sw0657840VlanTagBaseEnabled NOTIFICATION-TYPE
	STATUS		current
	DESCRIPTION
	   "Send the trap when the operational state of vlan is changed to tag-based vlan."
	::= { sw0657840TrapEntry 152 }

sw0657840VlanMetroModeEnabled NOTIFICATION-TYPE
    OBJECTS   {uplink}
	STATUS		current
	DESCRIPTION
	   "Send the trap when the operational state of vlan is changed to Metro-mode vlan.
        The OID value means the uplink port with this metro-mode vlan."
	::= { sw0657840TrapEntry 153 }

sw0657840VlanDoubleTagEnabled NOTIFICATION-TYPE
	STATUS		current
	DESCRIPTION
	   "Send the trap when the operational state of vlan is changed to Double-tag vlan."
	::= { sw0657840TrapEntry 154 }

sw0657840UserLogin NOTIFICATION-TYPE
    OBJECTS   {username}
	STATUS		current
	DESCRIPTION
	   "Send the trap when one user logins the system."
	::= { sw0657840TrapEntry 200 }

sw0657840UserLogout NOTIFICATION-TYPE
    OBJECTS   {username}
	STATUS		current
	DESCRIPTION
	   "Send the trap when one user logouts the system."
	::= { sw0657840TrapEntry 201 }

sw0657840TrapVariable	OBJECT IDENTIFIER ::= { sw0657840Produces 21 }

username OBJECT-TYPE
    SYNTAX      DisplayString
	MAX-ACCESS  read-only
	STATUS      current
	DESCRIPTION
	    "System account name."
	::= { sw0657840TrapVariable 1 }

groupId OBJECT-TYPE
    SYNTAX      INTEGER(1..8)
	MAX-ACCESS  read-only
	STATUS      current
	DESCRIPTION
	    "The Trunk group ID of LACP."
	::= { sw0657840TrapVariable 2 }

actorkey OBJECT-TYPE
    SYNTAX	INTEGER(1..2147483647)
	MAX-ACCESS  read-only
	STATUS      current
	DESCRIPTION
	    "This is the actor key information for LACP."
	::= { sw0657840TrapVariable 3 }

partnerkey OBJECT-TYPE
    SYNTAX	INTEGER(1..2147483647)
	MAX-ACCESS  read-only
	STATUS      current
	DESCRIPTION
	    "This is the partner key information for LACP."
	::= { sw0657840TrapVariable 4 }

uplink OBJECT-TYPE
    SYNTAX	DisplayString
	MAX-ACCESS  read-only
	STATUS      current
	DESCRIPTION
	    "Uplink port(s) in the metro-mode vlan."
	::= { sw0657840TrapVariable 5 }

END

--
-- DCP-TOPOLOGY-MIB.mib
-- Smartoptics DCP Topology Enterprise Specific MIB.
--
-- Copyright (c) 2021, Smartoptics
-- All rights reserved
--

DCP-TOPOLOGY-MIB DEFINITIONS ::= BEGIN
IMPORTS
    dcpGeneric
        FROM DCP-MIB
    MODULE-COMPLIANCE, OBJECT-GROUP
        FROM SNMPv2-CONF
    Unsigned32, OBJECT-TYPE, MODULE-IDENTITY
        FROM SNMPv2-SMI
    DisplayString
        FROM SNMPv2-TC;


-- December 30, 2021 at 08:00 GMT
-- 1.3.6.1.4.1.30826.2.2.5
dcpTopology MODULE-IDENTITY 
    LAST-UPDATED "202112300800Z"
    ORGANIZATION "Smartoptics."
    CONTACT-INFO "http://www.smartoptics.com"
    DESCRIPTION "This is the enterprise specific DCP TOPOLOGY MIB for Smartoptics"

    REVISION "202112300800Z"
    DESCRIPTION "The initial revision"
::= { dcpGeneric 5 }


--  Node definitions
-- 
-- 1.3.6.1.4.1.30826.2.2.5.1
dcpTopologyObjects OBJECT IDENTIFIER ::= { dcpTopology 1 }


-- 1.3.6.1.4.1.30826.2.2.5.1.1
dcpTopologyInternalTable OBJECT-TYPE
    SYNTAX SEQUENCE OF TopologyInternalEntry
    MAX-ACCESS not-accessible
    STATUS current
    DESCRIPTION
    "Keeps a list of the current topology internal in the system."
::= { dcpTopologyObjects 1 }


-- 1.3.6.1.4.1.30826.2.2.5.1.1.1
dcpTopologyInternalEntry OBJECT-TYPE
    SYNTAX TopologyInternalEntry
    MAX-ACCESS not-accessible
    STATUS current
    DESCRIPTION
    "Description."
INDEX { dcpTopologyInternalId }
::= { dcpTopologyInternalTable 1 }


TopologyInternalEntry ::=
    SEQUENCE { 
        dcpTopologyInternalId
        Unsigned32,
        dcpTopologyInternalSource
        DisplayString,
        dcpTopologyInternalDestination
        DisplayString
 }

-- 1.3.6.1.4.1.30826.2.2.5.1.1.1.1
dcpTopologyInternalId OBJECT-TYPE
    SYNTAX Unsigned32 (1..1000000)
    MAX-ACCESS not-accessible
    STATUS current
    DESCRIPTION
    "Unique index assigned to each topology internal."
::= { dcpTopologyInternalEntry 1 }

-- 1.3.6.1.4.1.30826.2.2.5.1.1.1.2
dcpTopologyInternalSource OBJECT-TYPE
    SYNTAX DisplayString
    MAX-ACCESS read-only
    STATUS current
    DESCRIPTION
    "Topology internal source."
::= { dcpTopologyInternalEntry 2 }

-- 1.3.6.1.4.1.30826.2.2.5.1.1.1.3
dcpTopologyInternalDestination OBJECT-TYPE
    SYNTAX DisplayString
    MAX-ACCESS read-only
    STATUS current
    DESCRIPTION
    "Topology internal destination."
::= { dcpTopologyInternalEntry 3 }


-- 1.3.6.1.4.1.30826.2.2.5.2
dcpTopologyMIBCompliance OBJECT IDENTIFIER ::= { dcpTopology 2 }


-- 1.3.6.1.4.1.30826.2.2.5.2.1
dcpTopologyMIBGroups OBJECT IDENTIFIER ::= { dcpTopologyMIBCompliance 1 }


-- 1.3.6.1.4.1.30826.2.2.5.2.1.1
dcpTopologyTableGroupV1 OBJECT-GROUP
    OBJECTS { dcpTopologyInternalSource, dcpTopologyInternalDestination }
    STATUS current
    DESCRIPTION 
    "Topology objects V1."
::= { dcpTopologyMIBGroups 1 }


-- 1.3.6.1.4.1.30826.2.2.5.2.2
dcpTopologyMIBCompliances OBJECT IDENTIFIER ::= { dcpTopologyMIBCompliance 2 }

-- 1.3.6.1.4.1.30826.2.2.5.2.2.1
dcpTopologyBasicComplV1 MODULE-COMPLIANCE
    STATUS      current
    DESCRIPTION
    "Basic implementation requirements for the DCP-TOPOLOGY-MIB V1."
    MODULE
    MANDATORY-GROUPS {
        dcpTopologyTableGroupV1 }
::= { dcpTopologyMIBCompliances 1 }


END

--
-- DCP-TOPOLOGY-MIB.mib
--

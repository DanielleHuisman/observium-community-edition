-- *****************************************************************
-- Copyright (c) 2017 SonicWall Inc.
-- All rights reserved.
-- *****************************************************************

SONICWALL-SMA-APPLIANCE-SYSTEM-HEALTH-MIB	DEFINITIONS ::= BEGIN
	IMPORTS
		sonicwallSMAAppliance	
			FROM SONICWALL-SMA-MIB
		OBJECT-TYPE, Integer32, NOTIFICATION-TYPE, enterprises, MODULE-IDENTITY
			FROM SNMPv2-SMI;

	sonicwallSystemHealth MODULE-IDENTITY
			LAST-UPDATED      "201804090001Z" 
			ORGANIZATION      "Sonicwall"
			CONTACT-INFO       
				"	SonicWall Inc.

					Tel: +1 408 745 9600
					Fax: +1 408 745 9300

				E-mail: support@sonicwall.com"
             DESCRIPTION       "This Sonicwall MIB provides System Health Info"
        	::= {sonicwallSMAAppliance 2}

	authenticatedUsers	OBJECT IDENTIFIER
		::=  {  sonicwallSystemHealth  1  }

	connectionUtilization	OBJECT IDENTIFIER
		::=  {  sonicwallSystemHealth  2  }

	cpuUtilization	OBJECT-TYPE	
		SYNTAX			Integer32
		MAX-ACCESS	read-only
		STATUS			current
		DESCRIPTION	"The current CPU percent utilization of the sum of \
		                             CPUs on the single node."
		::=  {  sonicwallSystemHealth  3  }

	memoryTotalUtilization	OBJECT IDENTIFIER
		::=  {  sonicwallSystemHealth  4  }
		
	ramUtilization	OBJECT-TYPE	
		SYNTAX			Integer32
		MAX-ACCESS	read-only
		STATUS			current
		DESCRIPTION	"The current virtual memory (RAM )  percentage being utilized."
		::=  {  memoryTotalUtilization  1  }

	swapUtilization	OBJECT-TYPE	
		SYNTAX			Integer32
		MAX-ACCESS	read-only
		STATUS			current
		DESCRIPTION	"The current virtual memory (Swap) percentage  being utilized."
		::=  {  memoryTotalUtilization  2  }

	bandwidthUtilization	OBJECT IDENTIFIER
		::=  {  sonicwallSystemHealth  5  }

	cpuCapacityWarning	NOTIFICATION-TYPE
		OBJECTS			{ cpuUtilization }	
		STATUS			current
		DESCRIPTION	"The heuristically determined percentage of cpu capacity \
		                             utilization of a single node system has exceeded the 90% \
		                             of the cpu capacity. This capacity is the cpuCapacityUtilization \
		                             for single node systems. "
		::=  {  sonicwallSystemHealth  6  }

	memoryCapacityWarning	NOTIFICATION-TYPE
		OBJECTS			{ ramUtilization }
		STATUS			current
		DESCRIPTION	"The heuristically determined percentage of memory \
		                            capacity utilization of a single node system has exceeded \
		                            the 90% of the memory capacity. This capacity is the \
		                            memoryCapacityUtilization for single node systems."
		::=  {  sonicwallSystemHealth  7  }

	userLimitWarning	NOTIFICATION-TYPE
		OBJECTS { currentlyLoggedIn }
		STATUS			current
		DESCRIPTION	"The number of currently authenticated active user \
		                            sessions on a single node (currentlyLoggedIn) has \
		                            reached 90 percent of the license capacity limit."
		::=  {  sonicwallSystemHealth  8  }

	currentlyLoggedIn	OBJECT-TYPE	
		SYNTAX			Integer32
		MAX-ACCESS	read-only
		STATUS			current
		DESCRIPTION	"Number of currently authenticated active user sessions." 
		::=  {  authenticatedUsers  1  }

	peakLoggedIn	OBJECT-TYPE	
		SYNTAX			Integer32
		MAX-ACCESS	read-only
		STATUS			current
		DESCRIPTION	"The maximum number of authenticated active user \
		                            sessions since the last reset; where reset interval \
		                            is 24 hours."
		::=  {  authenticatedUsers  2  }
	

	maximumlicensedUsers	OBJECT-TYPE	
		SYNTAX			Integer32
		MAX-ACCESS	read-only
		STATUS			current
		DESCRIPTION	"The maximum number of active user sessions the \
		                            appliance (or cluster of appliances) is licensed for."
		::=  {  authenticatedUsers  3  }

	currentConnections	OBJECT-TYPE	
		SYNTAX			Integer32
		MAX-ACCESS	read-only
		STATUS			current
		DESCRIPTION	"The number of connections currently being serviced \
		                            by the appliance ( or cluster of appliances)."
		::=  {  connectionUtilization  1  }

	peakConnections	OBJECT-TYPE	
		SYNTAX			Integer32
		MAX-ACCESS	read-only
		STATUS			current
		DESCRIPTION	"The maximum number of concurrent appliance \
		                            connections since the last reset; where the reset \
		                            interval is 24 hours."
		::=  {  connectionUtilization  2  }

	internalInterfaceCurrentThroughput	OBJECT-TYPE	
		SYNTAX			Integer32
		MAX-ACCESS	read-only
		STATUS			current
		DESCRIPTION	"The current SSL VPN throughput in Mega bits per \
		                            second as measured on the internal interface of the node \
		                            since the last reset interval; where reset interval is 24 hours."
		::=  {  bandwidthUtilization  1  }

	internalInterfacePeakThroughput	OBJECT-TYPE	

		SYNTAX			Integer32
		MAX-ACCESS	read-only
		STATUS			current
		DESCRIPTION	"The peak SSL VPN InternalInterface throughput in Mega \
		                             bits per second since the last reset interval; \
		                             where reset interval is 24 hours."
		::=  {  bandwidthUtilization  2  }

	externalInterfaceCurrentThroughput	OBJECT-TYPE	
		SYNTAX			Integer32
		MAX-ACCESS	read-only
		STATUS			current
		DESCRIPTION	"The current SSL VPN throughput in Mega bits per second \
		                             as measured on the external interface of the node since \
		                             the last reset interval; where reset interval is 24 hours."
		::=  {  bandwidthUtilization  3  }

	

	externalInterfacePeakThroughput	OBJECT-TYPE	

		SYNTAX			Integer32
		MAX-ACCESS	read-only
		STATUS			current
		DESCRIPTION	"The peak SSL VPN ExternalInterface throughput in \
		                             Mega bits per second since the last reset interval; \
		                             where reset interval is 24 hours."
		::=  {  bandwidthUtilization  4  }

	clusterlInterfaceCurrentThroughput	OBJECT-TYPE	

		SYNTAX			Integer32
		MAX-ACCESS	read-only
		STATUS			current
		DESCRIPTION	"The current SSL VPN ClusterInterface throughput in \
		                              Mega bits per second since the last reset interval; \
		                              where reset interval is 24 hours."
		::=  {  bandwidthUtilization  5  }

	clusterInterfacePeakThroughput	OBJECT-TYPE	

		SYNTAX			Integer32
		MAX-ACCESS	read-only
		STATUS			current
		DESCRIPTION	"The peak SSL VPN ClusterInterface throughput in \
		                            Mega bits per second since the last reset interval; \
		                            where reset interval is 24 hours."
		::=  {  bandwidthUtilization  6  }

	logUtilization	OBJECT-TYPE
		SYNTAX		        Integer32
		MAX-ACCESS	 read-only
		STATUS		        current
		DESCRIPTION	"Percent of log file partition being utilized"
		::= { sonicwallSystemHealth  9 }

	logCapacityWarning 	NOTIFICATION-TYPE
		OBJECTS { logUtilization }
		STATUS			current
		DESCRIPTION	"The percentage of log file disk space of a single \
		                            node system has exceeded the 90% of the total \
		                            capacity. "
		::=  {  sonicwallSystemHealth 100  }

	userLimitReached	NOTIFICATION-TYPE
		OBJECTS { currentlyLoggedIn }
		STATUS			current
		DESCRIPTION	"The number of currently authenticated active user \
		                            sessions on a single node (currentlyLoggedIn) has \
		                            reached the current license capacity limit."
		::=  {  sonicwallSystemHealth  102  }

	userLimitExceeded	NOTIFICATION-TYPE
		OBJECTS { currentlyLoggedIn }
		STATUS			current
		DESCRIPTION	"The number of currently authenticated active user \
		                            sessions on a single node (currentlyLoggedIn) has \
		                            exceeded the current license capacity limit."
               ::=  {  sonicwallSystemHealth  103  }


END

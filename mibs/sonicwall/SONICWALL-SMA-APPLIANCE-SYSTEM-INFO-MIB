-- *****************************************************************
-- Copyright (c) 2017 SonicWall Inc.
-- All rights reserved.
-- *****************************************************************

SONICWALL-SMA-APPLIANCE-SYSTEM-INFO-MIB	DEFINITIONS ::= BEGIN
	IMPORTS
		sonicwallSMAAppliance
			FROM SONICWALL-SMA-MIB
		OBJECT-TYPE, Integer32, NOTIFICATION-TYPE, MODULE-IDENTITY
			FROM SNMPv2-SMI
		InternationalDisplayString 
			FROM HOST-RESOURCES-MIB;


	sonicwallSystemInfo MODULE-IDENTITY
			LAST-UPDATED       "201804090001Z" 
			ORGANIZATION       "SonicWall"
			CONTACT-INFO       
				"	SonicWall Inc.

					Tel: +1 408 745 9600
					Fax: +1 408 745 9300

				E-mail: support@sonicwall.com"
			DESCRIPTION        "This SonicWall MIB provides System Info"
        	::= {sonicwallSMAAppliance 1}


	SMAVersion	OBJECT-TYPE	
		SYNTAX			InternationalDisplayString
		MAX-ACCESS	read-only
		STATUS			current
		DESCRIPTION	"Version of SMA running on this node in  \
		                             major.minor.micro-patch-build format."
		::=  {  sonicwallSystemInfo  1  }

	hardwareModel	OBJECT-TYPE	
		SYNTAX			InternationalDisplayString
		MAX-ACCESS	read-only
		STATUS			current
		DESCRIPTION	"The model number of this node."
		::=  {  sonicwallSystemInfo  2  }

	
	SMASystemUp	NOTIFICATION-TYPE
		STATUS			current
		DESCRIPTION	"The SMA single node system; identified by the IP \
		                             address the trap is sent from is back online."
		::=  {  sonicwallSystemInfo  4  }

	SMASystemDown	NOTIFICATION-TYPE
		STATUS			current
		DESCRIPTION	"The SMA single node system; identified by the IP \
		                             address the trap is sent from is going offline."
		::=  {  sonicwallSystemInfo  5  }


END

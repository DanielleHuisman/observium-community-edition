--
 --                     Sonus Networks CONFIDENTIAL
 --
 --  This listing of source code is proprietary and confidential to
 --  Sonus Networks, Inc.  It may not be copied or made available in
 --  any form (electronic or hard copy) to any person not authorized
 --  by Sonus Networks, Inc. All rights reserved.
 --
 --                Copyright (C) 2009-2013
 --                Sonus Networks, Inc.
 --                4 Technology Park Drive
 --                Westford, MA  01886, U.S.A.
 --
 --
 -- Release: 3.0
 --
UX-TRAP-MIB DEFINITIONS ::= BEGIN
	IMPORTS
		MODULE-IDENTITY, OBJECT-TYPE, NOTIFICATION-TYPE, IpAddress, enterprises, Counter32, Counter64
			FROM SNMPv2-SMI
		TEXTUAL-CONVENTION, DisplayString
			FROM SNMPv2-TC
		MODULE-COMPLIANCE, OBJECT-GROUP
			FROM SNMPv2-CONF
			uxAlarmActiveIndex,
			uxAlarmConfigIndex,
			uxAlarmActiveID,
			uxAlarmActiveSubID,
			uxAlarmActiveCondition,
			uxAlarmActiveSeverity,
			uxAlarmActiveCategory,
			uxAlarmActiveCancelType,
			uxAlarmActiveDecodeKey,
			uxAlarmActiveCount,
			uxAlarmActiveState,
			uxAlarmActiveSourceInstance,
			uxAlarmActiveFirstOccur,
			uxAlarmActiveLastOccur,
			uxAlarmActiveClrEvtID,
			uxAlarmActiveClrEvtSubID,
			uxAlarmActiveDescription,
			uxAlarmActiveHighestSeverityAlarm,
			uxAlarmActiveHardWareID
			FROM UX-OBJECTS-MIB;

 --iso            OBJECT IDENTIFIER ::= { 1 }
 --org            OBJECT IDENTIFIER ::= { iso 3 }
 --dod            OBJECT IDENTIFIER ::= { org 6 }
 --internet       OBJECT IDENTIFIER ::= { dod 1 }
 --directory      OBJECT IDENTIFIER ::= { internet 1 }
 --mgmt           OBJECT IDENTIFIER ::= { internet 2 }
 --mib-2          OBJECT IDENTIFIER ::= { mgmt 1 }
 --transmission   OBJECT IDENTIFIER ::= { mib-2 10 }
 --experimental   OBJECT IDENTIFIER ::= { internet 3 }
 --private        OBJECT IDENTIFIER ::= { internet 4 }
 --enterprises    OBJECT IDENTIFIER ::= { private 1 }

ux MODULE-IDENTITY
				LAST-UPDATED "200911041705Z" 
				ORGANIZATION "Sonus Networks" 
				CONTACT-INFO 
					"       TAC
					E-mail: tac@net.com"
				DESCRIPTION
					"The MIB module for Sonus entities. 
					This MIB module describes the enterprise traps for the Sonus SBC 1000 and 2000." 
				::= { enterprises 177 15 }

net OBJECT IDENTIFIER ::= { enterprises 177 }
uxObjects     OBJECT IDENTIFIER ::= { ux 1 }
uxTraps       OBJECT IDENTIFIER ::= { ux 2 }    

------------------------------------------------------------------
--ADcachingfailed ( Alarm )
------------------------------------------------------------------
	uxAlmADcachingfailed NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Failed to cache attributes from AD in memory. Suggested action - try again later. This alarm will be cleared by event AD caching successful."
 	::= { uxTraps 65537  }

------------------------------------------------------------------
--OnlineADqueryfailed ( Alarm )
------------------------------------------------------------------
	uxAlmOnlineADqueryfailed NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Failed to execute AD query. Suggested action - confirm that AD is network reachable, check the AD configuration as well as AD access credentials."
 	::= { uxTraps 65538  }

------------------------------------------------------------------
--Userloggedin ( Alarm )
------------------------------------------------------------------
	uxAlmUserloggedin NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"New user 'username' logged in from 'ip address' at 'time'."
 	::= { uxTraps 65540  }

------------------------------------------------------------------
--Userloginfailed ( Alarm )
------------------------------------------------------------------
	uxAlmUserloginfailed NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"User 'username' login failed from 'ip' at 'time'. This alarm will be cleared by event User logged in."
 	::= { uxTraps 65541  }

------------------------------------------------------------------
--ADUnreachable ( Alarm )
------------------------------------------------------------------
	uxAlmADUnreachable NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Either AD is network unreachable, or the AD credentials are invalid. This alarm will be cleared by 'AD Reachable' event."
 	::= { uxTraps 65542  }

------------------------------------------------------------------
--ADReachable ( Alarm )
------------------------------------------------------------------
	uxAlmADReachable NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Active directory is now reachable."
 	::= { uxTraps 65543  }

------------------------------------------------------------------
--ADcachingsuccessful ( Alarm )
------------------------------------------------------------------
	uxAlmADcachingsuccessful NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"AD caching was successful."
 	::= { uxTraps 65544  }

------------------------------------------------------------------
--ADbackupfailed ( Alarm )
------------------------------------------------------------------
	uxAlmADbackupfailed NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Failed to backup cached values from AD to storage device. Either the storage device is not present, or it is full. Contact Sonus TAC for further assistance."
 	::= { uxTraps 65545  }

------------------------------------------------------------------
--ADsuccessfullybackedup ( Alarm )
------------------------------------------------------------------
	uxAlmADsuccessfullybackedup NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Successful backup of cached values from AD to storage device."
 	::= { uxTraps 65546  }

------------------------------------------------------------------
--ADcachetruncated ( Alarm )
------------------------------------------------------------------
	uxAlmADcachetruncated NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"AD Cache is truncated, AD cache results have exceeded the maximum cache size. Consider caching only the required attributes. If the query is not found in cache, Online query will be performed, while affecting performance."
 	::= { uxTraps 65547  }

------------------------------------------------------------------
--RADIUSServerUnreachable ( Alarm )
------------------------------------------------------------------
	uxAlmRADIUSServerUnreachable NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Either the RADIUS server is network unreachable, or the configuration is incorrect.  Suggested action - check shared secret, listening port, RADIUS server IP. This alarm will be cleared by 'RADIUS Reachable' event."
 	::= { uxTraps 65548  }

------------------------------------------------------------------
--RADIUSReachable ( Alarm )
------------------------------------------------------------------
	uxAlmRADIUSReachable NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"RADIUS server is online."
 	::= { uxTraps 65549  }

------------------------------------------------------------------
--CDRloggingfailed ( Alarm )
------------------------------------------------------------------
	uxAlmCDRloggingfailed NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Sonus SBC failed to send CDR to RADIUS based accounting server. Either the server is network unreachable, or the configuration is incorrect.  Suggested action - check shared secret, listening port, RADIUS server IP."
 	::= { uxTraps 65550  }

------------------------------------------------------------------
--CDRbackupfailed ( Alarm )
------------------------------------------------------------------
	uxAlmCDRbackupfailed NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Sonus SBC failed to backup CDR in local file. Either running with low disk space or CDR backup maximum limit is crossed. Suggested action - Free up the disk space or save the CDR Queued file for future reference."
 	::= { uxTraps 65551  }

------------------------------------------------------------------
--InvalidCardIDEEPROMData ( Alarm )
------------------------------------------------------------------
	uxAlmInvalidCardIDEEPROMData NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"A Card was detected with invalid Card ID EEPROM contents (failed CRC-CCITT check). Suggested action - provide the entire alarm message including the numbers at the end to Sonus TAC for further assistance."
 	::= { uxTraps 131073  }

------------------------------------------------------------------
--CardHealthySignalFailure ( Alarm )
------------------------------------------------------------------
	uxAlmCardHealthySignalFailure NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"During Line Card activation, a Card Fault was detected after power was applied to the card. The Card will remain out-of-service.  Suggested action - reboot system. If issue persists, contact Sonus TAC with the alarm information."
 	::= { uxTraps 131074  }

------------------------------------------------------------------
--CardnotSupported ( Alarm )
------------------------------------------------------------------
	uxAlmCardnotSupported NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"A Card was detected which can be identified, but the Sonus SBC system software is unable to support. The Card will remain out-of-service. Suggested action - reboot system. If issue persists, contact Sonus TAC with the alarm information."
 	::= { uxTraps 131075  }

------------------------------------------------------------------
--PowerSupplyinputfailure ( Alarm )
------------------------------------------------------------------
	uxAlmPowerSupplyinputfailure NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"A Power supply module has indicated a failure of input power. The Sonus SBC System has lost Power Supply redundancy. Suggested action - Verify that the power cable is connected and that the PS is functioning properly."
 	::= { uxTraps 131076  }

------------------------------------------------------------------
--PowerSupplyinputrestored ( Alarm )
------------------------------------------------------------------
	uxAlmPowerSupplyinputrestored NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"A Power Supply module has indicated that input power has been restored. This event clears the 'Power Supply Input Failure' Alarm."
 	::= { uxTraps 131077  }

------------------------------------------------------------------
--PowerSupplyoutputfailure ( Alarm )
------------------------------------------------------------------
	uxAlmPowerSupplyoutputfailure NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"A Power Supply module has indicated a failure of output power. The Sonus SBC System has lost Power Supply redundancy. Suggested action - Verify that the PS is functioning properly."
 	::= { uxTraps 131078  }

------------------------------------------------------------------
--SingleFanfailure ( Alarm )
------------------------------------------------------------------
	uxAlmSingleFanfailure NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Check the System tab to find the Fan ID of the failed fan. Contact Sonus TAC with this information."
 	::= { uxTraps 131079  }

------------------------------------------------------------------
--MultipleFanFailures ( Alarm )
------------------------------------------------------------------
	uxAlmMultipleFanFailures NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Check the System tab to find the Fan ID's of the failed fans. Contact Sonus TAC with this information."
 	::= { uxTraps 131080  }

------------------------------------------------------------------
--SystemTemperatureWarm ( Alarm )
------------------------------------------------------------------
	uxAlmSystemTemperatureWarm NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The temperature sensors have indicated that the system is running warm (65°C threshold)."
 	::= { uxTraps 131081  }

------------------------------------------------------------------
--SystemTemperatureWarmCleared ( Alarm )
------------------------------------------------------------------
	uxAlmSystemTemperatureWarmCleared NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The temperature sensors have indicated that the system is no longer running warm (55°C threshold). This event clears the 'System Temperature Warm' Alarm."
 	::= { uxTraps 131082  }

------------------------------------------------------------------
--SystemTemperatureHot ( Alarm )
------------------------------------------------------------------
	uxAlmSystemTemperatureHot NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The temperature sensors have indicated that system is running hot."
 	::= { uxTraps 131083  }

------------------------------------------------------------------
--SystemTemperatureHotCleared ( Alarm )
------------------------------------------------------------------
	uxAlmSystemTemperatureHotCleared NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The temperature sensors have indicated that the system is no longer running hot (65°C threshold). This event clears the 'System Temperature Hot' Alarm."
 	::= { uxTraps 131084  }

------------------------------------------------------------------
--Licensesexpired ( Alarm )
------------------------------------------------------------------
	uxAlmLicensesexpired NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"License of the node has expired, all the licensed features would fail to work. Contact Sonus Enterprise Sales."
 	::= { uxTraps 196609  }

------------------------------------------------------------------
--Licenseexpiresin2weeks ( Alarm )
------------------------------------------------------------------
	uxAlmLicenseexpiresin2weeks NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"License of the node will expire in 2 weeks."
 	::= { uxTraps 196610  }

------------------------------------------------------------------
--NewLicenseapplied ( Alarm )
------------------------------------------------------------------
	uxAlmNewLicenseapplied NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"New License is applied on the node."
 	::= { uxTraps 196611  }

------------------------------------------------------------------
--FailedtoApplyLicense ( Alarm )
------------------------------------------------------------------
	uxAlmFailedtoApplyLicense NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Either an invalid key is used, or the license key applies to a different node, or the license key expiry is past the present date. Contact Sonus Sales to obtain a new license."
 	::= { uxTraps 196612  }

------------------------------------------------------------------
--Failedtoacquirelicense ( Alarm )
------------------------------------------------------------------
	uxAlmFailedtoacquirelicense NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The alarm is generated when the required license is not available.  Check the number of licensed SIP or TDM channels, the number of SIP registrations, SBA, Transcoding or AD. Suggested action - obtain license for missing functionality."
 	::= { uxTraps 196613  }

------------------------------------------------------------------
--ASMUnreachable ( Alarm )
------------------------------------------------------------------
	uxAlmASMUnreachable NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"ASM system can not be reached, system is down. Check whether the ASM is rebooting."
 	::= { uxTraps 327681  }

------------------------------------------------------------------
--ClearASMUnreachable ( Alarm )
------------------------------------------------------------------
	uxAlmClearASMUnreachable NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Clears alarm 'ASM Unreachable'."
 	::= { uxTraps 327682  }

------------------------------------------------------------------
--ASMFailureRecovered ( Alarm )
------------------------------------------------------------------
	uxAlmASMFailureRecovered NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"ASM system was previously unreachable, but has come up. This alarm doesn't autoclear so the user can investigate the cause, but the system should be working correctly now."
 	::= { uxTraps 327683  }

------------------------------------------------------------------
--ASMServicesNotRunning ( Alarm )
------------------------------------------------------------------
	uxAlmASMServicesNotRunning NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"ASM services are not running, calls through the ASM cannot be placed."
 	::= { uxTraps 327684  }

------------------------------------------------------------------
--ClearASMServicesNotRunning ( Alarm )
------------------------------------------------------------------
	uxAlmClearASMServicesNotRunning NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Clears alarm 'ASM Services Not Running'."
 	::= { uxTraps 327685  }

------------------------------------------------------------------
--ASMServicesRecovered ( Alarm )
------------------------------------------------------------------
	uxAlmASMServicesRecovered NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"ASM Services Recovered."
 	::= { uxTraps 327686  }

------------------------------------------------------------------
--ASMServiceRestartFailed ( Alarm )
------------------------------------------------------------------
	uxAlmASMServiceRestartFailed NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The system attempted to restart a failed service on the ASM, service did not start successfully. User interaction is required."
 	::= { uxTraps 327687  }

------------------------------------------------------------------
--ASMSystemStarted ( Alarm )
------------------------------------------------------------------
	uxAlmASMSystemStarted NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"This event is set when the SBA communication system is first established, and usually indicates that the Application Solution Module (ASM) has finished booting. It should come up at system startup, it may come again if the ASM hardware is rebooted."
 	::= { uxTraps 327688  }

------------------------------------------------------------------
--ASMSystemShuttingdown ( Alarm )
------------------------------------------------------------------
	uxAlmASMSystemShuttingdown NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"A planned or deliberate shut down is taking place on the Application Solution Module (ASM)."
 	::= { uxTraps 327689  }

------------------------------------------------------------------
--EthernetLinkDown ( Alarm )
------------------------------------------------------------------
	uxAlmEthernetLinkDown NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Ethernet port specified has lost link. Source Instance: Eth0/Eth1 via SBA Monitor."
 	::= { uxTraps 327690  }

------------------------------------------------------------------
--EthernetLinkUp ( Alarm )
------------------------------------------------------------------
	uxAlmEthernetLinkUp NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Ethernet port specific has recovered link. "
 	::= { uxTraps 327691  }

------------------------------------------------------------------
--ASMSBCIPSubnetMismatch ( Alarm )
------------------------------------------------------------------
	uxAlmASMSBCIPSubnetMismatch NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The ASM and Sonus SBC IP interfaces are in different subnets and cannot communicate."
 	::= { uxTraps 327692  }

------------------------------------------------------------------
--ASMSBCIPSubnetMatch ( Alarm )
------------------------------------------------------------------
	uxAlmASMSBCIPSubnetMatch NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The ASM and Sonus SBC IP interfaces are in the same subnet and can now communicate."
 	::= { uxTraps 327693  }

------------------------------------------------------------------
--ConfigurationchangeoccurredonActionSet ( Alarm )
------------------------------------------------------------------
	uxAlmConfigurationchangeoccurredonActionSet NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"There is an action set table number/name that should be printed with this event."
 	::= { uxTraps 458753  }

------------------------------------------------------------------
--ConfigurationchangeoccurredonNormalizationTable ( Alarm )
------------------------------------------------------------------
	uxAlmConfigurationchangeoccurredonNormalizationTable NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"There is a normalization table number/name that should be printed with this event."
 	::= { uxTraps 458754  }

------------------------------------------------------------------
--ConfigurationchangeoccurredonRouteTable ( Alarm )
------------------------------------------------------------------
	uxAlmConfigurationchangeoccurredonRouteTable NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"There is a route table number/name that should be printed with this event."
 	::= { uxTraps 458755  }

------------------------------------------------------------------
--ConfigurationchangeoccurredonTransformationTables ( Alarm )
------------------------------------------------------------------
	uxAlmConfigurationchangeoccurredonTransformationTables NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"There is a transformation table number/name that should be printed with this event."
 	::= { uxTraps 458756  }

------------------------------------------------------------------
--Routetemporarilydisabled ( Alarm )
------------------------------------------------------------------
	uxAlmRoutetemporarilydisabled NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"This alarm is set if a link is down or some other event has occured to take a route entry out of service."
 	::= { uxTraps 458757  }

------------------------------------------------------------------
--Routeenabled ( Alarm )
------------------------------------------------------------------
	uxAlmRouteenabled NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Route came up."
 	::= { uxTraps 458758  }

------------------------------------------------------------------
--ACallexceededthelimitfornumberofdestinations ( Alarm )
------------------------------------------------------------------
	uxAlmACallexceededthelimitfornumberofdestinations NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"A call with destination of X tried to be forked more than the limit allows (currently 8)."
 	::= { uxTraps 458759  }

------------------------------------------------------------------
--Callforkingusedwithnoforkinglicense ( Alarm )
------------------------------------------------------------------
	uxAlmCallforkingusedwithnoforkinglicense NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"A call with a destination of X was forked with no forking license available."
 	::= { uxTraps 458760  }

------------------------------------------------------------------
--InvocationofInvokeActionSetexceededthemaximumnestinglimit ( Alarm )
------------------------------------------------------------------
	uxAlmInvocationofInvokeActionSetexceededthemaximumnestinglimit NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"A call with with destination of X tried to execute InvokeActionSet more the the limit allows (currently 10)."
 	::= { uxTraps 458761  }

------------------------------------------------------------------
--ConfigurationchangeoccurredonCallbackTables ( Alarm )
------------------------------------------------------------------
	uxAlmConfigurationchangeoccurredonCallbackTables NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"There is a PSAP Callback table number/name that should be printed with this event."
 	::= { uxTraps 458762  }

------------------------------------------------------------------
--Channelisinservice ( Alarm )
------------------------------------------------------------------
	uxAlmChannelisinservice NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Channel is up and is in service. This clears the 'Channel out of service' alarm."
 	::= { uxTraps 524289  }

------------------------------------------------------------------
--Channelisoutofservice ( Alarm )
------------------------------------------------------------------
	uxAlmChannelisoutofservice NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Channel Out Of Service Alarm. This alarm is automatically cleared when Channel is in service."
 	::= { uxTraps 524290  }

------------------------------------------------------------------
--EmergencyCallAttempted ( Alarm )
------------------------------------------------------------------
	uxAlmEmergencyCallAttempted NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Emergency Call is Attempted from Calling Number, Calling Extension, Caller IP address."
 	::= { uxTraps 524291  }

------------------------------------------------------------------
--EmergencyCallCompleted ( Alarm )
------------------------------------------------------------------
	uxAlmEmergencyCallCompleted NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Emergency Call Alarm will be cleared after expiry time in emergency status table."
 	::= { uxTraps 524292  }

------------------------------------------------------------------
--SIPServernotresponding ( Alarm )
------------------------------------------------------------------
	uxAlmSIPServernotresponding NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"SIP server has failed to respond and has been taken out of service. This alarm will be cleared by the event 'SIP server became responsive'."
 	::= { uxTraps 589825  }

------------------------------------------------------------------
--SignalingGrouptakenoutofservice ( Alarm )
------------------------------------------------------------------
	uxAlmSignalingGrouptakenoutofservice NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"All servers in SG have failed.This alarm will be cleared by 'SIP Signaling group enabled' event."
 	::= { uxTraps 589826  }

------------------------------------------------------------------
--SignalingGroupdisabled ( Alarm )
------------------------------------------------------------------
	uxAlmSignalingGroupdisabled NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Configuration action has changed this Signaling Group from Enabled to Disabled."
 	::= { uxTraps 589827  }

------------------------------------------------------------------
--SIPTLSHandshakeAlertFailure ( Alarm )
------------------------------------------------------------------
	uxAlmSIPTLSHandshakeAlertFailure NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"This alarm is generated if TLS Connection failed with an Alert. The connection associated with a TLS Connection ID is aborted. Suggested action - look up the TLS Alert code definitions and determine what corrective actions are to be taken."
 	::= { uxTraps 589828  }

------------------------------------------------------------------
--SIPTLSHandshakeInactivityTimeoutFailure ( Alarm )
------------------------------------------------------------------
	uxAlmSIPTLSHandshakeInactivityTimeoutFailure NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"There was long period of inactivity during exchange of handshake messages for an associated TLS Connection ID. Suggested action - if network delays is experienced, tune the configurable timeout value as to set it to maximum 30 seconds."
 	::= { uxTraps 589829  }

------------------------------------------------------------------
--Configuredportnumbermismatch ( Alarm )
------------------------------------------------------------------
	uxAlmConfiguredportnumbermismatch NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Discrepancy of an FQDN/Port configured in the SipServer object that is different than the DNS SRV lookup. A DNS SRV record can return the port number for the selected protocol. The DNS SRV port value will take priority over the configured port."
 	::= { uxTraps 589830  }

------------------------------------------------------------------
--SIPServerbecameresponsive ( Alarm )
------------------------------------------------------------------
	uxAlmSIPServerbecameresponsive NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"SIP server came up."
 	::= { uxTraps 589831  }

------------------------------------------------------------------
--SIPclusterwentdown ( Alarm )
------------------------------------------------------------------
	uxAlmSIPclusterwentdown NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"SIP cluster went down.This is due to all the servers in the clusters are not responsive. This alarm will be cleared by the event 'Sip cluster enabled'. "
 	::= { uxTraps 589832  }

------------------------------------------------------------------
--SIPClusterenabled ( Alarm )
------------------------------------------------------------------
	uxAlmSIPClusterenabled NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"SIP cluster enabled."
 	::= { uxTraps 589833  }

------------------------------------------------------------------
--SIPSignalinggroupenabled ( Alarm )
------------------------------------------------------------------
	uxAlmSIPSignalinggroupenabled NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"SIP Signaling group enabled. "
 	::= { uxTraps 589834  }

------------------------------------------------------------------
--SIPSignalinggroupconfigDNSfailure ( Alarm )
------------------------------------------------------------------
	uxAlmSIPSignalinggroupconfigDNSfailure NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Failed to resolve the FQDN entries in the SIP Signaling Group. Suggested action - check the FQDN syntax."
 	::= { uxTraps 589835  }

------------------------------------------------------------------
--SIPSignalinggroupconfigFQDNresolved ( Alarm )
------------------------------------------------------------------
	uxAlmSIPSignalinggroupconfigFQDNresolved NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Successfully resolved the FQDN of the SIP Signaling group."
 	::= { uxTraps 589836  }

------------------------------------------------------------------
--SIPServerconfigDNSfailure ( Alarm )
------------------------------------------------------------------
	uxAlmSIPServerconfigDNSfailure NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Failed to resolve the SIP server FQDN entries in the SIP Server table. Suggested action - check the FQDN syntax."
 	::= { uxTraps 589837  }

------------------------------------------------------------------
--SIPServerconfigFQDNresolved ( Alarm )
------------------------------------------------------------------
	uxAlmSIPServerconfigFQDNresolved NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"SIP Server config FQDN resolved. "
 	::= { uxTraps 589838  }

------------------------------------------------------------------
--SIPcallsessionDNSfailure ( Alarm )
------------------------------------------------------------------
	uxAlmSIPcallsessionDNSfailure NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Failed to resolve an FQDN with DNS server during a SIP call session."
 	::= { uxTraps 589839  }

------------------------------------------------------------------
--AcquiringlicenseforRegisterfailed ( Alarm )
------------------------------------------------------------------
	uxAlmAcquiringlicenseforRegisterfailed NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Failed to acquire license from License Manager"
 	::= { uxTraps 589840  }

------------------------------------------------------------------
--Sessionleakorsomeotherresourceleak ( Alarm )
------------------------------------------------------------------
	uxAlmSessionleakorsomeotherresourceleak NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"SIP performs self-check for leaks. Please enable logging for sip and issue 'show resources' command."
 	::= { uxTraps 589841  }

------------------------------------------------------------------
--Failedtobindtonetworkinterface ( Alarm )
------------------------------------------------------------------
	uxAlmFailedtobindtonetworkinterface NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Failed to bind to network interface due to dynamic IP address not available."
 	::= { uxTraps 589842  }

------------------------------------------------------------------
--Successfullyboundtonetworkinterface ( Alarm )
------------------------------------------------------------------
	uxAlmSuccessfullyboundtonetworkinterface NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Successfully bound to network interface. DHCP lease renewed."
 	::= { uxTraps 589843  }

------------------------------------------------------------------
--SIPRegisterServernotresponding ( Alarm )
------------------------------------------------------------------
	uxAlmSIPRegisterServernotresponding NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"SIP Register server has failed to respond. This alarm will be cleared by the event 'SIP Register server became responsive'."
 	::= { uxTraps 589844  }

------------------------------------------------------------------
--SIPRegisterServerbecameresponsive ( Alarm )
------------------------------------------------------------------
	uxAlmSIPRegisterServerbecameresponsive NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"SIP Register server came up."
 	::= { uxTraps 589845  }

------------------------------------------------------------------
--Registrationnotvalidreceivedstalefalse ( Alarm )
------------------------------------------------------------------
	uxAlmRegistrationnotvalidreceivedstalefalse NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Stale is False"
 	::= { uxTraps 589846  }

------------------------------------------------------------------
--ConfigchangeforSIPendpointthatreceivedstalefalse ( Alarm )
------------------------------------------------------------------
	uxAlmConfigchangeforSIPendpointthatreceivedstalefalse NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Endpt which had Stale is False has config change"
 	::= { uxTraps 589847  }

------------------------------------------------------------------
--DChanneldown ( Alarm )
------------------------------------------------------------------
	uxAlmDChanneldown NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The data link layer of the port has come down."
 	::= { uxTraps 655361  }

------------------------------------------------------------------
--DChannelup ( Alarm )
------------------------------------------------------------------
	uxAlmDChannelup NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The data link layer of the port has come back up. "
 	::= { uxTraps 655362  }

------------------------------------------------------------------
--Callreleasedduetochannelrestartbyfarend ( Alarm )
------------------------------------------------------------------
	uxAlmCallreleasedduetochannelrestartbyfarend NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Call released as the ISDN channel has been restarted by far end."
 	::= { uxTraps 655363  }

------------------------------------------------------------------
--Portdisabledbyoperator ( Alarm )
------------------------------------------------------------------
	uxAlmPortdisabledbyoperator NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The physical layer of the port has been brought down by the operator."
 	::= { uxTraps 720897  }

------------------------------------------------------------------
--Portenabledbyoperator ( Alarm )
------------------------------------------------------------------
	uxAlmPortenabledbyoperator NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The physical layer of the port has been brought back up by the operator."
 	::= { uxTraps 720898  }

------------------------------------------------------------------
--DS1LoopbackEnter ( Alarm )
------------------------------------------------------------------
	uxAlmDS1LoopbackEnter NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The DS1 has been put into a loopback state by the operator."
 	::= { uxTraps 720899  }

------------------------------------------------------------------
--DS1LoopbackExit ( Alarm )
------------------------------------------------------------------
	uxAlmDS1LoopbackExit NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The DS1 has been taken out of the loopback state by the operator."
 	::= { uxTraps 720900  }

------------------------------------------------------------------
--RedAlarmLossofSignal ( Alarm )
------------------------------------------------------------------
	uxAlmRedAlarmLossofSignal NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The physical layer has detected a Red (LOS) alarm."
 	::= { uxTraps 720901  }

------------------------------------------------------------------
--RedAlarmLossofSignalcleared ( Alarm )
------------------------------------------------------------------
	uxAlmRedAlarmLossofSignalcleared NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The physical layer has detected a Red (LOS) alarm clearing."
 	::= { uxTraps 720902  }

------------------------------------------------------------------
--RedAlarmLossofFrame ( Alarm )
------------------------------------------------------------------
	uxAlmRedAlarmLossofFrame NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The physical layer has detected a Red (LOF) alarm."
 	::= { uxTraps 720903  }

------------------------------------------------------------------
--RedAlarmLossofFramecleared ( Alarm )
------------------------------------------------------------------
	uxAlmRedAlarmLossofFramecleared NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The physical layer has detected a Red (LOF) alarm clearing."
 	::= { uxTraps 720904  }

------------------------------------------------------------------
--BlueAlarm ( Alarm )
------------------------------------------------------------------
	uxAlmBlueAlarm NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The physical layer has detected a blue alarm."
 	::= { uxTraps 720905  }

------------------------------------------------------------------
--BlueAlarmCleared ( Alarm )
------------------------------------------------------------------
	uxAlmBlueAlarmCleared NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The physical layer has detected an alarm clearing."
 	::= { uxTraps 720906  }

------------------------------------------------------------------
--YellowAlarm ( Alarm )
------------------------------------------------------------------
	uxAlmYellowAlarm NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The physical layer has detected an yellow alarm.This can be originated because of an alarm assert issued by operator or a detection of alarm condition from far end."
 	::= { uxTraps 720907  }

------------------------------------------------------------------
--YellowAlarmCleared ( Alarm )
------------------------------------------------------------------
	uxAlmYellowAlarmCleared NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The physical layer has detected an yellow alarm clear."
 	::= { uxTraps 720908  }

------------------------------------------------------------------
--PortdisabledasportnotfoundonDS1 ( Alarm )
------------------------------------------------------------------
	uxAlmPortdisabledasportnotfoundonDS1 NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"This alarm is generated to indicate that a port which was present in the UI is now marked as disabled because the corresponding port was not present on the DS1 physical hardware."
 	::= { uxTraps 720909  }

------------------------------------------------------------------
--Clockrecoveryswitchedtoportconfiguredassecondary ( Alarm )
------------------------------------------------------------------
	uxAlmClockrecoveryswitchedtoportconfiguredassecondary NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"This alarm is generated to indicate that the primary port from which clock was being recovered has gone down and so clock recovery is now being performed on the secondary port."
 	::= { uxTraps 720910  }

------------------------------------------------------------------
--Clockrecoveryswitchovertosecondaryportcleared ( Alarm )
------------------------------------------------------------------
	uxAlmClockrecoveryswitchovertosecondaryportcleared NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"This event is generated to indicate that the primary port from which clock was being recovered is back in operation and so clock recovery is now being performed on the primary port."
 	::= { uxTraps 720911  }

------------------------------------------------------------------
--Clockrecoveryswitchedtofreerunclock ( Alarm )
------------------------------------------------------------------
	uxAlmClockrecoveryswitchedtofreerunclock NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"This alarm is generated to indicate that the primary and secondary ports from which clock was being recovered have gone down and so clock recovery is now being performed internally from oscillator holdover clock."
 	::= { uxTraps 720912  }

------------------------------------------------------------------
--Clockrecoveryswitchovertofreerunclockcleared ( Alarm )
------------------------------------------------------------------
	uxAlmClockrecoveryswitchovertofreerunclockcleared NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"This event is generated to indicate that either the primary or secondary port from which clock was being recovered is back in-service, so clock will be recovered from the in-service port instead of the oscillator holdover clock."
 	::= { uxTraps 720913  }

------------------------------------------------------------------
--Linecardnotdetected ( Alarm )
------------------------------------------------------------------
	uxAlmLinecardnotdetected NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Line card not detected."
 	::= { uxTraps 720914  }

------------------------------------------------------------------
--Linecarddetected ( Alarm )
------------------------------------------------------------------
	uxAlmLinecarddetected NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Line card detected."
 	::= { uxTraps 720915  }

------------------------------------------------------------------
--Portdisabledforrelaypassthroughstateactivation ( Alarm )
------------------------------------------------------------------
	uxAlmPortdisabledforrelaypassthroughstateactivation NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Port disabled because the corresponding port is activated for relay passthrough state."
 	::= { uxTraps 720916  }

------------------------------------------------------------------
--Portenabledforrelayonlinestateactivation ( Alarm )
------------------------------------------------------------------
	uxAlmPortenabledforrelayonlinestateactivation NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Port enabled because the corresponding port is re-activated for relay online state."
 	::= { uxTraps 720917  }

------------------------------------------------------------------
--Layer1down ( Alarm )
------------------------------------------------------------------
	uxAlmLayer1down NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The physical layer has detected layer 1 down due to state conditions that results in non-operational state of the BRI port. The physical layer state as per I.430 specification can be found in the UI Port View for troubleshooting."
 	::= { uxTraps 720918  }

------------------------------------------------------------------
--Layer1up ( Alarm )
------------------------------------------------------------------
	uxAlmLayer1up NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The physical layer 1 down alarm is cleared with operational state of the BRI port."
 	::= { uxTraps 720919  }

------------------------------------------------------------------
--Portdisabledasportnotfoundonanalogcard ( Alarm )
------------------------------------------------------------------
	uxAlmPortdisabledasportnotfoundonanalogcard NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Port is now marked as disabled because the corresponding port was not present on the analog physical hardware"
 	::= { uxTraps 720920  }

------------------------------------------------------------------
--Portsdisabledforrelaypassthrustatechgonanalogrelaycards ( Alarm )
------------------------------------------------------------------
	uxAlmPortsdisabledforrelaypassthrustatechgonanalogrelaycards NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Ports are now marked as disabled for activated relay passthrough state on analog FXS/FXO card pair."
 	::= { uxTraps 720921  }

------------------------------------------------------------------
--Portsenabledforrelayonlinestatechangeonanalogrelaycardpairs ( Alarm )
------------------------------------------------------------------
	uxAlmPortsenabledforrelayonlinestatechangeonanalogrelaycardpairs NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Ports are now marked as enabled for activated relay passthrough state on analog FXS/FXO card pair."
 	::= { uxTraps 720922  }

------------------------------------------------------------------
--Portstatusdowndetected ( Alarm )
------------------------------------------------------------------
	uxAlmPortstatusdowndetected NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Line down condition detected."
 	::= { uxTraps 720923  }

------------------------------------------------------------------
--Portstatusup ( Alarm )
------------------------------------------------------------------
	uxAlmPortstatusup NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Line down condition cleared."
 	::= { uxTraps 720924  }

------------------------------------------------------------------
--PortdisabledasportnotfoundonBRI ( Alarm )
------------------------------------------------------------------
	uxAlmPortdisabledasportnotfoundonBRI NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"This alarm is generated to indicate that a port which was present in the UI is now marked as disabled because the corresponding port was not present on the BRI physical hardware."
 	::= { uxTraps 720925  }

------------------------------------------------------------------
--Systemnotoperational ( Alarm )
------------------------------------------------------------------
	uxAlmSystemnotoperational NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"System not operational because DSP cannot be initialized. Contact Sonus TAC with the information in this alarm."
 	::= { uxTraps 720926  }

------------------------------------------------------------------
--DSPnotcomingup ( Alarm )
------------------------------------------------------------------
	uxAlmDSPnotcomingup NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"This alarm will be generated if a DSP  cannot be initialized. If the DSP does not come up, contact Sonus TAC with the information in this alarm."
 	::= { uxTraps 786433  }

------------------------------------------------------------------
--DSPreset ( Alarm )
------------------------------------------------------------------
	uxAlmDSPreset NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"This alarm will be generated if a DSP encounters a fatal error condition and has to be reinitialized."
 	::= { uxTraps 786434  }

------------------------------------------------------------------
--DSPCardisUP ( Alarm )
------------------------------------------------------------------
	uxAlmDSPCardisUP NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"This event will clear the 'DSP not coming up' and 'DSP reset' alarms."
 	::= { uxTraps 786435  }

------------------------------------------------------------------
--DSPChannelFailure ( Alarm )
------------------------------------------------------------------
	uxAlmDSPChannelFailure NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"This event will be generated if a DSP channel encounters a fatal error condition and has to be closed."
 	::= { uxTraps 786436  }

------------------------------------------------------------------
--TLSOwnServerCertificatewillExpire ( Alarm )
------------------------------------------------------------------
	uxAlmTLSOwnServerCertificatewillExpire NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The Server certificate will expire in a window time. Suggested Action: Generate, Export CSR and Import a new signed certificate."
 	::= { uxTraps 851969  }

------------------------------------------------------------------
--TLSOwnServerCertificatehasExpired ( Alarm )
------------------------------------------------------------------
	uxAlmTLSOwnServerCertificatehasExpired NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The Server certificate has expired. Suggested Action. Generate, Export CSR and Import a new signed certificate."
 	::= { uxTraps 851970  }

------------------------------------------------------------------
--TLSOwnServerCertificateismissing ( Alarm )
------------------------------------------------------------------
	uxAlmTLSOwnServerCertificateismissing NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"This Server certificate is found to be missing or has failed validations. Suggested Action. Generate, Export CSR and Import a new signed certificate."
 	::= { uxTraps 851971  }

------------------------------------------------------------------
--TLSSelfSignCertificateGenerationFailed ( Alarm )
------------------------------------------------------------------
	uxAlmTLSSelfSignCertificateGenerationFailed NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Failed to create a default self signed certificate on the system."
 	::= { uxTraps 851972  }

------------------------------------------------------------------
--NewandValidTLSOwnServerCertificateDetected ( Alarm )
------------------------------------------------------------------
	uxAlmNewandValidTLSOwnServerCertificateDetected NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"The Server certificate was uploaded, validated, and good to use in successfully establishing a TLS connection."
 	::= { uxTraps 851973  }

------------------------------------------------------------------
--InvalidSessionofaTLSconnection ( Alarm )
------------------------------------------------------------------
	uxAlmInvalidSessionofaTLSconnection NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"If a web-client tries to open TLS connection with invalid session-id, BMP will generate this event."
 	::= { uxTraps 917505  }

------------------------------------------------------------------
--BMPTLSHandshakeAlertFailure ( Alarm )
------------------------------------------------------------------
	uxAlmBMPTLSHandshakeAlertFailure NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"This alarm will be generated if TLS Connection failed with an Alert. The connection associated with a TLS Connection ID is aborted."
 	::= { uxTraps 917506  }

------------------------------------------------------------------
--BMPTLSHandshakeInactivityTimeoutFailure ( Alarm )
------------------------------------------------------------------
	uxAlmBMPTLSHandshakeInactivityTimeoutFailure NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"This alarm will be generated if there was long period of inactivity during exchange of handshake messages for an associated TLS Connection ID."
 	::= { uxTraps 917507  }

------------------------------------------------------------------
--Interfaceoperdown ( Alarm )
------------------------------------------------------------------
	uxAlmInterfaceoperdown NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Occurs when an Ethernet port (of ports 1, 2, 3 and 4) is operationally down (e.g. cable unplugged, mismatched speed/duplexity settings) and if administrative state is enabled. Is generated only on Sonus SBC 2000 platform."
 	::= { uxTraps 983041  }

------------------------------------------------------------------
--Interfaceoperup ( Alarm )
------------------------------------------------------------------
	uxAlmInterfaceoperup NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Is generated when an Ethernet port (of ports 1, 2, 3 and 4) becomes operationally up. This event automatically clears the 'Interface oper down' alarm."
 	::= { uxTraps 983042  }

------------------------------------------------------------------
--Interfaceadminup ( Alarm )
------------------------------------------------------------------
	uxAlmInterfaceadminup NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Is generated when the administrative state of the Port or Logical Interface is configured to be enabled. Is applicable to Sonus SBC 2000 platform only."
 	::= { uxTraps 983043  }

------------------------------------------------------------------
--Interfaceadmindown ( Alarm )
------------------------------------------------------------------
	uxAlmInterfaceadmindown NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Is generated when the administrative state of the Port or Logical Interface is configured to be disabled. Is applicable to Sonus SBC 2000 platform only. "
 	::= { uxTraps 983044  }

------------------------------------------------------------------
--AdminPortoperdown ( Alarm )
------------------------------------------------------------------
	uxAlmAdminPortoperdown NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Is generated when the Admin Port is operationally down (e.g. cable unplugged, mismatched duplex/speed settings). Is applicable to Sonus SBC 2000 platform only."
 	::= { uxTraps 983045  }

------------------------------------------------------------------
--AdminPortoperup ( Alarm )
------------------------------------------------------------------
	uxAlmAdminPortoperup NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Is generated with the port becomes operational after being in an *Admin port oper down* state. Is applicable to Sonus SBC 2000 platform only"
 	::= { uxTraps 983046  }

------------------------------------------------------------------
--Portoperdown ( Alarm )
------------------------------------------------------------------
	uxAlmPortoperdown NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"This event is generated when the port is operationally down.It is generated for Sonus SBC 1000 only."
 	::= { uxTraps 983047  }

------------------------------------------------------------------
--RIPlicensenotenabled ( Alarm )
------------------------------------------------------------------
	uxAlmRIPlicensenotenabled NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		" RIP feature license is not enabled."
 	::= { uxTraps 983048  }

------------------------------------------------------------------
--OSPFlicensenotenabled ( Alarm )
------------------------------------------------------------------
	uxAlmOSPFlicensenotenabled NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		" OSPF feature license is not enabled."
 	::= { uxTraps 983049  }

------------------------------------------------------------------
--LinkMonitorPeerDown ( Alarm )
------------------------------------------------------------------
	uxAlmLinkMonitorPeerDown NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Connection to the monitored host or gateway is down."
 	::= { uxTraps 983050  }

------------------------------------------------------------------
--LinkMonitorPeerReady ( Alarm )
------------------------------------------------------------------
	uxAlmLinkMonitorPeerReady NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Connection to the monitored host or gateway is established."
 	::= { uxTraps 983051  }

------------------------------------------------------------------
--Tunnelconnectiondisabledbyoperator ( Alarm )
------------------------------------------------------------------
	uxAlmTunnelconnectiondisabledbyoperator NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Tunnel connection is placed Out of Service by operator."
 	::= { uxTraps 983052  }

------------------------------------------------------------------
--Tunnelconnectionenabledbyoperator ( Alarm )
------------------------------------------------------------------
	uxAlmTunnelconnectionenabledbyoperator NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Tunnel connection is placed back in Service by operator."
 	::= { uxTraps 983053  }

------------------------------------------------------------------
--Tunnellinklost ( Alarm )
------------------------------------------------------------------
	uxAlmTunnellinklost NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Tunnel lost communication with the peer. This alarm will be cleared by event 'Tunnel link restored'."
 	::= { uxTraps 983054  }

------------------------------------------------------------------
--Tunnellinkrestored ( Alarm )
------------------------------------------------------------------
	uxAlmTunnellinkrestored NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Tunnel is successfully established with the peer"
 	::= { uxTraps 983055  }

------------------------------------------------------------------
--IPseclicensenotenabled ( Alarm )
------------------------------------------------------------------
	uxAlmIPseclicensenotenabled NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"IPsec feature license is not enabled."
 	::= { uxTraps 983056  }

------------------------------------------------------------------
--NegotiatedDuplexityHalf ( Alarm )
------------------------------------------------------------------
	uxAlmNegotiatedDuplexityHalf NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Port negotiated duplexity is half. This degrades the performance."
 	::= { uxTraps 983057  }

------------------------------------------------------------------
--NegotiatedDuplexityFull ( Alarm )
------------------------------------------------------------------
	uxAlmNegotiatedDuplexityFull NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Port negotiated duplexity is back to full."
 	::= { uxTraps 983058  }

------------------------------------------------------------------
--Preferredlinkdown ( Alarm )
------------------------------------------------------------------
	uxAlmPreferredlinkdown NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"This event is generated when the preferred link is down."
 	::= { uxTraps 983059  }

------------------------------------------------------------------
--Preferredlinkready ( Alarm )
------------------------------------------------------------------
	uxAlmPreferredlinkready NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"This event is generated when the the preferred link is ready for service. This event automatically clears the 'preferred Link down' alarm."
 	::= { uxTraps 983060  }

------------------------------------------------------------------
--Tunnelnotificationfailure ( Alarm )
------------------------------------------------------------------
	uxAlmTunnelnotificationfailure NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Tunnel negotiation failed. Suggested Action: Look up the 'Failure Reason' attribute details for the Source in the IPsec Tunnel Table."
 	::= { uxTraps 983061  }

------------------------------------------------------------------
--Tunnellocalsubnetsarenonnegotiable ( Alarm )
------------------------------------------------------------------
	uxAlmTunnellocalsubnetsarenonnegotiable NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"This event is generated when one or more local subnet failed negotiation as result of peer config mismatch."
 	::= { uxTraps 983062  }

------------------------------------------------------------------
--Tunnelremotesubnetsarenonnegotiable ( Alarm )
------------------------------------------------------------------
	uxAlmTunnelremotesubnetsarenonnegotiable NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"This event is generated when one or more remote subnet failed negotiation as result of peer config mismatch."
 	::= { uxTraps 983063  }

------------------------------------------------------------------
--ApplicationServicerestarted ( Alarm )
------------------------------------------------------------------
	uxAlmApplicationServicerestarted NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"A Sonus SBC Application service was restarted."
 	::= { uxTraps 1048577  }

------------------------------------------------------------------
--Activepartitionswitched ( Alarm )
------------------------------------------------------------------
	uxAlmActivepartitionswitched NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"System detected a problem during previous boot cycle, active partition has switched automatically. Suggested action - backup the configuration and re-apply the upgrade to the currently inactive partition."
 	::= { uxTraps 1048578  }

------------------------------------------------------------------
--Failedtomountpartition ( Alarm )
------------------------------------------------------------------
	uxAlmFailedtomountpartition NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"While booting, one of the partition could not be mounted. Likely a eUSB corruption. Contact Sonus TAC with the information in this alarm."
 	::= { uxTraps 1048579  }

------------------------------------------------------------------
--Failedtosetactivepartition ( Alarm )
------------------------------------------------------------------
	uxAlmFailedtosetactivepartition NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Failed to set active partition.Contact Sonus TAC with the information in this alarm."
 	::= { uxTraps 1048580  }

------------------------------------------------------------------
--Attempttorepairbootparametermismatchfailed ( Alarm )
------------------------------------------------------------------
	uxAlmAttempttorepairbootparametermismatchfailed NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Attempt to auto repair boot parmeters failed.Contact Sonus TAC with the information in this alarm."
 	::= { uxTraps 1048581  }

------------------------------------------------------------------
--Bootparametermismatchdetected ( Alarm )
------------------------------------------------------------------
	uxAlmBootparametermismatchdetected NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Boot parameter mismatch was detected.Attempting to auto repair."
 	::= { uxTraps 1048582  }

------------------------------------------------------------------
--FailedPoweronmemoryselftest ( Alarm )
------------------------------------------------------------------
	uxAlmFailedPoweronmemoryselftest NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Power-on self test failure."
 	::= { uxTraps 1048583  }

------------------------------------------------------------------
--FailedPoweronCoreSwitchtest ( Alarm )
------------------------------------------------------------------
	uxAlmFailedPoweronCoreSwitchtest NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Power-on self test failure."
 	::= { uxTraps 1048584  }

------------------------------------------------------------------
--FailedPoweronSecondarySwitchtest ( Alarm )
------------------------------------------------------------------
	uxAlmFailedPoweronSecondarySwitchtest NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Power-on self test failure."
 	::= { uxTraps 1048585  }

------------------------------------------------------------------
--FailedPoweronexternalQuadPHYtest ( Alarm )
------------------------------------------------------------------
	uxAlmFailedPoweronexternalQuadPHYtest NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Power-on self test failure."
 	::= { uxTraps 1048586  }

------------------------------------------------------------------
--FailedPoweronexternalSinglePHYtest ( Alarm )
------------------------------------------------------------------
	uxAlmFailedPoweronexternalSinglePHYtest NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Power-on self test failure."
 	::= { uxTraps 1048587  }

------------------------------------------------------------------
--FailedPoweronCPUPHYtest ( Alarm )
------------------------------------------------------------------
	uxAlmFailedPoweronCPUPHYtest NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Power-on self test failure."
 	::= { uxTraps 1048588  }

------------------------------------------------------------------
--FailedPoweronTSItest ( Alarm )
------------------------------------------------------------------
	uxAlmFailedPoweronTSItest NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Power-on self test failure."
 	::= { uxTraps 1048589  }

------------------------------------------------------------------
--FailedPoweroninternal5PortPHYtest ( Alarm )
------------------------------------------------------------------
	uxAlmFailedPoweroninternal5PortPHYtest NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Power-on self test failure."
 	::= { uxTraps 1048590  }

------------------------------------------------------------------
--SystemUpAfterPlannedRestart ( Alarm )
------------------------------------------------------------------
	uxAlmSystemUpAfterPlannedRestart NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"System up after planned restart."
 	::= { uxTraps 1048591  }

------------------------------------------------------------------
--SystemUpAfterUnplannedRestart ( Alarm )
------------------------------------------------------------------
	uxAlmSystemUpAfterUnplannedRestart NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"System up after unplanned restart."
 	::= { uxTraps 1048592  }

------------------------------------------------------------------
--Noresponse ( Alarm )
------------------------------------------------------------------
	uxAlmNoresponse NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"No response to seizure."
 	::= { uxTraps 1114113  }

------------------------------------------------------------------
--Remoteenddidnotbackoffinglare ( Alarm )
------------------------------------------------------------------
	uxAlmRemoteenddidnotbackoffinglare NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Remote end did not back off in glare."
 	::= { uxTraps 1114114  }

------------------------------------------------------------------
--Winkexpecteddidnotarrive ( Alarm )
------------------------------------------------------------------
	uxAlmWinkexpecteddidnotarrive NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Wink expected, did not arrive."
 	::= { uxTraps 1114115  }

------------------------------------------------------------------
--Nodialtone ( Alarm )
------------------------------------------------------------------
	uxAlmNodialtone NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Event of off-hook did not produce dial tone as expected."
 	::= { uxTraps 1114116  }

------------------------------------------------------------------
--CASsignalinggroupdisabled ( Alarm )
------------------------------------------------------------------
	uxAlmCASsignalinggroupdisabled NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"CAS signaling group disabled."
 	::= { uxTraps 1114117  }

------------------------------------------------------------------
--CASlicensenotenabled ( Alarm )
------------------------------------------------------------------
	uxAlmCASlicensenotenabled NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Call attempted but CAS feature is not enabled. This alarm is cleared by CAS license enabled event."
 	::= { uxTraps 1114118  }

------------------------------------------------------------------
--CASlicenseenabled ( Alarm )
------------------------------------------------------------------
	uxAlmCASlicenseenabled NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"License manager notify CAS that license is enabled."
 	::= { uxTraps 1114119  }

------------------------------------------------------------------
--WinkReceived ( Alarm )
------------------------------------------------------------------
	uxAlmWinkReceived NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Wink failure had occurred, but wink is received now."
 	::= { uxTraps 1114120  }

------------------------------------------------------------------
--DialToneReceived ( Alarm )
------------------------------------------------------------------
	uxAlmDialToneReceived NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"No Dial Tone was received, but Dial Tone is received now."
 	::= { uxTraps 1114121  }

------------------------------------------------------------------
--ResponseReceived ( Alarm )
------------------------------------------------------------------
	uxAlmResponseReceived NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"No Response to seizure was received, but Response is received now."
 	::= { uxTraps 1114122  }

------------------------------------------------------------------
--Invalidcharactersincallingnumber ( Alarm )
------------------------------------------------------------------
	uxAlmInvalidcharactersincallingnumber NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Invalid character(s) removed, correct issue and delete warning."
 	::= { uxTraps 1114123  }

------------------------------------------------------------------
--Invalidcharactersincallednumber ( Alarm )
------------------------------------------------------------------
	uxAlmInvalidcharactersincallednumber NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Invalid character(s) removed, correct issue and delete warning."
 	::= { uxTraps 1114124  }

------------------------------------------------------------------
--CASsignalinggroupenabled ( Alarm )
------------------------------------------------------------------
	uxAlmCASsignalinggroupenabled NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"CAS signaling group enabled."
 	::= { uxTraps 1114125  }

------------------------------------------------------------------
--CASR2CDBiterror ( Alarm )
------------------------------------------------------------------
	uxAlmCASR2CDBiterror NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"CAS-R2 CD Bits are mismatched."
 	::= { uxTraps 1114126  }

------------------------------------------------------------------
--CASR2CDBiterrorclear ( Alarm )
------------------------------------------------------------------
	uxAlmCASR2CDBiterrorclear NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"CAS-R2 CD Bits are now matching."
 	::= { uxTraps 1114127  }

------------------------------------------------------------------
--NetworkGlareoccured ( Alarm )
------------------------------------------------------------------
	uxAlmNetworkGlareoccured NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Network glare occured on this interface."
 	::= { uxTraps 1114128  }

------------------------------------------------------------------
--Configvalidationfailure ( Alarm )
------------------------------------------------------------------
	uxAlmConfigvalidationfailure NOTIFICATION-TYPE
	OBJECTS { 
		uxAlarmActiveIndex,
		uxAlarmConfigIndex,
		uxAlarmActiveID,
		uxAlarmActiveSubID,
		uxAlarmActiveCondition,
		uxAlarmActiveSeverity,
		uxAlarmActiveCategory,
		uxAlarmActiveCancelType,
		uxAlarmActiveDecodeKey,
		uxAlarmActiveCount,
		uxAlarmActiveState,
		uxAlarmActiveSourceInstance,
		uxAlarmActiveFirstOccur,
		uxAlarmActiveLastOccur,
		uxAlarmActiveClrEvtID,
		uxAlarmActiveClrEvtSubID,
		uxAlarmActiveDescription,
		uxAlarmActiveHighestSeverityAlarm,
		uxAlarmActiveHardWareID
	}
	STATUS  current
	DESCRIPTION
		"Config validation failure during startup. Please check the configuration."
 	::= { uxTraps 1179649  }

 END

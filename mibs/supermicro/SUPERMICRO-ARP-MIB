-- Copyright (C) 2008-2014 Super Micro Computer Inc. All Rights Reserved

-- ARP Proprietary MIB Definition
-- /*****************************************************************
--  *                                                               *
--  * $RCSfile: fsarp.mib,v $                                          *  
--  *                                                               *
--  * $Date: 2012/09/07 09:52:04 $                                                      *
--  *                                                               *
--  * $Revision: 1.8 $                                                  *
--  *                                                               *
--  ****************************************************************/

-- ARP MIB.

-- The MIB contains scalars used to configure ARP functionaly.

 SUPERMICRO-ARP-MIB DEFINITIONS ::= BEGIN
      
 IMPORTS 
    OBJECT-TYPE, MODULE-IDENTITY, IpAddress, 
    Counter32, Integer32,
    enterprises            FROM SNMPv2-SMI
    DisplayString,
    TruthValue, RowStatus  FROM SNMPv2-TC; 

-- futuresoftware OBJECT IDENTIFIER ::= { enterprises 2076 }

   fsarp MODULE-IDENTITY
   LAST-UPDATED "201209040000Z"
   ORGANIZATION "Super Micro Computer Inc."
   CONTACT-INFO "support@Supermicro.com"
    DESCRIPTION " This mib module is for ARP module"
    REVISION "201209040000Z"
    DESCRIPTION " This mib module is for ARP module"
::= { enterprises supermicro-computer-inc(10876) super-switch(101) basic(1) 109} 

-- The different groups in  ARP MIB are as follows:
   arp OBJECT IDENTIFIER ::= { fsarp 1 }
   arptest OBJECT IDENTIFIER ::= { fsarp 2 }

-- ARP Group
-- This group defines objects for ARP.
   fsArpCacheTimeout  OBJECT-TYPE
        SYNTAX   Integer32 (30..86400)
        MAX-ACCESS   read-write
        STATUS   current
        DESCRIPTION " Time after which the entry in cache is deleted "
        DEFVAL { 300 }
        ::= { arp 1 }

   fsArpCachePendTime  OBJECT-TYPE
        SYNTAX   Integer32	(30..3000)
        MAX-ACCESS   read-write
        STATUS   current
        DESCRIPTION " Time for which an unresolved entry will be
   		    held until response is received "
        DEFVAL { 30 }
        ::= { arp 2 }

   fsArpMaxRetries  OBJECT-TYPE
        SYNTAX   Integer32 (2..10)
        MAX-ACCESS   read-write
        STATUS   current
        DESCRIPTION " Maximum number of retry attempts before aborting
  		    resolving "
        DEFVAL { 3 }
        ::= { arp 3 }

-- ARPTEST Group
-- This group defines objects for ARPTEST.

   fsArpPendingEntryCount  OBJECT-TYPE
        SYNTAX   Integer32 
        MAX-ACCESS   read-only
        STATUS   current
        DESCRIPTION " Number of pending or ageout entries in the ARP Cache
  		    database "
        ::= { arptest 1 }


   fsArpCacheEntryCount  OBJECT-TYPE
        SYNTAX   Integer32 
        MAX-ACCESS   read-only
        STATUS   current
        DESCRIPTION " Number of ARP Cache entries in the ARP Cache
  		    database "
        ::= { arptest 2 }

   fsArpRedEntryTime  OBJECT-TYPE
        SYNTAX   Integer32
        MAX-ACCESS   read-only
        STATUS   current
        DESCRIPTION " Time when the node starts entering active state 
            from standby state "
        ::= { arptest 3 }

    fsArpRedExitTime  OBJECT-TYPE
        SYNTAX   Integer32
        MAX-ACCESS   read-only
        STATUS   current
        DESCRIPTION " Time when the node completes entering active state
            from standby state "
        ::= { arptest 4 }

   END

-- Copyright (C) 2008-2014 Super Micro Computer Inc. All Rights Reserved

-- /*****************************************************************
--  *                                                                *
--  * $Id: fsbgp4.mib,v 1.38 2013/09/02 14:02:34 siva Exp $          *
--  * fsbgp4.mib                                                     *
--  *                                                                *
--  * BGP4 Proprietary MIB.                                  *
--  *                                                                *
--  ****************************************************************/

-- MIB FOR BGP

SUPERMICRO-BGP-MIB DEFINITIONS ::= BEGIN 

IMPORTS 
MODULE-IDENTITY, OBJECT-TYPE,NOTIFICATION-TYPE, 
IpAddress, Unsigned32, Integer32, enterprises, Gauge32, Counter32 FROM SNMPv2-SMI
TEXTUAL-CONVENTION, DisplayString, RowStatus, TruthValue, 
                                                     DateAndTime  FROM SNMPv2-TC;
--InetAddressType                               FROM INET-ADDRESS-MIB;

-- futuresoftware  OBJECT IDENTIFIER ::= {enterprises 2076}

fsbgp MODULE-IDENTITY
    LAST-UPDATED "201209050000Z" 
    ORGANIZATION "Super Micro Computer Inc." 
    CONTACT-INFO "support@Supermicro.com"
    DESCRIPTION
    "The Proprietary BGP MIB"
    REVISION "201209050000Z"
    DESCRIPTION 
    "The Proprietary BGP MIB" 
    ::= { enterprises supermicro-computer-inc(10876) super-switch(101) basic(1) 41 }

   InetAddress ::= TEXTUAL-CONVENTION
    STATUS current
    DESCRIPTION
    "Denotes a generic Internet address.
    An InetAddress value is always interpreted within the context
    of an InetAddressType value. Every usage of the InetAddress
    textual convention is required to specify the InetAddressType
    object which provides the context.  It is suggested that the
    InetAddressType object is logically registered before the
    object(s) which use the InetAddress textual convention if
    they appear in the same logical row.

    The value of an InetAddress object must always be
    consistent with the value of the associated InetAddressType
    object. Attempts to set an InetAddress object to a value
    which is inconsistent with the associated InetAddressType
    must fail with an inconsistentValue error."
    SYNTAX  OCTET STRING (SIZE(0 .. 40))

   InetAddressType ::= TEXTUAL-CONVENTION
    STATUS current
    DESCRIPTION
    "A value that represents a type of Internet Address.
    unknown (0) An unknown address type. This value MUST be used if the
    value of the corresponding InetAddress object is a zero
    length string. It may also used to indicate an IP address
    which is not in one of the formats defined below.
    ipv4 (1)    An IPv4 address"
  SYNTAX  INTEGER {
                unknown (0),
                ipv4 (1),
                ipv6 (2)
    }

    BgpSafi ::= TEXTUAL-CONVENTION
--        DISPLAY-HINT "d"
        STATUS current
        DESCRIPTION
        "The representation of a BGP Safi"
        SYNTAX INTEGER {
                unknown     (0),
                unicast     (1),
                labelledIpv4 (4),
                vpnv4   (128)
        }

fsbgp4Scalars   OBJECT IDENTIFIER ::= {fsbgp 1} 

fsbgp4GlobalAdminStatus OBJECT-TYPE
    SYNTAX       INTEGER {
                            up  (1),
                            down(2)
                         }
    MAX-ACCESS   read-write
    STATUS       current 
    DESCRIPTION 
    "The desired state of the BGP system. The BGP4 speaker is
     functionally active only when the global admin status is up. The global
     admin status can be made up only if the fsbgp4LocalAs is configured."
    DEFVAL      { down }
    ::= { fsbgp4Scalars  1 }

fsbgp4LocalAs     OBJECT-TYPE
    SYNTAX      Unsigned32 (0..4294967295)
    MAX-ACCESS  read-write
    STATUS      current 
    DESCRIPTION 
    "The local autonomous system number.This object can be set only if
     fsbgp4GlobalAdminStatus is down."
    DEFVAL      { 0 }
    ::= { fsbgp4Scalars 2 }

fsbgp4Identifier OBJECT-TYPE
    SYNTAX      IpAddress
    MAX-ACCESS  read-write
    STATUS      current 
    DESCRIPTION
    "This object configures the BGP Identifier of local system. If global
     admin status is made up, by default the BGP Identifier will take
     the value of highest interface address. If the BGP Speaker is
     administratively active, then the BGP Identifier can be configured
     explicitly. If configured explicitly,then this configured value will be
     preserved even across BGP restarts. Inorder to restore the default value
     for BGP Identifier configure this object as 0.0.0.0. Peering sessions
     will be reset if the BGP Identifer is changed. This object can be set
     only if fsbgp4LocalAs has been configured."
    ::= { fsbgp4Scalars 3 }

fsbgp4Synchronization   OBJECT-TYPE
    SYNTAX     INTEGER {
                       enable  (1),
                       disable (2)
                   }
    MAX-ACCESS          read-write
    STATUS              current
    DESCRIPTION
    "Attribute to enable/disable synchronization within an AS.
     This object can be set only if fsbgp4LocalAs has been configured."
    DEFVAL     { disable }
    ::= { fsbgp4Scalars 4 }

fsbgp4DefaultLocalPref  OBJECT-TYPE
    SYNTAX              Unsigned32 ( 0 .. 2147483647 )
    MAX-ACCESS          read-write
    STATUS              current
    DESCRIPTION
    "The default value of local-pref that is to be sent in updates to internal
     peers.This object can be set only if fsbgp4LocalAs has been configured."
    DEFVAL     { 100 }
    ::=   { fsbgp4Scalars 5 }

fsbgp4AdvtNonBgpRt  OBJECT-TYPE
    SYNTAX          INTEGER
                    {
                        external(1),
                        externalAndinternal(2)
                    }
    MAX-ACCESS      read-write
    STATUS          current
    DESCRIPTION
    "This mib object can be used to configure the peer type to whom
     non-bgp routes can be propagated.
        external            - indicates non-bgp routes can be exported to only
                              external peers.All types of non-bgp routes
                              can be propagated to external peers.
        externalAndInternal - non-bgp routes can be propagated to both external
                              and internal peers.
     This object can be set only if fsbgp4LocalAs has been configured."
    DEFVAL     { externalAndinternal }
    ::= { fsbgp4Scalars 6 }

fsbgp4TraceEnable   OBJECT-TYPE
    SYNTAX          Unsigned32 (0..4294967295)
    MAX-ACCESS      read-write
    STATUS          current
    DESCRIPTION
    "This object can be used to enable trace dynamically in BGP
     module. A four byte integer value is specified for enabling
     the level of tracing.Each Bit in the four byte integer variable
     represents a level of Trace.
     The bits represents the levels as follows:
        0 - All Failures,
        1 - All Resource Allocation failure,
        2 - Init & Shutdown Trace,
        3 - Management Trace,
        4 - Control Path Trace,
        5 - Data Path Trace,
        6 - Peer Connection Trace,
        7 - Update Message Trace,
        8 - FDB Update Trace,
        9 - Keep-Alive Trace,
       10 - All Transmission Trace,
       11 - All Reception Trace,
       12 - Dampening Trace,
       13 - Events Trace,
       14 - High level Packet Dump
       15 - Low level packet Dump
       16 - Hex Dump
     The remaining  bits are unused.
     The combination of levels are also allowed. For example if the bits 1
     and  2 are set, then the Trace statements related to management and Data
     Path will be printed.
     The user have to enter the corresponding integer value for the bits set.
     For example if bits 1 and 2 are set then value of 6 should be entered.
     This object can be set only if fsbgp4LocalAs has been configured."
    ::= { fsbgp4Scalars 7 }

fsbgp4DebugEnable   OBJECT-TYPE
    SYNTAX          Unsigned32 (0..4294967295)
    MAX-ACCESS      read-write
    STATUS          current
    DESCRIPTION
    "This object can be used to enable debug dynamically in BGP module.
     Its a four byte integer value specified for enabling the level
     of debugging. Each Bit in the four byte integer variable
     represents a level of debug. The combination of levels are also
     allowed. This object can be set only if fsbgp4LocalAs is configured."
    ::= { fsbgp4Scalars 8 }

fsbgp4OverlappingRoute    OBJECT-TYPE
    SYNTAX                INTEGER
                          {
                              moreSpecific(1),
                              lessSpecific(2),
                              both(3)
                          }
    MAX-ACCESS            read-write
    STATUS                current
    DESCRIPTION
    "This object is used to configure the BGP speaker's policy for handling
     the overlapping routes. When an overlapping route is received, depending
     upon the configured policy either the less-specific routes or
     more-specific routes or both routes are installed in the RIB tree. This
     object can be set only if fsbgp4LocalAs has been configured and
     fsbgp4GlobalAdminStatus is down."
    DEFVAL { both }
    ::= { fsbgp4Scalars 9 }

fsbgp4MaxPeerEntry    OBJECT-TYPE
    SYNTAX            Integer32 (0..50)
                      -- MaxPeerEntry (Range should be modified
                      -- according to the DEFVAL)
    MAX-ACCESS        read-write
    STATUS            current
    DESCRIPTION 
    "The Maximum number of peers supported by BGP. This object can be set only
     if fsbgp4LocalAs has been configured.
     This object can not be set to a higher value than the initial value of the 
     object.However initial value can be changed in inc/system.size file"
    DEFVAL     { 50 }
    ::= { fsbgp4Scalars 10 }

fsbgp4MaxNoofRoutes         OBJECT-TYPE
    SYNTAX                  Integer32 (0..5000)
                            -- MaxNoofRoutes (Range should be modified
                            -- according to the DEFVAL )
    MAX-ACCESS              read-write
    STATUS                  current
    DESCRIPTION
    "It represents the maximum number of routes in the routing table. This
     object can be set only if fsbgp4LocalAs has been configured.
     This object can not be set to a higher value than the initial value of the 
     object.However initial value can be changed in inc/system.size file"
    DEFVAL     { 5000 }
    ::= { fsbgp4Scalars 11 }

fsbgp4AlwaysCompareMED      OBJECT-TYPE
    SYNTAX                  INTEGER
                            {
                                enable(1),
                                disable(2)
                            }
    MAX-ACCESS              read-write
    STATUS                  current
    DESCRIPTION
    "If this object is set to disable, then in best route decision process,
     MED will be compared only between routes received from the same
     autonomous system. If set to enable, irrespective of the autonomous
     system from which the routes are received, MED comparision will be done.
     This object can be set only if the fsbgp4LocalAs is set."
    DEFVAL  { disable }
    ::= { fsbgp4Scalars 12 }

fsbgp4DefaultOriginate      OBJECT-TYPE
    SYNTAX                  INTEGER
                            {
                                enable(1),
                                disable(2)
                            }
    MAX-ACCESS              read-write
    STATUS                  current
    DESCRIPTION
    "If this object is set to enable/disable the redistribution and
     advertisement of the default route (0.0.0.0/0). By default, the
     default routes are not redistributed into BGP. Only if this object
     is set as enable, the default route gets redistributed and advertised
     to BGP Peers. If the default route is neither present in IP FDB nor
     received from any Peer, enabling this object will not result in
     advertisement of default route. This object can be set only if the
     fsbgp4LocalAs is set."
    DEFVAL  { disable }
    ::= { fsbgp4Scalars 13 }

fsbgp4DefaultIpv4UniCast    OBJECT-TYPE
    SYNTAX                  INTEGER
                            {
                                enable(1),
                                disable(2)
                            }
    MAX-ACCESS              read-write
    STATUS                  current
    DESCRIPTION
    "If this object is set to enable, and if a neighbor is created, then
     the MP IPv4 Unicast Address Family Capability will be negotiate for
     that peer. If this object is set as disable and if a neighbor is
     created, then IPv4 unicast capability will not be negotiated for that
     neighbor, unless IPv4 unicast capability is explicitly configured for
     that neighbor. Changing the status of this object will not cause
     any change in the MP IPV4 Unicast negotiation status of the already
     existing peer. This object can be set only if fsbgp4LocalAs is
     configured."
    DEFVAL  { enable }
    ::= { fsbgp4Scalars 14 }

fsbgp4GRAdminStatus  OBJECT-TYPE 
    SYNTAX      INTEGER {
                       enable  (1),
                       disable (2)
                   }

    MAX-ACCESS  read-write
    STATUS      current 
    DESCRIPTION 
    "This object is used to enable or disable GR capability in BGP speaker."
    DEFVAL      { enable }
    ::= {  fsbgp4Scalars 15 } 

fsbgp4GRRestartTimeInterval    OBJECT-TYPE 
    SYNTAX  Integer32 (1..4096)
    MAX-ACCESS  read-write
    STATUS      current 
    DESCRIPTION 
    "This is the estimated time (in seconds) it will take for the BGP 
     session to be re-established after a restart. Suggested default value 
     should be less than or equal to Hold Time carried in open message.
     The GR restart time when re-configured will be used only in the new
     BGP sessions getting established and will not effect the already
     established BGP sessions."
    DEFVAL     { 90 }
    ::= {  fsbgp4Scalars 16 } 

fsbgp4GRSelectionDeferralTimeInterval    OBJECT-TYPE 
    SYNTAX  Integer32 (60..1800)
    MAX-ACCESS  read-write
    STATUS      current 
    DESCRIPTION 
    "This interval is the upper bound on the amount of time a router 
     defers its route selection. The value of this timer should be large 
     enough, so as to provide all the peers of the Restarting Speaker with 
     enough time to send all the routes to the Restarting Speaker."
    DEFVAL     { 60 }
    ::= {  fsbgp4Scalars 17 } 

fsbgp4GRStaleTimeInterval    OBJECT-TYPE 
    SYNTAX  Integer32 (90..3600)
    MAX-ACCESS  read-write
    STATUS      current 
    DESCRIPTION 
    "This interval is the upper bound on the amount of time a router retains 
     the stale routes.

     The GR stale time interval configured can be used only for the new peers 
     sessions established and not for the already established peer sessions"
    DEFVAL     { 150 }
    ::= {  fsbgp4Scalars 18 } 

fsbgp4GRMode    OBJECT-TYPE 
    SYNTAX      INTEGER {
                  restarting (1),
                  receiving (2),
		          none(3)	
                }

    MAX-ACCESS  read-only
    STATUS      current 
    DESCRIPTION 
    "This object indicates whether the BGP speaker is restarting speaker 
     or receiving speaker."
    ::= {  fsbgp4Scalars 19 } 

fsbgp4RestartSupport    OBJECT-TYPE 
    SYNTAX      INTEGER {
                       none (1),
                       plannedOnly (2),
                       plannedAndUnplanned (3)
                }
    MAX-ACCESS  read-write
    STATUS      current 
    DESCRIPTION 
    "The router's support for BGP graceful restart Options include:
     no restart support, only planned restarts, or both planned and unplanned 
     restarts. This object is persistent and when written the entity SHOULD
     save the change to non-volatile storage. When BGP GR admin status is 
     enabled, the restart option can be one of the following: only planned 
     restarts, or both planned and unplanned restarts."
    DEFVAL { none }
    ::= {  fsbgp4Scalars 20 } 

fsbgp4RestartStatus    OBJECT-TYPE 
    SYNTAX      INTEGER {
                       none (1),
                       plannedRestart (2),
                       unplannedRestart (3)
                }
    MAX-ACCESS  read-only
    STATUS      current 
    DESCRIPTION 
    "Current status of BGP graceful restart, it indicates whether the speaker 
    restarted or not if it is restarted whether it is a planned restart or unplanned restart "
    ::= {  fsbgp4Scalars 21 } 

fsbgp4RestartExitReason    OBJECT-TYPE 
      SYNTAX      INTEGER {
                none (1),           -- none attempted
                inProgress (2),     -- restart in progress
                completed (3),      -- successfully completed
                failure (4)         -- restart failure.
              }
    MAX-ACCESS  read-only
    STATUS      current 
    DESCRIPTION 
    "Describes the outcome of the last attempt at a graceful restart. 
    If the value is 'none': no restart  has yet been attempted. 
    'inProgress': a restart attempt is currently underway.
    'Completed': a restart is completed successfully.
    'failure': failure due to the speaker is not completed the 
    restart process within the restart interval."
    ::= {  fsbgp4Scalars 22 } 

fsbgp4RestartReason    OBJECT-TYPE 
    SYNTAX      INTEGER {
                            unknown (0),
                            softwareRestart (1),
                            swReloadUpgrade (2)
                          }

    MAX-ACCESS  read-write
    STATUS      current 
    DESCRIPTION 
    "The router's restarter reason code of BGP graceful restart. 
    Options include: unknown,softwarerestart,swreloadupgrade, 
    switchtoredundant. This object is persistent and when written 
    the entity SHOULD save the change to non-volatile storage."
    DEFVAL {softwareRestart}
    ::= {  fsbgp4Scalars 23 } 

fsbgp4ForwardingPreservation    OBJECT-TYPE 
    SYNTAX      INTEGER {
                       preserved (1),
                       notPreserved (2)
                }
    MAX-ACCESS  read-only
    STATUS      current 
    DESCRIPTION 
    "This object indicates whether the forwarding plane is preserved during restart or not"
    ::= {  fsbgp4Scalars 24 } 

fsbgp4IsTrapEnabled         OBJECT-TYPE
    SYNTAX                  INTEGER
                            {
                                enable(1),
                                disable(2)
                            }
    MAX-ACCESS              read-write
    STATUS                  current
    DESCRIPTION
    "If this object is set to disable, then the NOTIFICATION messages wont be sent to 
    the SNMP Manager. If enabled, NOTIFICATION messages are sent."
    DEFVAL  { enable }
    ::= { fsbgp4Scalars 25 }

fsbgp4NextHopProcessingInterval         OBJECT-TYPE
    SYNTAX                  Integer32
    MAX-ACCESS              read-write
    STATUS                  current
    DESCRIPTION
    "This object is used to configure the interval at which next hops will be mointored for reachablity"
    DEFVAL  { 60 }
    ::= { fsbgp4Scalars 26 }

fsbgp4IBGPRedistributionStatus       OBJECT-TYPE
    SYNTAX                  INTEGER
                            {
                                enable (1),
                                disable (2)
                            }
    MAX-ACCESS              read-write
    STATUS                  current
    DESCRIPTION
    "If this object is set to enable, IBGP routes will also be redistributed to other 
    IGP protocols when redistribution is enabled for that protocol"

    DEFVAL  { disable }
    ::= { fsbgp4Scalars 27 }

fsbgp4IBGPMaxPaths     OBJECT-TYPE
    SYNTAX      Integer32 (1..64)
    MAX-ACCESS  read-write
    STATUS      current 
    DESCRIPTION 
    "Maximum number of internal BGP multipath routes to be added per destination network in Routing table.
    When this object takes the value 1, then only best route is added to Forwarding table.
    This configuration will have effect only after hard/soft reset."
    DEFVAL      { 1 }
    ::= { fsbgp4Scalars 28 }

fsbgp4EBGPMaxPaths    OBJECT-TYPE
    SYNTAX      Integer32 (1..64)
    MAX-ACCESS  read-write
    STATUS      current 
    DESCRIPTION 
    "Maximum number of external BGP multipath routes to be added per destination network in Routing table.
    When this object takes the value 1, then only best route is added to Forwarding table.
    This configuration will have effect only after hard/soft reset."
    DEFVAL      { 1 }
    ::= { fsbgp4Scalars 29 }

fsbgp4EIBGPMaxPaths   OBJECT-TYPE
    SYNTAX      Integer32 (1..64)
    MAX-ACCESS  read-write
    STATUS      current 
    DESCRIPTION 
    "Maximum number of external plus internal BGP multipath routes (with same AS PATH) to be 
    added per destination network in Routing table.
    When this object takes the value 1, then only best route is added to Forwarding table.
    This configuration will have effect only after hard/soft reset."
    DEFVAL      { 1 }
    ::= { fsbgp4Scalars 30 }

fsbgp4OperIBGPMaxPaths    OBJECT-TYPE
    SYNTAX      Integer32 (1..64)
    MAX-ACCESS  read-only
    STATUS      current 
    DESCRIPTION 
    "Operational value for Maximum number of internal BGP multipath routes to be added per destination network
    in Routing table. 
    When this object takes the value 1, then only best route is added to Forwarding table."
    DEFVAL      { 1 }
    ::= { fsbgp4Scalars 31 }

fsbgp4OperEBGPMaxPaths   OBJECT-TYPE
    SYNTAX      Integer32 (1..64)
    MAX-ACCESS  read-only
    STATUS      current 
    DESCRIPTION 
    "Operational value for Maximum number of external BGP multipath routes that to be added per 
    destination network in Routing table.
    When this object takes the value 1, then only best route is added to Forwarding table."
    DEFVAL      { 1 }
    ::= { fsbgp4Scalars 32 }

fsbgp4OperEIBGPMaxPaths  OBJECT-TYPE
    SYNTAX      Integer32 (1..64)
    MAX-ACCESS  read-only
    STATUS      current 
    DESCRIPTION 
    "Operational value for Maximum number of  external plus internal BGP multipath routes 
    (with same AS PATH) to be added  per destination network in Routing table. 
     When this object takes the value 1, then only best route is added to Forwarding table."
     DEFVAL      { 1 }
    ::= { fsbgp4Scalars 33 }

fsbgp4FourByteASNSupportStatus    OBJECT-TYPE
    SYNTAX      INTEGER {
                       enable (1),
                       disable (2)
                }
    MAX-ACCESS  read-write
    STATUS      current
    DESCRIPTION
    "This object is used to enable or disable 4 byte ASN support in BGP Speaker.
     This can be configured only if fsbgp4GlobalAdminStatus is down."
    DEFVAL      { enable }
    ::= {  fsbgp4Scalars 34 }

fsbgp4FourByteASNotationType    OBJECT-TYPE
    SYNTAX      INTEGER {
                       asplain (1),
                       asdot (2)
                }
    MAX-ACCESS  read-write
    STATUS      current
    DESCRIPTION
    "This object denotes the notation to be used to display the 4 byte ASN. This
     will change only the way the AS number is represented within router show
     commands in the Command Line Interface (CLI) framework. This object can be
     configured only if fsbgp4FourByteASNSupportStatus is enabled"
    DEFVAL      { asplain }
    ::= {  fsbgp4Scalars 35 }

-- MIB FOR FSBGP_PEER_EXTENSIONS_TABLE BEGIN

-- This table is an Extension to the bgpPeerTable from stdbgp4.mib.
-- This table contains, one entry per BGP peer, information
-- about the BGP peer.

fsbgp4PeerExtTable          OBJECT-TYPE
    SYNTAX                  SEQUENCE OF Fsbgp4PeerExtEntry
    MAX-ACCESS              not-accessible
    STATUS                  deprecated 
    DESCRIPTION
    "BGP Peer Extension Table. The entries in the table specifies
    the additional features supported for a peer by futureBGP4
    Speaker in addition to the features specified as in bgpPeerTable 
    (described in  stdbgp4.mib.). All entries in this table can be
    configured only if fsbgp4LocalAs has be configured. This table is deprecated 
    and corresponding functionality is met using the objects in fsbgp4MpePeerExtTable. If 
    configured,this value overrides the values used in fsbgp4MpePeerExtTable MIB object"
    ::= { fsbgp 2 }

fsbgp4PeerExtEntry          OBJECT-TYPE
    SYNTAX                  Fsbgp4PeerExtEntry
    MAX-ACCESS              not-accessible
    STATUS                  deprecated
    DESCRIPTION
    "Entry containing information about the additional features supported
     for a peer by futureBGP4 Speaker. This object is deprecated and
    corresponding functionality is met using the objects in fsbgp4MpePeerExtTable. 
    If configured,this value overrides the values used in fsbgp4MpePeerExtTable MIB object"
    INDEX { fsbgp4PeerExtPeerRemoteAddr }
    ::= { fsbgp4PeerExtTable 1 }

Fsbgp4PeerExtEntry ::=    SEQUENCE {
                                fsbgp4PeerExtPeerRemoteAddr
                                    IpAddress,
                                fsbgp4PeerExtConfigurePeer
                                    INTEGER,
                                fsbgp4PeerExtPeerRemoteAs
                                    Unsigned32,
                                fsbgp4PeerExtEBGPMultiHop
                                    INTEGER,
                                fsbgp4PeerExtNextHopSelf
                                    INTEGER,
                                fsbgp4PeerExtConnSrcIfId
                                    Integer32,
                                fsbgp4PeerExtRflClient
                                    INTEGER
                            }

fsbgp4PeerExtPeerRemoteAddr     OBJECT-TYPE
    SYNTAX                      IpAddress
    MAX-ACCESS                  not-accessible
    STATUS                      deprecated
    DESCRIPTION
    "The remote IP address of this entry's BGP peer."
    ::= { fsbgp4PeerExtEntry 1 }

fsbgp4PeerExtConfigurePeer     OBJECT-TYPE
    SYNTAX                     INTEGER
                               {
                                   create (1),
                                   delete (2)
                               }
    MAX-ACCESS                 read-write
    STATUS                     deprecated
    DESCRIPTION
    "This object is used to create or delete a peer. If called with create
     and no matching peer exists, then a new peer entry will be created. The
     admin status of this newly created peer will be stop. To enable the peer
     set the peers remote AS (fsbgp4PeerExtPeerRemoteAS)and change the peer's
     admin state (bgpPeerAdminState in stdbgp4.mib) to start. If this object
     is called with create and a matching peer exists, then no action is done.
     If called with delete and if a matching peer exists, then the complete
     instance associated with that peer will be deleted."
    ::= { fsbgp4PeerExtEntry 2 }

fsbgp4PeerExtPeerRemoteAs   OBJECT-TYPE
    SYNTAX                  Unsigned32 (1..4294967295)
    MAX-ACCESS              read-write
    STATUS                  deprecated
    DESCRIPTION
    "The remote autonomous system number of the Peer. The peer admin status
     can be made up only if this object is configured for a valid AS number.
     When OPEN message is received from this peer during the BGP Connection
     establishment, this configured AS value is compared against the AS number
     received in the OPEN message. If both matches, then connection
     establishment continues. If there is any mismatch, then the connection is
     terminated. This object can be set only when the peer's admin status is 
     down."
    ::= { fsbgp4PeerExtEntry 3 } 

fsbgp4PeerExtEBGPMultiHop   OBJECT-TYPE
    SYNTAX                  INTEGER
                            {
                               enable(1),
                               disable(2)
                            }
    MAX-ACCESS              read-write
    STATUS                  deprecated
    DESCRIPTION
    "This objects enables the BGP4 Speaker to accept or attempt
     connections to external peers residing on network that are not directly
     connected. By default, only directly connected EBGP peers are allowed.
     For the internal peers, this object has no effect."
    DEFVAL { disable }
    ::= { fsbgp4PeerExtEntry 4 }

fsbgp4PeerExtNextHopSelf    OBJECT-TYPE
    SYNTAX                  INTEGER 
                            {
                                automatic(1),
                                self(2) 
                            }
    MAX-ACCESS  read-write
    STATUS      deprecated
    DESCRIPTION
    "This object specifies how the next hop attribute sent in the update 
     messages to this peer has to be generated.  When the object takes the
     value of self,the next Hop attribute will always be the sender Local
     Address else the next hop will be generated based on the IP address of
     the destination and the present next hop in the route information."
    DEFVAL { automatic }
    ::= { fsbgp4PeerExtEntry 5 }

fsbgp4PeerExtConnSrcIfId    OBJECT-TYPE
    SYNTAX                  Integer32 (0..65535) 
    MAX-ACCESS              read-only
    STATUS                  deprecated
    DESCRIPTION
    "This object specifies which address should be used as the source address
    of the TCP session initiated with the Peer. By default this object takes
    value as 0 and the source address of the TCP session is filled by TCP.
    This object can take value of any interface identifier. If this object
    refers to a valid interface identifier, then the TCP session initiated
    with the peer should have the corresponding interface address as the
    source address."
    DEFVAL { 0 }
    ::= { fsbgp4PeerExtEntry 6 }

fsbgp4PeerExtRflClient      OBJECT-TYPE
    SYNTAX                  INTEGER
                            {
    	                        nonClient (1),
                                client (2)
                            } 
    MAX-ACCESS          read-write
    STATUS              deprecated
	DESCRIPTION  
    "This object specifies whether the peer is Client peer or Non-Client
    peer. By default, the peer is created as Non-Client Peer."
	DEFVAL				{1}
	::= {fsbgp4PeerExtEntry 7 }

-- MIB FOR FSBGP_PEER_EXTENSIONS_TABLE END

--- Multi-Exit Discriminator Table
--- This table specifies the value that has to be assigned to the
--- Multi-Exit Discriminator attribute when an update is sent.

fsbgp4MEDTable  OBJECT-TYPE
    SYNTAX      SEQUENCE OF Fsbgp4MEDEntry
    MAX-ACCESS  not-accessible
    STATUS      deprecated
    DESCRIPTION
    "BGP4 MED table. This table contains the MED values that are to
     be assigned to routes. This table is deprecated and the corresponding 
     functionality is met using objects in fsbgp4MpeMEDTable. If configured,
     this value overrides the value used in fsbgp4MpeMEDTable."
    ::= {fsbgp 3 }

fsbgp4MEDEntry  OBJECT-TYPE
    SYNTAX      Fsbgp4MEDEntry
    MAX-ACCESS  not-accessible
    STATUS      deprecated
    DESCRIPTION
      "Entry containing information about the MED value."
    INDEX  { fsbgp4MEDIndex }
    ::= { fsbgp4MEDTable 1 }

Fsbgp4MEDEntry ::= SEQUENCE {
    fsbgp4MEDIndex
        Integer32,
    fsbgp4MEDAdminStatus
        INTEGER,
    fsbgp4MEDRemoteAS
        Unsigned32,
    fsbgp4MEDIPAddrPrefix
        IpAddress,
    fsbgp4MEDIPAddrPrefixLen
        Integer32,
    fsbgp4MEDIntermediateAS
        DisplayString,
    fsbgp4MEDDirection
        INTEGER,
    fsbgp4MEDValue
        Unsigned32,
    fsbgp4MEDPreference
        INTEGER
    }

fsbgp4MEDIndex  OBJECT-TYPE
    SYNTAX      Integer32 (1..10)
    MAX-ACCESS  not-accessible 
    STATUS      deprecated
    DESCRIPTION 
      " This is the index to the table. Any entry in the table can be 
        configured only if fsbgp4LocalAs is set."
    ::= { fsbgp4MEDEntry 1 } 

fsbgp4MEDAdminStatus    OBJECT-TYPE
    SYNTAX              INTEGER {
                            up(1),
                            down(2)
                        }
    MAX-ACCESS          read-write
    STATUS              deprecated
    DESCRIPTION
        "The desired state of this entry. The entries in a row are
         configurable only if the admin status is DOWN."
    ::= {fsbgp4MEDEntry 2 }

fsbgp4MEDRemoteAS   OBJECT-TYPE
    SYNTAX          Unsigned32 (0..4294967295)
    MAX-ACCESS      read-write
    STATUS          deprecated
    DESCRIPTION 
    " The remote autonomous system with which this entry is associated.
      A value of zero indicates that this entry is not valid and will not 
      be matched for when the MED value for an update is calculated."
    DEFVAL  { 0 }
    ::= { fsbgp4MEDEntry 3 }

fsbgp4MEDIPAddrPrefix   OBJECT-TYPE
    SYNTAX              IpAddress
    MAX-ACCESS          read-write
    STATUS              deprecated
    DESCRIPTION
    "An IP address prefix in the Network Layer Reachability Information
     field in updates. A value of zero indicates that the entry is not 
     valid and will not be matched for when the MED value for an update is 
     calculated."
    DEFVAL  { '00000000'H }
    ::= { fsbgp4MEDEntry 4 }

fsbgp4MEDIPAddrPrefixLen    OBJECT-TYPE
    SYNTAX                  Integer32 (0..32)
    MAX-ACCESS              read-write
    STATUS                  deprecated
    DESCRIPTION
    "Length in bits of the IP address prefix in the Network Layer Reachability
     Information field. A value of zero indicates that the entry is not 
     valid and will not be matched for when the MED value for an update is 
     calculated."
    DEFVAL  { 0 }
    ::= { fsbgp4MEDEntry 5 }

fsbgp4MEDIntermediateAS OBJECT-TYPE
    SYNTAX              DisplayString
    MAX-ACCESS          read-write
    STATUS              deprecated
    DESCRIPTION
          "Comma seperated list of AS numbers that are to
           be checked against the AS_PATH attribute of the Update.
           An empty field indicates that the same need not be
           checked for in the update.Maximum configurable size is 100."
    ::= { fsbgp4MEDEntry 6 }

fsbgp4MEDDirection  OBJECT-TYPE
    SYNTAX          INTEGER {
                        in(1),
                        out(2)
                    }
    MAX-ACCESS      read-write
    STATUS          deprecated
    DESCRIPTION
    "The direction of the update with which the entry is to be associated."
    DEFVAL  { in }
   ::= { fsbgp4MEDEntry 7 }

fsbgp4MEDValue  OBJECT-TYPE
    SYNTAX      Unsigned32 ( 0 .. 2147483647 )
    MAX-ACCESS  read-write
    STATUS      deprecated
    DESCRIPTION
    "The value assigned to the MED Attribute for the route present in NLRI"
    DEFVAL   { 0 }
    ::= { fsbgp4MEDEntry 8 }

fsbgp4MEDPreference OBJECT-TYPE
    SYNTAX          INTEGER {
                        false(1),
                        true(2)
                    }
    MAX-ACCESS      read-write
    STATUS          deprecated
    DESCRIPTION
    "This object specifies whether the value present
    in this entry takes precedence when the attribute
    is already present in the update message that has
    been received."
    DEFVAL  { false }
    ::= { fsbgp4MEDEntry 9 } 

--  Local Preference Table.
--  This table specifies the value that has to assigned to the
--  Local Preference attribute when an update is sent to an
--  internal Peer or received from an external or internal peer.

fsbgp4LocalPrefTable    OBJECT-TYPE
    SYNTAX              SEQUENCE OF Fsbgp4LocalPrefEntry
    MAX-ACCESS          not-accessible
    STATUS              deprecated
    DESCRIPTION
    "BGP Local Preference table.  This table contains,
    the value that is to be assigned to the Local
    Preference attibute."
    ::= { fsbgp 4 }

fsbgp4LocalPrefEntry    OBJECT-TYPE
    SYNTAX              Fsbgp4LocalPrefEntry
    MAX-ACCESS          not-accessible
    STATUS              deprecated
    DESCRIPTION
    "Entry containing information about the connection with a BGP peer."
    INDEX { fsbgp4LocalPrefIndex }
    ::= {fsbgp4LocalPrefTable 1 }

Fsbgp4LocalPrefEntry ::= SEQUENCE {
    fsbgp4LocalPrefIndex
        Integer32,
    fsbgp4LocalPrefAdminStatus
        INTEGER,
    fsbgp4LocalPrefRemoteAS
        Unsigned32,
    fsbgp4LocalPrefIPAddrPrefix
        IpAddress,
    fsbgp4LocalPrefIPAddrPrefixLen
        Integer32,
    fsbgp4LocalPrefIntermediateAS
        DisplayString,
    fsbgp4LocalPrefDirection
        INTEGER,
    fsbgp4LocalPrefValue
        Unsigned32,
    fsbgp4LocalPrefPreference
        INTEGER
    }

fsbgp4LocalPrefIndex    OBJECT-TYPE
    SYNTAX              Integer32  (1..10)
    MAX-ACCESS          not-accessible
    STATUS              deprecated
    DESCRIPTION
        "This is the index to the table. Any entry in the table can be
         configured only if fsbgp4LocalAs is set."
    ::= { fsbgp4LocalPrefEntry 1 }

fsbgp4LocalPrefAdminStatus  OBJECT-TYPE
    SYNTAX                  INTEGER {
                                up(1),
                                down(2)
                            }
    MAX-ACCESS              read-write
    STATUS                  deprecated
    DESCRIPTION
        "The desired state of this entry. The entries in a row are
         configurable only if the admin status is DOWN."
    ::= { fsbgp4LocalPrefEntry 2 }

fsbgp4LocalPrefRemoteAS OBJECT-TYPE
    SYNTAX             Unsigned32 (0..4294967295)
    MAX-ACCESS          read-write
    STATUS              deprecated
    DESCRIPTION
    "The remote autonomous system with which this entry
    is associated. A value of zero indicates that this
    entry is not valid and will not be matched for when
    the LocalPref value for an update is calculated."
    DEFVAL   { 0 }
    ::= { fsbgp4LocalPrefEntry 3 }

fsbgp4LocalPrefIPAddrPrefix OBJECT-TYPE
    SYNTAX                  IpAddress
    MAX-ACCESS              read-write
    STATUS                  deprecated
    DESCRIPTION
    "An IP address prefix in the Network Layer Reachability Information field.
     A value of zero indicates that the entry is not valid and will not be 
     matched for when the Local Pref value for an update is calculated."
    DEFVAL   { '00000000'H }
    ::= { fsbgp4LocalPrefEntry 4 }

fsbgp4LocalPrefIPAddrPrefixLen  OBJECT-TYPE
    SYNTAX                      Integer32 (0..32)
    MAX-ACCESS                  read-write
    STATUS                      deprecated
    DESCRIPTION
    "Length in bits of the IP address prefix in the Network Layer Reachability
    Information field.  A value of zero indicates that the entry is not valid 
    and will not be matched for when the Local Pref value for an update 
    is calculated."
    DEFVAL  { 0 }
    ::= { fsbgp4LocalPrefEntry 5 }

fsbgp4LocalPrefIntermediateAS   OBJECT-TYPE
    SYNTAX                      DisplayString
    MAX-ACCESS                  read-write
    STATUS                      deprecated
    DESCRIPTION
    "Comma separated list of AS numbers that are to
    be present in the AS_PATH attribute of the Update.
    An empty field indicates that the same need not be
    checked for in the update.Maximum configurable size is 100."
    ::= { fsbgp4LocalPrefEntry 6 }

fsbgp4LocalPrefDirection    OBJECT-TYPE
    SYNTAX                  INTEGER {
                                in(1), -- incoming updates
                                out(2) -- outgoing updates
                            }
    MAX-ACCESS              read-write
    STATUS                  deprecated
    DESCRIPTION
    "The direction of the update with which the entry is to be associated."
    DEFVAL  { in }
    ::= { fsbgp4LocalPrefEntry 7 }

fsbgp4LocalPrefValue    OBJECT-TYPE
    SYNTAX              Unsigned32 ( 0 .. 2147483647 )
    MAX-ACCESS          read-write
    STATUS              deprecated
    DESCRIPTION
    "The value assigned to the LP Attribute for the route present in NLRI"
    DEFVAL  { 100 }
    ::= { fsbgp4LocalPrefEntry 8 }

fsbgp4LocalPrefPreference   OBJECT-TYPE
    SYNTAX                  INTEGER {
                                false(1),
                                true(2)
                            }
    MAX-ACCESS              read-write
    STATUS                  deprecated
    DESCRIPTION
    "This object specifies whether the value present
     in this entry takes precedence when the attribute
     is already present in the update message that has
     been received."
    DEFVAL  { false }
    ::= { fsbgp4LocalPrefEntry 9 }

-- Update Filter Table.
-- This table is used to filter out routing updates

fsbgp4UpdateFilterTable     OBJECT-TYPE
    SYNTAX                  SEQUENCE OF Fsbgp4UpdateFilterEntry
    MAX-ACCESS              not-accessible
    STATUS                  deprecated
    DESCRIPTION
    "BGP Update Filter Table.  This table contains
    Rules to filter out updates based on the AS from
    which it is received, NLRI and AS through which it
    had passed."
    ::= { fsbgp 5 }

fsbgp4UpdateFilterEntry     OBJECT-TYPE
    SYNTAX                  Fsbgp4UpdateFilterEntry
    MAX-ACCESS              not-accessible
    STATUS                  deprecated
    DESCRIPTION
    	"Entry containing information about the updates
         that are to be filtered."
    INDEX { fsbgp4UpdateFilterIndex }
    ::= { fsbgp4UpdateFilterTable 1 }

Fsbgp4UpdateFilterEntry ::= SEQUENCE {
    fsbgp4UpdateFilterIndex
        Integer32,
    fsbgp4UpdateFilterAdminStatus
        INTEGER,
    fsbgp4UpdateFilterRemoteAS
        Unsigned32,
    fsbgp4UpdateFilterIPAddrPrefix
        IpAddress,
    fsbgp4UpdateFilterIPAddrPrefixLen
        Integer32,
    fsbgp4UpdateFilterIntermediateAS
        DisplayString,
    fsbgp4UpdateFilterDirection
        INTEGER,
    fsbgp4UpdateFilterAction
        INTEGER
    }

fsbgp4UpdateFilterIndex OBJECT-TYPE
    SYNTAX              Integer32  (1..10)
    MAX-ACCESS          not-accessible 
    STATUS              deprecated
    DESCRIPTION
    "This is the index to the table. Any entry in the table can be configured
     only if fsbgp4LocalAs is set."
    ::= { fsbgp4UpdateFilterEntry 1 }

fsbgp4UpdateFilterAdminStatus   OBJECT-TYPE
    SYNTAX                      INTEGER {
                                    up(1),
                                    down(2)
                                }
    MAX-ACCESS                  read-write
    STATUS                      deprecated
    DESCRIPTION
        "The desired state of this entry. The entries in a row are
         configurable only if the admin status is DOWN."
    ::= { fsbgp4UpdateFilterEntry 2 }

fsbgp4UpdateFilterRemoteAS  OBJECT-TYPE
    SYNTAX                 Unsigned32 (0..4294967295)
    MAX-ACCESS              read-write
    STATUS                  deprecated
    DESCRIPTION
    "The remote autonomous system with which this entry
    is associated. A value of zero indicates that this
    entry is not valid and will not be matched for when
    the update is checked."
    DEFVAL  { 0 }
    ::= { fsbgp4UpdateFilterEntry 3 }

fsbgp4UpdateFilterIPAddrPrefix  OBJECT-TYPE
    SYNTAX                      IpAddress
    MAX-ACCESS                  read-write
    STATUS                      deprecated
    DESCRIPTION
    "An IP address prefix in the Network Layer Reachability Information field.
     A value of zero in this field indicates that the NLRI field may not be 
     matched."
    DEFVAL  { '00000000'H }
    ::= { fsbgp4UpdateFilterEntry 4 }

fsbgp4UpdateFilterIPAddrPrefixLen   OBJECT-TYPE
    SYNTAX                          Integer32 (0..32)
    MAX-ACCESS                      read-write
    STATUS                          deprecated
    DESCRIPTION
    "Length in bits of the IP address prefix
    in the Network Layer Reachability
    Information field. A value of zero in this field
    indicates that the NLRI field may not be matched."
    DEFVAL { 0 }
    ::= { fsbgp4UpdateFilterEntry 5 }

fsbgp4UpdateFilterIntermediateAS    OBJECT-TYPE
    SYNTAX                          DisplayString
    MAX-ACCESS                      read-write
    STATUS                          deprecated
    DESCRIPTION
    "Comma separated list of AS numbers that are to
    be present in the AS_PATH attribute of the Update.
    An empty field indicates that the same need not be
    checked for in the update."
    ::= { fsbgp4UpdateFilterEntry 6 }

fsbgp4UpdateFilterDirection     OBJECT-TYPE
    SYNTAX                      INTEGER {
                                    in(1), -- incoming updates
                                    out(2) -- outgoing updates
                                }
    MAX-ACCESS                  read-write
    STATUS                      deprecated
    DESCRIPTION
    "The direction of the update with which the entry is to be associated."
    DEFVAL  { in }
    ::= { fsbgp4UpdateFilterEntry 7 }

fsbgp4UpdateFilterAction    OBJECT-TYPE
    SYNTAX                  INTEGER {
                                allow (1), -- do not filter
                                filter (2) -- filter
                            }
    MAX-ACCESS              read-write
    STATUS                  deprecated
    DESCRIPTION
    "The action to be taken when the characteristics
    that are specified in the entry is matched."
    DEFVAL  { filter }
    ::= { fsbgp4UpdateFilterEntry 8 }

-- Aggregation Table.
-- This table is used to aggregate the routing information
-- before the same are advertised to peers.

fsbgp4AggregateTable        OBJECT-TYPE
    SYNTAX                  SEQUENCE OF Fsbgp4AggregateEntry
    MAX-ACCESS              not-accessible
    STATUS                  deprecated
    DESCRIPTION
    "BGP Aggregate Table. The entries in the table
    specifies the IP address based on which the routing
    information has to be aggregated."
    ::= { fsbgp 6 }

fsbgp4AggregateEntry        OBJECT-TYPE
    SYNTAX                  Fsbgp4AggregateEntry
    MAX-ACCESS              not-accessible
    STATUS                  deprecated
    DESCRIPTION
    "Entry containing information about the IP address
    on which the aggregation has to be done."
    INDEX { fsbgp4AggregateIndex }
    ::= { fsbgp4AggregateTable 1 }

Fsbgp4AggregateEntry ::=    SEQUENCE {
                                fsbgp4AggregateIndex
                                    Integer32,
                                fsbgp4AggregateAdminStatus
                                    INTEGER,
                                fsbgp4AggregateIPAddrPrefix
                                    IpAddress,
                                fsbgp4AggregateIPAddrPrefixLen
                                    Integer32,
                                fsbgp4AggregateAdvertise
                                    INTEGER
                            }

fsbgp4AggregateIndex        OBJECT-TYPE
    SYNTAX                  Integer32  (1..10)
    MAX-ACCESS              not-accessible 
    STATUS                  deprecated
    DESCRIPTION
    "This is the index to the table.Any entry in the table can be
         configured only if fsbgp4LocalAs is set."
    ::= { fsbgp4AggregateEntry 1 }

fsbgp4AggregateAdminStatus  OBJECT-TYPE
    SYNTAX                  INTEGER {
                                up(1),
                                down(2)
                            }
    MAX-ACCESS              read-write
    STATUS                  deprecated
    DESCRIPTION
        "The desired state of this entry."
    ::= { fsbgp4AggregateEntry 2 }

fsbgp4AggregateIPAddrPrefix  OBJECT-TYPE
    SYNTAX                   IpAddress
    MAX-ACCESS               read-write
    STATUS                   deprecated
    DESCRIPTION
    "An IP address prefix in the Network Layer Reachability Information field.
     This field is configurable only if the admin status is DOWN"
    ::= { fsbgp4AggregateEntry 3 }

fsbgp4AggregateIPAddrPrefixLen  OBJECT-TYPE
    SYNTAX                      Integer32 (0..32)
    MAX-ACCESS                  read-write
    STATUS                      deprecated
    DESCRIPTION
    "Length in bits of the IP address prefix in the Network Layer Reachability
     Information field. This field is configurable only if the admin status
     is DOWN."
    ::= { fsbgp4AggregateEntry 4 }

fsbgp4AggregateAdvertise        OBJECT-TYPE
    SYNTAX                      INTEGER {
                                    summaryOnly (1),
                                    all (2)
                                }
    MAX-ACCESS                  read-write
    STATUS                      deprecated
    DESCRIPTION
    "This object specifies the route update that should be sent
     to the peers -
        summary-only - specifies that only the summarized route 
                       has to be advertised to peers.
        All          - specifies that both the summary and the
                       more-specific routes based on which the summary entry
                       was generated has to be advertised to the peers."
    ::=  { fsbgp4AggregateEntry 5 }

-- Route Redistribution (RRD) OBJECT DEFINITION BEGIN

   fsbgp4RRDGroup OBJECT IDENTIFIER ::=  { fsbgp 7 }

-- SCALAR_TABLE_BEGIN fsbgp4RRDGroup 3 

   fsbgp4RRDAdminStatus         OBJECT-TYPE
       SYNTAX                   INTEGER {
                                    disable(0),
                                    enable(1)
                                }
       MAX-ACCESS               read-write
       STATUS                   current
       DESCRIPTION
       "Controls redistribution of Direct, Static, IGP(OSPF,RIP) routes into
        BGP. If this object is set to enable, then routes from protocols as
        specified by fsbgp4RRDProtoMaskForEnable will be imported into BGP and
        the BGP learnt routes will be distributed to IGP. If this object is set
        as disable, then the routes learned from protocols specified by
        fsbgp4RRDProtoMaskForEnable will be removed from BGP and no route will
        be either distributed to or imported from IGP. This object can 
        be set only if fsbgp4GlobalAdminStatus is up. When the global admin
        state changes the fsbgp4RRDAdminStatus also changes."
       DEFVAL { enable }
       ::= { fsbgp4RRDGroup 1 }

  fsbgp4RRDProtoMaskForEnable       OBJECT-TYPE
       SYNTAX                       Integer32
                                    -- See the description
       MAX-ACCESS                   read-write
       STATUS                       current
       DESCRIPTION
       "The bit mask of source protocols from which routes are
       imported to BGP.(LSB corresponds to Bit 0)

            Bit 1, if set, indicates that direct routes can be 
            redistributed into BGP. (value = 2)

            Bit 2, if set, indicates that static routes can be 
            redistributed into BGP. (value = 4)

            Bit 7, if set, indicates that routes from RIP can be 
            redistributed into  BGP. (value = 128)

            Bit 12, if set, indicates that OSPF routes can be 
            redistributed into BGP. (value = 4096)

       Other bits are reserved for future use."
       ::= { fsbgp4RRDGroup 2 }

   fsbgp4RRDSrcProtoMaskForDisable      OBJECT-TYPE
       SYNTAX                       Integer32
                                        -- See the description
       MAX-ACCESS                       read-write
       STATUS                           current
       DESCRIPTION
       "The bit mask of source protocols from which redistribution 
       to BGP is disabled.(LSB corresponds to Bit 0)

            Bit 1, if set, indicates that direct routes cannot be 
            redistributed into BGP. (value = 2)

            Bit 2, if set, indicates that static routes cannot be 
            redistributed into BGP. (value = 4)

            Bit 7, if set, indicates that routes from RIP cannot be
            redistributed into BGP. (value = 128)

            Bit 12, if set, indicates that OSPF routes cannot be 
            redistributed into BGP. (value = 4096)

       Other bits are reserved for future use."
       ::= { fsbgp4RRDGroup 3 }

    fsbgp4RRDDefaultMetric  OBJECT-TYPE
        SYNTAX      Unsigned32 ( 0 .. 2147483647 )
        MAX-ACCESS  read-write
        STATUS      current
        DESCRIPTION
        "The default metric value for the IGP routes and static route. If
        configured to 0, the metric received from the IGP route will be used.
        If configured to other value, the MED value of the redistributed routes
        take this value. This value have no effect on the Direct routes."
        DEFVAL   { 0 }
       ::= { fsbgp4RRDGroup 4 }

     fsbgp4RRDRouteMapName              OBJECT-TYPE
        SYNTAX             DisplayString (SIZE (0..20))
        MAX-ACCESS         read-write
        STATUS             current
        DESCRIPTION        "Name  Identifies the  specified route-map
                            in the list of route-maps. If this Object needs to be
                            changed, first reset this object and then configure the
                            new value."
        ::= { fsbgp4RRDGroup 5 }

      fsbgp4RRDMatchTypeEnable   OBJECT-TYPE
         SYNTAX                  INTEGER
                                 {
                                    external(1),
                                    internal(2),
                                    nssa-external(4)
                                 } 
         MAX-ACCESS              read-write
         STATUS                  current
         DESCRIPTION             "Match type Enable specifies the OSPF route type that
                                  needs to be redistributed into BGP, This object is 
                                  used only ospf redistribution." 
         ::= { fsbgp4RRDGroup 6}

      fsbgp4RRDMatchTypeDisable   OBJECT-TYPE
         SYNTAX                   INTEGER
                                  {
                                     external(1),
                                     internal(2),
                                     nssa-external(4)
                                  } 
         MAX-ACCESS               read-write
         STATUS                   current
         DESCRIPTION              "Match type Disable specifies the OSPF route type 
                                   that should be disbled from redistribution into BGP.
                                   This object is used only for OSPF protocol." 
         ::= { fsbgp4RRDGroup 7}

    fsbgp4RRDMetricTable OBJECT-TYPE
        SYNTAX SEQUENCE OF Fsbgp4RRDMetricEntry
        MAX-ACCESS          not-accessible
        STATUS              current
        DESCRIPTION
            "A table describing the configuration of metric values to 
             the redistributed routes."
    ::= { fsbgp4RRDGroup 8 }

    fsbgp4RRDMetricEntry OBJECT-TYPE
        SYNTAX Fsbgp4RRDMetricEntry
        MAX-ACCESS          not-accessible
        STATUS              current
        DESCRIPTION
            "Information describing the configuration of single entry."
        INDEX {fsBgp4RRDMetricProtocolId}
    ::=  { fsbgp4RRDMetricTable 1 }

    Fsbgp4RRDMetricEntry ::= SEQUENCE {
        fsBgp4RRDMetricProtocolId                INTEGER,
        fsBgp4RRDMetricValue                    Integer32
    }

    fsBgp4RRDMetricProtocolId    OBJECT-TYPE
        SYNTAX              INTEGER
                            {
                              ospf(1),
                              rip(2),
                              connected(3),
                              static(4)
                             }
        MAX-ACCESS          not-accessible
        STATUS              current
        DESCRIPTION
            "Protocol Id for which the Metric value needs to be changed by the User."
    ::=  { fsbgp4RRDMetricEntry 1 }

    fsBgp4RRDMetricValue OBJECT-TYPE
        SYNTAX              Integer32
        MAX-ACCESS          read-write
        STATUS              current
        DESCRIPTION
            "The Metric value to be considered instead of the default value from RTM
             for the protocol specified. If the value not secified by the user, 
             default metric value is considered."
    ::=  { fsbgp4RRDMetricEntry 2 }

-- SCALAR_TABLE_END fsbgp4RRDGroup

-- RRD OBJECT DEFINITION END

-- MIB for Importing STATIC routes to BGP and Viewing non-BGP routes.

fsbgp4ImportRouteTable      OBJECT-TYPE
    SYNTAX                  SEQUENCE OF Fsbgp4ImportRouteEntry
    MAX-ACCESS              not-accessible
    STATUS                  deprecated
    DESCRIPTION
    "Non-BGP routes imported into the BGP RIB can be viewed through this table.
     Also allows importing a static route into BGP.After updating the RIB tree,
     if there is any change in the best route selected, then the  route is 
     updated to the Common Forwarding table."
    ::= { fsbgp 8 }

fsbgp4ImportRouteEntry      OBJECT-TYPE
    SYNTAX                  Fsbgp4ImportRouteEntry
    MAX-ACCESS              not-accessible
    STATUS                  deprecated
    DESCRIPTION
    "Import Route entry."
    INDEX   { 
                fsbgp4ImportRoutePrefix, 
                fsbgp4ImportRoutePrefixLen,
                fsbgp4ImportRouteProtocol,
                fsbgp4ImportRouteNextHop, 
                fsbgp4ImportRouteIfIndex,
                fsbgp4ImportRouteMetric
            }
    ::= { fsbgp4ImportRouteTable 1 }

Fsbgp4ImportRouteEntry ::= SEQUENCE {
        fsbgp4ImportRoutePrefix     IpAddress,
        fsbgp4ImportRoutePrefixLen  Integer32,
        fsbgp4ImportRouteProtocol   Integer32,
        fsbgp4ImportRouteNextHop    IpAddress,
        fsbgp4ImportRouteIfIndex    Integer32,
        fsbgp4ImportRouteMetric     Integer32,
        fsbgp4ImportRouteAction     INTEGER
    }

fsbgp4ImportRoutePrefix     OBJECT-TYPE
    SYNTAX                  IpAddress
    MAX-ACCESS              not-accessible 
    STATUS                  deprecated
    DESCRIPTION
    "Prefix of the route to be imported."
    ::= { fsbgp4ImportRouteEntry 1 }

fsbgp4ImportRoutePrefixLen   OBJECT-TYPE
    SYNTAX                   Integer32 (1..32) 
    MAX-ACCESS               not-accessible
    STATUS                   deprecated
    DESCRIPTION
    "Prefix length of the route."
    ::= { fsbgp4ImportRouteEntry 2 }

fsbgp4ImportRouteProtocol   OBJECT-TYPE
    SYNTAX                  Integer32 (2|3|8|13)
    MAX-ACCESS              not-accessible 
    STATUS                  deprecated
    DESCRIPTION
    "Protocol value for Non-BGP routes. 
     2- LOCAL, 
     3 - STATIC,
     8 - RIP, 
     13 - OSPF. 
     Only STATIC routes (protocol 3) can be added through this table. 
     However all non-BGP protocol (Local, Static, RIP, OSPF) routes can 
     be viewed."
    ::= { fsbgp4ImportRouteEntry 3 }

fsbgp4ImportRouteNextHop    OBJECT-TYPE
    SYNTAX                  IpAddress
    MAX-ACCESS              not-accessible
    STATUS                  deprecated
    DESCRIPTION
    "NextHop Ipaddress for the route."
    ::= { fsbgp4ImportRouteEntry 4 }

fsbgp4ImportRouteIfIndex    OBJECT-TYPE
    SYNTAX                  Integer32 (1..2147483647)
    MAX-ACCESS              not-accessible
    STATUS                  deprecated
    DESCRIPTION
    "Interface Index of the Route"
    ::= { fsbgp4ImportRouteEntry 5 }

fsbgp4ImportRouteMetric     OBJECT-TYPE
    SYNTAX                  Integer32 (1..2147483647)
    MAX-ACCESS              not-accessible
    STATUS                  deprecated
    DESCRIPTION
    "Metric for the route being imported."
    ::= { fsbgp4ImportRouteEntry 6 }

fsbgp4ImportRouteAction     OBJECT-TYPE
    SYNTAX                  INTEGER {
		                    add (1), -- route addition
		                    delete (2) -- route deletion
			                }
    MAX-ACCESS              read-write 
    STATUS                  deprecated
    DESCRIPTION
        "Controls addition or deletion of route."
        ::= { fsbgp4ImportRouteEntry 7}
             
        
-- MIB for Importing DIRECT/STATIC routes to BGP end
-- MIB for getting FSM transition history  
         
fsbgp4FsmTransitionHistTable      OBJECT-TYPE
    SYNTAX                  SEQUENCE OF Fsbgp4FsmTransitionHistEntry
    MAX-ACCESS              not-accessible
    STATUS                  deprecated
    DESCRIPTION
    "Gets FSM transitions history per peer   " 
    ::= { fsbgp 9 }

fsbgp4FsmTransitionHistEntry      OBJECT-TYPE
    SYNTAX                  Fsbgp4FsmTransitionHistEntry
    MAX-ACCESS              not-accessible
    STATUS                  deprecated
    DESCRIPTION
    "Fsm Hist  entry."
    INDEX   { 
            		fsbgp4Peer 
		}
        ::= { fsbgp4FsmTransitionHistTable 1 }

Fsbgp4FsmTransitionHistEntry ::= SEQUENCE {
        fsbgp4Peer   	IpAddress,
        fsbgp4FsmTransitionHist	DisplayString
    }

fsbgp4Peer     	OBJECT-TYPE
    SYNTAX                  IpAddress
    MAX-ACCESS              not-accessible
    STATUS                  deprecated
    DESCRIPTION
    "Peer from which FSM transition history would be read."
    ::= { fsbgp4FsmTransitionHistEntry 1 }

fsbgp4FsmTransitionHist     OBJECT-TYPE
    SYNTAX                 DisplayString 
    MAX-ACCESS              read-only
    STATUS                  deprecated
    DESCRIPTION
    " sequence of FSM states separated by space"
    ::= { fsbgp4FsmTransitionHistEntry 2 }
 
-- MIB for getting FSM transitions history end
-- MIB FOR FSBGP_ROUTEREFLECTOR 

fsbgpRfl   OBJECT IDENTIFIER ::= {fsbgp 10} 

fsbgp4RflScalars   OBJECT IDENTIFIER ::= {fsbgpRfl 1} 
 
fsbgp4RflbgpClusterId    OBJECT-TYPE 
    SYNTAX      OCTET STRING (SIZE (4)) 
    MAX-ACCESS  read-write
    STATUS      current 
    DESCRIPTION 
    "The configured Cluster-ID of the local router. By default, when the BGP
     speaker acts as Route Reflector, the BGP Identifier is used as the    
     cluster id. Administrator can overwrite the default cluster-id by
     configuring this object. This object can be configured only if
     fsbgp4LocalAS is configured."
    REFERENCE
    "RFC 2796 - BGP Route Reflection"
    ::= { fsbgp4RflScalars 1 } 

fsbgp4RflRflSupport OBJECT-TYPE 
    SYNTAX       INTEGER { 
                          none (1),
    	                  clientsupport (2), 
                          noClientSupport (3) 
                        } 
    MAX-ACCESS   read-write 
    STATUS       current
    DESCRIPTION 
    "The desired support of the Route Reflector in the cluster.
     Note that none(1) value is for read-only.  This object can be set only if 
     fsbgp4LocalAS is configured."
    DEFVAL       {2}  
    ::= { fsbgp4RflScalars  2 } 

--- Route Reflector PathAttrributes Table
--- Represents the information about BGP Route Reflection [RFC 2796] -
--- - path attributes for a specified path to a network.

fsbgp4RflRouteReflectorTable  OBJECT-TYPE
	SYNTAX      SEQUENCE OF Fsbgp4RflRouteReflectorEntry
	MAX-ACCESS  not-accessible
	STATUS      deprecated
	DESCRIPTION 
    "BGP Route Reflector Table. This table indicates the Rfl path attributes
    that are associated with specified path to a network."
	::= {fsbgpRfl 2 }

fsbgp4RflRouteReflectorEntry  OBJECT-TYPE
	SYNTAX      Fsbgp4RflRouteReflectorEntry
	MAX-ACCESS  not-accessible
	STATUS      deprecated
	DESCRIPTION
      "Entry containing information about the route reflection specific path 
       attributes received with a given route "
	INDEX  { fsbgp4RflPathAttrAddrPrefix,
             fsbgp4RflPathAttrAddrPrefixLen,
             fsbgp4RflPathAttrPeer
           }
	::= { fsbgp4RflRouteReflectorTable 1 }

Fsbgp4RflRouteReflectorEntry ::= SEQUENCE {
	fsbgp4RflPathAttrAddrPrefix
        IpAddress,
    fsbgp4RflPathAttrAddrPrefixLen
        Integer32,
    fsbgp4RflPathAttrPeer
        IpAddress,
    fsbgp4RflPathAttrOriginatorId
    	OCTET STRING,
    fsbgp4RflPathAttrClusterList
        OCTET STRING
    }

fsbgp4RflPathAttrAddrPrefix OBJECT-TYPE
	SYNTAX	    IpAddress
	MAX-ACCESS  not-accessible 
	STATUS      deprecated
	DESCRIPTION 
    "An IP address prefix in the NLRI field. This object is an IP address
    containing the prefix with the length specified by fsbgp4RflPathAttrAddrPrefixLen.
    Any bits beyond the length specified by fsbgp4RflPathAttrAddrPrefixLen are zeroed."
	::= { fsbgp4RflRouteReflectorEntry 1 } 

fsbgp4RflPathAttrAddrPrefixLen OBJECT-TYPE
	SYNTAX	    Integer32 (0..32)
	MAX-ACCESS  not-accessible 
	STATUS      deprecated
	DESCRIPTION 
    "Length in bits of the IP address prefix in NLRI field."
	::= { fsbgp4RflRouteReflectorEntry 2 } 

fsbgp4RflPathAttrPeer OBJECT-TYPE
	SYNTAX	    IpAddress
	MAX-ACCESS  not-accessible 
	STATUS      deprecated
	DESCRIPTION 
    "The address of the peer where the path information was learned."
	::= { fsbgp4RflRouteReflectorEntry 3 } 

fsbgp4RflPathAttrOriginatorId  OBJECT-TYPE
	SYNTAX	    OCTET STRING (SIZE (4)) 
	MAX-ACCESS  read-only
	STATUS      deprecated
	DESCRIPTION 
    "The Originator-ID identifying the router that initially advertised
     this destination to a Route Reflector. A value of 0.0.0.0 indicates
     the absence of this attribute."
    REFERENCE
    "This attribute is defined in [RFC 2796]"
	::= { fsbgp4RflRouteReflectorEntry 4 } 

fsbgp4RflPathAttrClusterList OBJECT-TYPE
    SYNTAX              OCTET STRING (SIZE (0..4096))
    MAX-ACCESS          read-only
    STATUS              deprecated
	DESCRIPTION
    "A sequence of four octet long values Cluster-IDs representing the reflection path
     that the route has passed. Each four octet long value represents the ID
     of a cluster that the route has traversed. A length of zero (0) 
     indicates the absence of this attibute."
    REFERENCE
    "This attribute is defined in [RFC 2796]"
	::= {fsbgp4RflRouteReflectorEntry 5 }

-- MIB FOR FSBGP_ROUTEREFLECTOR end
-- MIB FOR FSBGP_ROUTEFLAPDAMPING

fsbgp4Rfd   OBJECT IDENTIFIER ::= { fsbgp 11} 
fsbgp4RfdScalars   OBJECT IDENTIFIER ::= { fsbgp4Rfd 1} 
 
fsbgp4RfdCutOff OBJECT-TYPE 
    SYNTAX      Integer32 (2000..3999)
    MAX-ACCESS  read-write
    STATUS      current 
    DESCRIPTION 
    "The figure-of-merit value above which the route will be suppressed.
     This object can be set only if fsbgp4RfdAdminStatus is disabled
     is set to down and fsbgp4LocalAS is configured."
    DEFVAL      { 2000 }
    ::= { fsbgp4RfdScalars 1 } 

fsbgp4RfdReuse  OBJECT-TYPE 
    SYNTAX      Integer32 (100..1999)
    MAX-ACCESS  read-write
    STATUS      current 
    DESCRIPTION 
    "The figure-of-merit value below which the suppressed route will be reused.
     This object can be set only if fsbgp4RfdAdminStatus is disabled
     and fsbgp4LocalAS is configured."
    DEFVAL      { 750 }
    ::= { fsbgp4RfdScalars 2 } 

fsbgp4RfdCeiling    OBJECT-TYPE 
    SYNTAX          Integer32 (4000..10000)
    MAX-ACCESS      read-only
    STATUS          current 
    DESCRIPTION 
    "The highest value the figure-of-merit can attain."
    DEFVAL          { 8000 }
    ::= { fsbgp4RfdScalars 3 } 

fsbgp4RfdMaxHoldDownTime  OBJECT-TYPE 
    SYNTAX                Integer32 (1800..10800)
    MAX-ACCESS            read-write
    STATUS                current 
    DESCRIPTION 
    "Maximum time (in seconds) a route can be suppressed.
     This object can be set only if fsbgp4RfdAdminStatus is disabled
     and fsbgp4LocalAS is configured."
    DEFVAL                { 3600 }
    ::= { fsbgp4RfdScalars 4 } 

fsbgp4RfdDecayHalfLifeTime  OBJECT-TYPE 
    SYNTAX                  Integer32 (600..2700)
    MAX-ACCESS              read-write
    STATUS                  current 
    DESCRIPTION 
    "The time duration in seconds during which the figure-of-merit will be 
     reduced by half. This object can be set only if fsbgp4RfdAdminStatus is 
     disabled and fsbgp4LocalAS is configured."
    DEFVAL                  { 900 }
    ::= { fsbgp4RfdScalars 5 } 

fsbgp4RfdDecayTimerGranularity  OBJECT-TYPE 
    SYNTAX                      Integer32 (1..10800)
    MAX-ACCESS                  read-write
    STATUS                      current 
    DESCRIPTION 
    "Time granularity in seconds used to perform all decay calculations.
     This object can be set only if fsbgp4RfdAdminStatus is disabled
     and fsbgp4LocalAS is configured."
    DEFVAL                      { 1 }
    ::= { fsbgp4RfdScalars 6 } 

fsbgp4RfdReuseTimerGranularity  OBJECT-TYPE 
    SYNTAX                      Integer32 (15..10800)
    MAX-ACCESS                  read-write
    STATUS                      current 
    DESCRIPTION 
    "Time interval between evaluations of the reuse lists.
     This object can be set only if fsbgp4RfdAdminStatus is disabled
     and fsbgp4LocalAS is configured."
    DEFVAL                      { 15 }
    ::= { fsbgp4RfdScalars 7 } 

fsbgp4RfdReuseIndxArraySize OBJECT-TYPE 
    SYNTAX                  Integer32 (256..65535)
    MAX-ACCESS              read-write
    STATUS                  current 
    DESCRIPTION 
    "Size of reuse index arrays.This object can be set only if 
     fsbgp4GlobalAdminStatus is set to down and fsbgp4LocalAS is 
     configured." 
    DEFVAL                  { 1024 }
    ::= { fsbgp4RfdScalars 8 } 

fsbgp4RfdAdminStatus        OBJECT-TYPE 
    SYNTAX                  INTEGER {
                               enable (1),
                               disable (2)
    }
    MAX-ACCESS              read-write
    STATUS                  current 
    DESCRIPTION 
        "The desired state of the RouteFlap Dampening feature of the BGP system.
    The SupermicroBGP4 speaker's route flap dampending is functionally active only
    when the RFD admin status is enabled. The RFD admin status can be enabled
    only if the fsbgp4GlobalAdminStatus is set to up. When
    fsbgp4GlobalAdminStatus is set to down, RFD admin status will also be 
    disabled. On disabling RFD admin status, the route dampening history
    and peer dampening history will be cleared and the dampened routes will
    be advertised as feasible routes. By default after the 
    fsbgp4GlobalAdminStatus is set to up, the RFD admin status will be made up.
    If RfdAdmin is disabled the damping feature is alone the disabled, the 
    other rfd configurations will not be reset."
    DEFVAL      { enable }
    ::= { fsbgp4RfdScalars 9 } 


--- Routes Damping History Table

fsbgp4RfdRtDampHistTable OBJECT-TYPE
	SYNTAX          SEQUENCE OF Fsbgp4RfdRtDampHistEntry
	MAX-ACCESS      not-accessible
	STATUS          deprecated
	DESCRIPTION 
    "Route damping history table.This table contains the figure-of-merit and 
    the route status"
	::= { fsbgp4Rfd 2 }

fsbgp4RfdRtDampHistEntry  OBJECT-TYPE
	SYNTAX      Fsbgp4RfdRtDampHistEntry
	MAX-ACCESS  not-accessible
	STATUS      deprecated
	DESCRIPTION
      "Entry contains route damping history"
	INDEX  { fsbgp4PathAttrAddrPrefix,
             fsbgp4PathAttrAddrPrefixLen,
             fsbgp4PathAttrPeer,
             fsbgp4RtDampHistInstance
           }
	::= { fsbgp4RfdRtDampHistTable 1 }

Fsbgp4RfdRtDampHistEntry ::= SEQUENCE {
	fsbgp4PathAttrAddrPrefix
        IpAddress,
    fsbgp4PathAttrAddrPrefixLen
        Integer32,
    fsbgp4PathAttrPeer
        IpAddress,
    fsbgp4RtDampHistInstance
        Integer32,
    fsbgp4RfdRtFom
        Integer32,
    fsbgp4RfdRtLastUpdtTime
        Integer32,
    fsbgp4RfdRtState
        INTEGER,
    fsbgp4RfdRtStatus
        INTEGER
            
    }

fsbgp4PathAttrAddrPrefix OBJECT-TYPE
	SYNTAX	    IpAddress
	MAX-ACCESS  not-accessible 
	STATUS      deprecated
	DESCRIPTION 
    "An IP address prefix in the NLRI field. This object is an IP address
    containing the prefix with the length specified by 
    fsbgp4PathAttrAddrPrefixLen. Any bits beyond the length specified by 
    bgp4PathAttrAddrPrefixLen are 
    zeroed."
	::= { fsbgp4RfdRtDampHistEntry 1 } 

fsbgp4PathAttrAddrPrefixLen OBJECT-TYPE
	SYNTAX	    Integer32 (0..32)
	MAX-ACCESS  not-accessible
	STATUS      deprecated
	DESCRIPTION 
    "Length in bits of the IP address prefix in NLRI field."
	::= { fsbgp4RfdRtDampHistEntry 2 } 

fsbgp4PathAttrPeer OBJECT-TYPE
	SYNTAX	    IpAddress
	MAX-ACCESS  not-accessible
	STATUS      deprecated
	DESCRIPTION 
    "The Peer remote address of the peer where the path information was 
    learned."
	::= { fsbgp4RfdRtDampHistEntry 3 } 

fsbgp4RtDampHistInstance  OBJECT-TYPE
	SYNTAX	    Integer32 (1..10)
	MAX-ACCESS  not-accessible
	STATUS      deprecated
	DESCRIPTION 
    "Multiple damping histories can be present for the same destination when
     the peer is switching between two alternate AS Paths."
	::= { fsbgp4RfdRtDampHistEntry 4 } 

fsbgp4RfdRtFom  OBJECT-TYPE
	SYNTAX	    Integer32 (0..65535)
	MAX-ACCESS  read-only
	STATUS      deprecated
	DESCRIPTION 
    "The figure-of-merit of the route"
	::= { fsbgp4RfdRtDampHistEntry 5 } 

fsbgp4RfdRtLastUpdtTime OBJECT-TYPE
    SYNTAX       Integer32(1..2147483647)
    MAX-ACCESS   read-only
    STATUS       deprecated
	DESCRIPTION
    "The time when the route figure-of-merit was updated."
	::= {fsbgp4RfdRtDampHistEntry 6 }

fsbgp4RfdRtState    OBJECT-TYPE
	SYNTAX	        INTEGER {
                            none(1),
                            suppressed (2),
                            unsuppressed (3)
                            }
	MAX-ACCESS      read-only
	STATUS          deprecated
	DESCRIPTION 
    "The value gives the status whether the route is suppressed or not "
	::= { fsbgp4RfdRtDampHistEntry 7 } 

fsbgp4RfdRtStatus    OBJECT-TYPE
	SYNTAX	        INTEGER {
                            none(1),
                            feasibleroute (2),
                            unfeasibleroute (3)
                            }
	MAX-ACCESS      read-only
	STATUS          deprecated
	DESCRIPTION 
    "The value gives the status whether the route is  feasible or unfeasible 
    route"
	::= { fsbgp4RfdRtDampHistEntry 8 } 


--- Peers Damping History Table

fsbgp4RfdPeerDampHistTable  OBJECT-TYPE
	SYNTAX      SEQUENCE OF Fsbgp4RfdPeerDampHistEntry
	MAX-ACCESS  not-accessible
	STATUS      deprecated
	DESCRIPTION 
    "Peer Damping history table. It contains the peer figure-of-merit and 
    peer status."
	::= { fsbgp4Rfd 3 }

fsbgp4RfdPeerDampHistEntry  OBJECT-TYPE
	SYNTAX      Fsbgp4RfdPeerDampHistEntry
	MAX-ACCESS  not-accessible
	STATUS      deprecated
	DESCRIPTION
    "Entry contains peer damping history"
	INDEX  { fsbgp4PeerRemoteIpAddr
           }
	::= { fsbgp4RfdPeerDampHistTable 1 }

Fsbgp4RfdPeerDampHistEntry ::= SEQUENCE {
    fsbgp4PeerRemoteIpAddr
    	IpAddress,
    fsbgp4RfdPeerFom
        Integer32,
    fsbgp4RfdPeerLastUpdtTime
        Integer32,
    fsbgp4RfdPeerState
        INTEGER,
    fsbgp4RfdPeerStatus
        INTEGER
    }

fsbgp4PeerRemoteIpAddr OBJECT-TYPE
	SYNTAX	    IpAddress
	MAX-ACCESS  not-accessible 
	STATUS      deprecated
	DESCRIPTION 
    "The peer remote address of the peer."
	::= { fsbgp4RfdPeerDampHistEntry 1 } 

fsbgp4RfdPeerFom OBJECT-TYPE
    SYNTAX       Integer32(0..65535)
    MAX-ACCESS   read-only
    STATUS       deprecated
	DESCRIPTION
    "The current figure-of-merit of peer"
	::= {fsbgp4RfdPeerDampHistEntry 2 }

fsbgp4RfdPeerLastUpdtTime OBJECT-TYPE
    SYNTAX       Integer32(1..2147483647)
    MAX-ACCESS   read-only
    STATUS       deprecated
	DESCRIPTION
    "The time when the figure-of-merit was updated."
	::= {fsbgp4RfdPeerDampHistEntry 3 }

fsbgp4RfdPeerState    OBJECT-TYPE
	SYNTAX	        INTEGER {
                            none(1),
                            suppressed (2),
                            unsuppressed (3)
                            }
	MAX-ACCESS      read-only
	STATUS          deprecated
	DESCRIPTION 
    "This value gives the status whether peer is suppressed or not"
	::= {fsbgp4RfdPeerDampHistEntry 4 }

fsbgp4RfdPeerStatus    OBJECT-TYPE
        SYNTAX          INTEGER {
                            none(1),
                            peerup (2),
                            peerdown (3)
                            }
        MAX-ACCESS      read-only
        STATUS          deprecated
        DESCRIPTION
    "This value gives the status whether peer is up or down"
        ::= {fsbgp4RfdPeerDampHistEntry 5 }


---Routes Reuse List Table 

fsbgp4RfdRtsReuseListTable  OBJECT-TYPE
	SYNTAX      SEQUENCE OF Fsbgp4RfdRtsReuseListEntry
	MAX-ACCESS  not-accessible
	STATUS      deprecated
	DESCRIPTION 
    "Routes Reuse List Table. It contains the IP prefix and prefix length."
	::= { fsbgp4Rfd 4 }

fsbgp4RfdRtsReuseListEntry  OBJECT-TYPE
	SYNTAX      Fsbgp4RfdRtsReuseListEntry
	MAX-ACCESS  not-accessible
	STATUS      deprecated
	DESCRIPTION
    "Entry contains routes reuse list"
	INDEX  { fsbgp4RtIPPrefix,
                 fsbgp4RtIPPrefixLen,
                 fsbgp4PeerRemAddress,
                 fsbgp4RfdRtReuseListInstance 
           }
	::= { fsbgp4RfdRtsReuseListTable 1 }

Fsbgp4RfdRtsReuseListEntry ::= SEQUENCE {
    fsbgp4RtIPPrefix
        IpAddress,
    fsbgp4RtIPPrefixLen
        Integer32,
    fsbgp4PeerRemAddress
        IpAddress,
    fsbgp4RfdRtReuseListInstance
        Integer32,
    fsbgp4RfdRtReuseListRtFom
        Integer32,
    fsbgp4RfdRtReuseListRtLastUpdtTime
        Integer32,
    fsbgp4RfdRtReuseListRtState
        INTEGER,
    fsbgp4RfdRtReuseListRtStatus
        INTEGER
            
    }

fsbgp4RtIPPrefix OBJECT-TYPE
	SYNTAX	    IpAddress
	MAX-ACCESS  not-accessible 
	STATUS      deprecated
	DESCRIPTION 
    "An IP address prefix in the NLRI field. This object is an IP address
    containing the prefix with the length specified by fsbgp4RtIPPrefixLen.
    Any bits beyond the length specified by fsbgp4IPPrefixLen are 
    zeroed."
	::= { fsbgp4RfdRtsReuseListEntry 1 } 

fsbgp4RtIPPrefixLen OBJECT-TYPE
	SYNTAX	    Integer32 (0..32)
	MAX-ACCESS  not-accessible
	STATUS      deprecated
	DESCRIPTION 
    "Length in bits of the IP address prefix in NLRI field."
	::= { fsbgp4RfdRtsReuseListEntry 2 } 

fsbgp4PeerRemAddress OBJECT-TYPE
	SYNTAX	    IpAddress
	MAX-ACCESS  not-accessible
	STATUS      deprecated
	DESCRIPTION 
    "The Peer remote address of the peer where the path information was 
    learned."
	::= { fsbgp4RfdRtsReuseListEntry 3 } 

fsbgp4RfdRtReuseListInstance  OBJECT-TYPE
	SYNTAX	    Integer32 (0..10)
	MAX-ACCESS  not-accessible
	STATUS      deprecated
	DESCRIPTION 
    "Multiple entries can be present in the routes reuse list for the same
     destination. When the external peer is switching between two AS paths,
     both paths are penalized and inserted into routes reuse list.The Reuse
     List Instance is used to read the particular instance of reuse entry"
	::= {fsbgp4RfdRtsReuseListEntry  4 } 

fsbgp4RfdRtReuseListRtFom  OBJECT-TYPE
	SYNTAX	    Integer32 (0..65535)
	MAX-ACCESS  read-only
	STATUS      deprecated
	DESCRIPTION 
    "The figure-of-merit of the route which is in the routes reuse list"
	::= {fsbgp4RfdRtsReuseListEntry  5 } 

fsbgp4RfdRtReuseListRtLastUpdtTime OBJECT-TYPE
    SYNTAX       Integer32(1..2147483647)
    MAX-ACCESS   read-only
    STATUS       deprecated
	DESCRIPTION
    "The time when the route figure-of-merit was updated."
	::= {fsbgp4RfdRtsReuseListEntry 6 }

fsbgp4RfdRtReuseListRtState    OBJECT-TYPE
	SYNTAX	        INTEGER {
                            none(1),
                            suppressed (2),
                            unsuppressed (3)
                            }
	MAX-ACCESS      read-only
	STATUS          deprecated
	DESCRIPTION 
    "The value gives the status whether the route is suppressed or not "
	::= { fsbgp4RfdRtsReuseListEntry 7 } 

fsbgp4RfdRtReuseListRtStatus    OBJECT-TYPE
	SYNTAX	        INTEGER {
                            none(1),
                            feasibleroute (2),
                            unfeasibleroute (3)
                            }
	MAX-ACCESS      read-only
	STATUS          deprecated
	DESCRIPTION 
    "The value gives the status whether the route is  feasible or unfeasible 
    route"
	::= { fsbgp4RfdRtsReuseListEntry 8 } 

--- Peer's Reuse List Table

fsbgp4RfdPeerReuseListTable  OBJECT-TYPE
	SYNTAX      SEQUENCE OF Fsbgp4RfdPeerReuseListEntry
	MAX-ACCESS  not-accessible
	STATUS      deprecated
	DESCRIPTION 
    "Peer's Reuse List Table. It contains the Peer Remote Address."
	::= { fsbgp4Rfd 5 }

fsbgp4RfdPeerReuseListEntry  OBJECT-TYPE
	SYNTAX      Fsbgp4RfdPeerReuseListEntry
	MAX-ACCESS  not-accessible
	STATUS      deprecated
	DESCRIPTION
    "Entry contains routes reuse list"
	INDEX  { fsbgp4RfdPeerRemIpAddr
           }
	::= {fsbgp4RfdPeerReuseListTable  1 }

Fsbgp4RfdPeerReuseListEntry ::= SEQUENCE {
    fsbgp4RfdPeerRemIpAddr
    	IpAddress,
    fsbgp4RfdPeerReuseListPeerFom
        Integer32,
    fsbgp4RfdPeerReuseListLastUpdtTime 
        Integer32,
    fsbgp4RfdPeerReuseListPeerState
        INTEGER,
    fsbgp4RfdPeerReuseListPeerStatus
        INTEGER

    }

fsbgp4RfdPeerRemIpAddr OBJECT-TYPE
	SYNTAX	    IpAddress
	MAX-ACCESS  not-accessible 
	STATUS      deprecated
	DESCRIPTION 
    "The peer remote address of the peer which is in the peer's reuse list."
	::= { fsbgp4RfdPeerReuseListEntry 1 } 

fsbgp4RfdPeerReuseListPeerFom OBJECT-TYPE
    SYNTAX       Integer32(0..65535)
    MAX-ACCESS   read-only
    STATUS       deprecated
	DESCRIPTION
    "The current figure-of-merit of peer"
	::= {fsbgp4RfdPeerReuseListEntry 2 }

fsbgp4RfdPeerReuseListLastUpdtTime OBJECT-TYPE
    SYNTAX       Integer32(1..2147483647)
    MAX-ACCESS   read-only
    STATUS       deprecated
	DESCRIPTION
    "The time when the figure-of-merit was updated."
	::= {fsbgp4RfdPeerReuseListEntry 3 }


fsbgp4RfdPeerReuseListPeerState    OBJECT-TYPE
	SYNTAX	        INTEGER {
                            none(1),
                            suppressed (2),
                            unsuppressed (3)
                            }
	MAX-ACCESS      read-only
	STATUS          deprecated
	DESCRIPTION 
    "This value gives the status whether peer is suppressed or not"
	::= {fsbgp4RfdPeerReuseListEntry 4 }

fsbgp4RfdPeerReuseListPeerStatus    OBJECT-TYPE
	SYNTAX	        INTEGER {
                            none(1),
                            peerup (2),
                            peerdown (3)
                            }
	MAX-ACCESS      read-only
	STATUS          deprecated
	DESCRIPTION 
    "This value gives the status whether peer is up or down"
	::= {fsbgp4RfdPeerReuseListEntry 5 }

-- MIB FOR FSBGP_ROUTEFLAPDAMPING end
-- MIB FOR FSBGP_COMMUNITY

fsbgpComm   OBJECT IDENTIFIER ::= {fsbgp 12}

fsbgp4CommScalars   OBJECT IDENTIFIER ::= {fsbgpComm 1} 
 
fsbgp4CommMaxInFTblEntries  OBJECT-TYPE 
    SYNTAX              Integer32 (1..50000)
    MAX-ACCESS          read-write
    STATUS              current 
    DESCRIPTION 
    "Maximum Number of Entries in the Input Community Filter Table.
     This object can not be set to a higher value than the initial value of the 
     object.However initial value can be changed in inc/system.size file"
    DEFVAL              { 10000 }
    ::= { fsbgp4CommScalars 1 } 

fsbgp4CommMaxOutFTblEntries OBJECT-TYPE 
    SYNTAX              Integer32 (1..50000)
    MAX-ACCESS          read-write
    STATUS              current 
    DESCRIPTION 
    "Maximum number of entries in the outgoing community filter table.
     This object can not be set to a higher value than the initial value of the 
     object.However initial value can be changed in inc/system.size file"
    DEFVAL              { 10000 }
    ::= { fsbgp4CommScalars 2 } 

--- Routes Additive Community Table
--- Represents the additive communities configured for
--- destinations.

fsbgp4CommRouteAddCommTable OBJECT-TYPE
	SYNTAX        SEQUENCE OF Fsbgp4CommRouteAddCommEntry
	MAX-ACCESS    not-accessible
	STATUS        deprecated
	DESCRIPTION 
    "This table is used to configure additive communities
     for a given destination." 
	::= {fsbgpComm 2 }

fsbgp4CommRouteAddCommEntry  OBJECT-TYPE
	SYNTAX      Fsbgp4CommRouteAddCommEntry
	MAX-ACCESS  not-accessible
	STATUS      deprecated
	DESCRIPTION
    "Routes configured additive communities Table Entry"
    INDEX  {fsbgp4AddCommIpNetwork,
            fsbgp4AddCommIpPrefixLen,
            fsbgp4AddCommVal
          }
	::= { fsbgp4CommRouteAddCommTable 1 }

Fsbgp4CommRouteAddCommEntry ::= SEQUENCE {
    fsbgp4AddCommIpNetwork
        IpAddress,
    fsbgp4AddCommIpPrefixLen
        Integer32,
    fsbgp4AddCommVal
        Unsigned32,
    fsbgp4AddCommRowStatus
	     RowStatus
    }

fsbgp4AddCommIpNetwork OBJECT-TYPE
	SYNTAX	   IpAddress
	MAX-ACCESS  not-accessible
	STATUS      deprecated
	DESCRIPTION 
    "IP address of the destination"
	::= { fsbgp4CommRouteAddCommEntry 1 } 

fsbgp4AddCommIpPrefixLen   OBJECT-TYPE
	SYNTAX	    Integer32 (1..32)
	MAX-ACCESS   not-accessible
	STATUS       deprecated
	DESCRIPTION 
    "IP prefix length for the destination"
	::= { fsbgp4CommRouteAddCommEntry 2 } 

fsbgp4AddCommVal    OBJECT-TYPE
	SYNTAX	        Unsigned32  (65536..4294901759|4294967041..4294967043)
	MAX-ACCESS       not-accessible
	STATUS           deprecated
	DESCRIPTION 
    "Additive Community configured for the Route"
	::= { fsbgp4CommRouteAddCommEntry 3 } 

fsbgp4AddCommRowStatus    OBJECT-TYPE
	SYNTAX	         RowStatus
	MAX-ACCESS	 read-create
	STATUS	         deprecated
	DESCRIPTION 
	"Row status for creating entries into this table.This object can be set
     only if fsbgp4LocalAS is configured."
	::= { fsbgp4CommRouteAddCommEntry 4 } 

--- Routes Delete Community Table
--- Represents the communities to be deleted for the
--- destinations.

fsbgp4CommRouteDeleteCommTable OBJECT-TYPE
	SYNTAX        SEQUENCE OF Fsbgp4CommRouteDeleteCommEntry
	MAX-ACCESS    not-accessible
	STATUS        deprecated
	DESCRIPTION 
    "This table is used to configure delete communities
     for a given destination."
	::= {fsbgpComm 3 }

fsbgp4CommRouteDeleteCommEntry  OBJECT-TYPE
	SYNTAX      Fsbgp4CommRouteDeleteCommEntry
	MAX-ACCESS  not-accessible
	STATUS      deprecated
	DESCRIPTION
    "Routes configured delete communities Table Entry"
    INDEX  {fsbgp4DeleteCommIpNetwork,
            fsbgp4DeleteCommIpPrefixLen,
            fsbgp4DeleteCommVal
          }
	::= { fsbgp4CommRouteDeleteCommTable 1 }

Fsbgp4CommRouteDeleteCommEntry ::= SEQUENCE {
    fsbgp4DeleteCommIpNetwork
        IpAddress,
    fsbgp4DeleteCommIpPrefixLen
        Integer32,
    fsbgp4DeleteCommVal
        Unsigned32,
    fsbgp4DeleteCommRowStatus
	     RowStatus
    }

fsbgp4DeleteCommIpNetwork OBJECT-TYPE
	SYNTAX	   IpAddress
	MAX-ACCESS  not-accessible
	STATUS      deprecated
	DESCRIPTION 
    "IP address of the destination"
	::= { fsbgp4CommRouteDeleteCommEntry 1 } 

fsbgp4DeleteCommIpPrefixLen   OBJECT-TYPE
	SYNTAX	    Integer32 (1..32)
	MAX-ACCESS   not-accessible
	STATUS       deprecated
	DESCRIPTION 
    "IP prefix length for the destination"
	::= { fsbgp4CommRouteDeleteCommEntry 2 } 

fsbgp4DeleteCommVal    OBJECT-TYPE
	SYNTAX	        Unsigned32  (65536..4294901759|4294967041..4294967043)
	MAX-ACCESS       not-accessible
	STATUS           deprecated
	DESCRIPTION 
    "Delete Community configured for the Route"
	::= { fsbgp4CommRouteDeleteCommEntry 3 } 

fsbgp4DeleteCommRowStatus    OBJECT-TYPE
	SYNTAX	         RowStatus
	MAX-ACCESS	      read-create
	STATUS	         deprecated
	DESCRIPTION 
	"Row status for creating entries into this table.This object can be set 
         only if fsbgp4LocalAS is configured."
	::= { fsbgp4CommRouteDeleteCommEntry 4 } 

--- Routes Community Set Status Table
--- Represents the status or local policy (can be either, addition of 
--- communities, deletion of communities or both or complete
--- ommission of communities) for destinations.

fsbgp4CommRouteCommSetStatusTable OBJECT-TYPE
	SYNTAX        SEQUENCE OF Fsbgp4CommRouteCommSetStatusEntry
	MAX-ACCESS    not-accessible
	STATUS        deprecated
	DESCRIPTION 
    "This table is used to configure the local policy of communities
    for a given destination."
	::= {fsbgpComm 4 }

fsbgp4CommRouteCommSetStatusEntry  OBJECT-TYPE
	SYNTAX      Fsbgp4CommRouteCommSetStatusEntry
	MAX-ACCESS  not-accessible
	STATUS      deprecated
	DESCRIPTION
    "Routes configured delete communities Table Entry"
    INDEX  {fsbgp4CommSetStatusIpNetwork,
            fsbgp4CommSetStatusIpPrefixLen
          }
	::= { fsbgp4CommRouteCommSetStatusTable 1 }

Fsbgp4CommRouteCommSetStatusEntry ::= SEQUENCE {
    fsbgp4CommSetStatusIpNetwork
        IpAddress,
    fsbgp4CommSetStatusIpPrefixLen
        Integer32,
    fsbgp4CommSetStatus
        INTEGER,
    fsbgp4CommSetStatusRowStatus
	RowStatus
    }

fsbgp4CommSetStatusIpNetwork OBJECT-TYPE
	SYNTAX	   IpAddress
	MAX-ACCESS  not-accessible
	STATUS      deprecated
	DESCRIPTION 
    "IP address of the destination"
	::= { fsbgp4CommRouteCommSetStatusEntry 1 } 

fsbgp4CommSetStatusIpPrefixLen   OBJECT-TYPE
	SYNTAX	    Integer32 (1..32)
	MAX-ACCESS   not-accessible
	STATUS       deprecated
	DESCRIPTION 
    "IP prefix length for the destination"
	::= { fsbgp4CommRouteCommSetStatusEntry 2 } 

fsbgp4CommSetStatus OBJECT-TYPE
	SYNTAX	        INTEGER {
                                 none    (1),
                                 set     (2),
                                 setnone (3),
                                 modify  (4)
                              }
	MAX-ACCESS       read-create
	STATUS           deprecated
	DESCRIPTION 
    "Community Set status for the Route. 
       o none     - is for read-only 
       o set      - to send only with configured additive communities
       o setnone  - to send without communities, 
       o modify   - to strip delete communities in received 
                    communities and add additive communities
     This object can be set only if fsbgp4LocalAs is configured." 
    DEFVAL { 4 }
	::= { fsbgp4CommRouteCommSetStatusEntry 3 } 

fsbgp4CommSetStatusRowStatus    OBJECT-TYPE
	SYNTAX	         RowStatus
	MAX-ACCESS	 read-create
	STATUS	         deprecated
	DESCRIPTION 
	"Row status for creating entries into this table.
     This object can be set only if fsbgp4LocalAs is configured."
	::= { fsbgp4CommRouteCommSetStatusEntry 4 } 

--- Peer Community Send Status Table
--- Represents the status or local policy (can be either, send or 
--- do not send of communities) for peers.

fsbgp4CommPeerSendStatusTable  OBJECT-TYPE
	SYNTAX                      SEQUENCE OF Fsbgp4CommPeerSendStatusEntry
	MAX-ACCESS                  not-accessible
	STATUS                      deprecated
	DESCRIPTION 
    "This table is used to configure the local policy of communities
    to send or not for a given peer."
	::= {fsbgpComm 5 }

fsbgp4CommPeerSendStatusEntry  OBJECT-TYPE
	SYNTAX                      Fsbgp4CommPeerSendStatusEntry
	MAX-ACCESS                  not-accessible
	STATUS                      deprecated
	DESCRIPTION
    "Peer community Send Status Table Entry"
	INDEX  { fsbgp4PeerAddress
          }
	::= { fsbgp4CommPeerSendStatusTable 1 }
Fsbgp4CommPeerSendStatusEntry ::= SEQUENCE {
    fsbgp4PeerAddress
    	 IpAddress,
    fsbgp4CommSendStatus
       INTEGER,
    fsbgp4CommPeerSendRowStatus
		 RowStatus
    }

fsbgp4PeerAddress   OBJECT-TYPE
	SYNTAX	        IpAddress
	MAX-ACCESS       not-accessible
	STATUS           deprecated
	DESCRIPTION 
    "IP address of the Peer"
	::= { fsbgp4CommPeerSendStatusEntry 1 } 

fsbgp4CommSendStatus    OBJECT-TYPE
	SYNTAX	            INTEGER {
    	                           none (1), 
                                   send (2),
                                   donotsend (3)
                                }
	MAX-ACCESS          read-create
	STATUS              deprecated
	DESCRIPTION 
    "Community Send status of the peer.
       o none       - is for read-only 
       o send       - send communities to this peer
       o donotsend  - do not send communities to this peer.
     This object can be set only if fsbgp4LocalAs is configured."
    DEFVAL { 3 }
	::= { fsbgp4CommPeerSendStatusEntry 2 } 

fsbgp4CommPeerSendRowStatus OBJECT-TYPE
	SYNTAX	                RowStatus
	MAX-ACCESS	             read-create
	STATUS	                deprecated
	DESCRIPTION 
	"Row status for creating entries into this table. This object can be set
     only if fsbgp4LocalAs is configured."
	::= { fsbgp4CommPeerSendStatusEntry 3 } 

--- Incoming Filter Table
--- Represents the incoming filter status (can be either accept/deny)
--- for a given community value

fsbgp4CommInFilterTable  OBJECT-TYPE
	SYNTAX              SEQUENCE OF Fsbgp4CommInFilterEntry
	MAX-ACCESS          not-accessible
	STATUS              current
	DESCRIPTION 
    "This table is used to configure the incoming filter status
    for a given community value"
	::= {fsbgpComm 6 }

fsbgp4CommInFilterEntry  OBJECT-TYPE
	SYNTAX      Fsbgp4CommInFilterEntry
	MAX-ACCESS  not-accessible
	STATUS      current
	DESCRIPTION
    "Incoming Communities Filter Table Entry"
	INDEX  { fsbgp4InFilterCommVal
          }
	::= { fsbgp4CommInFilterTable 1 }

Fsbgp4CommInFilterEntry ::= SEQUENCE {
    fsbgp4InFilterCommVal
    	 Unsigned32,
    fsbgp4CommIncomingFilterStatus
       INTEGER,
    fsbgp4InFilterRowStatus
		 RowStatus
    }

fsbgp4InFilterCommVal   OBJECT-TYPE
	SYNTAX	            Unsigned32 (65536..4294901759|4294967041..4294967043) 
	MAX-ACCESS           not-accessible
	STATUS               current
	DESCRIPTION 
    "The community value for which the input filtering
    policy is to be updated"
	::= { fsbgp4CommInFilterEntry 1 } 

fsbgp4CommIncomingFilterStatus  OBJECT-TYPE
	SYNTAX	                    INTEGER {
    	                                   none   (1), 
                                           accept (2),
                                           deny   (3)
                                        }
	MAX-ACCESS                  read-create
	STATUS                      current
	DESCRIPTION 
    "Incoming filtering policy for the community.
       o none   - is for read-only 
       o accept - Accept the community value.
       o deny   - Deny the community value."
    DEFVAL              { 2 }
	::= { fsbgp4CommInFilterEntry 2 } 

fsbgp4InFilterRowStatus OBJECT-TYPE
	SYNTAX	                RowStatus
	MAX-ACCESS	            read-create
	STATUS	                current
	DESCRIPTION 
	"Row status for creating entries into this table.This object can be set
     only if fsbgp4LocalAs is configured."
	::= { fsbgp4CommInFilterEntry 3 } 

--- Outgoing Filter Table
--- Represents the outgoing filter status (can be either adevertise/filter)
--- for a given community value

fsbgp4CommOutFilterTable OBJECT-TYPE
	SYNTAX              SEQUENCE OF Fsbgp4CommOutFilterEntry
	MAX-ACCESS          not-accessible
	STATUS              current
	DESCRIPTION 
    "This table is used to configure the outgoing filter status
    for a given community value"
	::= {fsbgpComm 7 }

fsbgp4CommOutFilterEntry OBJECT-TYPE
	SYNTAX              Fsbgp4CommOutFilterEntry
	MAX-ACCESS          not-accessible
	STATUS              current
	DESCRIPTION
    "Outgoing Communities Filter Table Entry"
	INDEX  { fsbgp4OutFilterCommVal
          }
	::= { fsbgp4CommOutFilterTable 1 }

Fsbgp4CommOutFilterEntry ::= SEQUENCE {
    fsbgp4OutFilterCommVal
    	 Unsigned32,
    fsbgp4CommOutgoingFilterStatus
       INTEGER,
    fsbgp4OutFilterRowStatus
		 RowStatus
    }

fsbgp4OutFilterCommVal  OBJECT-TYPE
	SYNTAX	            Unsigned32  (65536..4294901759|4294967041..4294967043)
	MAX-ACCESS           not-accessible
	STATUS               current
	DESCRIPTION 
    "The community value for which the outgoing filtering
     policy is to be updated"
	::= { fsbgp4CommOutFilterEntry 1 } 

fsbgp4CommOutgoingFilterStatus  OBJECT-TYPE
	SYNTAX	                    INTEGER {
                                            none (1), 
                                            advertise (2),
                                            filter (3)
                                        }
	MAX-ACCESS                  read-create
	STATUS                      current
	DESCRIPTION 
    "Outgoing filtering policy for the community.
       o none       - is for read-only 
       o advertise - Advertise the community value.
       o filter    - Filter the community value."
    DEFVAL                      { 2 }
    ::= { fsbgp4CommOutFilterEntry 2 } 

fsbgp4OutFilterRowStatus OBJECT-TYPE
	SYNTAX	                RowStatus
	MAX-ACCESS	             read-create
	STATUS	                current
	DESCRIPTION 
	"Row status for creating entries into this table.This object can be set
     only if fsbgp4LocalAs is configured."
	::= { fsbgp4CommOutFilterEntry 3 } 


--- Received Route Communities Table
--- Represents all the communities that are received
--- with a given destination.

fsbgp4CommReceivedRouteCommTable  OBJECT-TYPE
    SYNTAX      SEQUENCE OF Fsbgp4CommReceivedRouteCommEntry
    MAX-ACCESS  not-accessible
    STATUS      deprecated
    DESCRIPTION
    "Received Communities table which contains the Communities 
     associated with the route that is received from peer."
    ::= {fsbgpComm 8 }

fsbgp4CommReceivedRouteCommEntry OBJECT-TYPE
    SYNTAX          Fsbgp4CommReceivedRouteCommEntry
    MAX-ACCESS      not-accessible
    STATUS          deprecated
    DESCRIPTION
    "Received Communities table which contains the Communities 
     associated with the route that is received from peer."
    INDEX  { fsbgp4IpNet,
             fsbgp4IPPrefixLength,
             fsbgp4PeerRemAddr
           }
    ::= { fsbgp4CommReceivedRouteCommTable 1 }

Fsbgp4CommReceivedRouteCommEntry ::= SEQUENCE {
    fsbgp4IpNet
        IpAddress,
    fsbgp4IPPrefixLength
        Integer32,
    fsbgp4PeerRemAddr
        IpAddress,
    fsbgp4ReceivedRouteCommPath
        OCTET STRING
    }

fsbgp4IpNet    OBJECT-TYPE
	SYNTAX	   IpAddress
	MAX-ACCESS  not-accessible
	STATUS      deprecated
	DESCRIPTION 
    "IP address of the destination"
	::= { fsbgp4CommReceivedRouteCommEntry 1 } 

fsbgp4IPPrefixLength   OBJECT-TYPE
	SYNTAX	           Integer32 (1..32)
	MAX-ACCESS          not-accessible
	STATUS              deprecated
	DESCRIPTION 
    "IP prefix length for the destination"
	::= { fsbgp4CommReceivedRouteCommEntry 2 } 

fsbgp4PeerRemAddr OBJECT-TYPE
   SYNTAX         IpAddress
   MAX-ACCESS     not-accessible
   STATUS         deprecated
   DESCRIPTION
   "The remote IP Address of peer"
   ::= { fsbgp4CommReceivedRouteCommEntry 3 }

fsbgp4ReceivedRouteCommPath OBJECT-TYPE
   SYNTAX              OCTET STRING (SIZE(0..800))
   MAX-ACCESS          read-only
   STATUS              deprecated
   DESCRIPTION
   "The Community Values received for the destination from this peer"
   ::= { fsbgp4CommReceivedRouteCommEntry 4 }

-- MIB FOR FSBGP_COMMUNITY end
-- MIB FOR FSBGP_EXTCOMM

fsbgpExtComm   OBJECT IDENTIFIER ::= {fsbgp 13} 

fsbgp4ExtCommScalars   OBJECT IDENTIFIER ::= {fsbgpExtComm 1} 
 
fsbgp4ExtCommMaxInFTblEntries   OBJECT-TYPE 
    SYNTAX                  Integer32 (1..10000)
    MAX-ACCESS              read-write
    STATUS                  current 
    DESCRIPTION 
    "Maximum Number of Entries in the Input Extended Community Filter Table.
     This object can not be set to a higher value than the initial value of the 
     object.However initial value can be changed in inc/system.size file"
    DEFVAL              { 2000 }
    ::= { fsbgp4ExtCommScalars 1 } 

fsbgp4ExtCommMaxOutFTblEntries  OBJECT-TYPE 
    SYNTAX                  Integer32 (1..10000)
    MAX-ACCESS              read-write
    STATUS                  current 
    DESCRIPTION 
    "Maximum number of entries in the outgoing extended community filter table.
     This object can not be set to a higher value than the initial value of the 
     object.However initial value can be changed in inc/system.size file"
    DEFVAL              { 2000 }
    ::= { fsbgp4ExtCommScalars 2 } 

--- Routes Additive Ext-Community Table
--- Represents the additive extended communities configured for
--- destinations.

fsbgp4ExtCommRouteAddExtCommTable OBJECT-TYPE
	SYNTAX        SEQUENCE OF Fsbgp4ExtCommRouteAddExtCommEntry
	MAX-ACCESS    not-accessible
	STATUS        deprecated
	DESCRIPTION 
    "This table is used to configure additive extended communities
     for a given destination."
	::= {fsbgpExtComm 2 }

fsbgp4ExtCommRouteAddExtCommEntry  OBJECT-TYPE
	SYNTAX      Fsbgp4ExtCommRouteAddExtCommEntry
	MAX-ACCESS  not-accessible
	STATUS      deprecated
	DESCRIPTION
    "Routes configured additive ext-communities Table Entry"
    INDEX  {fsbgp4AddExtCommIpNetwork,
            fsbgp4AddExtCommIpPrefixLen,
            fsbgp4AddExtCommVal
           }
	::= { fsbgp4ExtCommRouteAddExtCommTable 1 }

Fsbgp4ExtCommRouteAddExtCommEntry ::= SEQUENCE {
    fsbgp4AddExtCommIpNetwork
        IpAddress,
    fsbgp4AddExtCommIpPrefixLen
        Integer32,
    fsbgp4AddExtCommVal
        OCTET STRING,
    fsbgp4AddExtCommRowStatus
	     RowStatus
    }

fsbgp4AddExtCommIpNetwork OBJECT-TYPE
	SYNTAX	   IpAddress
	MAX-ACCESS  not-accessible
	STATUS      deprecated
	DESCRIPTION 
    "IP address of the destination"
	::= { fsbgp4ExtCommRouteAddExtCommEntry 1 } 

fsbgp4AddExtCommIpPrefixLen   OBJECT-TYPE
	SYNTAX	    Integer32 (1..32)
	MAX-ACCESS   not-accessible
	STATUS       deprecated
	DESCRIPTION 
    "IP prefix length for the destination"
	::= { fsbgp4ExtCommRouteAddExtCommEntry 2 } 

fsbgp4AddExtCommVal    OBJECT-TYPE
	SYNTAX	        OCTET STRING  (SIZE(8)) 
	MAX-ACCESS       not-accessible
	STATUS           deprecated
	DESCRIPTION 
    "Additive Ext-Community for the destination"
	::= { fsbgp4ExtCommRouteAddExtCommEntry 3 } 

fsbgp4AddExtCommRowStatus    OBJECT-TYPE
	SYNTAX	         RowStatus
	MAX-ACCESS	     read-create
	STATUS	         deprecated
	DESCRIPTION 
	"Row status for creating entries into this table.This object can be set
     only if fsbgp4LocalAs is configured."
	::= { fsbgp4ExtCommRouteAddExtCommEntry 4 } 

--- Routes Delete Ext-Community Table
--- Represents the extended communities to be deleted for the
--- destinations.

fsbgp4ExtCommRouteDeleteExtCommTable OBJECT-TYPE
	SYNTAX        SEQUENCE OF Fsbgp4ExtCommRouteDeleteExtCommEntry
	MAX-ACCESS    not-accessible
	STATUS        deprecated
	DESCRIPTION 
    "This table is used to configure delete extended communities
     for a given destination."
	::= {fsbgpExtComm 3 }

fsbgp4ExtCommRouteDeleteExtCommEntry  OBJECT-TYPE
	SYNTAX      Fsbgp4ExtCommRouteDeleteExtCommEntry
	MAX-ACCESS  not-accessible
	STATUS      deprecated
	DESCRIPTION
    "Routes configured delete ext-communities Table Entry"
    INDEX  {fsbgp4DeleteExtCommIpNetwork,
            fsbgp4DeleteExtCommIpPrefixLen,
            fsbgp4DeleteExtCommVal
           }
	::= { fsbgp4ExtCommRouteDeleteExtCommTable 1 }

Fsbgp4ExtCommRouteDeleteExtCommEntry ::= SEQUENCE {
    fsbgp4DeleteExtCommIpNetwork
        IpAddress,
    fsbgp4DeleteExtCommIpPrefixLen
        Integer32,
    fsbgp4DeleteExtCommVal
	     OCTET STRING,
    fsbgp4DeleteExtCommRowStatus
	     RowStatus
    }

fsbgp4DeleteExtCommIpNetwork OBJECT-TYPE
	SYNTAX	   IpAddress
	MAX-ACCESS  not-accessible
	STATUS      deprecated
	DESCRIPTION 
    "IP address of the destination"
	::= { fsbgp4ExtCommRouteDeleteExtCommEntry 1 } 

fsbgp4DeleteExtCommIpPrefixLen   OBJECT-TYPE
	SYNTAX	    Integer32 (1..32)
	MAX-ACCESS   not-accessible
	STATUS       deprecated
	DESCRIPTION 
    "IP prefix length for the destination"
	::= { fsbgp4ExtCommRouteDeleteExtCommEntry 2 } 

fsbgp4DeleteExtCommVal    OBJECT-TYPE
	SYNTAX	        OCTET STRING  (SIZE(8)) 
	MAX-ACCESS       not-accessible
	STATUS           deprecated
	DESCRIPTION 
    "Delete Ext-Community for the destination"
	::= { fsbgp4ExtCommRouteDeleteExtCommEntry 3 } 

fsbgp4DeleteExtCommRowStatus    OBJECT-TYPE
	SYNTAX	         RowStatus
	MAX-ACCESS	      read-create
	STATUS	         deprecated
	DESCRIPTION 
	"Row status to create entries into this table. This object can be set only
         if fsbgp4LocalAs is configured."
	::= { fsbgp4ExtCommRouteDeleteExtCommEntry 4 } 

--- Routes Ext-Community Set Status Table
--- Represents the status or local policy (can be either, addition of extended
--- communities, deletion of extended communities or both or complete
--- ommission of extended communities) for destinations.

fsbgp4ExtCommRouteExtCommSetStatusTable OBJECT-TYPE
	SYNTAX        SEQUENCE OF Fsbgp4ExtCommRouteExtCommSetStatusEntry
	MAX-ACCESS    not-accessible
	STATUS        deprecated
	DESCRIPTION 
    "This table is used to configure the local policy of extended communities
     for a given destination."
	::= {fsbgpExtComm 4 }

fsbgp4ExtCommRouteExtCommSetStatusEntry  OBJECT-TYPE
	SYNTAX      Fsbgp4ExtCommRouteExtCommSetStatusEntry
	MAX-ACCESS  not-accessible
	STATUS      deprecated
	DESCRIPTION
    "Routes configured delete ext-communities Table Entry"
    INDEX  { fsbgp4ExtCommSetStatusIpNetwork,
             fsbgp4ExtCommSetStatusIpPrefixLen
           }
	::= { fsbgp4ExtCommRouteExtCommSetStatusTable 1 }

Fsbgp4ExtCommRouteExtCommSetStatusEntry ::= SEQUENCE {
    fsbgp4ExtCommSetStatusIpNetwork
        IpAddress,
    fsbgp4ExtCommSetStatusIpPrefixLen
        Integer32,
    fsbgp4ExtCommSetStatus
        INTEGER,
    fsbgp4ExtCommSetStatusRowStatus
	RowStatus
    }

fsbgp4ExtCommSetStatusIpNetwork OBJECT-TYPE
	SYNTAX	   IpAddress
	MAX-ACCESS  not-accessible
	STATUS      deprecated
	DESCRIPTION 
    "IP address of the destination"
	::= { fsbgp4ExtCommRouteExtCommSetStatusEntry 1 } 

fsbgp4ExtCommSetStatusIpPrefixLen   OBJECT-TYPE
	SYNTAX	    Integer32 (1..32)
	MAX-ACCESS   not-accessible
	STATUS       deprecated
	DESCRIPTION 
    "IP prefix length of the destination"
	::= { fsbgp4ExtCommRouteExtCommSetStatusEntry 2 } 

fsbgp4ExtCommSetStatus OBJECT-TYPE
	SYNTAX	        INTEGER {
                                 none    (1),
                                 set     (2),
                                 setnone (3),
                                 modify  (4)
                              }
	MAX-ACCESS       read-create
	STATUS           deprecated
	DESCRIPTION 
    "Ext-Community Set status for the Route. 
       o none     - is for read-only 
       o set      - to send only with configured additive ext-communities
       o setnone  - to send without ext-communities, 
       o modify   - to strip delete ext-communities in received extended 
                    communities and add additive ext-communities.
     This object can be set only if fsbgp4LocalAs is configured." 
    DEFVAL { 4 }
	::= { fsbgp4ExtCommRouteExtCommSetStatusEntry 3 } 

fsbgp4ExtCommSetStatusRowStatus    OBJECT-TYPE
	SYNTAX	         RowStatus
	MAX-ACCESS	      read-create
	STATUS	         deprecated
	DESCRIPTION 
	"Row status to create entries into this table. This object can be set only
         if fsbgp4LocalAs is configured."
	::= { fsbgp4ExtCommRouteExtCommSetStatusEntry 4 } 

--- Peer Extended Community Send Status Table
--- Represents the status or local policy (can be either, send or 
--- do not send of extended communities) for peers.

fsbgp4ExtCommPeerSendStatusTable  OBJECT-TYPE
	SYNTAX                  SEQUENCE OF Fsbgp4ExtCommPeerSendStatusEntry
	MAX-ACCESS              not-accessible
	STATUS                  deprecated
	DESCRIPTION 
    "This table is used to configure the local policy of extended communities
    to send or not for a given peer."
	::= {fsbgpExtComm 5}

fsbgp4ExtCommPeerSendStatusEntry  OBJECT-TYPE
	SYNTAX      Fsbgp4ExtCommPeerSendStatusEntry
	MAX-ACCESS  not-accessible
	STATUS      deprecated
	DESCRIPTION
    "Peer extended community Send Status Table Entry"
	INDEX  { fsbgp4ExtCommPeerAddress
          }
	::= { fsbgp4ExtCommPeerSendStatusTable 1 }

Fsbgp4ExtCommPeerSendStatusEntry ::= SEQUENCE {
    fsbgp4ExtCommPeerAddress
    	IpAddress,
    fsbgp4ExtCommPeerSendStatus
        INTEGER,
    fsbgp4ExtCommPeerSendStatusRowStatus
		 RowStatus
    }

fsbgp4ExtCommPeerAddress    OBJECT-TYPE
	SYNTAX	             IpAddress
	MAX-ACCESS           not-accessible
	STATUS               deprecated
	DESCRIPTION 
    "IP address of the Peer"
	::= { fsbgp4ExtCommPeerSendStatusEntry 1 } 

fsbgp4ExtCommPeerSendStatus OBJECT-TYPE
	SYNTAX	            INTEGER {
                                   none       (1),
                                   send       (2),
                                   donotsend  (3)
                                }
	MAX-ACCESS          read-create
	STATUS              deprecated
	DESCRIPTION 
    "Extended Community Send status of the peer.
       o none     - is for read-only 
       o send       - send extended communities to this peer
       o donotsend  - do not send extended communities to this peer.
     This object can be set only if fsbgp4LocalAs is configured."
    DEFVAL { 3 }
	::= { fsbgp4ExtCommPeerSendStatusEntry 2 } 

fsbgp4ExtCommPeerSendStatusRowStatus  OBJECT-TYPE
	SYNTAX	                    RowStatus
	MAX-ACCESS	                 read-create
	STATUS	                    deprecated
	DESCRIPTION 
	"Row status to create entries into this table.This object can be set only
         if fsbgp4LocalAs is configured."
	::= { fsbgp4ExtCommPeerSendStatusEntry 3 } 

--- Incoming Extended Community Filter Table
--- Represents the incoming filter status (can be either accept/deny)
--- for a given extended community value

fsbgp4ExtCommInFilterTable  OBJECT-TYPE
	SYNTAX              SEQUENCE OF Fsbgp4ExtCommInFilterEntry
	MAX-ACCESS          not-accessible
	STATUS              current
	DESCRIPTION 
    "This table is used to configure the incoming filter status
     for a given extended community value"
	::= {fsbgpExtComm 6}

fsbgp4ExtCommInFilterEntry  OBJECT-TYPE
	SYNTAX      Fsbgp4ExtCommInFilterEntry
	MAX-ACCESS  not-accessible
	STATUS      current
	DESCRIPTION
    "Incoming Extended Communities Filter Table Entry"
	INDEX  { fsbgp4ExtCommInFilterCommVal
           }
	::= { fsbgp4ExtCommInFilterTable 1 }

Fsbgp4ExtCommInFilterEntry ::= SEQUENCE {
    fsbgp4ExtCommInFilterCommVal
        OCTET STRING,
    fsbgp4ExtCommIncomingFilterStatus
      INTEGER,
    fsbgp4ExtCommInFilterRowStatus
		RowStatus
    }

fsbgp4ExtCommInFilterCommVal    OBJECT-TYPE
	SYNTAX	        OCTET STRING  (SIZE(8)) 
	MAX-ACCESS      not-accessible
	STATUS          current
	DESCRIPTION 
    "The extended community value for which the input filtering
     policy is to be updated"
	::= { fsbgp4ExtCommInFilterEntry 1 } 

fsbgp4ExtCommIncomingFilterStatus   OBJECT-TYPE
	SYNTAX	                        INTEGER {
                                        none   (1),
                                        accept (2),
                                        deny   (3)
                                    }
	MAX-ACCESS                      read-create
	STATUS                          current
	DESCRIPTION 
    "Incoming filtering policy for the extended community.
       o none     - is for read-only 
       o accept - Accept the extended community value.
       o deny   - Deny the extended community value."
    DEFVAL              { 2 } 
	::= { fsbgp4ExtCommInFilterEntry 2 } 

fsbgp4ExtCommInFilterRowStatus  OBJECT-TYPE
	SYNTAX	               RowStatus
	MAX-ACCESS	            read-create
	STATUS	               current
	DESCRIPTION 
    "Row Status for creating the entries into this table.This object can be set
     only if fsbgp4LocalAs is configured."
	::= { fsbgp4ExtCommInFilterEntry 3 } 

--- Outgoing Extended Community Filter Table
--- Represents the outgoing filter status (can be either adevertise/filter)
--- for a given extended community value

fsbgp4ExtCommOutFilterTable OBJECT-TYPE
	SYNTAX              SEQUENCE OF Fsbgp4ExtCommOutFilterEntry
	MAX-ACCESS          not-accessible
	STATUS              current
	DESCRIPTION 
    "This table is used to configure the outgoing filter status
     for a given extended community value"
	::= {fsbgpExtComm 7}

fsbgp4ExtCommOutFilterEntry OBJECT-TYPE
	SYNTAX              Fsbgp4ExtCommOutFilterEntry
	MAX-ACCESS          not-accessible
	STATUS              current
	DESCRIPTION
    "Outgoing Extended Communities Filter Table Entry"
	INDEX  { fsbgp4ExtCommOutFilterCommVal
           }
	::= { fsbgp4ExtCommOutFilterTable 1 }

Fsbgp4ExtCommOutFilterEntry ::= SEQUENCE {
    fsbgp4ExtCommOutFilterCommVal
        OCTET STRING,
    fsbgp4ExtCommOutgoingFilterStatus
        INTEGER,
    fsbgp4ExtCommOutFilterRowStatus
		 RowStatus
    }

fsbgp4ExtCommOutFilterCommVal   OBJECT-TYPE
	SYNTAX	                OCTET STRING  (SIZE(8)) 
	MAX-ACCESS              not-accessible
	STATUS                  current
	DESCRIPTION 
    "The extended community value for which the outgoing filtering
     policy is to be updated"
	::= { fsbgp4ExtCommOutFilterEntry 1 } 

fsbgp4ExtCommOutgoingFilterStatus   OBJECT-TYPE
	SYNTAX	                        INTEGER {
                                        none        (1),
                                        advertise   (2),
                                        noadvertise (3)
                                    }
	MAX-ACCESS                      read-create
	STATUS                          current
	DESCRIPTION 
    "Outgoing filtering policy for the extended community.
       o none     - is for read-only 
       o advertise - Advertise the extended community value.
       o filter    - Filter the extended community value."
	::= { fsbgp4ExtCommOutFilterEntry 2 } 

fsbgp4ExtCommOutFilterRowStatus OBJECT-TYPE
	SYNTAX	                RowStatus
	MAX-ACCESS	             read-create
	STATUS	                current
	DESCRIPTION 
    "Row Status to create entries into this table.This object can be set
     only if fsbgp4LocalAs is configured."
	::= { fsbgp4ExtCommOutFilterEntry 3 } 

--- Peer Link Bandwidth Table
--- Represents the link bandwidth for a given peer.

fsbgp4PeerLinkBwTable   OBJECT-TYPE
	SYNTAX              SEQUENCE OF Fsbgp4PeerLinkBwEntry
	MAX-ACCESS          not-accessible
	STATUS              deprecated
	DESCRIPTION 
    "This table is used to configure the link bandwidths for a given peer"
	::= {fsbgpExtComm 8}

fsbgp4PeerLinkBwEntry   OBJECT-TYPE
	SYNTAX              Fsbgp4PeerLinkBwEntry
	MAX-ACCESS          not-accessible
	STATUS              deprecated
	DESCRIPTION
    "Peer Link Bandwidth Table Entry"
	INDEX  { fsbgp4PeerLinkRemAddr
          }
	::= { fsbgp4PeerLinkBwTable 1 }

Fsbgp4PeerLinkBwEntry ::= SEQUENCE {
    fsbgp4PeerLinkRemAddr
    	IpAddress,
    fsbgp4LinkBandWidth
      Unsigned32,
    fsbgp4PeerLinkBwRowStatus
		RowStatus
    }

fsbgp4PeerLinkRemAddr   OBJECT-TYPE
	SYNTAX	            IpAddress
	MAX-ACCESS           not-accessible
	STATUS               deprecated
	DESCRIPTION 
    "IP address of the Peer"
	::= { fsbgp4PeerLinkBwEntry 1 } 

fsbgp4LinkBandWidth OBJECT-TYPE
	SYNTAX	        Unsigned32 (7000..4294967295)
	MAX-ACCESS       read-create
	STATUS           deprecated
	DESCRIPTION 
    "Link Bandwidth in bytes per second.This object can be set only if 
     fsbgp4LocalAs is configured."
	::= { fsbgp4PeerLinkBwEntry 2 } 

fsbgp4PeerLinkBwRowStatus   OBJECT-TYPE
	SYNTAX	                RowStatus
	MAX-ACCESS	             read-create
	STATUS	                deprecated
	DESCRIPTION 
    "Row Status to create entries into this table.
     This object can be set only if fsbgp4LocalAs is configured." 
	::= { fsbgp4PeerLinkBwEntry 3 } 

--- Received Route Extended Communities Table
--- Represents all the extended communities that are received
--- with a given destination.

fsbgp4ExtCommReceivedRouteExtCommTable  OBJECT-TYPE
    SYNTAX      SEQUENCE OF Fsbgp4ExtCommReceivedRouteExtCommEntry
    MAX-ACCESS  not-accessible
    STATUS      deprecated
    DESCRIPTION
    "Received Extended Communities table which contains the Extended 
     Communities associated with the route that is received from peer."
    ::= {fsbgpExtComm 9 }

fsbgp4ExtCommReceivedRouteExtCommEntry OBJECT-TYPE
    SYNTAX          Fsbgp4ExtCommReceivedRouteExtCommEntry
    MAX-ACCESS      not-accessible
    STATUS          deprecated
    DESCRIPTION
    "Received extended communities table Entry"
    INDEX  { fsbgp4ExtCommIpNet,
             fsbgp4ExtCommIPPrefixLength,
             fsbgp4ExtCommPeerRemAddr
           }
    ::= { fsbgp4ExtCommReceivedRouteExtCommTable 1 }

Fsbgp4ExtCommReceivedRouteExtCommEntry ::= SEQUENCE {
    fsbgp4ExtCommIpNet
        IpAddress,
    fsbgp4ExtCommIPPrefixLength
        Integer32,
    fsbgp4ExtCommPeerRemAddr
        IpAddress,
    fsbgp4ReceivedRouteExtCommPath
        OCTET STRING
    }

fsbgp4ExtCommIpNet    OBJECT-TYPE
	SYNTAX	   IpAddress
	MAX-ACCESS  not-accessible
	STATUS      deprecated
	DESCRIPTION 
    "IP address of the destination"
	::= { fsbgp4ExtCommReceivedRouteExtCommEntry 1 } 

fsbgp4ExtCommIPPrefixLength   OBJECT-TYPE
	SYNTAX	           Integer32 (1..32)
	MAX-ACCESS          not-accessible
	STATUS              deprecated
	DESCRIPTION 
    "IP prefix length for the destination"
	::= { fsbgp4ExtCommReceivedRouteExtCommEntry 2 } 

fsbgp4ExtCommPeerRemAddr OBJECT-TYPE
   SYNTAX         IpAddress
   MAX-ACCESS     not-accessible
   STATUS         deprecated
   DESCRIPTION
   "The remote IP Address of peer"
   ::= { fsbgp4ExtCommReceivedRouteExtCommEntry 3 }

fsbgp4ReceivedRouteExtCommPath OBJECT-TYPE
   SYNTAX              OCTET STRING (SIZE(0..800))
   MAX-ACCESS          read-only
   STATUS              deprecated
   DESCRIPTION
   "The ExtCommunity Values received for the destination from this peer"
   ::= { fsbgp4ExtCommReceivedRouteExtCommEntry 4 }

-- MIB FOR FSBGP_EXTCOMM end
-- MIB FOR FSBGP_CABILITIES

fsbgpCaps   OBJECT IDENTIFIER ::= {fsbgp 14}

fsbgpCapScalars   OBJECT IDENTIFIER ::= {fsbgpCaps 1} 
 
fsbgp4CapabilitySupportAvailable    OBJECT-TYPE 
    SYNTAX      TruthValue 
    MAX-ACCESS  read-write
    STATUS      current 
    DESCRIPTION 
    "This variable determines whether the Capability Advertisement
    Support is enabled or not.This object can be set only if 
    fsbgp4GlobalAdminStatus is set to down and fsbgp4LocalAS is configured."
    DEFVAL      { true }
    ::= { fsbgpCapScalars 1 } 

fsbgp4MaxCapsPerPeer    OBJECT-TYPE
	SYNTAX	            Integer32 (1..255)
	MAX-ACCESS          read-write
	STATUS              current
	DESCRIPTION 
    "The maximum number of Capabilities that can be supported per peer 
     or received from peer.
     This object can not be set to a higher value than the initial value of the 
     object.However initial value can be changed in inc/system.size file"
    DEFVAL      { 10 }
    ::= { fsbgpCapScalars 2 } 

fsbgp4MaxInstancesPerCap    OBJECT-TYPE
    SYNTAX	            Integer32 (1..255)
    MAX-ACCESS              read-write
    STATUS                  current
    DESCRIPTION 
    "The maximum number of Instances of same Capability code can be advertised 
     to peer or received from peer.
     This object can not be set to a higher value than the initial value of the 
     object.However initial value can be changed in inc/system.size file"
    DEFVAL      { 5 }
    ::= { fsbgpCapScalars 3 } 

fsbgp4MaxCapDataSize    OBJECT-TYPE
	SYNTAX	        Integer32 (4..252)
    MAX-ACCESS          read-write
    STATUS              current
    DESCRIPTION 
    "The maximum size of the Capability Data size of each Capability.
     To enable packing, the size should be multiples of 4.
     This object can not be set to a higher value than the initial value of the 
     object.However initial value can be changed in inc/system.size file"
    DEFVAL      { 16 }
    ::= { fsbgpCapScalars 4 } 


--- Supported Capabilities Table

fsbgp4CapSupportedCapsTable  OBJECT-TYPE
	SYNTAX      SEQUENCE OF Fsbgp4CapSupportedCapsEntry
	MAX-ACCESS  not-accessible
	STATUS      deprecated
	DESCRIPTION 
    "Supported Capabilities Table. This table contains, the capabilities
     that are supported for particular peer"
	::= {fsbgpCaps 2 }

fsbgp4CapSupportedCapsEntry OBJECT-TYPE
	SYNTAX                  Fsbgp4CapSupportedCapsEntry
	MAX-ACCESS              not-accessible
	STATUS                  deprecated
	DESCRIPTION
    "Entry contains supported Capabilites"
	INDEX  { fsbgp4CapPeerRemoteIpAddr,
                 fsbgp4SupportedCapabilityCode, 
                 fsbgp4SupportedCapabilityInstance
           }
	::= { fsbgp4CapSupportedCapsTable 1 }

Fsbgp4CapSupportedCapsEntry ::= SEQUENCE {
    fsbgp4CapPeerRemoteIpAddr
    	IpAddress,
    fsbgp4SupportedCapabilityCode
        Integer32,
    fsbgp4SupportedCapabilityInstance
        Integer32,
    fsbgp4SupportedCapabilityLength
        Integer32,
    fsbgp4SupportedCapabilityValue
        OCTET STRING,
    fsbgp4CapSupportedCapsRowStatus
	 RowStatus
    }

fsbgp4CapPeerRemoteIpAddr OBJECT-TYPE
	SYNTAX	    IpAddress
	MAX-ACCESS  not-accessible 
	STATUS      deprecated
	DESCRIPTION 
    "The remote IP Address of Peer "
	::= { fsbgp4CapSupportedCapsEntry 1 } 

fsbgp4SupportedCapabilityCode   OBJECT-TYPE
	SYNTAX	                    Integer32 (0..255)
	MAX-ACCESS                  not-accessible
	STATUS                      deprecated
	DESCRIPTION 
    "BGP-4 Capability Advertisement Capability Code that is supported for 
     peer."

	::= { fsbgp4CapSupportedCapsEntry 2 } 

fsbgp4SupportedCapabilityInstance   OBJECT-TYPE
	SYNTAX	                    Integer32 (1..255)
	MAX-ACCESS                  not-accessible
	STATUS                      deprecated
	DESCRIPTION 
    "Multiple instances of a given Capability may be supported
    by a BGP speaker.  This variable is used to index them."
	::= { fsbgp4CapSupportedCapsEntry 3 } 

fsbgp4SupportedCapabilityLength OBJECT-TYPE
	SYNTAX	                    Integer32 (0..251)
	MAX-ACCESS                  read-create
	STATUS                      deprecated
	DESCRIPTION 
    "The length of the supported Capability data"
	::= { fsbgp4CapSupportedCapsEntry 4 } 

fsbgp4SupportedCapabilityValue  OBJECT-TYPE
	SYNTAX	                    OCTET STRING (SIZE(0..251))
	MAX-ACCESS                  read-create
	STATUS                      deprecated
	DESCRIPTION 
    "The value of the supported Capability"
	::= { fsbgp4CapSupportedCapsEntry 5 } 

fsbgp4CapSupportedCapsRowStatus OBJECT-TYPE
	SYNTAX	                    RowStatus
	MAX-ACCESS                  read-create
	STATUS	                    deprecated
	DESCRIPTION 
	" The variable displays the status of the entry.Setting it to
        'invalid' has the effect of rendering it inoperative."
	::= { fsbgp4CapSupportedCapsEntry 6 } 

fsbgp4StrictCapabilityMatchTable  OBJECT-TYPE
	SYNTAX      SEQUENCE OF Fsbgp4StrictCapabilityMatchEntry
	MAX-ACCESS  not-accessible
	STATUS      deprecated
	DESCRIPTION 
    "Strict Capability Match table.If the Strict Capability Match is enabled 
     for particular peer, the BGP session will be established only if peer 
     supports all the Capabilites that are supported by the speaker for 
     that peer.If enabled and the capabilities do not match strictly,then
     the BGP session is terminated, without any attempt to auto re-peer.
     If disabled, BGP session is established with common capabilities,if 
     present."
	::= {fsbgpCaps 3 }


fsbgp4StrictCapabilityMatchEntry OBJECT-TYPE
	SYNTAX                  Fsbgp4StrictCapabilityMatchEntry
	MAX-ACCESS              not-accessible
	STATUS                  deprecated
	DESCRIPTION
    "Entry contains Strict Capability Match"
	INDEX  { fsbgp4PeerRemIpAddr
           }
	::= { fsbgp4StrictCapabilityMatchTable 1 }

Fsbgp4StrictCapabilityMatchEntry ::= SEQUENCE {
    fsbgp4PeerRemIpAddr
    	IpAddress,
    fsbgp4StrictCapabilityMatch
        INTEGER
    }
fsbgp4PeerRemIpAddr OBJECT-TYPE
	SYNTAX	    IpAddress
	MAX-ACCESS  not-accessible 
	STATUS      deprecated
	DESCRIPTION 
    "The remote IP Address of Peer"
	::= { fsbgp4StrictCapabilityMatchEntry 1 } 

fsbgp4StrictCapabilityMatch OBJECT-TYPE
    SYNTAX                  INTEGER { 
    	                            enabled (1), 
    	                            disabled (2) 
                            } 
    MAX-ACCESS              read-write
    STATUS                  deprecated
	DESCRIPTION
    "This value gives whether Strict Capability Match is enabled or 
      disabled for particular peer"
    DEFVAL                  { disabled }
	::= { fsbgp4StrictCapabilityMatchEntry 2 } 


--- Announced Capabilities Table

fsbgp4CapsAnnouncedTable OBJECT-TYPE
	SYNTAX      SEQUENCE OF Fsbgp4CapsAnnouncedEntry
	MAX-ACCESS  not-accessible
	STATUS      deprecated
	DESCRIPTION 
    "This Announced Capabilities table contains the capabilities that are 
     announced to the peer."
	::= {fsbgpCaps 4 }

fsbgp4CapsAnnouncedEntry OBJECT-TYPE
	SYNTAX          Fsbgp4CapsAnnouncedEntry
	MAX-ACCESS      not-accessible
	STATUS          deprecated
	DESCRIPTION
    "Entry contains the Capabilities that are announced to peer"
	INDEX  { fsbgp4PeerIpAddr,
                 fsbgp4PeerCapAnnouncedCode,
                 fsbgp4PeerCapAnnouncedInstance
           }
	::= { fsbgp4CapsAnnouncedTable 1 }

Fsbgp4CapsAnnouncedEntry ::= SEQUENCE {
    fsbgp4PeerIpAddr
    	IpAddress,
    fsbgp4PeerCapAnnouncedCode
        Integer32,
    fsbgp4PeerCapAnnouncedInstance
        Integer32,
    fsbgp4PeerCapAnnouncedLength
        Integer32,
    fsbgp4PeerCapAnnouncedValue
        OCTET STRING
    }

fsbgp4PeerIpAddr OBJECT-TYPE
	SYNTAX	    IpAddress
	MAX-ACCESS  not-accessible 
	STATUS      deprecated
	DESCRIPTION 
    "The remote IP Address of BGP Peer"
	::= { fsbgp4CapsAnnouncedEntry 1 } 

fsbgp4PeerCapAnnouncedCode OBJECT-TYPE
	SYNTAX	               Integer32 (0..255)
	MAX-ACCESS             not-accessible
	STATUS                 deprecated
	DESCRIPTION 
    "BGP-4 Capability Advertisement Capability Code that is announced to peer."
	::= { fsbgp4CapsAnnouncedEntry 2 } 

fsbgp4PeerCapAnnouncedInstance  OBJECT-TYPE
	SYNTAX	                Integer32 (1..255)
	MAX-ACCESS              not-accessible
	STATUS                  deprecated
	DESCRIPTION 
    "Multiple instances of a given capability may be announced
     to peer.  This variable is used to index them."

	::= { fsbgp4CapsAnnouncedEntry 3 } 

fsbgp4PeerCapAnnouncedLength    OBJECT-TYPE
	SYNTAX	                    Integer32 (0..251)
	MAX-ACCESS                  read-only
	STATUS                      deprecated
	DESCRIPTION 
    "The length of the Capability data of announced Capability"
	::= { fsbgp4CapsAnnouncedEntry 4 } 

fsbgp4PeerCapAnnouncedValue     OBJECT-TYPE
	SYNTAX	                    OCTET STRING (SIZE(0..251))
	MAX-ACCESS                  read-only
	STATUS                      deprecated
	DESCRIPTION 
    "The value of announced Capability"
	::= { fsbgp4CapsAnnouncedEntry 5 } 


--- Received Capabilities Table

fsbgp4CapReceivedCapsTable  OBJECT-TYPE
	SYNTAX      SEQUENCE OF Fsbgp4CapReceivedCapsEntry
	MAX-ACCESS  not-accessible
	STATUS      deprecated
	DESCRIPTION 
    "Received Capabilities table which contains the Capabilities that are
      received from peer."
	::= {fsbgpCaps 5 }

fsbgp4CapReceivedCapsEntry OBJECT-TYPE
	SYNTAX                  Fsbgp4CapReceivedCapsEntry
	MAX-ACCESS              not-accessible
	STATUS                  deprecated
	DESCRIPTION
    "Entry contains the received Capabilities"
	INDEX  { fsbgp4PeerRemoteAddress,
                 fsbgp4PeerCapReceivedCode,
                 fsbgp4PeerCapReceivedInstance
           }
	::= { fsbgp4CapReceivedCapsTable 1 }

Fsbgp4CapReceivedCapsEntry ::= SEQUENCE {
    fsbgp4PeerRemoteAddress
    	IpAddress,
    fsbgp4PeerCapReceivedCode
        Integer32,
    fsbgp4PeerCapReceivedInstance
        Integer32,
    fsbgp4PeerCapReceivedLength
        Integer32,
    fsbgp4PeerCapReceivedValue
        OCTET STRING
    }

fsbgp4PeerRemoteAddress OBJECT-TYPE
	SYNTAX	            IpAddress
	MAX-ACCESS          not-accessible
	STATUS              deprecated
	DESCRIPTION 
    "The remote IP Address of peer"
	::= { fsbgp4CapReceivedCapsEntry 1 } 

fsbgp4PeerCapReceivedCode       OBJECT-TYPE
	SYNTAX	                    Integer32 (0..255)
	MAX-ACCESS                  not-accessible
	STATUS                      deprecated
	DESCRIPTION 
    "BGP-4 Capability Advertisement Capability Code that is received from peer."
	::= { fsbgp4CapReceivedCapsEntry 2 } 

fsbgp4PeerCapReceivedInstance       OBJECT-TYPE
	SYNTAX	                    Integer32 (1..255)
	MAX-ACCESS                  not-accessible
	STATUS                      deprecated
	DESCRIPTION 
    "Multiple instances of a given Capability may be received from
     peer.  This variable is used to index them."
	::= { fsbgp4CapReceivedCapsEntry 3 } 

fsbgp4PeerCapReceivedLength     OBJECT-TYPE
	SYNTAX	                    Integer32 (0..251)
	MAX-ACCESS                  read-only
	STATUS                      deprecated
	DESCRIPTION 
    "The length of Capability data received from peer"
	::= { fsbgp4CapReceivedCapsEntry 4 } 

fsbgp4PeerCapReceivedValue      OBJECT-TYPE
	SYNTAX	                    OCTET STRING (SIZE(0..251))
	MAX-ACCESS                  read-only
	STATUS                      deprecated
	DESCRIPTION 
    "The value of Capability received from peer"
	::= { fsbgp4CapReceivedCapsEntry 5 } 

--- Accepted Capabilities Table

fsbgp4CapAcceptedCapsTable  OBJECT-TYPE
	SYNTAX      SEQUENCE OF Fsbgp4CapAcceptedCapsEntry
	MAX-ACCESS  not-accessible
	STATUS      deprecated
	DESCRIPTION 
    "Accepted Capabilities table which contains the Capabilities that are
      received from peer and accepted by the speaker."
	::= {fsbgpCaps 6 }

fsbgp4CapAcceptedCapsEntry OBJECT-TYPE
	SYNTAX                  Fsbgp4CapAcceptedCapsEntry
	MAX-ACCESS              not-accessible
	STATUS                  deprecated
	DESCRIPTION
    "Entry contains the accepted Capabilities"
	INDEX  { fsbgp4CapAcceptedPeerRemAddr,
                 fsbgp4PeerCapAcceptedCode,
                 fsbgp4PeerCapAcceptedInstance
           }
	::= { fsbgp4CapAcceptedCapsTable 1 }

Fsbgp4CapAcceptedCapsEntry ::= SEQUENCE {
    fsbgp4CapAcceptedPeerRemAddr
    	IpAddress,
    fsbgp4PeerCapAcceptedCode
        Integer32,
    fsbgp4PeerCapAcceptedInstance
        Integer32,
    fsbgp4PeerCapAcceptedLength
        Integer32,
    fsbgp4PeerCapAcceptedValue
        OCTET STRING
    }

fsbgp4CapAcceptedPeerRemAddr OBJECT-TYPE
	SYNTAX	            IpAddress
	MAX-ACCESS          not-accessible
	STATUS              deprecated
	DESCRIPTION 
    "The remote IP Address of peer"
	::= { fsbgp4CapAcceptedCapsEntry 1 } 

fsbgp4PeerCapAcceptedCode       OBJECT-TYPE
	SYNTAX	                    Integer32 (0..255)
	MAX-ACCESS                  not-accessible
	STATUS                      deprecated
	DESCRIPTION 
    "BGP-4 Capability Advertisement Capability Code that is received from peer 
    and supported by speaker."
	::= { fsbgp4CapAcceptedCapsEntry 2 } 

fsbgp4PeerCapAcceptedInstance       OBJECT-TYPE
	SYNTAX	                    Integer32 (1..255)
	MAX-ACCESS                  not-accessible
	STATUS                      deprecated
	DESCRIPTION 
    "Multiple instances of a given Capability may be received from
    peer and accepted by speaker.  This variable is used to index them."
	::= { fsbgp4CapAcceptedCapsEntry 3 } 

fsbgp4PeerCapAcceptedLength     OBJECT-TYPE
	SYNTAX	                    Integer32 (0..251)
	MAX-ACCESS                  read-only
	STATUS                      deprecated
	DESCRIPTION 
    "The length of accepted Capability data "
	::= { fsbgp4CapAcceptedCapsEntry 4 } 

fsbgp4PeerCapAcceptedValue      OBJECT-TYPE
	SYNTAX	                    OCTET STRING (SIZE(0..251))
	MAX-ACCESS                  read-only
	STATUS                      deprecated
	DESCRIPTION 
    "The value of accepted Capability "
    ::= { fsbgp4CapAcceptedCapsEntry 5 }

-- MIB FOR FSBGP_CABILITIES end

-- MIB FOR FS_BGP_ASC STARTS

fsbgpAsc   OBJECT IDENTIFIER ::= {fsbgp 15} 

fsbgpAscScalars OBJECT IDENTIFIER ::= {fsbgpAsc 1}

    fsbgpAscConfedId OBJECT-TYPE
        SYNTAX Unsigned32 (0 .. 4294967295)
        MAX-ACCESS read-write
        STATUS current
        DESCRIPTION 
        "The Local Confederation Identification number of 
        the AS confederation, a value of zero indicates the 
        absence of this value. The object fsbgp4LocalAs must be
        configured prior to configuring this object.
        If already set (to non-zero value), this value must be 
        reset to zero (represets absence of confed) before 
        reconfiguring confed id."
        DEFVAL {0}
        ::= {fsbgpAscScalars 1}

    fsbgpAscConfedBestPathCompareMED OBJECT-TYPE
        SYNTAX INTEGER 
        {
                set(1),
                clear(2)
        }
        MAX-ACCESS read-write
        STATUS current
        DESCRIPTION
        "This object is used to  compare MED among paths learned 
        from confed peers. if this object value is set and AS path 
        contains only AS_CONFED segments then then MED should be 
        compared if this object value is clear and sanitized path 
        has different left-most entry in AS path then MED should not 
        be compared"
        DEFVAL {clear}
        ::= {fsbgpAscScalars 2}

    fsbgpAscConfedPeerTable OBJECT-TYPE
        SYNTAX     SEQUENCE OF FsbgpAscConfedPeerEntry
        MAX-ACCESS not-accessible
        STATUS     current
        DESCRIPTION
        "BGP peer confederation table, this table contains information 
        about the Member-ASs of the confederation"
        ::= { fsbgpAsc 2 }

    fsbgpAscConfedPeerEntry OBJECT-TYPE
        SYNTAX     FsbgpAscConfedPeerEntry
        MAX-ACCESS not-accessible
        STATUS     current
        DESCRIPTION
        "Entry containing information about a member-AS of the confederation."
        INDEX {
                    fsbgpAscConfedPeerASNo
              }
        ::= { fsbgpAscConfedPeerTable 1 }

    FsbgpAscConfedPeerEntry ::= SEQUENCE {
        fsbgpAscConfedPeerASNo
            Unsigned32,
        fsbgpAscConfedPeerStatus
            INTEGER
        }

    fsbgpAscConfedPeerASNo OBJECT-TYPE
        SYNTAX     Unsigned32 (1..4294967295)
        MAX-ACCESS not-accessible
        STATUS     current
        DESCRIPTION
        "The local AS number of member-AS,
        a value of zero indicates the absence of this value "
        ::= { fsbgpAscConfedPeerEntry 1 }


    fsbgpAscConfedPeerStatus OBJECT-TYPE
        SYNTAX     INTEGER  
        {
            enable(1),
            disable(2)
        }
        MAX-ACCESS read-write
        STATUS     current
        DESCRIPTION
        "This object is used to  enable or disable the member-AS.
        Use disable, if member-AS entry needs to disabled,
        Use enable, if member-AS entry needs to be enabled."
        ::= { fsbgpAscConfedPeerEntry 2 }


-- MIB FOR Route Refresh STARTS
fsbgp4RtRefresh   OBJECT IDENTIFIER ::= {fsbgp 16} 

-- Route Refresh Scalars 

    fsbgp4RtRefreshAllPeerInboundRequest OBJECT-TYPE
        SYNTAX     TruthValue   
        MAX-ACCESS read-write 
        STATUS     deprecated
        DESCRIPTION
        "Setting this object triggers the sending of the Route Refresh message
         to all the peers. This object will be cleared once the Route Refresh
         message is sent to all the peers.Route-Refresh message support is a 
         default feature.If not negotiated via capability negotiation, inbound 
         soft-reconfig is performed internally on setting this object."
         DEFVAL      { false }
        ::= { fsbgp4RtRefresh 1 }


-- Route Refresh Inbound Table 

    fsbgp4RtRefreshInboundTable OBJECT-TYPE
        SYNTAX     SEQUENCE OF Fsbgp4RtRefreshInboundEntry
        MAX-ACCESS not-accessible
        STATUS     deprecated
        DESCRIPTION
        "Route Refresh Inbound Table"
        ::= { fsbgp4RtRefresh 2 }

    fsbgp4RtRefreshInboundEntry OBJECT-TYPE
        SYNTAX     Fsbgp4RtRefreshInboundEntry
        MAX-ACCESS not-accessible
        STATUS     deprecated
        DESCRIPTION
        "Entry corresponds to Route Refresh Inbound."
        INDEX {
                fsbgp4RtRefreshInboundPeerType,
                fsbgp4RtRefreshInboundPeerAddr
              }
        ::= { fsbgp4RtRefreshInboundTable 1 }

    Fsbgp4RtRefreshInboundEntry ::= SEQUENCE {
        fsbgp4RtRefreshInboundPeerType
           InetAddressType,
        fsbgp4RtRefreshInboundPeerAddr
           OCTET STRING,
        fsbgp4RtRefreshInboundRequest
           TruthValue
        }

    fsbgp4RtRefreshInboundPeerType OBJECT-TYPE
        SYNTAX     InetAddressType
        MAX-ACCESS not-accessible
        STATUS     deprecated
        DESCRIPTION
        "Address Family Identifier of the peer remote address"
        ::= { fsbgp4RtRefreshInboundEntry 1 }

    fsbgp4RtRefreshInboundPeerAddr OBJECT-TYPE
        SYNTAX    OCTET STRING (SIZE (1..16))
        MAX-ACCESS not-accessible
        STATUS     deprecated
        DESCRIPTION
        "The IP address of the peeri for which the Route Refresh request has to
        be issued."
        ::= { fsbgp4RtRefreshInboundEntry 2 }
        
    fsbgp4RtRefreshInboundRequest OBJECT-TYPE
        SYNTAX     TruthValue   
        MAX-ACCESS read-write 
        STATUS     deprecated
        DESCRIPTION
        "Setting this object triggers the sending of the Route Refresh message
        to the peer. This object will be cleared once the Route Refresh message
        is sent to the peer. Route-Refresh message support is a default feature
        If not negotiated via capability negotiation, inbound soft-reconfig is
        internally done on setting this object."
        ::= { fsbgp4RtRefreshInboundEntry 3 }

--
-- Route Refresh Statistics Table
--

    fsbgp4RtRefreshStatisticsTable OBJECT-TYPE
        SYNTAX     SEQUENCE OF Fsbgp4RtRefreshStatisticsEntry
        MAX-ACCESS not-accessible
        STATUS     deprecated
        DESCRIPTION
        "Route Refresh Statistics Table"
        ::= { fsbgp4RtRefresh 3 }

    fsbgp4RtRefreshStatisticsEntry OBJECT-TYPE
        SYNTAX     Fsbgp4RtRefreshStatisticsEntry
        MAX-ACCESS not-accessible
        STATUS     deprecated
        DESCRIPTION
        "Entry gives the statistics of Route Refresh."
        INDEX {
                fsbgp4RtRefreshStatisticsPeerType,
                fsbgp4RtRefreshStatisticsPeerAddr
              }
        ::= { fsbgp4RtRefreshStatisticsTable 1 }

     Fsbgp4RtRefreshStatisticsEntry ::= SEQUENCE {
        fsbgp4RtRefreshStatisticsPeerType
            InetAddressType,
        fsbgp4RtRefreshStatisticsPeerAddr
           OCTET STRING,
        fsbgp4RtRefreshStatisticsRtRefMsgSentCntr 
           Counter32,
        fsbgp4RtRefreshStatisticsRtRefMsgTxErrCntr 
           Counter32,
        fsbgp4RtRefreshStatisticsRtRefMsgRcvdCntr 
           Counter32,
        fsbgp4RtRefreshStatisticsRtRefMsgInvalidCntr 
           Counter32
          
        }

     fsbgp4RtRefreshStatisticsPeerType OBJECT-TYPE
        SYNTAX     InetAddressType
        MAX-ACCESS not-accessible
        STATUS     deprecated
        DESCRIPTION
        "Address Family Identifier of the peer remote address."
        ::= { fsbgp4RtRefreshStatisticsEntry 1 }

    fsbgp4RtRefreshStatisticsPeerAddr OBJECT-TYPE
        SYNTAX    OCTET STRING (SIZE (1..16))  
        MAX-ACCESS not-accessible
        STATUS     deprecated
        DESCRIPTION
        "The IP address of the peer for which the Route Refresh Statistics has
        to be read."
        ::= { fsbgp4RtRefreshStatisticsEntry 2 }
 

     fsbgp4RtRefreshStatisticsRtRefMsgSentCntr OBJECT-TYPE
        SYNTAX     Counter32 
        MAX-ACCESS read-only 
        STATUS     deprecated
        DESCRIPTION
        " The number of Route Refresh messages sent to the peer."
        ::= { fsbgp4RtRefreshStatisticsEntry 3 }
 
     fsbgp4RtRefreshStatisticsRtRefMsgTxErrCntr OBJECT-TYPE
        SYNTAX     Counter32 
        MAX-ACCESS read-only 
        STATUS     deprecated
        DESCRIPTION
        " The number of Route Refresh messages that could not be 
          transmitted to the peer."
        ::= { fsbgp4RtRefreshStatisticsEntry 4 }
 
    fsbgp4RtRefreshStatisticsRtRefMsgRcvdCntr OBJECT-TYPE
        SYNTAX     Counter32 
        MAX-ACCESS read-only 
        STATUS     deprecated
        DESCRIPTION
        " The number of Route Refresh messages received from the peer."
        ::= { fsbgp4RtRefreshStatisticsEntry 5 }
 
     fsbgp4RtRefreshStatisticsRtRefMsgInvalidCntr OBJECT-TYPE
        SYNTAX     Counter32 
        MAX-ACCESS read-only 
        STATUS     deprecated
        DESCRIPTION
        " The number of invalid Route Refresh messages received from the peer."
        ::= { fsbgp4RtRefreshStatisticsEntry 6 }
 

-- MIB for TCP MD5 Authentication starts.

fsbgp4TCPMD5Auth   OBJECT IDENTIFIER ::= {fsbgp 17} 

-- TCP MD5 Authentication Table

    fsbgp4TCPMD5AuthTable OBJECT-TYPE
        SYNTAX     SEQUENCE OF Fsbgp4TCPMD5AuthEntry
        MAX-ACCESS not-accessible
        STATUS     current
        DESCRIPTION
        "TCP MD5 Authientication Table"
        ::= { fsbgp4TCPMD5Auth 1 }

    fsbgp4TCPMD5AuthEntry OBJECT-TYPE
        SYNTAX     Fsbgp4TCPMD5AuthEntry
        MAX-ACCESS not-accessible
        STATUS     current
        DESCRIPTION
        "Entry corresponds to the TCP MD5 authentication password."
        INDEX {
                fsbgp4TCPMD5AuthPeerType,
                fsbgp4TCPMD5AuthPeerAddr
              }
        ::= { fsbgp4TCPMD5AuthTable 1 }

     Fsbgp4TCPMD5AuthEntry ::= SEQUENCE {
        fsbgp4TCPMD5AuthPeerType
            InetAddressType,
        fsbgp4TCPMD5AuthPeerAddr
           OCTET STRING,
        fsbgp4TCPMD5AuthPassword 
           OCTET STRING,
        fsbgp4TCPMD5AuthPwdSet
           INTEGER 
        }


     fsbgp4TCPMD5AuthPeerType OBJECT-TYPE
        SYNTAX     InetAddressType
        MAX-ACCESS not-accessible
        STATUS     current
        DESCRIPTION
        "Address Family Identifier of the peer remote address."
        ::= { fsbgp4TCPMD5AuthEntry 1 }


    fsbgp4TCPMD5AuthPeerAddr OBJECT-TYPE
        SYNTAX    OCTET STRING (SIZE (1 .. 16))
        MAX-ACCESS not-accessible
        STATUS     current
        DESCRIPTION
        "The IP address of the peer for which the TCP MD5 Authentication
        Password has to be set.
        to be read."
        ::= { fsbgp4TCPMD5AuthEntry 2 }
 

    fsbgp4TCPMD5AuthPassword OBJECT-TYPE
        SYNTAX     OCTET STRING (SIZE (1..80)) 
        MAX-ACCESS read-write
        STATUS     current
        DESCRIPTION
        " The TCP MD5 Authentication Password that has to be sent with all TCP
        packets originated from the peer."
        ::= { fsbgp4TCPMD5AuthEntry 3 }

    fsbgp4TCPMD5AuthPwdSet OBJECT-TYPE
	    SYNTAX	    INTEGER 
                    {
                      set (1),
                      clear (2)
                    } 
	    MAX-ACCESS	read-write
	    STATUS	    current
	    DESCRIPTION 
        " This object indicates whether TCP MD5 password needs to be set/reset
          for the peer. This object needs to be set before the object 
          fsbgp4TCPMD5AuthPassword can be set."
        DEFVAL  { clear }
        ::= { fsbgp4TCPMD5AuthEntry 4 }

-- MIB FOR OutBound Soft-Reconfig STARTS
fsbgp4SoftReconfigOut   OBJECT IDENTIFIER ::= {fsbgp 18} 

-- OutBound Soft-Reconfig Scalars 

    fsbgp4SoftReconfigAllPeerOutboundRequest OBJECT-TYPE
        SYNTAX     TruthValue   
        MAX-ACCESS read-write 
        STATUS     deprecated
        DESCRIPTION
        "Setting this object triggers the outbound soft-reconfig process
         for all peers. This object value is cleared once the soft-reconfig
         (outbound) process is completed."
         DEFVAL      { false }
        ::= { fsbgp4SoftReconfigOut 1 }

-- Soft Re-config Outbound Table 

    fsbgp4SoftReconfigOutboundTable OBJECT-TYPE
        SYNTAX     SEQUENCE OF Fsbgp4SoftReconfigOutboundEntry
        MAX-ACCESS not-accessible
        STATUS     deprecated
        DESCRIPTION
        "Soft Reconfig outbound Table"
        ::= { fsbgp4SoftReconfigOut 2 }

    fsbgp4SoftReconfigOutboundEntry OBJECT-TYPE
        SYNTAX     Fsbgp4SoftReconfigOutboundEntry
        MAX-ACCESS not-accessible
        STATUS     deprecated
        DESCRIPTION
        "Entry corresponds to Soft Reconfig outbound."
        INDEX {
                fsbgp4SoftReconfigOutboundPeerType,
                fsbgp4SoftReconfigOutboundPeerAddr
              }
        ::= { fsbgp4SoftReconfigOutboundTable 1 }

    Fsbgp4SoftReconfigOutboundEntry ::= SEQUENCE {
        fsbgp4SoftReconfigOutboundPeerType
            InetAddressType,
        fsbgp4SoftReconfigOutboundPeerAddr
           OCTET STRING,
        fsbgp4SoftReconfigOutboundRequest
           TruthValue
        }

    fsbgp4SoftReconfigOutboundPeerType OBJECT-TYPE
        SYNTAX     InetAddressType
        MAX-ACCESS not-accessible
        STATUS     deprecated
        DESCRIPTION
        "Address Family Identifier of the peer remote address"
        ::= { fsbgp4SoftReconfigOutboundEntry 1 }

    fsbgp4SoftReconfigOutboundPeerAddr OBJECT-TYPE
        SYNTAX    OCTET STRING (SIZE (1 .. 16))
        MAX-ACCESS not-accessible
        STATUS     deprecated
        DESCRIPTION
        "The IP address of the peer for which the outbound soft-reconfig has to
        be performed."
        ::= { fsbgp4SoftReconfigOutboundEntry 2 }
        
    fsbgp4SoftReconfigOutboundRequest OBJECT-TYPE
        SYNTAX     TruthValue   
        MAX-ACCESS read-write 
        STATUS     deprecated
        DESCRIPTION
        "Setting this object triggers the outbound soft-reconfig process for the         peer. This object value is cleared once the soft-reconfig process is
         completed." 
        ::= { fsbgp4SoftReconfigOutboundEntry 3 }

--- Extensions to the fsbgp4 mib
--- Peer Table

fsbgp4MpeBgpPeerTable        OBJECT-TYPE
    SYNTAX          SEQUENCE OF Fsbgp4MpeBgpPeerEntry
    MAX-ACCESS      not-accessible
    STATUS          current
    DESCRIPTION
        "BGP peer table.  This table contains, one entry per BGP peer,
        information about the connections with BGP peers."
    ::= { fsbgp 19 }

fsbgp4MpeBgpPeerEntry    OBJECT-TYPE
    SYNTAX      Fsbgp4MpeBgpPeerEntry
    MAX-ACCESS  not-accessible
    STATUS      current
    DESCRIPTION
        "Entry containing information about the connection with a BGP peer."
    INDEX {
            fsbgp4mpebgpPeerRemoteAddrType,
            fsbgp4mpebgpPeerRemoteAddr
          }
    ::= { fsbgp4MpeBgpPeerTable 1 }

Fsbgp4MpeBgpPeerEntry ::= SEQUENCE {
    fsbgp4mpebgpPeerRemoteAddrType
        InetAddressType,
    fsbgp4mpebgpPeerIdentifier
        InetAddress,
    fsbgp4mpebgpPeerState
           INTEGER,
  fsbgp4mpebgpPeerAdminStatus
           INTEGER,
    fsbgp4mpebgpPeerNegotiatedVersion
           Integer32,
    fsbgp4mpebgpPeerLocalAddr
           InetAddress,
    fsbgp4mpebgpPeerLocalPort
           Integer32,
    fsbgp4mpebgpPeerRemoteAddr
           InetAddress,
    fsbgp4mpebgpPeerRemotePort
           Integer32,
    fsbgp4mpebgpPeerRemoteAs
           Unsigned32,
    fsbgp4mpebgpPeerInUpdates
           Counter32,
    fsbgp4mpebgpPeerOutUpdates
           Counter32,
    fsbgp4mpebgpPeerInTotalMessages
           Counter32,
    fsbgp4mpebgpPeerOutTotalMessages
           Counter32,
    fsbgp4mpebgpPeerLastError
           OCTET STRING,
    fsbgp4mpebgpPeerFsmEstablishedTransitions
           Counter32,
    fsbgp4mpebgpPeerFsmEstablishedTime
           Gauge32,
    fsbgp4mpebgpPeerConnectRetryInterval
           Integer32,
    fsbgp4mpebgpPeerHoldTime
           Integer32,
    fsbgp4mpebgpPeerKeepAlive
           Integer32,
    fsbgp4mpebgpPeerHoldTimeConfigured
           Integer32,
    fsbgp4mpebgpPeerKeepAliveConfigured
           Integer32,
    fsbgp4mpebgpPeerMinASOriginationInterval
           Integer32,
    fsbgp4mpebgpPeerMinRouteAdvertisementInterval
           Integer32,
    fsbgp4mpebgpPeerInUpdateElapsedTime
           Gauge32,
    fsbgp4mpebgpPeerEndOfRIBMarkerSentStatus
	   INTEGER,
    fsbgp4mpebgpPeerEndOfRIBMarkerReceivedStatus
	   INTEGER,
    fsbgp4mpebgpPeerRestartMode
	   INTEGER,
    fsbgp4mpePeerRestartTimeInterval
           Integer32,
    fsbgp4mpePeerAllowAutomaticStart
           INTEGER,
    fsbgp4mpePeerAllowAutomaticStop
           INTEGER,
    fsbgp4mpebgpPeerIdleHoldTimeConfigured
           Integer32,
    fsbgp4mpeDampPeerOscillations
           INTEGER,
    fsbgp4mpePeerDelayOpen
           INTEGER,
    fsbgp4mpebgpPeerDelayOpenTimeConfigured
           Integer32,
    fsbgp4mpePeerPrefixUpperLimit
           Integer32,
    fsbgp4mpePeerTcpConnectRetryCnt
           Integer32,
    fsbgp4mpePeerTcpCurrentConnectRetryCnt
           Integer32,
    fsbgp4mpeIsPeerDamped
           INTEGER,
    fsbgp4mpePeerSessionAuthStatus
           INTEGER,
    fsbgp4mpePeerTCPAOKeyIdInUse
           Integer32,
    fsbgp4mpePeerTCPAOAuthNoMKTDiscard
           INTEGER,
    fsbgp4mpePeerTCPAOAuthICMPAccept
           INTEGER,
    fsbgp4mpePeerIpPrefixNameIn
           DisplayString,
    fsbgp4mpePeerIpPrefixNameOut
           DisplayString
    }

fsbgp4mpebgpPeerRemoteAddrType OBJECT-TYPE
    SYNTAX          InetAddressType
    MAX-ACCESS      not-accessible
    STATUS          current
    DESCRIPTION
        "Type of the remote peer"
    ::= { fsbgp4MpeBgpPeerEntry 1 }

fsbgp4mpebgpPeerIdentifier   OBJECT-TYPE
    SYNTAX          InetAddress
    MAX-ACCESS      read-only
    STATUS          current
    DESCRIPTION
        "The BGP Identifier of this entry's BGP peer."
    ::= { fsbgp4MpeBgpPeerEntry 2 }
fsbgp4mpebgpPeerState    OBJECT-TYPE
    SYNTAX      INTEGER {
                    idle(1),
                    connect(2),
                    active(3),
                    opensent(4),
                    openconfirm(5),
                    established(6)
                }
    MAX-ACCESS  read-only
    STATUS      current
    DESCRIPTION
        "The BGP peer connection state."
    ::= { fsbgp4MpeBgpPeerEntry 3 }

fsbgp4mpebgpPeerAdminStatus  OBJECT-TYPE
    SYNTAX          INTEGER {
                        stop(1),
                        start(2),
                        auto-start(3)
                    }
    MAX-ACCESS      read-write
    STATUS          current
    DESCRIPTION
        "The desired state of the BGP connection.  A transition from
        'stop' to 'start' will cause the BGP Start Event to be generated.
        A transition from 'start' to 'stop' will cause the BGP Stop
        Event to be generated.  This parameter can be used to restart BGP
        peer connections. Whenever the 'fsbgp4mpePeerAllowAutomaticStart' is
        enabled, 'fsbgp4mpebgpPeerAdminStatus' will take the value 'auto-start'.
        The peer waits till the IdleHold Timer expires, and then it will 
        proceed to generate the BGP Start Event. 'fsbgp4mpebgpPeerAdminStatus'
        takes the value 'stop' under two circumstances:
        1) Whenever the administrator manually triggers BGP Stop Event.
        2) Whenever the 'fsbgp4mpePeerAllowAutomaticStop' is enabled and also if 
        the IdleHold Timer exceeds its Maximum Threshold value, then BGP Stop 
        Event is issued automatically, without the manual intervention of the
        administrator.
        Care should be used in providing write access
        to this object without adequate authentication."
    ::= { fsbgp4MpeBgpPeerEntry 4 }

fsbgp4mpebgpPeerNegotiatedVersion    OBJECT-TYPE
    SYNTAX                  Integer32
    MAX-ACCESS              read-only
    STATUS                  current
    DESCRIPTION
        "The negotiated version of BGP running between the two peers."
    ::= { fsbgp4MpeBgpPeerEntry 5 }

fsbgp4mpebgpPeerLocalAddr    OBJECT-TYPE
    SYNTAX          InetAddress
    MAX-ACCESS      read-only
    STATUS          current
    DESCRIPTION
        "The local IP address of this entry's BGP connection."
    ::= { fsbgp4MpeBgpPeerEntry 6 }

fsbgp4mpebgpPeerLocalPort    OBJECT-TYPE
    SYNTAX          Integer32 (0..65535)
    MAX-ACCESS      read-only
    STATUS          current
    DESCRIPTION
        "The local port for the TCP connection between the BGP peers."
    ::= { fsbgp4MpeBgpPeerEntry 7 }

fsbgp4mpebgpPeerRemoteAddr   OBJECT-TYPE
    SYNTAX          InetAddress
    MAX-ACCESS      not-accessible
    STATUS          current
    DESCRIPTION
        "The remote IP address of this entry's BGP peer."
    ::= { fsbgp4MpeBgpPeerEntry 8 }

fsbgp4mpebgpPeerRemotePort   OBJECT-TYPE
    SYNTAX          Integer32 (0..65535)
    MAX-ACCESS      read-only
    STATUS          current
    DESCRIPTION
        "The remote port for the TCP connection between the BGP peers.
        Note that the objects bgpPeerLocalAddr, bgpPeerLocalPort,
        bgpPeerRemoteAddr and bgpPeerRemotePort provide the appropriate
        reference to the standard MIB TCP connection table."
    ::= { fsbgp4MpeBgpPeerEntry 9 }

fsbgp4mpebgpPeerRemoteAs OBJECT-TYPE
    SYNTAX      Unsigned32 (0..4294967295)
    MAX-ACCESS  read-only
    STATUS      current
    DESCRIPTION
        "The remote autonomous system number."
    ::= { fsbgp4MpeBgpPeerEntry 10 }

fsbgp4mpebgpPeerInUpdates    OBJECT-TYPE
    SYNTAX          Counter32
    MAX-ACCESS      read-only
    STATUS          current
    DESCRIPTION
        "The number of BGP UPDATE messages received on this connection.
        This object should be initialized to zero (0) when the connection
        is established."
    ::= { fsbgp4MpeBgpPeerEntry 11 }

fsbgp4mpebgpPeerOutUpdates   OBJECT-TYPE
    SYNTAX          Counter32
    MAX-ACCESS      read-only
    STATUS          current
    DESCRIPTION
        "The number of BGP UPDATE messages transmitted on this connection.
        This object should be initialized to zero (0) when the connection
        is established."
    ::= { fsbgp4MpeBgpPeerEntry 12 }

fsbgp4mpebgpPeerInTotalMessages  OBJECT-TYPE
    SYNTAX              Counter32
    MAX-ACCESS          read-only
    STATUS              current
    DESCRIPTION
        "The total number of messages received from the remote peer on this
        connection.  This object should be initialized to zero when the
        connection is established."
    ::= { fsbgp4MpeBgpPeerEntry 13 }
fsbgp4mpebgpPeerOutTotalMessages OBJECT-TYPE
    SYNTAX              Counter32
    MAX-ACCESS          read-only
    STATUS              current
    DESCRIPTION
        "The total number of messages transmitted to the remote peer on
         this connection.  This object should be initialized to zero when
        the connection is established."
    ::= { fsbgp4MpeBgpPeerEntry 14 }

fsbgp4mpebgpPeerLastError    OBJECT-TYPE
    SYNTAX          OCTET STRING (SIZE (2))
    MAX-ACCESS      read-only
    STATUS          current
    DESCRIPTION
        "The last error code and subcode seen by this peer on this connection.
        If no error has occurred, this field is zero.  Otherwise, the first
        byte of this two byte OCTET STRING contains the error code, and the
        second byte contains the subcode."
    ::= { fsbgp4MpeBgpPeerEntry 15 }

fsbgp4mpebgpPeerFsmEstablishedTransitions    OBJECT-TYPE
    SYNTAX                          Counter32
    MAX-ACCESS                      read-only
    STATUS                          current
    DESCRIPTION
        "The total number of times the BGP FSM transitioned into the
        established state."
    ::= { fsbgp4MpeBgpPeerEntry 16 }
fsbgp4mpebgpPeerFsmEstablishedTime   OBJECT-TYPE
    SYNTAX                  Gauge32
    MAX-ACCESS              read-only
    STATUS                  current
    DESCRIPTION
        "This timer indicates how long (in seconds) this peer has been in the
         Established state or how long since this peer was last in the
         Established state.  It is set to zero when a new peer is configured
         or the router is booted."
    ::= { fsbgp4MpeBgpPeerEntry 17 }

fsbgp4mpebgpPeerConnectRetryInterval OBJECT-TYPE
    SYNTAX                  Integer32 (1..65535)
    MAX-ACCESS              read-write
    STATUS                  current
    DESCRIPTION
        "Time interval in seconds for the ConnectRetry timer.  The suggested
        value for this timer is 120 seconds."
    ::= { fsbgp4MpeBgpPeerEntry 18 }
fsbgp4mpebgpPeerHoldTime     OBJECT-TYPE
    SYNTAX          Integer32  ( 0 | 3..65535 )
    MAX-ACCESS      read-only
    STATUS          current
    DESCRIPTION
        "Time interval in seconds for the Hold Timer established with the
        peer.  The value of this object is calculated by this BGP speaker
        by using the smaller of the value in bgpPeerHoldTimeConfigured and
        the Hold Time received in the OPEN message.  This value must be at
        lease three seconds if it is not zero (0) in which case the Hold
        Timer has not been established with the peer, or, the value of
        bgpPeerHoldTimeConfigured is zero (0)."
    ::= { fsbgp4MpeBgpPeerEntry 19 }

fsbgp4mpebgpPeerKeepAlive    OBJECT-TYPE
    SYNTAX          Integer32 ( 0 | 1..21845 )
    MAX-ACCESS      read-only
    STATUS          current
    DESCRIPTION
        "Time interval in seconds for the KeepAlive timer established with
        the peer.  The value of this object is calculated by this BGP
        speaker such that, when compared with bgpPeerHoldTime, it has the
        same proportion as what bgpPeerKeepAliveConfigured has when compared
        with bgpPeerHoldTimeConfigured.  If the value of this object is
        zero (0), it indicates that the KeepAlive timer has not been
        established with the peer, or, the value of bgpPeerKeepAliveConfigured
        is zero (0)."
   ::= { fsbgp4MpeBgpPeerEntry 20 }
fsbgp4mpebgpPeerHoldTimeConfigured   OBJECT-TYPE
    SYNTAX                  Integer32 ( 0 | 3..65535 )
    MAX-ACCESS              read-write
    STATUS                  current
    DESCRIPTION
        "Time interval in seconds for the Hold Time configured for this
        BGP speaker with this peer.  This value is placed in an OPEN
        message sent to this peer by this BGP speaker, and is compared
        with the Hold Time field in an OPEN message received from the peer
        when determining the Hold Time (bgpPeerHoldTime) with the peer.
        This value must not be less than three seconds if it is not zero (0)
        in which case the Hold Time is NOT to be established with the peer.
        The suggested value for this timer is 90 seconds."
    ::= { fsbgp4MpeBgpPeerEntry 21 }

fsbgp4mpebgpPeerKeepAliveConfigured  OBJECT-TYPE
    SYNTAX                  Integer32 ( 0 | 1..21845 )
    MAX-ACCESS              read-write
    STATUS                  current
    DESCRIPTION
        "Time interval in seconds for the
         KeepAlive timer configured for this BGP
         speaker with this peer.  The value of this
         object will only determine the
         KEEPALIVE messages' frequency relative to
         the value specified in
         bgpPeerHoldTimeConfigured; the actual
         time interval for the KEEPALIVE messages
         is indicated by bgpPeerKeepAlive.  A
         reasonable maximum value for this timer
         would be configured to be one
         third of that of
         bgpPeerHoldTimeConfigured.
         If the value of this object is zero (0),
         now periodical KEEPALIVE messages are sent
         to the peer after the BGP connection has
         been established.  The suggested value for
         this timer is 30 seconds."
    ::= { fsbgp4MpeBgpPeerEntry 22 }

fsbgp4mpebgpPeerMinASOriginationInterval OBJECT-TYPE
    SYNTAX                      Integer32 (1..65535)
    MAX-ACCESS                  read-write
    STATUS                      current
    DESCRIPTION
        "Time interval in seconds for the
         MinASOriginationInterval timer.
         The suggested value for this timer is 15
         seconds."
    ::= { fsbgp4MpeBgpPeerEntry 23 }

fsbgp4mpebgpPeerMinRouteAdvertisementInterval    OBJECT-TYPE
    SYNTAX                              Integer32 (1..65535)
    MAX-ACCESS                          read-write
    STATUS                              current
    DESCRIPTION
        "Time interval in seconds for the
         MinRouteAdvertisementInterval timer.
         The suggested value for this timer is 30
         seconds."
    ::= { fsbgp4MpeBgpPeerEntry 24 }
fsbgp4mpebgpPeerInUpdateElapsedTime  OBJECT-TYPE
    SYNTAX                  Gauge32
    MAX-ACCESS              read-only
    STATUS                  current
    DESCRIPTION
        "Elapsed time in seconds since the last BGP
         UPDATE message was received from the peer.
         Each time bgpPeerInUpdates is incremented,
         the value of this object is set to zero
         (0)."
    ::= { fsbgp4MpeBgpPeerEntry 25 }

fsbgp4mpebgpPeerEndOfRIBMarkerSentStatus  OBJECT-TYPE
    SYNTAX          INTEGER {
                           none(0), --  if GR capability is not enabled
                           true(1),-- End-Of-RIB marker not sent to peer
                           false(2) -- End-Of-RIB marker sent to peer
                    }
    MAX-ACCESS              read-only
    STATUS                  current
    DESCRIPTION
    "This object indicates that whether the End-Of-RIB marker sent to peer or not"
    ::= { fsbgp4MpeBgpPeerEntry 26 }

fsbgp4mpebgpPeerEndOfRIBMarkerReceivedStatus  OBJECT-TYPE
    SYNTAX          INTEGER {
                           none(0),-- If GR capability is not enabled
                           true(1),-- End-Of-RIB marker not received from peer
                           false(2) -- End-Of-RIB marker received from peer
                    }
    MAX-ACCESS              read-only
    STATUS                  current
    DESCRIPTION
    "This object indicates that whether the End-Of-RIB marker received from peer or not"
    ::= { fsbgp4MpeBgpPeerEntry 27 }

fsbgp4mpebgpPeerRestartMode  OBJECT-TYPE
    SYNTAX    INTEGER {
                    restarting (1),
                    receiving (2),
	            none(3)	
              }
    MAX-ACCESS              read-only
    STATUS                  current
    DESCRIPTION
    "This object indicates whether the peer BGP speaker is restarting speaker or receiving speaker or not having GR capability"
    ::= { fsbgp4MpeBgpPeerEntry 28 }

fsbgp4mpePeerRestartTimeInterval    OBJECT-TYPE 
    SYNTAX  Integer32 (1..4096)
    MAX-ACCESS  read-only
    STATUS      current 
    DESCRIPTION 
    "This is the time (in seconds) received from peer through GR capability of open message. This is used in receiving speaker to make sure that the restarting speaker restarted within this interval"
    ::= { fsbgp4MpeBgpPeerEntry 29 }

fsbgp4mpePeerAllowAutomaticStart    OBJECT-TYPE
        SYNTAX          INTEGER {
                                enable(1),
                                disable(2)
                                }
        MAX-ACCESS      read-write
        STATUS          current
        DESCRIPTION
        "This MIB object specifies whether BGP session with the associated peer
          can be started automatically. This object when set to 'disabled',
          requires manual start for initiating BGP session with the peer via
          MIB object 'fsbgp4mpebgpPeerAdminStatus'. When set to 'enabled',
          the peer session can be automatically started in the IDLE state,
          after a BGP Peer session is brought down either by Autostop or via
          reception of invalid BGP message. The BGP session will be automatically
          started after an interval specified by
          'fsbgp4mpebgpPeerIdleHoldTimeConfigured'. If
          fsbgp4mpeDampPeerOscillations is enabled, then automaticStart will not
          occur if peer is damped."

        DEFVAL { disable }
        ::= { fsbgp4MpeBgpPeerEntry 30 }

fsbgp4mpePeerAllowAutomaticStop      OBJECT-TYPE
        SYNTAX          INTEGER {
                                enable(1),
                                disable(2)
                                }
        MAX-ACCESS      read-write
        STATUS          current
        DESCRIPTION
        " This MIB object specifies whether a BGP connection needs to be
        automatically stopped after a TCP connect-retry count value specified
        by MIB object 'fsbgp4mpePeerTcpConnectRetryCnt'. The resources
        allocated for the BGP peer are released and it continues to remain in
        IDLE state. After an automatic stop, the Peer connection needs to be 
        re-intiated manually by the administrator. When AutomaticStop is
        disabled, the connect retry count value is set to 0."


        DEFVAL { disable }
        ::= {  fsbgp4MpeBgpPeerEntry 31 }

fsbgp4mpebgpPeerIdleHoldTimeConfigured   OBJECT-TYPE
        SYNTAX                  Integer32 ( 1..65535 )
        MAX-ACCESS              read-write
        STATUS                  current
        DESCRIPTION
        "IdleHoldTime specifies the length of time the BGP peer is held in the
        Idle state prior to allowing the next automatic restart.
        The IdleHoldTime is configured only when the
        fsbgp4mpePeerAllowAutomaticStart is Enabled or when the
        fsbgp4mpeDampPeerOscillations is Enabled. The configurable value
        differs based on the two options that are enabled.The Suggested default
        value is 60 secs for automatic start and after each dampening, the value
        of the IdleHoldTime is doubled consecutively." 
      
        DEFVAL { 60 }
        ::= {  fsbgp4MpeBgpPeerEntry 32 }


fsbgp4mpeDampPeerOscillations    OBJECT-TYPE
        SYNTAX          INTEGER {
                                enable(1),
                                disable(2)
                                }
        MAX-ACCESS      read-write
        STATUS          current
        DESCRIPTION
        "The DampPeerOscillations option specifies that the implementation
        engages additional logic to damp the oscillations of BGP peers in
        the face of series of automatic start and automatic stop operations
        in the IDLE state.The DampPeerOscillations option indicates that the
        BGP connection is using logic that damps BGP peer oscillations in
        states other than 'established' state."


        DEFVAL { disable }
        ::= {  fsbgp4MpeBgpPeerEntry 33 }

fsbgp4mpePeerDelayOpen          OBJECT-TYPE
        SYNTAX          INTEGER {
                                enable(1),
                                disable(2)
                                }
        MAX-ACCESS      read-write
        STATUS          current
        DESCRIPTION
        "This MIB object allows configuration option to enable/disable delay
        in sending of OPEN messages to the BGP peer for a specific time period
        (DelayOpenTime). The delay allows the remote BGP Peer to send the first
        OPEN message."

        
        DEFVAL { disable }
        ::= {  fsbgp4MpeBgpPeerEntry 34 }

fsbgp4mpebgpPeerDelayOpenTimeConfigured  OBJECT-TYPE
        SYNTAX                  Integer32 ( 0..65535 )
        MAX-ACCESS              read-write
        STATUS                  current
        DESCRIPTION
        "The DelayOpen time specifies the amount of time the BGP Peer should
        delay in sending the OPEN message to the remote peer. If the
        fsbgp4mpePeerDelayOpen option is enabled, the DelayOpen time can bei
        configured. The default value is kept as 0 secs, which implies thati
        the BGP Peer can send an OPEN message without any delay to its
        neighbor."
    
        DEFVAL { 0 }
        ::= {  fsbgp4MpeBgpPeerEntry 35 }

fsbgp4mpePeerPrefixUpperLimit     OBJECT-TYPE
        SYNTAX                  Integer32 (1..5000)
        MAX-ACCESS              read-write
        STATUS                  current
        DESCRIPTION
        "BGP speaker imposes a locally-configured, upper bound on the number of
        address prefixes the speaker is willing to accept from a neighbor. The
        default value is calculated as the following: 

        fsbgp4MaxNoofRoutes / fsbgp4MaxPeerEntry

        Administrator can configure a value less than the default value at
        runtime. Prefixes exceeding the PrefixUpperLimit will not be processedi
        by the system."
        DEFVAL { 100 }
        ::= {fsbgp4MpeBgpPeerEntry 36}

fsbgp4mpePeerTcpConnectRetryCnt  OBJECT-TYPE
        SYNTAX          Integer32 (1..50)
        MAX-ACCESS          read-write
        STATUS              current
        DESCRIPTION
        "This counter denotes the Maximum number of times the BGP Peer has
        tried to issue a TCP-Connect with its neighboring peers.
        The default value for the counter is set as 5." 
        DEFVAL { 5 }
        ::= {fsbgp4MpeBgpPeerEntry 37}


fsbgp4mpePeerTcpCurrentConnectRetryCnt  OBJECT-TYPE
        SYNTAX          Integer32 (1..50)
        MAX-ACCESS      read-only
        STATUS              current
        DESCRIPTION
        " This counter denotes the number of times the BGP Peer has tried to
        issue a TCP-Connect with its neighboring peers. It is an internal value.
        It increments for each Autostop event. If the
        'fsbgp4mpePeerTcpCurrentConnectRetryCnt' exceeds the
        'fsbgp4mpePeerTcpConnectRetryCnt'  value, PeerDampening is performed,
        provided the corresponding flag is enabled."
        ::= {fsbgp4MpeBgpPeerEntry 38}

fsbgp4mpeIsPeerDamped       OBJECT-TYPE
        SYNTAX          INTEGER {
                                enable(1),
                                disable(2)
                                }
        MAX-ACCESS      read-only
        STATUS          current
        DESCRIPTION
        "This MIB object specifies the PeerDamped Status. If it is enabled, it
        denotes that the peer is in damped state. If it is disabled, it
        denotes that either the peer has recovered from the damped state or not
        entered into the Damped state. If enabled and if the IdleHold Timer
        Threshold value is exceeded, issue Manual Stop, reset the 
        fsbgp4mpePeerTcpCurrentConnectRetryCnt value to zero and disable the 
        fsbgp4mpePeerAllowAutomaticStart."

        DEFVAL { disable }
        ::= {  fsbgp4MpeBgpPeerEntry 39 }

fsbgp4mpePeerSessionAuthStatus OBJECT-TYPE
        SYNTAX      INTEGER {
                            no-session (1),
                            authenticatedMd5 (2),
                            unauthenticated (3),
                            authenticatedTcpAo (4)
                            }
       MAX-ACCESS   read-only
       STATUS       current
       DESCRIPTION
       "This object indicates whether peer-session is TCP MD5/TCP-AO
       authenticated or not. If no session is established yet, its value is
       no-session"
       ::= { fsbgp4MpeBgpPeerEntry 40 }

fsbgp4mpePeerTCPAOKeyIdInUse OBJECT-TYPE
       SYNTAX       Integer32 (0 .. 255)
       MAX-ACCESS   read-only
       STATUS       current
       DESCRIPTION
       "Key id of the MKT which is used by the TCP session of the peer, 
        this field will be valid only when value of 
        fsbgp4mpePeerSessionAuthStatus is authenticated-tcp-ao"
       ::= { fsbgp4MpeBgpPeerEntry 41 }

fsbgp4mpePeerTCPAOAuthNoMKTDiscard OBJECT-TYPE
       SYNTAX      INTEGER
       {
           accept (1),
           discard (2)
       }
       MAX-ACCESS  read-write
       STATUS      current
       DESCRIPTION
       "Discard packet for the peer, if packets are received with TCP-AO
       and no matching MKT is found, default value is accept"
       DEFVAL { accept }
       ::=  { fsbgp4MpeBgpPeerEntry 42 }

fsbgp4mpePeerTCPAOAuthICMPAccept OBJECT-TYPE
       SYNTAX      INTEGER
       {
           accept (1),
           ignore (2)
       }
       MAX-ACCESS  read-write
       STATUS      current
       DESCRIPTION
       "Accept ICMPv4 type 3 & ICMPv6 type 1 messages for the TCP-AO 
       authenticated peer, default value is ignore"
       DEFVAL { ignore }
       ::=  { fsbgp4MpeBgpPeerEntry 43 }

fsbgp4mpePeerIpPrefixNameIn OBJECT-TYPE
    SYNTAX              DisplayString
    MAX-ACCESS          read-write
    STATUS              current
    DESCRIPTION
        "This object is used to configure the IP Prefix list name in IN direction for this peer entry."
    ::= { fsbgp4MpeBgpPeerEntry 44 }

fsbgp4mpePeerIpPrefixNameOut OBJECT-TYPE
    SYNTAX              DisplayString
    MAX-ACCESS          read-write
    STATUS              current
    DESCRIPTION
        "This object is used to configure the IP Prefix list name in OUT direction for this peer entry."
    ::= { fsbgp4MpeBgpPeerEntry 45 }

-- BGP4 Received Path Attribute Table.  This table
-- contains, one entry per path to a network, path
-- attributes received from all peers running BGP-4.

fsbgp4MpeBgp4PathAttrTable   OBJECT-TYPE
    SYNTAX          SEQUENCE OF Fsbgp4MpeBgp4PathAttrEntry
    MAX-ACCESS      not-accessible
    STATUS          current
    DESCRIPTION
        "The BGP-4 Received Path Attribute Table
         contains information about paths to
         destination networks received from all
         BGP4 peers."
    ::= { fsbgp 20 }
fsbgp4MpeBgp4PathAttrEntry   OBJECT-TYPE
    SYNTAX          Fsbgp4MpeBgp4PathAttrEntry
    MAX-ACCESS      not-accessible
    STATUS          current
    DESCRIPTION
        "Information about a path to a network."
    INDEX { fsbgp4mpebgp4PathAttrRouteAfi,
            fsbgp4mpebgp4PathAttrRouteSafi,
            fsbgp4mpebgp4PathAttrIpAddrPrefix,
            fsbgp4mpebgp4PathAttrIpAddrPrefixLen,
            fsbgp4mpebgp4PathAttrPeerType,
            fsbgp4mpebgp4PathAttrPeer
          }
    ::= { fsbgp4MpeBgp4PathAttrTable 1 }

Fsbgp4MpeBgp4PathAttrEntry ::= SEQUENCE {
    fsbgp4mpebgp4PathAttrRouteAfi
        InetAddressType,
    fsbgp4mpebgp4PathAttrRouteSafi
        BgpSafi,
    fsbgp4mpebgp4PathAttrPeerType
        InetAddressType,
    fsbgp4mpebgp4PathAttrPeer
        InetAddress,
    fsbgp4mpebgp4PathAttrIpAddrPrefixLen
        Integer32,
    fsbgp4mpebgp4PathAttrIpAddrPrefix
        InetAddress,
    fsbgp4mpebgp4PathAttrOrigin
        INTEGER,
    fsbgp4mpebgp4PathAttrASPathSegment
        OCTET STRING,
    fsbgp4mpebgp4PathAttrNextHop
        InetAddress,
    fsbgp4mpebgp4PathAttrMultiExitDisc
        Integer32,
    fsbgp4mpebgp4PathAttrLocalPref
        Integer32,
    fsbgp4mpebgp4PathAttrAtomicAggregate
        INTEGER,
    fsbgp4mpebgp4PathAttrAggregatorAS
        Unsigned32,
    fsbgp4mpebgp4PathAttrAggregatorAddr
        IpAddress,
    fsbgp4mpebgp4PathAttrCalcLocalPref
        Integer32,
    fsbgp4mpebgp4PathAttrBest
        INTEGER,
    fsbgp4mpebgp4PathAttrCommunity
        OCTET STRING,
    fsbgp4mpebgp4PathAttrOriginatorId
        OCTET STRING,
    fsbgp4mpebgp4PathAttrClusterList
        OCTET STRING,
    fsbgp4mpebgp4PathAttrExtCommunity
        OCTET STRING,
    fsbgp4mpebgp4PathAttrUnknown
        OCTET STRING,
    fsbgp4mpebgp4PathAttrLabel
        OCTET STRING,
    fsbgp4mpebgp4PathAttrAS4PathSegment
        OCTET STRING,
    fsbgp4mpebgp4PathAttrAggregatorAS4
        Unsigned32
}

fsbgp4mpebgp4PathAttrRouteAfi OBJECT-TYPE
    SYNTAX          InetAddressType
    MAX-ACCESS      not-accessible
    STATUS          current
    DESCRIPTION
        "The AFI of the prefix"
    ::= { fsbgp4MpeBgp4PathAttrEntry 1 }

fsbgp4mpebgp4PathAttrRouteSafi OBJECT-TYPE
    SYNTAX          BgpSafi
    MAX-ACCESS      not-accessible
    STATUS          current
    DESCRIPTION
        "The SAFI of the prefix"
    ::= { fsbgp4MpeBgp4PathAttrEntry 2 }
fsbgp4mpebgp4PathAttrPeerType  OBJECT-TYPE
    SYNTAX          InetAddressType
    MAX-ACCESS      not-accessible
    STATUS          current
    DESCRIPTION
        "The AFI of the peer"
    ::= { fsbgp4MpeBgp4PathAttrEntry 3 }

fsbgp4mpebgp4PathAttrPeer    OBJECT-TYPE
    SYNTAX          InetAddress
    MAX-ACCESS      not-accessible
    STATUS          current
    DESCRIPTION
        "The IP address of the peer where the path
         information was learned."
    ::= { fsbgp4MpeBgp4PathAttrEntry 4 }

fsbgp4mpebgp4PathAttrIpAddrPrefixLen OBJECT-TYPE
    SYNTAX                  Integer32 (0..32)
    MAX-ACCESS              not-accessible
    STATUS                  current
    DESCRIPTION
        "Length in bits of the IP address prefix
         in the Network Layer Reachability
         Information field."
    ::= { fsbgp4MpeBgp4PathAttrEntry 5 }

fsbgp4mpebgp4PathAttrIpAddrPrefix    OBJECT-TYPE
    SYNTAX                  InetAddress
    MAX-ACCESS              not-accessible
    STATUS                  current
    DESCRIPTION
        "An IP address prefix in the Network Layer
         Reachability Information field.  This object
         is an IP address containing the prefix with
         length specified by
         bgp4PathAttrIpAddrPrefixLen.
         Any bits beyond the length specified by
         bgp4PathAttrIpAddrPrefixLen are zeroed."
    ::= { fsbgp4MpeBgp4PathAttrEntry 6 }

fsbgp4mpebgp4PathAttrOrigin  OBJECT-TYPE
    SYNTAX          INTEGER {
                        igp(1),-- networks are interior
                        egp(2),-- networks learned via EGP
                        incomplete(3) -- undetermined
                    }
    MAX-ACCESS      read-only
    STATUS          current
    DESCRIPTION
        "The ultimate origin of the path
         information."
    ::= { fsbgp4MpeBgp4PathAttrEntry 7 }

fsbgp4mpebgp4PathAttrASPathSegment   OBJECT-TYPE
    SYNTAX                  OCTET STRING (SIZE (2..255))
    MAX-ACCESS              read-only
    STATUS                  current
    DESCRIPTION
        "The sequence of AS path segments.  Each AS
         path segment is represented by a triple
         <type, length, value>.
         The type is a 1-octet field which has two
         possible values:
         1      AS_SET: unordered set of ASs, traversed by a
                route in the UPDATE message.
         2      AS_SEQUENCE: ordered set of ASs, traversed by
                a route in the UPDATE message.
         The length is a 1-octet field containing the
         number of ASs in the value field.
         The value field contains one or more AS
         numbers, each AS is represented in the octet
         string as a pair of octets according to the
         following algorithm:
         first-byte-of-pair = ASNumber / 256;
         second-byte-of-pair = ASNumber & 255;"
    ::= { fsbgp4MpeBgp4PathAttrEntry 8 }

fsbgp4mpebgp4PathAttrNextHop OBJECT-TYPE
    SYNTAX          InetAddress
    MAX-ACCESS      read-only
    STATUS          current
    DESCRIPTION
        "The address of the border router that
         should be used for the destination network."
    ::= { fsbgp4MpeBgp4PathAttrEntry 9 }

fsbgp4mpebgp4PathAttrMultiExitDisc   OBJECT-TYPE
    SYNTAX                  Integer32 (-1..2147483647)
    MAX-ACCESS              read-only
    STATUS                  current
    DESCRIPTION
        "This metric is used to discriminate
         between multiple exit points to an
         adjacent autonomous system.  A value of -1
         indicates the absence of this attribute."
    ::= { fsbgp4MpeBgp4PathAttrEntry 10 }

fsbgp4mpebgp4PathAttrLocalPref   OBJECT-TYPE
    SYNTAX              Integer32 (-1..2147483647)
    MAX-ACCESS          read-only
    STATUS              current
    DESCRIPTION
        "The originating BGP4 speaker's degree of
         preference for an advertised route.  A
         value of -1 indicates the absence of this
         attribute."
    ::= { fsbgp4MpeBgp4PathAttrEntry 11 }


fsbgp4mpebgp4PathAttrAtomicAggregate OBJECT-TYPE
    SYNTAX                  INTEGER {
                                lessSpecificRrouteNotSelected(1),
                                lessSpecificRouteSelected(2)
                            }
    MAX-ACCESS              read-only
    STATUS                  current
    DESCRIPTION
        "Whether or not the local system has
         selected a less specific route without
         selecting a more specific route."
    ::= { fsbgp4MpeBgp4PathAttrEntry 12 }

fsbgp4mpebgp4PathAttrAggregatorAS    OBJECT-TYPE
    SYNTAX                  Unsigned32 (0..4294967295)
    MAX-ACCESS              read-only
    STATUS                  current
    DESCRIPTION
        "The AS number of the last BGP4 speaker that
         performed route aggregation.  A value of
         zero (0) indicates the absence of this
         attribute."
    ::= { fsbgp4MpeBgp4PathAttrEntry 13 }

fsbgp4mpebgp4PathAttrAggregatorAddr  OBJECT-TYPE
    SYNTAX                  IpAddress
    MAX-ACCESS              read-only
    STATUS                  current
    DESCRIPTION
        "The IP address of the last BGP4 speaker
         that performed route aggregation.  A value
         of 0.0.0.0 indicates the absence of this
         attribute."
    ::= { fsbgp4MpeBgp4PathAttrEntry 14 }

fsbgp4mpebgp4PathAttrCalcLocalPref   OBJECT-TYPE
    SYNTAX                  Integer32 (-1..2147483647)
    MAX-ACCESS              read-only
    STATUS                  current
    DESCRIPTION
        "The degree of preference calculated by the
         receiving BGP4 speaker for an advertised
         route.  A value of -1 indicates the
         absence of this attribute."
    ::= { fsbgp4MpeBgp4PathAttrEntry 15 }

fsbgp4mpebgp4PathAttrBest    OBJECT-TYPE
    SYNTAX          INTEGER {
                        nonbest(1),-- not chosen as best route
                        best(2), -- chosen as best route
                        stale(3) -- chosen as stale route
                    }
    MAX-ACCESS      read-only
    STATUS          current
    DESCRIPTION
        "An indication of whether or not this route
         was chosen as the best BGP4 route."
    ::= { fsbgp4MpeBgp4PathAttrEntry 16 }

fsbgp4mpebgp4PathAttrCommunity OBJECT-TYPE
    SYNTAX          OCTET STRING (SIZE(0..800))
    MAX-ACCESS      read-only
    STATUS          current
    DESCRIPTION
        "The community values received for this destinatin
        from the peer"
    ::= { fsbgp4MpeBgp4PathAttrEntry 17 }

fsbgp4mpebgp4PathAttrOriginatorId OBJECT-TYPE
    SYNTAX          OCTET STRING (SIZE(4))
    MAX-ACCESS      read-only
    STATUS          current
    DESCRIPTION
        "The Originator-ID identifying the router that initially
       advertised this destination to a Route Reflector.
       A value of 0.0.0.0 indicates the absence of this attribute"
    REFERENCE
        "This attribute is defined in [RFC 2796]"
    ::= { fsbgp4MpeBgp4PathAttrEntry 18 }

fsbgp4mpebgp4PathAttrClusterList OBJECT-TYPE
    SYNTAX          OCTET STRING (SIZE(0..4096))
    MAX-ACCESS      read-only
    STATUS          current
    DESCRIPTION
        "A sequence of four octet long values Cluster-IDs representing
        the reflection path that the route has passed. Each four octet
        long value represents the ID of a cluster that the route has
        traversed. A length of zero (0) indicates the absence of this
        attibute."
    REFERENCE
        "This attribute is defined in [RFC 2796]"
    ::= { fsbgp4MpeBgp4PathAttrEntry 19 }

fsbgp4mpebgp4PathAttrExtCommunity OBJECT-TYPE
    SYNTAX          OCTET STRING (SIZE(0..800))
    MAX-ACCESS      read-only
    STATUS          current
    DESCRIPTION
        "The extended community values received for this
        destinatin from the peer"
    ::= { fsbgp4MpeBgp4PathAttrEntry 20 }

fsbgp4mpebgp4PathAttrUnknown OBJECT-TYPE
    SYNTAX          OCTET STRING (SIZE(0..255))
    MAX-ACCESS      read-only
    STATUS          current
    DESCRIPTION
        "One or more path attributes not understood
            by this BGP4 speaker.  Size zero (0)
         indicates the absence of such
         attribute(s).  Octets beyond the maximum
         size, if any, are not recorded by this
         object."
    ::= { fsbgp4MpeBgp4PathAttrEntry 21 }

fsbgp4mpebgp4PathAttrLabel  OBJECT-TYPE
    SYNTAX          OCTET STRING (SIZE(0..24))
    MAX-ACCESS      read-only
    STATUS          current
    DESCRIPTION
         "MPLS Label received for this destination from the peer "
    ::= { fsbgp4MpeBgp4PathAttrEntry 22 }

fsbgp4mpebgp4PathAttrAS4PathSegment   OBJECT-TYPE
    SYNTAX                  OCTET STRING (SIZE (2..255))
    MAX-ACCESS              read-only
    STATUS                  current
    DESCRIPTION
        "The sequence of AS path segments.  Each AS
         path segment is represented by a triple
         <type, length, value>.
         The type is a 1-octet field which has two
         possible values:
         1      AS_SET: unordered set of ASs, traversed by a
                route in the UPDATE message.
         2      AS_SEQUENCE: ordered set of ASs, traversed by
                a route in the UPDATE message.
         The length is a 1-octet field containing the
         number of ASs in the value field.
         The value field contains one or more AS
         numbers, each AS is represented in the octet
         string as 2 pairs of octets."
    REFERENCE
        "This attribute is defined in [RFC 6793]"
    ::= { fsbgp4MpeBgp4PathAttrEntry 23 }

fsbgp4mpebgp4PathAttrAggregatorAS4    OBJECT-TYPE
    SYNTAX                  Unsigned32 (0..4294967295)
    MAX-ACCESS              read-only
    STATUS                  current
    DESCRIPTION
        "The 4 Byte AS number of the last BGP4 speaker that
         performed route aggregation.  A value of
         zero (0) indicates the absence of this
         attribute."
    REFERENCE
        "This attribute is defined in [RFC 6793]"
    ::= { fsbgp4MpeBgp4PathAttrEntry 24 }

-- MIB FOR FSBGP_PEER_EXTENSIONS_TABLE BEGIN

-- This table is an Extension to the bgpPeerTable from stdbgp4.mib.
-- This table contains, one entry per BGP peer, information
-- about the BGP peer.

fsbgp4MpePeerExtTable          OBJECT-TYPE
    SYNTAX                  SEQUENCE OF Fsbgp4MpePeerExtEntry
    MAX-ACCESS              not-accessible
    STATUS                  current
    DESCRIPTION
    "BGP Peer Extension Table. The entries in the table specifies
     the additional features supported for a peer by futureBGP4
     Speaker in addition to the features specified as in bgpPeerTable
     (described in  stdbgp4.mib.). All entries in this table can be
     configured only if fsbgp4LocalAs has be configured."
    ::= { fsbgp 21 }

fsbgp4MpePeerExtEntry          OBJECT-TYPE
    SYNTAX                  Fsbgp4MpePeerExtEntry
    MAX-ACCESS              not-accessible
    STATUS                  current
    DESCRIPTION
    "Entry containing information about the additional features supported
     for a peer by futureBGP4 Speaker."
    INDEX {fsbgp4mpePeerExtPeerType,
        fsbgp4mpePeerExtPeerRemoteAddr }
    ::= { fsbgp4MpePeerExtTable 1 }

Fsbgp4MpePeerExtEntry ::=    SEQUENCE {
                                fsbgp4mpePeerExtPeerType
                                    InetAddressType,
                                fsbgp4mpePeerExtPeerRemoteAddr
                                    InetAddress,
                                fsbgp4mpePeerExtConfigurePeer
                                    INTEGER,
                                fsbgp4mpePeerExtPeerRemoteAs
                                    Unsigned32,
                                fsbgp4mpePeerExtEBGPMultiHop
                                    INTEGER,
                                fsbgp4mpePeerExtEBGPHopLimit
                                    Integer32,
                                fsbgp4mpePeerExtNextHopSelf
                                    INTEGER,
                                fsbgp4mpePeerExtRflClient
                                    INTEGER,
                                fsbgp4mpePeerExtTcpSendBufSize
                                    Integer32,
                                fsbgp4mpePeerExtTcpRcvBufSize
                                    Integer32,
                                fsbgp4mpePeerExtLclAddress
                                    InetAddress,
                                fsbgp4mpePeerExtNetworkAddress
                                    InetAddress,
                                fsbgp4mpePeerExtGateway
                                    InetAddress,
                                fsbgp4mpePeerExtCommSendStatus
                                    INTEGER,
                                fsbgp4mpePeerExtECommSendStatus
                                    INTEGER,
                                fsbgp4mpePeerExtPassive
                                    INTEGER,
                                fsbgp4mpePeerExtDefaultOriginate
                                    INTEGER,
                                fsbgp4mpePeerExtActivateMPCapability
                                    INTEGER,
                                fsbgp4mpePeerExtDeactivateMPCapability
                                    INTEGER,
                                fsbgp4mpePeerExtMplsVpnVrfAssociated
                                    DisplayString,
                                fsbgp4mpePeerExtMplsVpnCERouteTargetAdvt
                                    INTEGER,
                                fsbgp4mpePeerExtMplsVpnCESiteOfOrigin
                                   DisplayString
                            }

fsbgp4mpePeerExtPeerType           OBJECT-TYPE
    SYNTAX                      InetAddressType
    MAX-ACCESS                  not-accessible
    STATUS                      current
    DESCRIPTION
    "The Type of the remote peer "
    ::= { fsbgp4MpePeerExtEntry 1 }

fsbgp4mpePeerExtPeerRemoteAddr     OBJECT-TYPE
    SYNTAX                      InetAddress
    MAX-ACCESS                  not-accessible
    STATUS                      current
    DESCRIPTION
    "The remote IP address of this entry's BGP peer."
    ::= { fsbgp4MpePeerExtEntry 2 }

fsbgp4mpePeerExtConfigurePeer     OBJECT-TYPE
    SYNTAX                     INTEGER
                               {
                                   create (1),
                                   delete (2)
                               }
    MAX-ACCESS                 read-write
    STATUS                     current
    DESCRIPTION
    "This object is used to create or delete a peer. If called with create
     and no matching peer exists, then a new peer entry will be created. The
     admin status of this newly created peer will be stop. To enable the peer
     set the peers remote AS (fsbgp4mpePeerExtPeerRemoteAS)and change the peer's
     admin state (bgpPeerAdminState in stdbgp4.mib) to start. If this object
     is called with create and a matching peer exists, then no action is done.
     If called with delete and if a matching peer exists, then the complete
     instance associated with that peer will be deleted."
    ::= { fsbgp4MpePeerExtEntry 3 }

fsbgp4mpePeerExtPeerRemoteAs   OBJECT-TYPE
    SYNTAX                  Unsigned32 (1..4294967295)
    MAX-ACCESS              read-write
    STATUS                  current
    DESCRIPTION
    "The remote autonomous system number of the Peer. The peer admin status
     can be made up only if this object is configured for a valid AS number.
     When OPEN message is received from this peer during the BGP Connection
     establishment, this configured AS value is compared against the AS number
     received in the OPEN message. If both matches, then connection
     establishment continues. If there is any mismatch, then the connection is
     terminated. This object can be set only when the peer's admin status is 
     down."
    ::= { fsbgp4MpePeerExtEntry 4 } 

fsbgp4mpePeerExtEBGPMultiHop   OBJECT-TYPE
    SYNTAX                  INTEGER
                            {
                               enable(1),
                               disable(2)
                            }
    MAX-ACCESS              read-write
    STATUS                  current
    DESCRIPTION
    "This objects enables the BGP4 Speaker to accept or attempt
     connections to external peers residing on network that are not directly
     connected. By default, only directly connected EBGP peers are allowed.
     For the internal peers, this object has no effect."
    DEFVAL { disable }
    ::= { fsbgp4MpePeerExtEntry 5 }

fsbgp4mpePeerExtEBGPHopLimit   OBJECT-TYPE
    SYNTAX                  Integer32 (1..255)
    MAX-ACCESS              read-write
    STATUS                  current
    DESCRIPTION
    "This objects enables the BGP4 Speaker to accept or attempt
     connections to external peers residing on network that are not directly
     connected and seperated by a maximum hop limit as configured by this
     object.  For the internal peers, this object has no effect."
    DEFVAL { 1 }
    ::= { fsbgp4MpePeerExtEntry 6 }

fsbgp4mpePeerExtNextHopSelf    OBJECT-TYPE
    SYNTAX                  INTEGER 
                            {
                                automatic(1),
                                self(2) 
                            }
    MAX-ACCESS  read-write
    STATUS      current
    DESCRIPTION
    "This object specifies how the next hop attribute sent in the update 
     messages to this peer has to be generated.  When the object takes the
     value of self,the next Hop attribute will always be the sender Local
     Address else the next hop will be generated based on the IP address of
     the destination and the present next hop in the route information."
    DEFVAL { automatic }
    ::= { fsbgp4MpePeerExtEntry 7 }

fsbgp4mpePeerExtRflClient      OBJECT-TYPE
    SYNTAX                  INTEGER
                            {
    	                        nonClient (1),
                                client (2)
                            } 
    MAX-ACCESS          read-write
    STATUS              current
	DESCRIPTION  
    "This object specifies whether the peer is Client peer or Non-Client
    peer. By default, the peer is created as Non-Client Peer."
	DEFVAL				{1}
	::= {fsbgp4MpePeerExtEntry 8 }

fsbgp4mpePeerExtTcpSendBufSize   OBJECT-TYPE
    SYNTAX                    Integer32 (4096..65536)
    MAX-ACCESS                read-write
    STATUS                    current
    DESCRIPTION
    "This object configures the tcp window size on the sender side." 
    DEFVAL { 65536 }
    ::= { fsbgp4MpePeerExtEntry 9 }

fsbgp4mpePeerExtTcpRcvBufSize   OBJECT-TYPE
    SYNTAX                    Integer32 (4096..65536)
    MAX-ACCESS                read-write
    STATUS                    current
    DESCRIPTION
    "This object configures the tcp window size on the receiver side." 
    DEFVAL { 65536 }
    ::= { fsbgp4MpePeerExtEntry 10 }

fsbgp4mpePeerExtLclAddress    OBJECT-TYPE
    SYNTAX                 InetAddress  
    MAX-ACCESS  read-write
    STATUS      current
    DESCRIPTION
    "This object specifies which address should be used as the source address
    of the TCP session initiated with the Peer. By default this object takes
    value as 0 and the source address of the TCP session is filled by TCP.
    This object can take value of any interface address. If this object
    refers to a valid interface address, then the TCP session initiated
    with the peer should have this interface address as the source address."
    ::= { fsbgp4MpePeerExtEntry 11 }

fsbgp4mpePeerExtNetworkAddress    OBJECT-TYPE
    SYNTAX                     InetAddress  
    MAX-ACCESS  read-write
    STATUS      current
    DESCRIPTION
    "This object specifies the remote peer's network address. TCP connection is
     established using the peer's remote-address. If the peer's remote-address
     is a IPv4 address, the peer's network address carries the IPv6 network
     address. Similarly, if the peer's remote-address is a IPv6 address, the
     peer's network address carries the IPv4 network address. This object can
     be configured only after the peer's remote-address and the corresponding
     local interface are configured." 
    ::= { fsbgp4MpePeerExtEntry 12 }

fsbgp4mpePeerExtGateway    OBJECT-TYPE
    SYNTAX              InetAddress  
    MAX-ACCESS  read-write
    STATUS      current
    DESCRIPTION
    "This object specifies  the gateway router's address that will be used as 
     nexthop in the routes advertised to the peer. This ensures that the 
     traffic coming from this peer is routed through this gateway."
    ::= { fsbgp4MpePeerExtEntry 13 }

fsbgp4mpePeerExtCommSendStatus    OBJECT-TYPE
    SYNTAX                     INTEGER {
                                   none (1), 
                                   send (2),
                                   donotsend (3)
                                }
    MAX-ACCESS          read-create
    STATUS              current
    DESCRIPTION 
    "Community Send status of the peer.
       o none       - is for read-only 
       o send       - send communities to this peer
       o donotsend  - do not send communities to this peer."
    DEFVAL { send }
    ::= { fsbgp4MpePeerExtEntry 14 } 

fsbgp4mpePeerExtECommSendStatus OBJECT-TYPE
    SYNTAX                       INTEGER {
                                   none       (1),
                                   send       (2),
                                   donotsend  (3)
                                }
    MAX-ACCESS          read-create
    STATUS              current
    DESCRIPTION 
    "Extended Community Send status of the peer.
       o none     - is for read-only 
       o send       - send extended communities to this peer
       o donotsend  - do not send extended communities to this peer."
    DEFVAL { send }
    ::= { fsbgp4MpePeerExtEntry 15 } 

fsbgp4mpePeerExtPassive        OBJECT-TYPE
    SYNTAX                     INTEGER
                               {
                                   enable (1),
                                   disable (2)
                               }
    MAX-ACCESS                 read-write
    STATUS                     current
    DESCRIPTION
    "This object is used to set a peer connection to be passive, that means
     the speaker will not initiate the session with that peer instead it
     waits for the remote peer to initiate the session"
    ::= { fsbgp4MpePeerExtEntry 16 }

fsbgp4mpePeerExtDefaultOriginate        OBJECT-TYPE
    SYNTAX                           INTEGER
                                     {
                                         enable(1),
                                         disable(2)
                                     }
    MAX-ACCESS                       read-write
    STATUS                           current
    DESCRIPTION
    "If this object is set to enable/disable the advertisement of the default
     route to the peer. This object overrides the global default
     route configuration (fsbgp4DefaultOriginate) and always send a default
     route to the peer with self next-hop. This advertisement occurs
     irrespective of the presence of default route in FDB. This object can
     be set only if the fsbgp4LocalAs is set."
    DEFVAL  { disable }
    ::= { fsbgp4MpePeerExtEntry 17 }

fsbgp4mpePeerExtActivateMPCapability    OBJECT-TYPE
    SYNTAX                           INTEGER
                                     {
                                         ipv4unicast(1),
                                         ipv6unicast(2),
                                         vpnv4unicast(8)
                                     }
    MAX-ACCESS                       read-write
    STATUS                           current
    DESCRIPTION
    "This object is set to activate the corresponding MP Capability.
     If any of MP Capability is activate, then this capability should
     be negotiated while establishing session with this neighbor.
     Any get on this object will return only ZERO."
    ::= { fsbgp4MpePeerExtEntry 18 }

fsbgp4mpePeerExtDeactivateMPCapability    OBJECT-TYPE
    SYNTAX                             INTEGER
                                       {
                                           ipv4unicast(1),
                                           ipv6unicast(2),
                                           vpnv4unicast(8)
                                       }
    MAX-ACCESS                         read-write
    STATUS                             current
    DESCRIPTION
    "This object is set to deactivate the corresponding MP Capability.
     If any of MP Capability is deactivate, then this capability should
     not be negotiated while establishing session with this neighbor.
     Any get on this object will return only ZERO."
    ::= { fsbgp4MpePeerExtEntry 19 }

fsbgp4mpePeerExtMplsVpnVrfAssociated OBJECT-TYPE
    SYNTAX          DisplayString (SIZE (0..16))
    MAX-ACCESS      read-create
    STATUS          current
    DESCRIPTION
    "Denotes the VRF associated with the CE peer. If the Vrf Name 
     is not configured, the peer will be normal peer.
     with respect to this VRF."
    ::= { fsbgp4MpePeerExtEntry 20 } 

fsbgp4mpePeerExtMplsVpnCERouteTargetAdvt   OBJECT-TYPE
    SYNTAX      INTEGER {
                            send (1),
                            donotsend (2)
                        }
    MAX-ACCESS  read-create
    STATUS      current
    DESCRIPTION
    "This variable is used to inform whether the PE can receive Route
     Targets from CE, or PE can send Route Targets(RT) to CE router.
     By default sending RT to CE and receiving RT from CE are disabled."
    DEFVAL {donotsend}
    ::= { fsbgp4MpePeerExtEntry 21 } 

fsbgp4mpePeerExtMplsVpnCESiteOfOrigin OBJECT-TYPE
    SYNTAX      DisplayString (SIZE (0..8))
    MAX-ACCESS  read-create
    STATUS      current
    DESCRIPTION
    "Site Of Origin for the site connected CE peer"
    ::= { fsbgp4MpePeerExtEntry 22 } 

-- MIB FOR FSBGP_PEER_EXTENSIONS_TABLE END

--- Multi-Exit Discriminator Table
--- This table specifies the value that has to be assigned to the
--- Multi-Exit Discriminator attribute when an update is sent.

fsbgp4MpeMEDTable  OBJECT-TYPE
    SYNTAX      SEQUENCE OF Fsbgp4MpeMEDEntry
    MAX-ACCESS  not-accessible
    STATUS      current
    DESCRIPTION
    "BGP4 MED table. This table contains the MED values that are to
     be assigned to routes."
    ::= {fsbgp 22 }

fsbgp4MpeMEDEntry  OBJECT-TYPE
    SYNTAX      Fsbgp4MpeMEDEntry
    MAX-ACCESS  not-accessible
    STATUS      current
    DESCRIPTION
      "Entry containing information about the MED value."
    INDEX  { fsbgp4mpeMEDIndex }
    ::= { fsbgp4MpeMEDTable 1 }

Fsbgp4MpeMEDEntry ::= SEQUENCE {
    fsbgp4mpeMEDIndex
        Integer32,
    fsbgp4mpeMEDAdminStatus
        INTEGER,
    fsbgp4mpeMEDRemoteAS
        Unsigned32,
    fsbgp4mpeMEDIPAddrAfi
        InetAddressType,
    fsbgp4mpeMEDIPAddrSafi
        BgpSafi,
    fsbgp4mpeMEDIPAddrPrefix
        InetAddress,
    fsbgp4mpeMEDIPAddrPrefixLen
        Integer32,
    fsbgp4mpeMEDIntermediateAS
        DisplayString,
    fsbgp4mpeMEDDirection
        INTEGER,
    fsbgp4mpeMEDValue
        Unsigned32,
    fsbgp4mpeMEDPreference
        INTEGER,
    fsbgp4mpeMEDVrfName
        DisplayString
    }

fsbgp4mpeMEDIndex  OBJECT-TYPE
    SYNTAX      Integer32 (1..10)
    MAX-ACCESS  not-accessible 
    STATUS      current
    DESCRIPTION 
      " This is the index to the table. Any entry in the table can be 
        configured only if fsbgp4LocalAs is set."
    ::= { fsbgp4MpeMEDEntry 1 } 

fsbgp4mpeMEDAdminStatus    OBJECT-TYPE
    SYNTAX              INTEGER {
                            up(1),
                            down(2)
                        }
    MAX-ACCESS          read-write
    STATUS              current
    DESCRIPTION
        "The desired state of this entry. The entries in a row are
         configurable only if the admin status is DOWN."
    ::= {fsbgp4MpeMEDEntry 2 }

fsbgp4mpeMEDRemoteAS   OBJECT-TYPE
    SYNTAX          Unsigned32 (0..4294967295)
    MAX-ACCESS      read-write
    STATUS          current
    DESCRIPTION 
    " The remote autonomous system with which this entry is associated.
      A value of zero indicates that this entry is not valid and will not 
      be matched for when the MED value for an update is calculated."
    DEFVAL  { 0 }
    ::= { fsbgp4MpeMEDEntry 3 }

fsbgp4mpeMEDIPAddrAfi      OBJECT-TYPE
    SYNTAX              InetAddressType
    MAX-ACCESS          read-write
    STATUS              current
    DESCRIPTION
    "Type of IP address prefix in the Network Layer Reachability Information
     field in updates. This field needs to be set before setting the object
     fsbgp4mpeMEDIPAddrPrefix."
    ::= { fsbgp4MpeMEDEntry 4 }

fsbgp4mpeMEDIPAddrSafi     OBJECT-TYPE
    SYNTAX              BgpSafi
    MAX-ACCESS          read-write
    STATUS              current
    DESCRIPTION
    "Type of IP address prefix in the Network Layer Reachability Information
     field in updates. This field needs to be set before setting the object
     fsbgp4mpeMEDIPAddrPrefix."
    ::= { fsbgp4MpeMEDEntry 5 }

fsbgp4mpeMEDIPAddrPrefix   OBJECT-TYPE
    SYNTAX              InetAddress
    MAX-ACCESS          read-write
    STATUS              current
    DESCRIPTION
    "An IP address prefix in the Network Layer Reachability Information
     field in updates. A value of zero indicates that the entry is not 
     valid and will not be matched for when the MED value for an update is 
     calculated."
    DEFVAL  { '00000000'H }
    ::= { fsbgp4MpeMEDEntry 6 }

fsbgp4mpeMEDIPAddrPrefixLen    OBJECT-TYPE
    SYNTAX                  Integer32 (0..32)
    MAX-ACCESS              read-write
    STATUS                  current
    DESCRIPTION
    "Length in bits of the IP address prefix in the Network Layer Reachability
     Information field. A value of zero indicates that the entry is not 
     valid and will not be matched for when the MED value for an update is 
     calculated."
    DEFVAL  { 0 }
    ::= { fsbgp4MpeMEDEntry 7 }

fsbgp4mpeMEDIntermediateAS OBJECT-TYPE
    SYNTAX              DisplayString
    MAX-ACCESS          read-write
    STATUS              current
    DESCRIPTION
          "Comma seperated list of AS numbers that are to
           be checked against the AS_PATH attribute of the Update.
           An empty field indicates that the same need not be
           checked for in the update.Maximum configurable size is 100."
    ::= { fsbgp4MpeMEDEntry 8 }

fsbgp4mpeMEDDirection  OBJECT-TYPE
    SYNTAX          INTEGER {
                        in(1),
                        out(2)
                    }
    MAX-ACCESS      read-write
    STATUS          current
    DESCRIPTION
    "The direction of the update with which the entry is to be associated."
    DEFVAL  { in }
   ::= { fsbgp4MpeMEDEntry 9 }

fsbgp4mpeMEDValue  OBJECT-TYPE
    SYNTAX      Unsigned32 ( 0 .. 2147483647 )
    MAX-ACCESS  read-write
    STATUS      current
    DESCRIPTION
    "The value assigned to the MED Attribute for the route present in NLRI"
    DEFVAL   { 0 }
    ::= { fsbgp4MpeMEDEntry 10 }

fsbgp4mpeMEDPreference OBJECT-TYPE
    SYNTAX          INTEGER {
                        false(1),
                        true(2)
                    }
    MAX-ACCESS      read-write
    STATUS          current
    DESCRIPTION
    "This object specifies whether the value present
    in this entry takes precedence when the attribute
    is already present in the update message that has
    been received."
    DEFVAL  { false }
    ::= { fsbgp4MpeMEDEntry 11 } 

fsbgp4mpeMEDVrfName    OBJECT-TYPE
   SYNTAX           DisplayString (SIZE (0..16))
   MAX-ACCESS       read-write
   STATUS           current
   DESCRIPTION
       "The human-readable name of the VPN."
    ::= { fsbgp4MpeMEDEntry 12 }

--  Local Preference Table.
--  This table specifies the value that has to assigned to the
--  Local Preference attribute when an update is sent to an
--  internal Peer or received from an external or internal peer.

fsbgp4MpeLocalPrefTable    OBJECT-TYPE
    SYNTAX              SEQUENCE OF Fsbgp4MpeLocalPrefEntry
    MAX-ACCESS          not-accessible
    STATUS              current
    DESCRIPTION
    "BGP Local Preference table.  This table contains,
    the value that is to be assigned to the Local
    Preference attibute."
    ::= { fsbgp 23 }

fsbgp4MpeLocalPrefEntry    OBJECT-TYPE
    SYNTAX              Fsbgp4MpeLocalPrefEntry
    MAX-ACCESS          not-accessible
    STATUS              current
    DESCRIPTION
    "Entry containing information about the connection with a BGP peer."
    INDEX { fsbgp4mpeLocalPrefIndex }
    ::= {fsbgp4MpeLocalPrefTable 1 }

Fsbgp4MpeLocalPrefEntry ::= SEQUENCE {
    fsbgp4mpeLocalPrefIndex
        Integer32,
    fsbgp4mpeLocalPrefAdminStatus
        INTEGER,
    fsbgp4mpeLocalPrefRemoteAS
        Unsigned32,
    fsbgp4mpeLocalPrefIPAddrAfi
        InetAddressType,
    fsbgp4mpeLocalPrefIPAddrSafi
        BgpSafi,
    fsbgp4mpeLocalPrefIPAddrPrefix
        InetAddress,
    fsbgp4mpeLocalPrefIPAddrPrefixLen
        Integer32,
    fsbgp4mpeLocalPrefIntermediateAS
        DisplayString,
    fsbgp4mpeLocalPrefDirection
        INTEGER,
    fsbgp4mpeLocalPrefValue
        Unsigned32,
    fsbgp4mpeLocalPrefPreference
        INTEGER,
    fsbgp4mpeLocalPrefVrfName
        DisplayString
    }

fsbgp4mpeLocalPrefIndex    OBJECT-TYPE
    SYNTAX              Integer32  (1..10)
    MAX-ACCESS          not-accessible
    STATUS              current
    DESCRIPTION
        "This is the index to the table. Any entry in the table can be
         configured only if fsbgp4mpeLocalAs is set."
    ::= { fsbgp4MpeLocalPrefEntry 1 }

fsbgp4mpeLocalPrefAdminStatus  OBJECT-TYPE
    SYNTAX                  INTEGER {
                                up(1),
                                down(2)
                            }
    MAX-ACCESS              read-write
    STATUS                  current
    DESCRIPTION
        "The desired state of this entry. The entries in a row are
         configurable only if the admin status is DOWN."
    ::= { fsbgp4MpeLocalPrefEntry 2 }

fsbgp4mpeLocalPrefRemoteAS OBJECT-TYPE
    SYNTAX              Unsigned32 (0..4294967295)
    MAX-ACCESS          read-write
    STATUS              current
    DESCRIPTION
    "The remote autonomous system with which this entry
    is associated. A value of zero indicates that this
    entry is not valid and will not be matched for when
    the LocalPref value for an update is calculated."
    DEFVAL   { 0 }
    ::= { fsbgp4MpeLocalPrefEntry 3 }

fsbgp4mpeLocalPrefIPAddrAfi    OBJECT-TYPE
    SYNTAX                  InetAddressType
    MAX-ACCESS              read-write
    STATUS                  current
    DESCRIPTION
    "Type of IP address prefix in the Network Layer Reachability 
     Information field. This field needs to be set before setting the object
     fsbgp4mpeLocalPrefIPAddrPrefix."
    ::= { fsbgp4MpeLocalPrefEntry 4 }

fsbgp4mpeLocalPrefIPAddrSafi   OBJECT-TYPE
    SYNTAX                  BgpSafi
    MAX-ACCESS              read-write
    STATUS                  current
    DESCRIPTION
    "Sub-sequent address family of IP address prefix in the 
     Network Layer Reachability Information field.This field needs to be set
     before setting the object fsbgp4mpeLocalPrefIPAddrPrefix. "
    ::= { fsbgp4MpeLocalPrefEntry 5 }

fsbgp4mpeLocalPrefIPAddrPrefix OBJECT-TYPE
    SYNTAX                  InetAddress
    MAX-ACCESS              read-write
    STATUS                  current
    DESCRIPTION
    "An IP address prefix in the Network Layer Reachability Information field.
     A value of zero indicates that the entry is not valid and will not be 
     matched for when the Local Pref value for an update is calculated."
    DEFVAL   { '00000000'H }
    ::= { fsbgp4MpeLocalPrefEntry 6 }

fsbgp4mpeLocalPrefIPAddrPrefixLen  OBJECT-TYPE
    SYNTAX                      Integer32 (0..32)
    MAX-ACCESS                  read-write
    STATUS                      current
    DESCRIPTION
    "Length in bits of the IP address prefix in the Network Layer Reachability
    Information field.  A value of zero indicates that the entry is not valid 
    and will not be matched for when the Local Pref value for an update 
    is calculated."
    DEFVAL  { 0 }
    ::= { fsbgp4MpeLocalPrefEntry 7 }

fsbgp4mpeLocalPrefIntermediateAS   OBJECT-TYPE
    SYNTAX                      DisplayString
    MAX-ACCESS                  read-write
    STATUS                      current
    DESCRIPTION
    "Comma separated list of AS numbers that are to
    be present in the AS_PATH attribute of the Update.
    An empty field indicates that the same need not be
    checked for in the update.Maximum configurable size is 100."
    ::= { fsbgp4MpeLocalPrefEntry 8 }

fsbgp4mpeLocalPrefDirection    OBJECT-TYPE
    SYNTAX                  INTEGER {
                                in(1), -- incoming updates
                                out(2) -- outgoing updates
                            }
    MAX-ACCESS              read-write
    STATUS                  current
    DESCRIPTION
    "The direction of the update with which the entry is to be associated."
    DEFVAL  { in }
    ::= { fsbgp4MpeLocalPrefEntry 9 }

fsbgp4mpeLocalPrefValue    OBJECT-TYPE
    SYNTAX              Unsigned32 ( 0 .. 2147483647 )
    MAX-ACCESS          read-write
    STATUS              current
    DESCRIPTION
    "The value assigned to the LP Attribute for the route present in NLRI"
    DEFVAL  { 100 }
    ::= { fsbgp4MpeLocalPrefEntry 10 }

fsbgp4mpeLocalPrefPreference   OBJECT-TYPE
    SYNTAX                  INTEGER {
                                false(1),
                                true(2)
                            }
    MAX-ACCESS              read-write
    STATUS                  current
    DESCRIPTION
    "This object specifies whether the value present
     in this entry takes precedence when the attribute
     is already present in the update message that has
     been received."
    DEFVAL  { false }
    ::= { fsbgp4MpeLocalPrefEntry 11 }

fsbgp4mpeLocalPrefVrfName  OBJECT-TYPE
   SYNTAX               DisplayString (SIZE (0..16))
   MAX-ACCESS           read-write
   STATUS               current
   DESCRIPTION
       "The human-readable name of the VPN."
    ::= { fsbgp4MpeLocalPrefEntry 12 }

-- Update Filter Table.
-- This table is used to filter out routing updates

fsbgp4MpeUpdateFilterTable     OBJECT-TYPE
    SYNTAX                  SEQUENCE OF Fsbgp4MpeUpdateFilterEntry
    MAX-ACCESS              not-accessible
    STATUS                  current
    DESCRIPTION
    "BGP Update Filter Table.  This table contains
    Rules to filter out updates based on the AS from
    which it is received, NLRI and AS through which it
    had passed."
    ::= { fsbgp 24 }

fsbgp4MpeUpdateFilterEntry     OBJECT-TYPE
    SYNTAX                  Fsbgp4MpeUpdateFilterEntry
    MAX-ACCESS              not-accessible
    STATUS                  current
    DESCRIPTION
    	"Entry containing information about the updates
         that are to be filtered."
    INDEX { fsbgp4mpeUpdateFilterIndex }
    ::= { fsbgp4MpeUpdateFilterTable 1 }

Fsbgp4MpeUpdateFilterEntry ::= SEQUENCE {
    fsbgp4mpeUpdateFilterIndex
        Integer32,
    fsbgp4mpeUpdateFilterAdminStatus
        INTEGER,
    fsbgp4mpeUpdateFilterRemoteAS
        Unsigned32,
    fsbgp4mpeUpdateFilterIPAddrAfi
        InetAddressType,
    fsbgp4mpeUpdateFilterIPAddrSafi
        BgpSafi,
    fsbgp4mpeUpdateFilterIPAddrPrefix
        InetAddress,
    fsbgp4mpeUpdateFilterIPAddrPrefixLen
        Integer32,
    fsbgp4mpeUpdateFilterIntermediateAS
        DisplayString,
    fsbgp4mpeUpdateFilterDirection
        INTEGER,
    fsbgp4mpeUpdateFilterAction
        INTEGER,
    fsbgp4mpeUpdateFilterVrfName
        DisplayString
    }

fsbgp4mpeUpdateFilterIndex OBJECT-TYPE
    SYNTAX              Integer32  (1..10)
    MAX-ACCESS          not-accessible 
    STATUS              current
    DESCRIPTION
    "This is the index to the table. Any entry in the table can be configured
     only if fsbgp4LocalAs is set."
    ::= { fsbgp4MpeUpdateFilterEntry 1 }

fsbgp4mpeUpdateFilterAdminStatus   OBJECT-TYPE
    SYNTAX                      INTEGER {
                                    up(1),
                                    down(2)
                                }
    MAX-ACCESS                  read-write
    STATUS                      current
    DESCRIPTION
        "The desired state of this entry. The entries in a row are
         configurable only if the admin status is DOWN."
    ::= { fsbgp4MpeUpdateFilterEntry 2 }

fsbgp4mpeUpdateFilterRemoteAS  OBJECT-TYPE
    SYNTAX                  Unsigned32 (0..4294967295)
    MAX-ACCESS              read-write
    STATUS                  current
    DESCRIPTION
    "The remote autonomous system with which this entry
    is associated. A value of zero indicates that this
    entry is not valid and will not be matched for when
    the update is checked."
    DEFVAL  { 0 }
    ::= { fsbgp4MpeUpdateFilterEntry 3 }

fsbgp4mpeUpdateFilterIPAddrAfi     OBJECT-TYPE
    SYNTAX                      InetAddressType
    MAX-ACCESS                  read-write
    STATUS                      current
    DESCRIPTION
    "Type of IP address prefix in the Network Layer Reachability 
     Information field. This field needs to be set, before setting the object
     fsbgp4mpeUpdateFilterIPAddrPrefix."
    ::= { fsbgp4MpeUpdateFilterEntry 4 }

fsbgp4mpeUpdateFilterIPAddrSafi    OBJECT-TYPE
    SYNTAX                      BgpSafi
    MAX-ACCESS                  read-write
    STATUS                      current
    DESCRIPTION
    "SAFI of IP address prefix in the Network Layer Reachability 
     Information field. This field needs to be set, before setting the object
     fsbgp4mpeUpdateFilterIPAddrPrefix."
    ::= { fsbgp4MpeUpdateFilterEntry 5 }

fsbgp4mpeUpdateFilterIPAddrPrefix  OBJECT-TYPE
    SYNTAX                      InetAddress
    MAX-ACCESS                  read-write
    STATUS                      current
    DESCRIPTION
    "An IP address prefix in the Network Layer Reachability Information field.
     A value of zero in this field indicates that the NLRI field may not be 
     matched."
    DEFVAL  { '00000000'H }
    ::= { fsbgp4MpeUpdateFilterEntry 6 }

fsbgp4mpeUpdateFilterIPAddrPrefixLen   OBJECT-TYPE
    SYNTAX                          Integer32 (0..32)
    MAX-ACCESS                      read-write
    STATUS                          current
    DESCRIPTION
    "Length in bits of the IP address prefix
    in the Network Layer Reachability
    Information field. A value of zero in this field
    indicates that the NLRI field may not be matched."
    DEFVAL { 0 }
    ::= { fsbgp4MpeUpdateFilterEntry 7 }

fsbgp4mpeUpdateFilterIntermediateAS    OBJECT-TYPE
    SYNTAX                          DisplayString
    MAX-ACCESS                      read-write
    STATUS                          current
    DESCRIPTION
    "Comma separated list of AS numbers that are to
    be present in the AS_PATH attribute of the Update.
    An empty field indicates that the same need not be
    checked for in the update."
    ::= { fsbgp4MpeUpdateFilterEntry 8 }

fsbgp4mpeUpdateFilterDirection     OBJECT-TYPE
    SYNTAX                      INTEGER {
                                    in(1), -- incoming updates
                                    out(2) -- outgoing updates
                                }
    MAX-ACCESS                  read-write
    STATUS                      current
    DESCRIPTION
    "The direction of the update with which the entry is to be associated."
    DEFVAL  { in }
    ::= { fsbgp4MpeUpdateFilterEntry 9 }

fsbgp4mpeUpdateFilterAction    OBJECT-TYPE
    SYNTAX                  INTEGER {
                                allow (1), -- do not filter
                                filter (2) -- filter
                            }
    MAX-ACCESS              read-write
    STATUS                  current
    DESCRIPTION
    "The action to be taken when the characteristics
    that are specified in the entry is matched."
    DEFVAL  { filter }
    ::= { fsbgp4MpeUpdateFilterEntry 10 }

fsbgp4mpeUpdateFilterVrfName   OBJECT-TYPE
   SYNTAX                   DisplayString (SIZE (0..16))
   MAX-ACCESS               read-write
   STATUS                   current
   DESCRIPTION
       "The human-readable name of the VPN."
    ::= { fsbgp4MpeUpdateFilterEntry 11 }

-- Aggregation Table.
-- This table is used to aggregate the routing information
-- before the same are advertised to peers.

fsbgp4MpeAggregateTable        OBJECT-TYPE
    SYNTAX                  SEQUENCE OF Fsbgp4MpeAggregateEntry
    MAX-ACCESS              not-accessible
    STATUS                  current
    DESCRIPTION
    "BGP Aggregate Table. The entries in the table
    specifies the IP address based on which the routing
    information has to be aggregated."
    ::= { fsbgp 25 }

fsbgp4MpeAggregateEntry        OBJECT-TYPE
    SYNTAX                  Fsbgp4MpeAggregateEntry
    MAX-ACCESS              not-accessible
    STATUS                  current
    DESCRIPTION
    "Entry containing information about the IP address
    on which the aggregation has to be done."
    INDEX { fsbgp4mpeAggregateIndex }
    ::= { fsbgp4MpeAggregateTable 1 }

Fsbgp4MpeAggregateEntry ::=    SEQUENCE {
                                fsbgp4mpeAggregateIndex
                                    Integer32,
                                fsbgp4mpeAggregateAdminStatus
                                    INTEGER,
                                fsbgp4mpeAggregateIPAddrAfi
                                    InetAddressType,
                                fsbgp4mpeAggregateIPAddrSafi
                                    BgpSafi,
                                fsbgp4mpeAggregateIPAddrPrefix
                                    InetAddress,
                                fsbgp4mpeAggregateIPAddrPrefixLen
                                    Integer32,
                                fsbgp4mpeAggregateAdvertise
                                    INTEGER,
                                fsbgp4mpeAggregateVrfName
                                    DisplayString,
                                fsbgp4mpeAggregateAsSet
                                    INTEGER,
                                fsbgp4mpeAggregateAdvertiseRouteMapName
                                    DisplayString,
                                fsbgp4mpeAggregateSuppressRouteMapName
                                    DisplayString,
                                fsbgp4mpeAggregateAttributeRouteMapName
                                    DisplayString
                            }

fsbgp4mpeAggregateIndex        OBJECT-TYPE
    SYNTAX                  Integer32
    MAX-ACCESS              not-accessible 
    STATUS                  current
    DESCRIPTION
    "This is the index to the table.Any entry in the table can be
         configured only if fsbgp4LocalAs is set."
    ::= { fsbgp4MpeAggregateEntry 1 }

fsbgp4mpeAggregateAdminStatus  OBJECT-TYPE
    SYNTAX                  INTEGER {
                                up(1),
                                down(2),
                                invalid(3)
                            }
    MAX-ACCESS              read-write
    STATUS                  current
    DESCRIPTION
        "The desired state of this entry. When the adminstatus is set to up,
         the aggregate entry will be made active and the aggregate route 
         will be formed for this entry. When the adminstatus is set to down,
         the aggregate route, if advertised will be withdrawn and the 
         more-specific routes will be advertised. When the adminstatus is 
         set to invalid, the aggregate entry will be deleted."
    ::= { fsbgp4MpeAggregateEntry 2 }

fsbgp4mpeAggregateIPAddrAfi     OBJECT-TYPE
    SYNTAX                   InetAddressType
    MAX-ACCESS               read-write
    STATUS                   current
    DESCRIPTION
    "Type of IP address prefix in the Network Layer Reachability 
     Information field. This field needs to be set before setting the object
     fsbgp4mpeAggregateIPAddrPrefix. "
    ::= { fsbgp4MpeAggregateEntry 3 }

fsbgp4mpeAggregateIPAddrSafi   OBJECT-TYPE
    SYNTAX                  BgpSafi
    MAX-ACCESS              read-write
    STATUS                  current
    DESCRIPTION
    "SAFI of IP address prefix in the Network Layer Reachability 
     Information field. This field needs to be set before setting the object
     fsbgp4mpeAggregateIPAddrPrefix..
     [Note] SAFI for Carrying Label (4) can't be set. The configuration with
     SAFI unicast(1) holds good for both labelled and unlabelled prefixes."
    ::= { fsbgp4MpeAggregateEntry 4 }

fsbgp4mpeAggregateIPAddrPrefix  OBJECT-TYPE
    SYNTAX                   InetAddress
    MAX-ACCESS               read-write
    STATUS                   current
    DESCRIPTION
    "An IP address prefix in the Network Layer Reachability Information field.
     This field is configurable only if the admin status is DOWN"
    ::= { fsbgp4MpeAggregateEntry 5 }

fsbgp4mpeAggregateIPAddrPrefixLen  OBJECT-TYPE
    SYNTAX                      Integer32 (0..32)
    MAX-ACCESS                  read-write
    STATUS                      current
    DESCRIPTION
    "Length in bits of the IP address prefix in the Network Layer Reachability
     Information field. This field is configurable only if the admin status
     is DOWN."
    ::= { fsbgp4MpeAggregateEntry 6 }

fsbgp4mpeAggregateAdvertise        OBJECT-TYPE
    SYNTAX                      INTEGER {
                                    summaryOnly (1),
                                    all (2)
                                }
    MAX-ACCESS                  read-write
    STATUS                      current
    DESCRIPTION
    "This object specifies the route update that should be sent
     to the peers -
        summary-only - specifies that only the summarized route 
                       has to be advertised to peers.
        All          - specifies that both the summary and the
                       more-specific routes based on which the summary entry
                       was generated has to be advertised to the peers."
    ::=  { fsbgp4MpeAggregateEntry 7 }

fsbgp4mpeAggregateVrfName      OBJECT-TYPE
   SYNTAX                   DisplayString (SIZE (0..16))
   MAX-ACCESS               read-write
   STATUS                   current
   DESCRIPTION
       "The human-readable name of the VPN."
    ::=  { fsbgp4MpeAggregateEntry 8 }

fsbgp4mpeAggregateAsSet     OBJECT-TYPE
    SYNTAX                  INTEGER {
                                enable(1),
                                disable(2)
                                }
    MAX-ACCESS              read-write
    STATUS                  current
    DESCRIPTION
        "Enables/Disables the  autonomous system set path information. 
         It is an optional parameter "
     ::= { fsbgp4MpeAggregateEntry 9 }
fsbgp4mpeAggregateAdvertiseRouteMapName      OBJECT-TYPE
   SYNTAX                   DisplayString (SIZE (1..20))
   MAX-ACCESS               read-write
   STATUS                   current
   DESCRIPTION
       "The human-readable name for adverise route-map. The route map contains
       the rules for advertising the routes while aggregation. When we use
       advertise-map, only advertise-map influences the creation of aggregate
       entry. In absence of advertise-map, the aggregate route inherits the
       attributes of the more specific routes, both suppressed and unsuppressed.
       When advertise-map is used with fsbgp4mpeAggregateAsSet (as enable)  and
       suppress map, the aggregate inherits the attributes of only the routes
       that are selected in the advertise-map, irrespective of whether
       suppress-map suppresses the routes."
    ::=  { fsbgp4MpeAggregateEntry 10 }

fsbgp4mpeAggregateSuppressRouteMapName      OBJECT-TYPE
   SYNTAX                   DisplayString (SIZE (1..20))
   MAX-ACCESS               read-write
   STATUS                   current
   DESCRIPTION
       "The human-readable name for suppress route-map. The route map contains
       the rules for suppressing the routes while aggregation. when we use
       suppress-map configuration along with (summaryonly option set for)
       fsbgp4mpeAggregateAdvertise, it does'nt have any effect. And the
       more-specific routes that the suppress-map suppresses are not
       advertised. Other routes are advertised. When we use
       fsbgp4mpeAggregateAsSet (with enabled option) with suppress-map although
       suppress routes are not advertised, the aggregated routes inherits the
       attributes of all the suppressesed rotues. But it can be overwritten by
       attribute-map."
    ::=  { fsbgp4MpeAggregateEntry 11 }

fsbgp4mpeAggregateAttributeRouteMapName      OBJECT-TYPE
   SYNTAX                   DisplayString (SIZE (1..20))
   MAX-ACCESS               read-write
   STATUS                   current
   DESCRIPTION
       "The human-readable name for attribute route-map. The route map contains
        the rules for setting the attributes the aggregated route. When
        attribute-map and advertise-map along with fsbgp4mpeAggregateAsSet (enable)
        and other configurations, the attribute-map overrides the attribute that
        are configured in the attribute-map."
    ::=  { fsbgp4MpeAggregateEntry 12 }



-- SCALAR_TABLE_END fsbgp4RRDGroup

-- RRD OBJECT DEFINITION END

-- MIB for Importing STATIC routes to BGP and Viewing non-BGP routes.

fsbgp4MpeImportRouteTable      OBJECT-TYPE
    SYNTAX                  SEQUENCE OF Fsbgp4MpeImportRouteEntry
    MAX-ACCESS              not-accessible
    STATUS                  current
    DESCRIPTION
    "Non-BGP routes imported into the BGP RIB can be viewed through this table.
     Also allows importing a static route into BGP.After updating the RIB tree,
     if there is any change in the best route selected, then the  route is 
     updated to the Common Forwarding table."
    ::= { fsbgp 26 }

fsbgp4MpeImportRouteEntry      OBJECT-TYPE
    SYNTAX                  Fsbgp4MpeImportRouteEntry
    MAX-ACCESS              not-accessible
    STATUS                  current
    DESCRIPTION
    "Import Route entry."
    INDEX   { 
                fsbgp4mpeImportRoutePrefixAfi, 
                fsbgp4mpeImportRoutePrefixSafi, 
                fsbgp4mpeImportRoutePrefix, 
                fsbgp4mpeImportRoutePrefixLen,
                fsbgp4mpeImportRouteProtocol,
                fsbgp4mpeImportRouteNextHop, 
                fsbgp4mpeImportRouteIfIndex,
                fsbgp4mpeImportRouteMetric,
                fsbgp4mpeImportRouteVrf
            }
    ::= { fsbgp4MpeImportRouteTable 1 }

Fsbgp4MpeImportRouteEntry ::= SEQUENCE {
        fsbgp4mpeImportRoutePrefixAfi  InetAddressType,
        fsbgp4mpeImportRoutePrefixSafi BgpSafi,
        fsbgp4mpeImportRoutePrefix     InetAddress,
        fsbgp4mpeImportRoutePrefixLen  Integer32,
        fsbgp4mpeImportRouteProtocol   Integer32,
        fsbgp4mpeImportRouteNextHop    InetAddress,
        fsbgp4mpeImportRouteIfIndex    Integer32,
        fsbgp4mpeImportRouteMetric     Integer32,
        fsbgp4mpeImportRouteVrf        DisplayString,
        fsbgp4mpeImportRouteAction     INTEGER
    }

fsbgp4mpeImportRoutePrefixAfi  OBJECT-TYPE
    SYNTAX                  InetAddressType
    MAX-ACCESS              not-accessible 
    STATUS                  current
    DESCRIPTION
    "Type of Prefix of the route to be imported."
    ::= { fsbgp4MpeImportRouteEntry 1 }

fsbgp4mpeImportRoutePrefixSafi OBJECT-TYPE
    SYNTAX                  BgpSafi
    MAX-ACCESS              not-accessible 
    STATUS                  current
    DESCRIPTION
    "SAFI of Prefix of the route to be imported. Only UNICAST (1) is allowed
    right now. Route can be imported into VRF by providing SAFI (1) and
    VRF name."
    ::= { fsbgp4MpeImportRouteEntry 2 }

fsbgp4mpeImportRoutePrefix     OBJECT-TYPE
    SYNTAX                  InetAddress
    MAX-ACCESS              not-accessible 
    STATUS                  current
    DESCRIPTION
    "Prefix of the route to be imported."
    ::= { fsbgp4MpeImportRouteEntry 3 }

fsbgp4mpeImportRoutePrefixLen   OBJECT-TYPE
    SYNTAX                   Integer32 (1..32) 
    MAX-ACCESS               not-accessible
    STATUS                   current
    DESCRIPTION
    "Prefix length of the route."
    ::= { fsbgp4MpeImportRouteEntry 4 }

fsbgp4mpeImportRouteProtocol   OBJECT-TYPE
    SYNTAX                  Integer32 (2|3|8|13)
    MAX-ACCESS              not-accessible 
    STATUS                  current
    DESCRIPTION
    "Protocol value for Non-BGP routes. 
     2- LOCAL, 
     3 - STATIC,
     8 - RIP, 
     13 - OSPF. 
     Only STATIC routes (protocol 3) can be added through this table. 
     However all non-BGP protocol (Local, Static, RIP, OSPF) routes can 
     be viewed."
    ::= { fsbgp4MpeImportRouteEntry 5 }

fsbgp4mpeImportRouteNextHop    OBJECT-TYPE
    SYNTAX                  InetAddress
    MAX-ACCESS              not-accessible
    STATUS                  current
    DESCRIPTION
    "NextHop Ipaddress for the route."
    ::= { fsbgp4MpeImportRouteEntry 6 }

fsbgp4mpeImportRouteIfIndex    OBJECT-TYPE
    SYNTAX                  Integer32 (1..2147483647)
    MAX-ACCESS              not-accessible
    STATUS                  current
    DESCRIPTION
    "Interface Index of the Route"
    ::= { fsbgp4MpeImportRouteEntry 7 }

fsbgp4mpeImportRouteMetric     OBJECT-TYPE
    SYNTAX                  Integer32 (1..2147483647)
    MAX-ACCESS              not-accessible
    STATUS                  current
    DESCRIPTION
    "Metric for the route being imported."
    ::= { fsbgp4MpeImportRouteEntry 8 }

fsbgp4mpeImportRouteVrf        OBJECT-TYPE
    SYNTAX                  DisplayString (SIZE (0..16))  
    MAX-ACCESS              not-accessible
    STATUS                  current
    DESCRIPTION
    "Vrf in which the route should be imported. If the rotueis to be installed
    in default VRF, the value should be NULL string"
    ::= { fsbgp4MpeImportRouteEntry 9 }

fsbgp4mpeImportRouteAction     OBJECT-TYPE
    SYNTAX                  INTEGER {
		                    add (1), -- route addition
		                    delete (2) -- route deletion
			                }
    MAX-ACCESS              read-write 
    STATUS                  current
    DESCRIPTION
        "Controls addition or deletion of route."
        ::= { fsbgp4MpeImportRouteEntry 10 }
             
        
-- MIB for Importing DIRECT/STATIC routes to BGP end
-- MIB for getting FSM transition history  
         
fsbgp4MpeFsmTransitionHistTable      OBJECT-TYPE
    SYNTAX                  SEQUENCE OF Fsbgp4MpeFsmTransitionHistEntry
    MAX-ACCESS              not-accessible
    STATUS                  current
    DESCRIPTION
    "Gets FSM transitions history per peer   " 
    ::= { fsbgp 27 }

fsbgp4MpeFsmTransitionHistEntry      OBJECT-TYPE
    SYNTAX                  Fsbgp4MpeFsmTransitionHistEntry
    MAX-ACCESS              not-accessible
    STATUS                  current
    DESCRIPTION
    "Fsm Hist  entry."
    INDEX   { 
            		fsbgp4mpePeerType,
            		fsbgp4mpePeer 
		}
        ::= { fsbgp4MpeFsmTransitionHistTable 1 }

Fsbgp4MpeFsmTransitionHistEntry ::= SEQUENCE {
        fsbgp4mpePeerType          InetAddressType,
        fsbgp4mpePeer   	InetAddress,
        fsbgp4mpeFsmTransitionHist	DisplayString
    }

fsbgp4mpePeerType              OBJECT-TYPE
    SYNTAX                  InetAddressType
    MAX-ACCESS              not-accessible
    STATUS                  current
    DESCRIPTION
    "Type of Peer from which FSM transition history would be read."
    ::= { fsbgp4MpeFsmTransitionHistEntry 1 }

fsbgp4mpePeer     	OBJECT-TYPE
    SYNTAX                  InetAddress
    MAX-ACCESS              not-accessible
    STATUS                  current
    DESCRIPTION
    "Peer from which FSM transition history would be read."
    ::= { fsbgp4MpeFsmTransitionHistEntry 2 }

fsbgp4mpeFsmTransitionHist     OBJECT-TYPE
    SYNTAX                 DisplayString 
    MAX-ACCESS              read-only
    STATUS                  current
    DESCRIPTION
    " sequence of FSM states separated by space"
    ::= { fsbgp4MpeFsmTransitionHistEntry 3 }
 
--- Routes Damping History Table

fsbgp4MpeRfd   OBJECT IDENTIFIER ::= { fsbgp 28} 

fsbgp4MpeRfdRtDampHistTable OBJECT-TYPE
	SYNTAX          SEQUENCE OF Fsbgp4MpeRfdRtDampHistEntry
	MAX-ACCESS      not-accessible
	STATUS          current
	DESCRIPTION 
    "Route damping history table.This table contains the figure-of-merit and 
    the route status"
	::= { fsbgp4MpeRfd 1 }

fsbgp4MpeRfdRtDampHistEntry  OBJECT-TYPE
	SYNTAX      Fsbgp4MpeRfdRtDampHistEntry
	MAX-ACCESS  not-accessible
	STATUS      current
	DESCRIPTION
      "Entry contains route damping history"
    	INDEX  { fsbgp4mpePathAttrAddrPrefixAfi,
           fsbgp4mpePathAttrAddrPrefixSafi,
           fsbgp4mpePathAttrAddrPrefix,
           fsbgp4mpePathAttrAddrPrefixLen,
           fsbgp4mpePathAttrPeerType,
           fsbgp4mpePathAttrPeer
           }
	::= { fsbgp4MpeRfdRtDampHistTable 1 }

Fsbgp4MpeRfdRtDampHistEntry ::= SEQUENCE {
    fsbgp4mpePathAttrAddrPrefixAfi
        InetAddressType,
    fsbgp4mpePathAttrAddrPrefixSafi
        BgpSafi,
    fsbgp4mpePathAttrAddrPrefix
        InetAddress,
    fsbgp4mpePathAttrAddrPrefixLen
        Integer32,
    fsbgp4mpePathAttrPeerType
        InetAddressType,
    fsbgp4mpePathAttrPeer
        InetAddress,
    fsbgp4mpeRfdRtFom
        Integer32,
    fsbgp4mpeRfdRtLastUpdtTime
        Integer32,
    fsbgp4mpeRfdRtState
        INTEGER,
    fsbgp4mpeRfdRtStatus
        INTEGER,
    fsbgp4mpeRfdRtFlapCount
        Integer32,
    fsbgp4mpeRfdRtFlapTime
        Integer32,
    fsbgp4mpeRfdRtReuseTime
        Integer32
    }

fsbgp4mpePathAttrAddrPrefixAfi OBJECT-TYPE
    SYNTAX                  InetAddressType
    MAX-ACCESS              not-accessible
    STATUS                  current
    DESCRIPTION 
    "AFI of the route "
    ::= { fsbgp4MpeRfdRtDampHistEntry 1 } 

fsbgp4mpePathAttrAddrPrefixSafi    OBJECT-TYPE
    SYNTAX                      BgpSafi
    MAX-ACCESS                  not-accessible 
    STATUS                      current
    DESCRIPTION 
    "SAFI of the route "
    ::= { fsbgp4MpeRfdRtDampHistEntry 2 } 

fsbgp4mpePathAttrAddrPrefix OBJECT-TYPE
	SYNTAX	    InetAddress
	MAX-ACCESS  not-accessible 
	STATUS      current
	DESCRIPTION 
    "An IP address prefix in the NLRI field. This object is an IP address
    containing the prefix with the length specified by 
    fsbgp4mpePathAttrAddrPrefixLen. Any bits beyond the length specified by 
    bgp4PathAttrAddrPrefixLen are 
    zeroed."
	::= { fsbgp4MpeRfdRtDampHistEntry 3 } 

fsbgp4mpePathAttrAddrPrefixLen OBJECT-TYPE
	SYNTAX	    Integer32 (0..32)
	MAX-ACCESS  not-accessible
	STATUS      current
	DESCRIPTION 
    "Length in bits of the IP address prefix in NLRI field."
	::= { fsbgp4MpeRfdRtDampHistEntry 4 } 

fsbgp4mpePathAttrPeerType  OBJECT-TYPE
    SYNTAX              InetAddressType
    MAX-ACCESS          not-accessible
    STATUS              current
    DESCRIPTION 
    "AFI of the peer "
    ::= { fsbgp4MpeRfdRtDampHistEntry 5 } 

fsbgp4mpePathAttrPeer OBJECT-TYPE
	SYNTAX	    InetAddress
	MAX-ACCESS  not-accessible
	STATUS      current
	DESCRIPTION 
    "The Peer remote address of the peer where the path information was 
    learned."
	::= { fsbgp4MpeRfdRtDampHistEntry 6 } 

fsbgp4mpeRfdRtFom  OBJECT-TYPE
	SYNTAX	    Integer32 (0..65535)
	MAX-ACCESS  read-only
	STATUS      current
	DESCRIPTION 
    "The figure-of-merit of the route"
	::= { fsbgp4MpeRfdRtDampHistEntry 7 } 

fsbgp4mpeRfdRtLastUpdtTime OBJECT-TYPE
    SYNTAX       Integer32(1..2147483647)
    MAX-ACCESS   read-only
    STATUS       current
	DESCRIPTION
    "The time when the route figure-of-merit was updated."
	::= {fsbgp4MpeRfdRtDampHistEntry 8 }

fsbgp4mpeRfdRtState    OBJECT-TYPE
	SYNTAX	        INTEGER {
                            none(1),
                            suppressed (2),
                            unsuppressed (3)
                            }
	MAX-ACCESS      read-only
	STATUS          current
	DESCRIPTION 
    "The value gives the status whether the route is suppressed or not "
	::= { fsbgp4MpeRfdRtDampHistEntry 9 } 

fsbgp4mpeRfdRtStatus    OBJECT-TYPE
	SYNTAX	        INTEGER {
                            none(1),
                            feasibleroute (2),
                            unfeasibleroute (3)
                            }
	MAX-ACCESS      read-only
	STATUS          current
	DESCRIPTION 
    "The value gives the status whether the route is  feasible or unfeasible 
    route"
	::= { fsbgp4MpeRfdRtDampHistEntry 10 } 

fsbgp4mpeRfdRtFlapCount    OBJECT-TYPE
        SYNTAX           Integer32
        MAX-ACCESS       read-only
        STATUS           current
        DESCRIPTION 
      "This value gives the number of times the route being flapped"
         ::= { fsbgp4MpeRfdRtDampHistEntry 11 }

fsbgp4mpeRfdRtFlapTime    OBJECT-TYPE
        SYNTAX            Integer32(1..2147483647)
        MAX-ACCESS        read-only
        STATUS            current
        DESCRIPTION
       "The time calculated for a route, from when a route is being flapped for 
        first time, time in seconds"
          ::= { fsbgp4MpeRfdRtDampHistEntry 12 }

fsbgp4mpeRfdRtReuseTime    OBJECT-TYPE
        SYNTAX             Integer32(1..2147483647)
        MAX-ACCESS         read-only
        STATUS             current
        DESCRIPTION
       "The time after which a route can be reused again after it moves to 
        suppressed state from unsuppressed state, time in seconds"
          ::= { fsbgp4MpeRfdRtDampHistEntry 13 }

--- Peers Damping History Table


fsbgp4MpeRfdPeerDampHistTable  OBJECT-TYPE
	SYNTAX      SEQUENCE OF Fsbgp4MpeRfdPeerDampHistEntry
	MAX-ACCESS  not-accessible
	STATUS      current
	DESCRIPTION 
    "Peer Damping history table. It contains the peer figure-of-merit and 
    peer status."
	::= { fsbgp4MpeRfd 2 }

fsbgp4MpeRfdPeerDampHistEntry  OBJECT-TYPE
	SYNTAX      Fsbgp4MpeRfdPeerDampHistEntry
	MAX-ACCESS  not-accessible
	STATUS      current
	DESCRIPTION
    "Entry contains peer damping history"
    INDEX  { fsbgp4mpePeerRemoteIpAddrType,
             fsbgp4mpePeerRemoteIpAddr
           }
	::= { fsbgp4MpeRfdPeerDampHistTable 1 }

Fsbgp4MpeRfdPeerDampHistEntry ::= SEQUENCE {
    fsbgp4mpePeerRemoteIpAddrType
        InetAddressType,
    fsbgp4mpePeerRemoteIpAddr
    	InetAddress,
    fsbgp4mpeRfdPeerFom
        Integer32,
    fsbgp4mpeRfdPeerLastUpdtTime
        Integer32,
    fsbgp4mpeRfdPeerState
        INTEGER,
    fsbgp4mpeRfdPeerStatus
        INTEGER
    }

fsbgp4mpePeerRemoteIpAddrType  OBJECT-TYPE
    SYNTAX                  InetAddressType
    MAX-ACCESS              not-accessible 
    STATUS                  current
    DESCRIPTION 
    "AFI of the remote peer "
    ::= { fsbgp4MpeRfdPeerDampHistEntry 1 } 

fsbgp4mpePeerRemoteIpAddr OBJECT-TYPE
	SYNTAX	    InetAddress
	MAX-ACCESS  not-accessible 
	STATUS      current
	DESCRIPTION 
    "The peer remote address of the peer."
	::= { fsbgp4MpeRfdPeerDampHistEntry 2 } 

fsbgp4mpeRfdPeerFom OBJECT-TYPE
    SYNTAX       Integer32(0..65535)
    MAX-ACCESS   read-only
    STATUS       current
	DESCRIPTION
    "The current figure-of-merit of peer"
	::= {fsbgp4MpeRfdPeerDampHistEntry 3 }

fsbgp4mpeRfdPeerLastUpdtTime OBJECT-TYPE
    SYNTAX       Integer32(1..2147483647)
    MAX-ACCESS   read-only
    STATUS       current
	DESCRIPTION
    "The time when the figure-of-merit was updated."
	::= {fsbgp4MpeRfdPeerDampHistEntry 4 }

fsbgp4mpeRfdPeerState    OBJECT-TYPE
	SYNTAX	        INTEGER {
                            none(1),
                            suppressed (2),
                            unsuppressed (3)
                            }
	MAX-ACCESS      read-only
	STATUS          current
	DESCRIPTION 
    "This value gives the status whether peer is suppressed or not"
	::= {fsbgp4MpeRfdPeerDampHistEntry 5 }

fsbgp4mpeRfdPeerStatus    OBJECT-TYPE
        SYNTAX          INTEGER {
                            none(1),
                            peerup (2),
                            peerdown (3)
                            }
        MAX-ACCESS      read-only
        STATUS          current
        DESCRIPTION
    "This value gives the status whether peer is up or down"
        ::= {fsbgp4MpeRfdPeerDampHistEntry 6 }


---Routes Reuse List Table 

fsbgp4MpeRfdRtsReuseListTable  OBJECT-TYPE
	SYNTAX      SEQUENCE OF Fsbgp4MpeRfdRtsReuseListEntry
	MAX-ACCESS  not-accessible
	STATUS      current
	DESCRIPTION 
    "Routes Reuse List Table. It contains the IP prefix and prefix length."
	::= { fsbgp4MpeRfd 3 }

fsbgp4MpeRfdRtsReuseListEntry  OBJECT-TYPE
	SYNTAX      Fsbgp4MpeRfdRtsReuseListEntry
	MAX-ACCESS  not-accessible
	STATUS      current
	DESCRIPTION
    "Entry contains routes reuse list"
	INDEX  { fsbgp4mpeRtAfi,
                 fsbgp4mpeRtSafi,
		 fsbgp4mpeRtIPPrefix,
                 fsbgp4mpeRtIPPrefixLen,
                 fsbgp4mpeRfdRtsReusePeerType,
                 fsbgp4mpePeerRemAddress
           }
	::= { fsbgp4MpeRfdRtsReuseListTable 1 }

Fsbgp4MpeRfdRtsReuseListEntry ::= SEQUENCE {
    fsbgp4mpeRtAfi
        InetAddressType,
    fsbgp4mpeRtSafi
        BgpSafi,
    fsbgp4mpeRtIPPrefix
        InetAddress,
    fsbgp4mpeRtIPPrefixLen
        Integer32,
    fsbgp4mpeRfdRtsReusePeerType
        InetAddressType,
    fsbgp4mpePeerRemAddress
        InetAddress,
    fsbgp4mpeRfdRtReuseListRtFom
        Integer32,
    fsbgp4mpeRfdRtReuseListRtLastUpdtTime
        Integer32,
    fsbgp4mpeRfdRtReuseListRtState
        INTEGER,
    fsbgp4mpeRfdRtReuseListRtStatus
        INTEGER
            
    }

fsbgp4mpeRtAfi     OBJECT-TYPE
    SYNTAX      InetAddressType
    MAX-ACCESS  not-accessible 
    STATUS      current
    DESCRIPTION 
    "AFI of the route"
    ::= { fsbgp4MpeRfdRtsReuseListEntry 1 } 

fsbgp4mpeRtSafi    OBJECT-TYPE
    SYNTAX      BgpSafi
    MAX-ACCESS  not-accessible 
    STATUS      current
    DESCRIPTION 
    "AFI of the route"
    ::= { fsbgp4MpeRfdRtsReuseListEntry 2 } 

fsbgp4mpeRtIPPrefix OBJECT-TYPE
	SYNTAX	    InetAddress
	MAX-ACCESS  not-accessible 
	STATUS      current
	DESCRIPTION 
    "An IP address prefix in the NLRI field. This object is an IP address
    containing the prefix with the length specified by fsbgp4RtIPPrefixLen.
    Any bits beyond the length specified by fsbgp4IPPrefixLen are 
    zeroed."
	::= { fsbgp4MpeRfdRtsReuseListEntry 3 } 

fsbgp4mpeRtIPPrefixLen OBJECT-TYPE
	SYNTAX	    Integer32 (0..32)
	MAX-ACCESS  not-accessible
	STATUS      current
	DESCRIPTION 
    "Length in bits of the IP address prefix in NLRI field."
	::= { fsbgp4MpeRfdRtsReuseListEntry 4 } 

fsbgp4mpeRfdRtsReusePeerType   OBJECT-TYPE
    SYNTAX                  InetAddressType
    MAX-ACCESS              not-accessible
    STATUS                  current
    DESCRIPTION 
    "AFI of the remote peer"
    ::= { fsbgp4MpeRfdRtsReuseListEntry 5 } 

fsbgp4mpePeerRemAddress OBJECT-TYPE
	SYNTAX	    InetAddress
	MAX-ACCESS  not-accessible
	STATUS      current
	DESCRIPTION 
    "The Peer remote address of the peer where the path information was 
    learned."
	::= { fsbgp4MpeRfdRtsReuseListEntry 6 } 

fsbgp4mpeRfdRtReuseListRtFom  OBJECT-TYPE
	SYNTAX	    Integer32 (0..65535)
	MAX-ACCESS  read-only
	STATUS      current
	DESCRIPTION 
    "The figure-of-merit of the route which is in the routes reuse list"
	::= {fsbgp4MpeRfdRtsReuseListEntry  7 } 

fsbgp4mpeRfdRtReuseListRtLastUpdtTime OBJECT-TYPE
    SYNTAX       Integer32(1..2147483647)
    MAX-ACCESS   read-only
    STATUS       current
	DESCRIPTION
    "The time when the route figure-of-merit was updated."
	::= {fsbgp4MpeRfdRtsReuseListEntry 8 }

fsbgp4mpeRfdRtReuseListRtState    OBJECT-TYPE
	SYNTAX	        INTEGER {
                            none(1),
                            suppressed (2),
                            unsuppressed (3)
                            }
	MAX-ACCESS      read-only
	STATUS          current
	DESCRIPTION 
    "The value gives the status whether the route is suppressed or not "
	::= { fsbgp4MpeRfdRtsReuseListEntry 9 } 

fsbgp4mpeRfdRtReuseListRtStatus    OBJECT-TYPE
	SYNTAX	        INTEGER {
                            none(1),
                            feasibleroute (2),
                            unfeasibleroute (3)
                            }
	MAX-ACCESS      read-only
	STATUS          current
	DESCRIPTION 
    "The value gives the status whether the route is  feasible or unfeasible 
    route"
	::= { fsbgp4MpeRfdRtsReuseListEntry 10 } 

--- Peer's Reuse List Table

fsbgp4MpeRfdPeerReuseListTable  OBJECT-TYPE
	SYNTAX      SEQUENCE OF Fsbgp4MpeRfdPeerReuseListEntry
	MAX-ACCESS  not-accessible
	STATUS      current
	DESCRIPTION 
    "Peer's Reuse List Table. It contains the Peer Remote Address."
	::= { fsbgp4MpeRfd 4 }

fsbgp4MpeRfdPeerReuseListEntry  OBJECT-TYPE
	SYNTAX      Fsbgp4MpeRfdPeerReuseListEntry
	MAX-ACCESS  not-accessible
	STATUS      current
	DESCRIPTION
    "Entry contains routes reuse list"
    	INDEX  { fsbgp4mpeRfdPeerRemIpAddrType,
             fsbgp4mpeRfdPeerRemIpAddr
           }
	::= {fsbgp4MpeRfdPeerReuseListTable  1 }

Fsbgp4MpeRfdPeerReuseListEntry ::= SEQUENCE {
    fsbgp4mpeRfdPeerRemIpAddrType
        InetAddressType,
    fsbgp4mpeRfdPeerRemIpAddr
    	InetAddress,
    fsbgp4mpeRfdPeerReuseListPeerFom
        Integer32,
    fsbgp4mpeRfdPeerReuseListLastUpdtTime 
        Integer32,
    fsbgp4mpeRfdPeerReuseListPeerState
        INTEGER,
    fsbgp4mpeRfdPeerReuseListPeerStatus
        INTEGER

    }

fsbgp4mpeRfdPeerRemIpAddrType  OBJECT-TYPE
    SYNTAX                  InetAddressType
    MAX-ACCESS              not-accessible 
    STATUS                  current
    DESCRIPTION 
    "AFI of the peer"
    ::= { fsbgp4MpeRfdPeerReuseListEntry 1 } 

fsbgp4mpeRfdPeerRemIpAddr OBJECT-TYPE
	SYNTAX	    InetAddress
	MAX-ACCESS  not-accessible 
	STATUS      current
	DESCRIPTION 
    "The peer remote address of the peer which is in the peer's reuse list."
	::= { fsbgp4MpeRfdPeerReuseListEntry 2 } 

fsbgp4mpeRfdPeerReuseListPeerFom OBJECT-TYPE
    SYNTAX       Integer32(0..65535)
    MAX-ACCESS   read-only
    STATUS       current
	DESCRIPTION
    "The current figure-of-merit of peer"
	::= {fsbgp4MpeRfdPeerReuseListEntry 3 }

fsbgp4mpeRfdPeerReuseListLastUpdtTime OBJECT-TYPE
    SYNTAX       Integer32(1..2147483647)
    MAX-ACCESS   read-only
    STATUS       current
	DESCRIPTION
    "The time when the figure-of-merit was updated."
	::= {fsbgp4MpeRfdPeerReuseListEntry 4 }


fsbgp4mpeRfdPeerReuseListPeerState    OBJECT-TYPE
	SYNTAX	        INTEGER {
                            none(1),
                            suppressed (2),
                            unsuppressed (3)
                            }
	MAX-ACCESS      read-only
	STATUS          current
	DESCRIPTION 
    "This value gives the status whether peer is suppressed or not"
	::= {fsbgp4MpeRfdPeerReuseListEntry 5 }

fsbgp4mpeRfdPeerReuseListPeerStatus    OBJECT-TYPE
	SYNTAX	        INTEGER {
                            none(1),
                            peerup (2),
                            peerdown (3)
                            }
	MAX-ACCESS      read-only
	STATUS          current
	DESCRIPTION 
    "This value gives the status whether peer is up or down"
	::= {fsbgp4MpeRfdPeerReuseListEntry 6 }

-- MIB FOR FSBGP_ROUTEFLAPDAMPING end
-- MIB FOR FSBGP_COMMUNITY
--- Routes Additive Community Table
--- Represents the additive communities configured for
--- destinations.

fsbgpMpeComm   OBJECT IDENTIFIER ::= { fsbgp 29} 
fsbgp4MpeCommRouteAddCommTable OBJECT-TYPE
	SYNTAX        SEQUENCE OF Fsbgp4MpeCommRouteAddCommEntry
	MAX-ACCESS    not-accessible
	STATUS        current
	DESCRIPTION 
    "This table is used to configure additive communities
     for a given destination." 
	::= {fsbgpMpeComm 1 }

fsbgp4MpeCommRouteAddCommEntry  OBJECT-TYPE
	SYNTAX      Fsbgp4MpeCommRouteAddCommEntry
	MAX-ACCESS  not-accessible
	STATUS      current
	DESCRIPTION
    "Routes configured additive communities Table Entry"
    INDEX  {fsbgp4mpeAddCommRtAfi,
            fsbgp4mpeAddCommRtSafi,
            fsbgp4mpeAddCommIpNetwork,
            fsbgp4mpeAddCommIpPrefixLen,
            fsbgp4mpeAddCommVal
          }
	::= { fsbgp4MpeCommRouteAddCommTable 1 }

Fsbgp4MpeCommRouteAddCommEntry ::= SEQUENCE {
    fsbgp4mpeAddCommRtAfi
        InetAddressType,
    fsbgp4mpeAddCommRtSafi
        BgpSafi,
    fsbgp4mpeAddCommIpNetwork
        InetAddress,
    fsbgp4mpeAddCommIpPrefixLen
        Integer32,
    fsbgp4mpeAddCommVal
        Unsigned32,
    fsbgp4mpeAddCommRowStatus
        RowStatus
    }

fsbgp4mpeAddCommRtAfi  OBJECT-TYPE
    SYNTAX          InetAddressType
    MAX-ACCESS      not-accessible
    STATUS          current
    DESCRIPTION
    "AFI of IP address of the destination"
    ::= { fsbgp4MpeCommRouteAddCommEntry 1 } 

fsbgp4mpeAddCommRtSafi OBJECT-TYPE
    SYNTAX          BgpSafi
    MAX-ACCESS      not-accessible
    STATUS          current
    DESCRIPTION
    "SAFI of IP address of the destination"
    ::= { fsbgp4MpeCommRouteAddCommEntry 2 } 

fsbgp4mpeAddCommIpNetwork OBJECT-TYPE
	SYNTAX	   InetAddress
	MAX-ACCESS  not-accessible
	STATUS      current
	DESCRIPTION 
    "IP address of the destination"
	::= { fsbgp4MpeCommRouteAddCommEntry 3 } 

fsbgp4mpeAddCommIpPrefixLen   OBJECT-TYPE
	SYNTAX	    Integer32 (1..32)
	MAX-ACCESS   not-accessible
	STATUS       current
	DESCRIPTION 
    "IP prefix length for the destination"
	::= { fsbgp4MpeCommRouteAddCommEntry 4 } 

fsbgp4mpeAddCommVal    OBJECT-TYPE
	SYNTAX	        Unsigned32  (65536..4294901759|4294967041..4294967043)
	MAX-ACCESS       not-accessible
	STATUS           current
	DESCRIPTION 
    "Additive Community configured for the Route"
	::= { fsbgp4MpeCommRouteAddCommEntry 5 } 

fsbgp4mpeAddCommRowStatus    OBJECT-TYPE
	SYNTAX	         RowStatus
	MAX-ACCESS	 read-create
	STATUS	         current
	DESCRIPTION 
	"Row status for creating entries into this table.This object can be set
     only if fsbgp4LocalAS is configured."
	::= { fsbgp4MpeCommRouteAddCommEntry 6 } 

--- Routes Delete Community Table
--- Represents the communities to be deleted for the
--- destinations.

fsbgp4MpeCommRouteDeleteCommTable OBJECT-TYPE
	SYNTAX        SEQUENCE OF Fsbgp4MpeCommRouteDeleteCommEntry
	MAX-ACCESS    not-accessible
	STATUS        current
	DESCRIPTION 
    "This table is used to configure delete communities
     for a given destination."
	::= {fsbgpMpeComm 2}

fsbgp4MpeCommRouteDeleteCommEntry  OBJECT-TYPE
	SYNTAX      Fsbgp4MpeCommRouteDeleteCommEntry
	MAX-ACCESS  not-accessible
	STATUS      current
	DESCRIPTION
    "Routes configured delete communities Table Entry"
    INDEX  {fsbgp4mpeDeleteCommRtAfi,
            fsbgp4mpeDeleteCommRtSafi,
            fsbgp4mpeDeleteCommIpNetwork,
            fsbgp4mpeDeleteCommIpPrefixLen,
            fsbgp4mpeDeleteCommVal
          }
	::= { fsbgp4MpeCommRouteDeleteCommTable 1 }

Fsbgp4MpeCommRouteDeleteCommEntry ::= SEQUENCE {
    fsbgp4mpeDeleteCommRtAfi
        InetAddressType,
    fsbgp4mpeDeleteCommRtSafi
        BgpSafi,
    fsbgp4mpeDeleteCommIpNetwork
        InetAddress,
    fsbgp4mpeDeleteCommIpPrefixLen
        Integer32,
    fsbgp4mpeDeleteCommVal
        Unsigned32,
    fsbgp4mpeDeleteCommRowStatus
	     RowStatus
    }

fsbgp4mpeDeleteCommRtAfi   OBJECT-TYPE
    SYNTAX              InetAddressType
    MAX-ACCESS          not-accessible
    STATUS              current
    DESCRIPTION 
    "AFI of IP address of the destination"
    ::= { fsbgp4MpeCommRouteDeleteCommEntry 1 } 

fsbgp4mpeDeleteCommRtSafi  OBJECT-TYPE
    SYNTAX              BgpSafi
    MAX-ACCESS          not-accessible
    STATUS              current
    DESCRIPTION 
    "SAFI of IP address of the destination"
    ::= { fsbgp4MpeCommRouteDeleteCommEntry 2 } 

fsbgp4mpeDeleteCommIpNetwork OBJECT-TYPE
	SYNTAX	   InetAddress
	MAX-ACCESS  not-accessible
	STATUS      current
	DESCRIPTION 
    "IP address of the destination"
	::= { fsbgp4MpeCommRouteDeleteCommEntry 3 } 

fsbgp4mpeDeleteCommIpPrefixLen   OBJECT-TYPE
	SYNTAX	    Integer32 (1..32)
	MAX-ACCESS   not-accessible
	STATUS       current
	DESCRIPTION 
    "IP prefix length for the destination"
	::= { fsbgp4MpeCommRouteDeleteCommEntry 4 } 

fsbgp4mpeDeleteCommVal    OBJECT-TYPE
	SYNTAX	        Unsigned32  (65536..4294901759|4294967041..4294967043)
	MAX-ACCESS       not-accessible
	STATUS           current
	DESCRIPTION 
    "Delete Community configured for the Route"
	::= { fsbgp4MpeCommRouteDeleteCommEntry 5 } 

fsbgp4mpeDeleteCommRowStatus    OBJECT-TYPE
	SYNTAX	         RowStatus
	MAX-ACCESS	      read-create
	STATUS	         current
	DESCRIPTION 
	"Row status for creating entries into this table.This object can be set 
         only if fsbgp4LocalAS is configured."
	::= { fsbgp4MpeCommRouteDeleteCommEntry 6 } 

--- Routes Community Set Status Table
--- Represents the status or local policy (can be either, addition of 
--- communities, deletion of communities or both or complete
--- ommission of communities) for destinations.

fsbgp4MpeCommRouteCommSetStatusTable OBJECT-TYPE
	SYNTAX        SEQUENCE OF Fsbgp4MpeCommRouteCommSetStatusEntry
	MAX-ACCESS    not-accessible
	STATUS        current
	DESCRIPTION 
    "This table is used to configure the local policy of communities
    for a given destination."
	::= {fsbgpMpeComm 3 }

fsbgp4MpeCommRouteCommSetStatusEntry  OBJECT-TYPE
	SYNTAX      Fsbgp4MpeCommRouteCommSetStatusEntry
	MAX-ACCESS  not-accessible
	STATUS      current
	DESCRIPTION
    "Routes configured delete communities Table Entry"
    INDEX  {fsbgp4mpeCommSetStatusAfi,
            fsbgp4mpeCommSetStatusSafi,
            fsbgp4mpeCommSetStatusIpNetwork,
            fsbgp4mpeCommSetStatusIpPrefixLen
          }
	::= { fsbgp4MpeCommRouteCommSetStatusTable 1 }

Fsbgp4MpeCommRouteCommSetStatusEntry ::= SEQUENCE {
    fsbgp4mpeCommSetStatusAfi
        InetAddressType,
    fsbgp4mpeCommSetStatusSafi
        BgpSafi,
    fsbgp4mpeCommSetStatusIpNetwork
        InetAddress,
    fsbgp4mpeCommSetStatusIpPrefixLen
        Integer32,
    fsbgp4mpeCommSetStatus
        INTEGER,
    fsbgp4mpeCommSetStatusRowStatus
	RowStatus
    }

fsbgp4mpeCommSetStatusAfi  OBJECT-TYPE
    SYNTAX              InetAddressType
    MAX-ACCESS          not-accessible
    STATUS              current
    DESCRIPTION 
    "AFI of IP address of the destination"
    ::= { fsbgp4MpeCommRouteCommSetStatusEntry 1 } 

fsbgp4mpeCommSetStatusSafi OBJECT-TYPE
    SYNTAX              BgpSafi
    MAX-ACCESS          not-accessible
    STATUS              current
    DESCRIPTION 
    "SAFI of IP address of the destination"
    ::= { fsbgp4MpeCommRouteCommSetStatusEntry 2 } 

fsbgp4mpeCommSetStatusIpNetwork OBJECT-TYPE
	SYNTAX	   InetAddress
	MAX-ACCESS  not-accessible
	STATUS      current
	DESCRIPTION 
    "IP address of the destination"
	::= { fsbgp4MpeCommRouteCommSetStatusEntry 3 } 

fsbgp4mpeCommSetStatusIpPrefixLen   OBJECT-TYPE
	SYNTAX	    Integer32 (1..32)
	MAX-ACCESS   not-accessible
	STATUS       current
	DESCRIPTION 
    "IP prefix length for the destination"
	::= { fsbgp4MpeCommRouteCommSetStatusEntry 4 } 

fsbgp4mpeCommSetStatus OBJECT-TYPE
	SYNTAX	        INTEGER {
                                 none    (1),
                                 set     (2),
                                 setnone (3),
                                 modify  (4)
                              }
	MAX-ACCESS       read-create
	STATUS           current
	DESCRIPTION 
    "Community Set status for the Route. 
       o none     - is for read-only 
       o set      - to send only with configured additive communities
       o setnone  - to send without communities, 
       o modify   - to strip delete communities in received 
                    communities and add additive communities
     This object can be set only if fsbgp4LocalAs is configured." 
    DEFVAL { 4 }
	::= { fsbgp4MpeCommRouteCommSetStatusEntry 5 } 

fsbgp4mpeCommSetStatusRowStatus    OBJECT-TYPE
	SYNTAX	         RowStatus
	MAX-ACCESS	 read-create
	STATUS	         current
	DESCRIPTION 
	"Row status for creating entries into this table.
     This object can be set only if fsbgp4LocalAs is configured."
	::= { fsbgp4MpeCommRouteCommSetStatusEntry 6 } 

-- MIB FOR FSBGP_COMMUNITY end
-- MIB FOR FSBGP_EXTCOMM

--- Routes Additive Ext-Community Table
--- Represents the additive extended communities configured for
--- destinations.
fsbgpMpeExtComm   OBJECT IDENTIFIER ::= {fsbgp 30} 

fsbgp4MpeExtCommRouteAddExtCommTable OBJECT-TYPE
	SYNTAX        SEQUENCE OF Fsbgp4MpeExtCommRouteAddExtCommEntry
	MAX-ACCESS    not-accessible
	STATUS        current
	DESCRIPTION 
    "This table is used to configure additive extended communities
     for a given destination."
	::= {fsbgpMpeExtComm 1 }

fsbgp4MpeExtCommRouteAddExtCommEntry  OBJECT-TYPE
	SYNTAX      Fsbgp4MpeExtCommRouteAddExtCommEntry
	MAX-ACCESS  not-accessible
	STATUS      current
	DESCRIPTION
    "Routes configured additive ext-communities Table Entry"
    INDEX  {fsbgp4mpeAddExtCommRtAfi,
            fsbgp4mpeAddExtCommRtSafi,
            fsbgp4mpeAddExtCommIpNetwork,
            fsbgp4mpeAddExtCommIpPrefixLen,
            fsbgp4mpeAddExtCommVal
           }
	::= { fsbgp4MpeExtCommRouteAddExtCommTable 1 }

Fsbgp4MpeExtCommRouteAddExtCommEntry ::= SEQUENCE {
    fsbgp4mpeAddExtCommRtAfi
        InetAddressType,
    fsbgp4mpeAddExtCommRtSafi
        BgpSafi,
    fsbgp4mpeAddExtCommIpNetwork
        InetAddress,
    fsbgp4mpeAddExtCommIpPrefixLen
        Integer32,
    fsbgp4mpeAddExtCommVal
        OCTET STRING,
    fsbgp4mpeAddExtCommRowStatus
	     RowStatus
    }

fsbgp4mpeAddExtCommRtAfi   OBJECT-TYPE
    SYNTAX              InetAddressType
    MAX-ACCESS          not-accessible
    STATUS              current
    DESCRIPTION 
    "AFI of IP address of the destination"
    ::= { fsbgp4MpeExtCommRouteAddExtCommEntry 1 } 

fsbgp4mpeAddExtCommRtSafi  OBJECT-TYPE
    SYNTAX              BgpSafi
    MAX-ACCESS          not-accessible
    STATUS              current
    DESCRIPTION 
    "AFI of IP address of the destination"
    ::= { fsbgp4MpeExtCommRouteAddExtCommEntry 2 } 

fsbgp4mpeAddExtCommIpNetwork OBJECT-TYPE
	SYNTAX	   InetAddress
	MAX-ACCESS  not-accessible
	STATUS      current
	DESCRIPTION 
    "IP address of the destination"
	::= { fsbgp4MpeExtCommRouteAddExtCommEntry 3 } 

fsbgp4mpeAddExtCommIpPrefixLen   OBJECT-TYPE
	SYNTAX	    Integer32 (1..32)
	MAX-ACCESS   not-accessible
	STATUS       current
	DESCRIPTION 
    "IP prefix length for the destination"
	::= { fsbgp4MpeExtCommRouteAddExtCommEntry 4 } 

fsbgp4mpeAddExtCommVal    OBJECT-TYPE
	SYNTAX	        OCTET STRING  (SIZE(8)) 
	MAX-ACCESS       not-accessible
	STATUS           current
	DESCRIPTION 
    "Additive Ext-Community for the destination"
	::= { fsbgp4MpeExtCommRouteAddExtCommEntry 5 } 

fsbgp4mpeAddExtCommRowStatus    OBJECT-TYPE
	SYNTAX	         RowStatus
	MAX-ACCESS	     read-create
	STATUS	         current
	DESCRIPTION 
	"Row status for creating entries into this table.This object can be set
     only if fsbgp4LocalAs is configured."
	::= { fsbgp4MpeExtCommRouteAddExtCommEntry 6 } 

--- Routes Delete Ext-Community Table
--- Represents the extended communities to be deleted for the
--- destinations.

fsbgp4MpeExtCommRouteDeleteExtCommTable OBJECT-TYPE
	SYNTAX        SEQUENCE OF Fsbgp4MpeExtCommRouteDeleteExtCommEntry
	MAX-ACCESS    not-accessible
	STATUS        current
	DESCRIPTION 
    "This table is used to configure delete extended communities
     for a given destination."
	::= {fsbgpMpeExtComm 2 }

fsbgp4MpeExtCommRouteDeleteExtCommEntry  OBJECT-TYPE
	SYNTAX      Fsbgp4MpeExtCommRouteDeleteExtCommEntry
	MAX-ACCESS  not-accessible
	STATUS      current
	DESCRIPTION
    "Routes configured delete ext-communities Table Entry"
    INDEX  {fsbgp4mpeDeleteExtCommRtAfi,
            fsbgp4mpeDeleteExtCommRtSafi,
            fsbgp4mpeDeleteExtCommIpNetwork,
            fsbgp4mpeDeleteExtCommIpPrefixLen,
            fsbgp4mpeDeleteExtCommVal
           }
	::= { fsbgp4MpeExtCommRouteDeleteExtCommTable 1 }

Fsbgp4MpeExtCommRouteDeleteExtCommEntry ::= SEQUENCE {
    fsbgp4mpeDeleteExtCommRtAfi
        InetAddressType,
    fsbgp4mpeDeleteExtCommRtSafi
        BgpSafi,
    fsbgp4mpeDeleteExtCommIpNetwork
        InetAddress,
    fsbgp4mpeDeleteExtCommIpPrefixLen
        Integer32,
    fsbgp4mpeDeleteExtCommVal
	     OCTET STRING,
    fsbgp4mpeDeleteExtCommRowStatus
	     RowStatus
    }

fsbgp4mpeDeleteExtCommRtAfi    OBJECT-TYPE
    SYNTAX                  InetAddressType
    MAX-ACCESS              not-accessible
    STATUS                  current
    DESCRIPTION 
    "AFI of IP address of the destination"
    ::= { fsbgp4MpeExtCommRouteDeleteExtCommEntry 1 } 

fsbgp4mpeDeleteExtCommRtSafi   OBJECT-TYPE
    SYNTAX                  BgpSafi
    MAX-ACCESS              not-accessible
    STATUS                  current
    DESCRIPTION 
    "SAFI of IP address of the destination"
    ::= { fsbgp4MpeExtCommRouteDeleteExtCommEntry 2 } 
fsbgp4mpeDeleteExtCommIpNetwork OBJECT-TYPE
	SYNTAX	   InetAddress
	MAX-ACCESS  not-accessible
	STATUS      current
	DESCRIPTION 
    "IP address of the destination"
	::= { fsbgp4MpeExtCommRouteDeleteExtCommEntry 3 } 

fsbgp4mpeDeleteExtCommIpPrefixLen   OBJECT-TYPE
	SYNTAX	    Integer32 (1..32)
	MAX-ACCESS   not-accessible
	STATUS       current
	DESCRIPTION 
    "IP prefix length for the destination"
	::= { fsbgp4MpeExtCommRouteDeleteExtCommEntry 4 } 

fsbgp4mpeDeleteExtCommVal    OBJECT-TYPE
	SYNTAX	        OCTET STRING  (SIZE(8)) 
	MAX-ACCESS       not-accessible
	STATUS           current
	DESCRIPTION 
    "Delete Ext-Community for the destination"
	::= { fsbgp4MpeExtCommRouteDeleteExtCommEntry 5 } 

fsbgp4mpeDeleteExtCommRowStatus    OBJECT-TYPE
	SYNTAX	         RowStatus
	MAX-ACCESS	      read-create
	STATUS	         current
	DESCRIPTION 
	"Row status to create entries into this table. This object can be set only
         if fsbgp4LocalAs is configured."
	::= { fsbgp4MpeExtCommRouteDeleteExtCommEntry 6 } 

--- Routes Ext-Community Set Status Table
--- Represents the status or local policy (can be either, addition of extended
--- communities, deletion of extended communities or both or complete
--- ommission of extended communities) for destinations.

fsbgp4MpeExtCommRouteExtCommSetStatusTable OBJECT-TYPE
	SYNTAX        SEQUENCE OF Fsbgp4MpeExtCommRouteExtCommSetStatusEntry
	MAX-ACCESS    not-accessible
	STATUS        current
	DESCRIPTION 
    "This table is used to configure the local policy of extended communities
     for a given destination."
	::= {fsbgpMpeExtComm 3 }

fsbgp4MpeExtCommRouteExtCommSetStatusEntry  OBJECT-TYPE
	SYNTAX      Fsbgp4MpeExtCommRouteExtCommSetStatusEntry
	MAX-ACCESS  not-accessible
	STATUS      current
	DESCRIPTION
    "Routes configured delete ext-communities Table Entry"
    INDEX  { fsbgp4mpeExtCommSetStatusRtAfi,
             fsbgp4mpeExtCommSetStatusRtSafi,
             fsbgp4mpeExtCommSetStatusIpNetwork,
             fsbgp4mpeExtCommSetStatusIpPrefixLen
           }
	::= { fsbgp4MpeExtCommRouteExtCommSetStatusTable 1 }

Fsbgp4MpeExtCommRouteExtCommSetStatusEntry ::= SEQUENCE {
    fsbgp4mpeExtCommSetStatusRtAfi
        InetAddressType,
    fsbgp4mpeExtCommSetStatusRtSafi
        BgpSafi,
    fsbgp4mpeExtCommSetStatusIpNetwork
        InetAddress,
    fsbgp4mpeExtCommSetStatusIpPrefixLen
        Integer32,
    fsbgp4mpeExtCommSetStatus
        INTEGER,
    fsbgp4mpeExtCommSetStatusRowStatus
	RowStatus
    }

fsbgp4mpeExtCommSetStatusRtAfi OBJECT-TYPE
    SYNTAX                  InetAddressType
    MAX-ACCESS              not-accessible
    STATUS                  current
    DESCRIPTION 
    "AFI of IP address of the destination"
    ::= { fsbgp4MpeExtCommRouteExtCommSetStatusEntry 1 } 

fsbgp4mpeExtCommSetStatusRtSafi    OBJECT-TYPE
    SYNTAX                      BgpSafi
    MAX-ACCESS                  not-accessible
    STATUS                      current
    DESCRIPTION 
    "SAFI of IP address of the destination"
    ::= { fsbgp4MpeExtCommRouteExtCommSetStatusEntry 2 } 

fsbgp4mpeExtCommSetStatusIpNetwork OBJECT-TYPE
	SYNTAX	   InetAddress
	MAX-ACCESS  not-accessible
	STATUS      current
	DESCRIPTION 
    "IP address of the destination"
	::= { fsbgp4MpeExtCommRouteExtCommSetStatusEntry 3 } 

fsbgp4mpeExtCommSetStatusIpPrefixLen   OBJECT-TYPE
	SYNTAX	    Integer32 (1..32)
	MAX-ACCESS   not-accessible
	STATUS       current
	DESCRIPTION 
    "IP prefix length of the destination"
	::= { fsbgp4MpeExtCommRouteExtCommSetStatusEntry 4 } 

fsbgp4mpeExtCommSetStatus OBJECT-TYPE
	SYNTAX	        INTEGER {
                                 none    (1),
                                 set     (2),
                                 setnone (3),
                                 modify  (4)
                              }
	MAX-ACCESS       read-create
	STATUS           current
	DESCRIPTION 
    "Ext-Community Set status for the Route. 
       o none     - is for read-only 
       o set      - to send only with configured additive ext-communities
       o setnone  - to send without ext-communities, 
       o modify   - to strip delete ext-communities in received extended 
                    communities and add additive ext-communities.
     This object can be set only if fsbgp4LocalAs is configured." 
    DEFVAL { 4 }
	::= { fsbgp4MpeExtCommRouteExtCommSetStatusEntry 5 } 

fsbgp4mpeExtCommSetStatusRowStatus    OBJECT-TYPE
	SYNTAX	         RowStatus
	MAX-ACCESS	      read-create
	STATUS	         current
	DESCRIPTION 
	"Row status to create entries into this table. This object can be set only
         if fsbgp4LocalAs is configured."
	::= { fsbgp4MpeExtCommRouteExtCommSetStatusEntry 6 } 

--- Peer Link Bandwidth Table
--- Represents the link bandwidth for a given peer.

fsbgp4MpePeerLinkBwTable   OBJECT-TYPE
	SYNTAX              SEQUENCE OF Fsbgp4MpePeerLinkBwEntry
	MAX-ACCESS          not-accessible
	STATUS              current
	DESCRIPTION 
    "This table is used to configure the link bandwidths for a given peer"
	::= {fsbgpMpeExtComm 4}

fsbgp4MpePeerLinkBwEntry   OBJECT-TYPE
	SYNTAX              Fsbgp4MpePeerLinkBwEntry
	MAX-ACCESS          not-accessible
	STATUS              current
	DESCRIPTION
    "Peer Link Bandwidth Table Entry"
    	INDEX  { fsbgp4mpePeerLinkType,
             fsbgp4mpePeerLinkRemAddr
          }
	::= { fsbgp4MpePeerLinkBwTable 1 }

Fsbgp4MpePeerLinkBwEntry ::= SEQUENCE {
    fsbgp4mpePeerLinkType
        InetAddressType,
    fsbgp4mpePeerLinkRemAddr
    	InetAddress,
    fsbgp4mpeLinkBandWidth
      Unsigned32,
    fsbgp4mpePeerLinkBwRowStatus
		RowStatus
    }

fsbgp4mpePeerLinkType      OBJECT-TYPE
    SYNTAX              InetAddressType
    MAX-ACCESS          not-accessible
    STATUS              current
    DESCRIPTION 
    "AFI of IP address of the Peer"
    ::= { fsbgp4MpePeerLinkBwEntry 1 } 

fsbgp4mpePeerLinkRemAddr   OBJECT-TYPE
	SYNTAX	            InetAddress
	MAX-ACCESS           not-accessible
	STATUS               current
	DESCRIPTION 
    "IP address of the Peer"
	::= { fsbgp4MpePeerLinkBwEntry 2 } 

fsbgp4mpeLinkBandWidth OBJECT-TYPE
	SYNTAX	        Unsigned32 (7000..4294967295)
	MAX-ACCESS       read-create
	STATUS           current
	DESCRIPTION 
    "Link Bandwidth in bytes per second.This object can be set only if 
     fsbgp4LocalAs is configured."
	::= { fsbgp4MpePeerLinkBwEntry 3 } 

fsbgp4mpePeerLinkBwRowStatus   OBJECT-TYPE
	SYNTAX	                RowStatus
	MAX-ACCESS	             read-create
	STATUS	                current
	DESCRIPTION 
    "Row Status to create entries into this table.
     This object can be set only if fsbgp4LocalAs is configured." 
	::= { fsbgp4MpePeerLinkBwEntry 4 } 

-- MIB FOR FSBGP_EXTCOMM end
-- MIB FOR FSBGP_CABILITIES

fsbgpMpeCaps   OBJECT IDENTIFIER ::= {fsbgp 31}
--- Supported Capabilities Table

fsbgp4MpeCapSupportedCapsTable  OBJECT-TYPE
	SYNTAX      SEQUENCE OF Fsbgp4MpeCapSupportedCapsEntry
	MAX-ACCESS  not-accessible
	STATUS      current
	DESCRIPTION 
    "Supported Capabilities Table. This table contains, the capabilities
     that are supported for particular peer"
	::= {fsbgpMpeCaps 1 }

fsbgp4MpeCapSupportedCapsEntry OBJECT-TYPE
	SYNTAX                  Fsbgp4MpeCapSupportedCapsEntry
	MAX-ACCESS              not-accessible
	STATUS                  current
	DESCRIPTION
    "Entry contains supported Capabilites"
	INDEX  { fsbgp4mpeCapPeerType,
		 fsbgp4mpeCapPeerRemoteIpAddr,
                 fsbgp4mpeSupportedCapabilityCode, 
                 fsbgp4mpeSupportedCapabilityLength,
                 fsbgp4mpeSupportedCapabilityValue
           }
	::= { fsbgp4MpeCapSupportedCapsTable 1 }

Fsbgp4MpeCapSupportedCapsEntry ::= SEQUENCE {
    fsbgp4mpeCapPeerType
        InetAddressType,
    fsbgp4mpeCapPeerRemoteIpAddr
    	InetAddress,
    fsbgp4mpeSupportedCapabilityCode
        Integer32,
    fsbgp4mpeSupportedCapabilityLength
        Integer32,
    fsbgp4mpeSupportedCapabilityValue
        OCTET STRING,
    fsbgp4mpeCapSupportedCapsRowStatus
	 RowStatus,
    fsbgp4mpeCapAnnouncedStatus
        INTEGER,
    fsbgp4mpeCapReceivedStatus
        INTEGER,
    fsbgp4mpeCapNegotiatedStatus
        INTEGER,
    fsbgp4mpeCapConfiguredStatus
        INTEGER
    }

fsbgp4mpeCapPeerType OBJECT-TYPE
    SYNTAX        InetAddressType
    MAX-ACCESS  not-accessible
    STATUS      current
    DESCRIPTION
    "The remote IP Address of Peer "
    ::= { fsbgp4MpeCapSupportedCapsEntry 1 }

fsbgp4mpeCapPeerRemoteIpAddr OBJECT-TYPE
	SYNTAX	    InetAddress (SIZE (4..16)) 
	MAX-ACCESS  not-accessible 
	STATUS      current
	DESCRIPTION 
    "The remote IP Address of Peer "
	::= { fsbgp4MpeCapSupportedCapsEntry 2 } 

fsbgp4mpeSupportedCapabilityCode   OBJECT-TYPE
	SYNTAX	                    Integer32 (0..255)
	MAX-ACCESS                  not-accessible
	STATUS                      current
	DESCRIPTION 
    "BGP-4 Capability Advertisement Capability Code that is supported for 
     peer."

	::= { fsbgp4MpeCapSupportedCapsEntry 3 } 

fsbgp4mpeSupportedCapabilityLength OBJECT-TYPE
	SYNTAX	                    Integer32 (0..251)
	MAX-ACCESS                  not-accessible 
	STATUS                      current
	DESCRIPTION 
    "The length of the supported Capability data. Currently the
     max size is set as 16. Update the BGP_MAX_CAP_DATA_SIZE in
     inc/system.size file or BGP_DEF_MAX_CAP_DATA_SIZE in
     inc/size.h to increase this MAX value."
	::= { fsbgp4MpeCapSupportedCapsEntry 5 } 

fsbgp4mpeSupportedCapabilityValue  OBJECT-TYPE
	SYNTAX	                    OCTET STRING (SIZE(0..64)) 
	MAX-ACCESS                  not-accessible 
	STATUS                      current
	DESCRIPTION 
    "The value of the supported Capability"
	::= { fsbgp4MpeCapSupportedCapsEntry 6 } 

fsbgp4mpeCapSupportedCapsRowStatus OBJECT-TYPE
	SYNTAX	                    RowStatus
	MAX-ACCESS                  read-create
	STATUS	                    current
	DESCRIPTION 
	" The variable displays the status of the entry.Setting it to
        'invalid' has the effect of rendering it inoperative."
	::= { fsbgp4MpeCapSupportedCapsEntry 7 } 

fsbgp4mpeCapAnnouncedStatus        OBJECT-TYPE
    SYNTAX                      INTEGER {
                                    announced (1),
                                    notAnnounced (2)
                                  }
    MAX-ACCESS                  read-only
    STATUS                      current
    DESCRIPTION 
    " The variable displays the status whether the capability is 
      announced to the peer or not." 
    ::= { fsbgp4MpeCapSupportedCapsEntry 8 } 

fsbgp4mpeCapReceivedStatus        OBJECT-TYPE
    SYNTAX                      INTEGER {
                                    received (1),
                                    notReceived (2)
                                  }
    MAX-ACCESS                  read-only
    STATUS                      current
    DESCRIPTION 
    " The variable displays the status whether the capability is 
      received from the peer or not." 
    ::= { fsbgp4MpeCapSupportedCapsEntry 9 } 


fsbgp4mpeCapNegotiatedStatus       OBJECT-TYPE
    SYNTAX                      INTEGER {
                                    negotiated (1),
                                    notNegotiated(2)
                                  }
    MAX-ACCESS                  read-only
    STATUS                      current
    DESCRIPTION 
    " The variable displays the status whether the capability is 
      Negotiated to the peer or not." 
    ::= { fsbgp4MpeCapSupportedCapsEntry 10 } 

fsbgp4mpeCapConfiguredStatus       OBJECT-TYPE
    SYNTAX                      INTEGER {
                                    configured (1),
                                    automatic (2)
                                  }
    MAX-ACCESS                  read-only
    STATUS                      current
    DESCRIPTION
    "The variable displays the status whether the capability is
     enabled by default or through configuration"
    ::= { fsbgp4MpeCapSupportedCapsEntry 11 }

-- MIB FOR Route Refresh STARTS
fsbgp4MpeRtRefresh   OBJECT IDENTIFIER ::= {fsbgp 32} 

-- Route Refresh Inbound Table 

    fsbgp4MpeRtRefreshInboundTable OBJECT-TYPE
        SYNTAX     SEQUENCE OF Fsbgp4MpeRtRefreshInboundEntry
        MAX-ACCESS not-accessible
        STATUS     current
        DESCRIPTION
        "Route Refresh Inbound Table"
        ::= { fsbgp4MpeRtRefresh 1 }

    fsbgp4MpeRtRefreshInboundEntry OBJECT-TYPE
        SYNTAX     Fsbgp4MpeRtRefreshInboundEntry
        MAX-ACCESS not-accessible
        STATUS     current
        DESCRIPTION
        "Entry corresponds to Route Refresh Inbound."
        INDEX {
                fsbgp4mpeRtRefreshInboundPeerType,
                fsbgp4mpeRtRefreshInboundPeerAddr,
                fsbgp4mpeRtRefreshInboundAfi,
                fsbgp4mpeRtRefreshInboundSafi
              }
        ::= { fsbgp4MpeRtRefreshInboundTable 1 }

    Fsbgp4MpeRtRefreshInboundEntry ::= SEQUENCE {
        fsbgp4mpeRtRefreshInboundPeerType
           InetAddressType,
        fsbgp4mpeRtRefreshInboundPeerAddr
           InetAddress,
        fsbgp4mpeRtRefreshInboundAfi
           InetAddressType,
        fsbgp4mpeRtRefreshInboundSafi
           BgpSafi,
        fsbgp4mpeRtRefreshInboundRequest
          INTEGER,
        fsbgp4mpeRtRefreshInboundPrefixFilter
          INTEGER
        }

    fsbgp4mpeRtRefreshInboundPeerType OBJECT-TYPE
        SYNTAX     InetAddressType
        MAX-ACCESS not-accessible
        STATUS     current
        DESCRIPTION
        "Address Family Identifier of the peer remote address"
        ::= { fsbgp4MpeRtRefreshInboundEntry 1 }

    fsbgp4mpeRtRefreshInboundPeerAddr OBJECT-TYPE
        SYNTAX    InetAddress
        MAX-ACCESS not-accessible
        STATUS     current
        DESCRIPTION
        "The IP address of the peer for which the Route Refresh request has to
        be issued."
        ::= { fsbgp4MpeRtRefreshInboundEntry 2 }
        
    fsbgp4mpeRtRefreshInboundAfi   OBJECT-TYPE
        SYNTAX      InetAddressType
        MAX-ACCESS  not-accessible
        STATUS      current
        DESCRIPTION
        "The AFI for which the Route-Refresh message is to be sent"
        ::= { fsbgp4MpeRtRefreshInboundEntry 3 }

    fsbgp4mpeRtRefreshInboundSafi OBJECT-TYPE
        SYNTAX      BgpSafi
        MAX-ACCESS  not-accessible
        STATUS      current
        DESCRIPTION
        "The SAFI for which the Route-Refresh message is to be sent"
        ::= { fsbgp4MpeRtRefreshInboundEntry 4 }

    fsbgp4mpeRtRefreshInboundRequest OBJECT-TYPE
        SYNTAX     INTEGER
                   {
                       true (1)
                   }

        MAX-ACCESS read-write
        STATUS     current
        DESCRIPTION
        "Setting this object triggers the sending of the Route Refresh message
        to the peer. This object will be cleared once the Route Refresh message
        is sent to the peer. Route-Refresh message support is a default feature
        If not negotiated via capability negotiation, inbound soft-reconfig is
        internally done on setting this object."
        ::= { fsbgp4MpeRtRefreshInboundEntry 5 }

   fsbgp4mpeRtRefreshInboundPrefixFilter OBJECT-TYPE
        SYNTAX     INTEGER
                   {
                       true (1)
                   }

        MAX-ACCESS read-write
        STATUS     current
        DESCRIPTION
        "Setting this object triggers the sending of the ORF entris in the
        Route Refresh message to the peer. This object will be cleared once
        the ORF message is sent to the peer. Get operation of this object will always return 
        zero."
        ::= { fsbgp4MpeRtRefreshInboundEntry 6 }



--
-- Route Refresh Statistics Table
--

    fsbgp4MpeRtRefreshStatisticsTable OBJECT-TYPE
        SYNTAX     SEQUENCE OF Fsbgp4MpeRtRefreshStatisticsEntry
        MAX-ACCESS not-accessible
        STATUS     current
        DESCRIPTION
        "Route Refresh Statistics Table"
        ::= { fsbgp4MpeRtRefresh 2 }

    fsbgp4MpeRtRefreshStatisticsEntry OBJECT-TYPE
        SYNTAX     Fsbgp4MpeRtRefreshStatisticsEntry
        MAX-ACCESS not-accessible
        STATUS     current
        DESCRIPTION
        "Entry gives the statistics of Route Refresh."
        INDEX {
                fsbgp4mpeRtRefreshStatisticsPeerType,
                fsbgp4mpeRtRefreshStatisticsPeerAddr,
                fsbgp4mpeRtRefreshStatisticsAfi,
                fsbgp4mpeRtRefreshStatisticsSafi
              }
        ::= { fsbgp4MpeRtRefreshStatisticsTable 1 }

     Fsbgp4MpeRtRefreshStatisticsEntry ::= SEQUENCE {
        fsbgp4mpeRtRefreshStatisticsPeerType
            InetAddressType,
        fsbgp4mpeRtRefreshStatisticsPeerAddr
           InetAddress,
        fsbgp4mpeRtRefreshStatisticsAfi
           InetAddressType,
        fsbgp4mpeRtRefreshStatisticsSafi
           BgpSafi,
        fsbgp4mpeRtRefreshStatisticsRtRefMsgSentCntr 
           Counter32,
        fsbgp4mpeRtRefreshStatisticsRtRefMsgTxErrCntr 
           Counter32,
        fsbgp4mpeRtRefreshStatisticsRtRefMsgRcvdCntr 
           Counter32,
        fsbgp4mpeRtRefreshStatisticsRtRefMsgInvalidCntr 
           Counter32
          
        }

     fsbgp4mpeRtRefreshStatisticsPeerType OBJECT-TYPE
        SYNTAX     InetAddressType
        MAX-ACCESS not-accessible
        STATUS     current
        DESCRIPTION
        "Address Family Identifier of the peer remote address."
        ::= { fsbgp4MpeRtRefreshStatisticsEntry 1 }

    fsbgp4mpeRtRefreshStatisticsPeerAddr OBJECT-TYPE
        SYNTAX     InetAddress
        MAX-ACCESS not-accessible
        STATUS     current
        DESCRIPTION
        "The IP address of the peer for which the Route Refresh Statistics has
        to be read."
        ::= { fsbgp4MpeRtRefreshStatisticsEntry 2 }
 
    fsbgp4mpeRtRefreshStatisticsAfi OBJECT-TYPE
        SYNTAX     InetAddressType
        MAX-ACCESS not-accessible
        STATUS     current
        DESCRIPTION
        "AFI for for which the Route Refresh Statistics has
        to be read."
        ::= { fsbgp4MpeRtRefreshStatisticsEntry 3 }

    fsbgp4mpeRtRefreshStatisticsSafi OBJECT-TYPE
        SYNTAX     BgpSafi 
        MAX-ACCESS not-accessible
        STATUS     current
        DESCRIPTION
        "SAFI for for which the Route Refresh Statistics has
        to be read."
        ::= { fsbgp4MpeRtRefreshStatisticsEntry 4 }

     fsbgp4mpeRtRefreshStatisticsRtRefMsgSentCntr OBJECT-TYPE
        SYNTAX     Counter32 
        MAX-ACCESS read-only 
        STATUS     current
        DESCRIPTION
        " The number of Route Refresh messages sent to the peer."
        ::= { fsbgp4MpeRtRefreshStatisticsEntry 5 }
 
     fsbgp4mpeRtRefreshStatisticsRtRefMsgTxErrCntr OBJECT-TYPE
        SYNTAX     Counter32 
        MAX-ACCESS read-only 
        STATUS     current
        DESCRIPTION
        " The number of Route Refresh messages that could not be 
          transmitted to the peer."
        ::= { fsbgp4MpeRtRefreshStatisticsEntry 6 }
 
    fsbgp4mpeRtRefreshStatisticsRtRefMsgRcvdCntr OBJECT-TYPE
        SYNTAX     Counter32 
        MAX-ACCESS read-only 
        STATUS     current
        DESCRIPTION
        " The number of Route Refresh messages received from the peer."
        ::= { fsbgp4MpeRtRefreshStatisticsEntry 7 }
 
     fsbgp4mpeRtRefreshStatisticsRtRefMsgInvalidCntr OBJECT-TYPE
        SYNTAX     Counter32 
        MAX-ACCESS read-only 
        STATUS     current
        DESCRIPTION
        " The number of invalid Route Refresh messages received from the peer."
        ::= { fsbgp4MpeRtRefreshStatisticsEntry 8 }
 
-- MIB FOR OutBound Soft-Reconfig STARTS
fsbgp4MpeSoftReconfigOut   OBJECT IDENTIFIER ::= {fsbgp 33} 

    fsbgp4MpeSoftReconfigOutboundTable OBJECT-TYPE
        SYNTAX     SEQUENCE OF Fsbgp4MpeSoftReconfigOutboundEntry
        MAX-ACCESS not-accessible
        STATUS     current
        DESCRIPTION
        "Soft Reconfig outbound Table"
        ::= { fsbgp4MpeSoftReconfigOut 1 }

    fsbgp4MpeSoftReconfigOutboundEntry OBJECT-TYPE
        SYNTAX     Fsbgp4MpeSoftReconfigOutboundEntry
        MAX-ACCESS not-accessible
        STATUS     current
        DESCRIPTION
        "Entry corresponds to Soft Reconfig outbound."
        INDEX {
                fsbgp4mpeSoftReconfigOutboundPeerType,
                fsbgp4mpeSoftReconfigOutboundPeerAddr,
                fsbgp4mpeSoftReconfigOutboundAfi,
                fsbgp4mpeSoftReconfigOutboundSafi
              }
        ::= { fsbgp4MpeSoftReconfigOutboundTable 1 }

    Fsbgp4MpeSoftReconfigOutboundEntry ::= SEQUENCE {
        fsbgp4mpeSoftReconfigOutboundPeerType
            InetAddressType,
        fsbgp4mpeSoftReconfigOutboundPeerAddr
           InetAddress,
        fsbgp4mpeSoftReconfigOutboundAfi
            InetAddressType,
        fsbgp4mpeSoftReconfigOutboundSafi
            BgpSafi,
        fsbgp4mpeSoftReconfigOutboundRequest
          INTEGER
        }

    fsbgp4mpeSoftReconfigOutboundPeerType OBJECT-TYPE
        SYNTAX     InetAddressType
        MAX-ACCESS not-accessible
        STATUS     current
        DESCRIPTION
        "Address Family Identifier of the peer remote address"
        ::= { fsbgp4MpeSoftReconfigOutboundEntry 1 }

    fsbgp4mpeSoftReconfigOutboundPeerAddr OBJECT-TYPE
        SYNTAX    InetAddress
        MAX-ACCESS not-accessible
        STATUS     current
        DESCRIPTION
        "The IP address of the peer for which the outbound soft-reconfig has to
        be performed."
        ::= { fsbgp4MpeSoftReconfigOutboundEntry 2 }
        
    fsbgp4mpeSoftReconfigOutboundAfi   OBJECT-TYPE
        SYNTAX     InetAddressType
        MAX-ACCESS not-accessible
        STATUS     current
        DESCRIPTION
        "AFI for which the outbound soft-reconfig has to
        be performed."
        ::= { fsbgp4MpeSoftReconfigOutboundEntry 3 }

    fsbgp4mpeSoftReconfigOutboundSafi  OBJECT-TYPE
        SYNTAX     BgpSafi
        MAX-ACCESS not-accessible
        STATUS     current
        DESCRIPTION
        "SAFI for which the outbound soft-reconfig has to
        be performed."
        ::= { fsbgp4MpeSoftReconfigOutboundEntry 4 }

    fsbgp4mpeSoftReconfigOutboundRequest OBJECT-TYPE
        SYNTAX     INTEGER
                   {
                       true (1)
                   }

        MAX-ACCESS read-write
        STATUS     current
        DESCRIPTION
        "Setting this object triggers the outbound soft-reconfig process for the         peer. This object value is cleared once the soft-reconfig process is
         completed." 
        ::= { fsbgp4MpeSoftReconfigOutboundEntry 5 }

--
-- Prefix counter table
--

    fsbgp4MpePrefixCountersTable OBJECT-TYPE
        SYNTAX     SEQUENCE OF Fsbgp4MpePrefixCountersEntry
        MAX-ACCESS not-accessible
        STATUS     current
        DESCRIPTION
        "Additional per-peer, per AFI/SAFI counters for prefixes"
        ::= { fsbgp 34 }

    fsbgp4MpePrefixCountersEntry OBJECT-TYPE
        SYNTAX     Fsbgp4MpePrefixCountersEntry
        MAX-ACCESS not-accessible
        STATUS     current
        DESCRIPTION
        "Entry containing information about a bgp-peer's prefix
        counters."
        INDEX {
        fsbgp4MpePeerRemoteAddrType,
        fsbgp4MpePeerRemoteAddr,
        fsbgp4MpePrefixCountersAfi,
        fsbgp4MpePrefixCountersSafi
            }
        ::= { fsbgp4MpePrefixCountersTable 1 }

    Fsbgp4MpePrefixCountersEntry ::= SEQUENCE {
        fsbgp4MpePeerRemoteAddrType
            InetAddressType,
        fsbgp4MpePeerRemoteAddr
            InetAddress,
        fsbgp4MpePrefixCountersAfi
            InetAddressType,
        fsbgp4MpePrefixCountersSafi
            BgpSafi,
        fsbgp4MpePrefixCountersPrefixesReceived
            Counter32,
        fsbgp4MpePrefixCountersPrefixesSent
            Counter32,
        fsbgp4MpePrefixCountersWithdrawsReceived
            Counter32,
        fsbgp4MpePrefixCountersWithdrawsSent
            Counter32,
        fsbgp4MpePrefixCountersInPrefixes
            Gauge32,
        fsbgp4MpePrefixCountersInPrefixesAccepted
            Gauge32,
        fsbgp4MpePrefixCountersInPrefixesRejected
            Gauge32,
        fsbgp4MpePrefixCountersOutPrefixes
            Gauge32
        }

    fsbgp4MpePeerRemoteAddrType OBJECT-TYPE
        SYNTAX     InetAddressType
        MAX-ACCESS not-accessible
        STATUS     current
        DESCRIPTION
        "The type of the remote address of peer."
        ::= { fsbgp4MpePrefixCountersEntry 1 }

    fsbgp4MpePeerRemoteAddr   OBJECT-TYPE
        SYNTAX     InetAddress
        MAX-ACCESS not-accessible
        STATUS     current
        DESCRIPTION
        "The remote address of the peer."
        ::= { fsbgp4MpePrefixCountersEntry 2 }

    fsbgp4MpePrefixCountersAfi OBJECT-TYPE
        SYNTAX     InetAddressType
        MAX-ACCESS not-accessible
        STATUS     current
        DESCRIPTION
        "The AFI index of the per-peer, per prefix counters"
        ::= { fsbgp4MpePrefixCountersEntry 3 }

    fsbgp4MpePrefixCountersSafi OBJECT-TYPE
        SYNTAX     BgpSafi
        MAX-ACCESS not-accessible
        STATUS     current
        DESCRIPTION
        "The SAFI index of the per-peer, per prefix counters"
        ::= { fsbgp4MpePrefixCountersEntry 4 }

    fsbgp4MpePrefixCountersPrefixesReceived OBJECT-TYPE
        SYNTAX     Counter32
        MAX-ACCESS read-only
        STATUS     current
        DESCRIPTION
        "Total number of discrete prefixes received from this peer. The
        value in fsbgp4MpePrefixCountersPrefixesReceived will be greater
        than or equal to what is in fsbgp4MpePrefixCountersInPrefixes, 
        since it will reflect prefixes received from this peer which
        may have been subsquently withdrawn, and hence will no longer
        be stored in the Adj-Ribs-In for that peer."
        ::= { fsbgp4MpePrefixCountersEntry 5 }

    fsbgp4MpePrefixCountersPrefixesSent OBJECT-TYPE
        SYNTAX     Counter32
        MAX-ACCESS read-only
        STATUS     current
        DESCRIPTION
        "Total number of prefixes which the local BGP speaker
        has announced to this peer.  The value for 
        fsbgp4MpePrefixCountersPrefixesSent will be greater than or equal to 
        fsbgp4MpePrefixCountersOutPrefixes, since it reflects prefixes 
        which have been subsequently withdrawn after their announcement
        (assuming any such withdrawn prefixes exist)."
        ::= { fsbgp4MpePrefixCountersEntry 6 }

    fsbgp4MpePrefixCountersWithdrawsReceived OBJECT-TYPE
        SYNTAX     Counter32
        MAX-ACCESS read-only
        STATUS     current
        DESCRIPTION
        "Total number of prefixes withdrawn by this peer.  Specifically,
        this is the total number of withdrawn-routes which have
        been received in UPDATE messages from this peer."
        ::= { fsbgp4MpePrefixCountersEntry 7 }

    fsbgp4MpePrefixCountersWithdrawsSent  OBJECT-TYPE
        SYNTAX      Counter32
        MAX-ACCESS  read-only
        STATUS      current
        DESCRIPTION
        "Total number of prefixes which have been reported as 
        withdrawn by the local BGP speaker to the peer in 
        locally generated UPDATE messages to the peer."
        ::= { fsbgp4MpePrefixCountersEntry 8 }
	
	fsbgp4MpePrefixCountersInPrefixes OBJECT-TYPE
        SYNTAX     Gauge32
        MAX-ACCESS read-only
        STATUS     current
        DESCRIPTION
        "The number of prefixes received from a peer and are
         stored in the Adj-Ribs-In for that peer."
        -- jmh - note that we're allowing stuff to be discarded
        ::= { fsbgp4MpePrefixCountersEntry 9 }


    fsbgp4MpePrefixCountersInPrefixesAccepted OBJECT-TYPE
        SYNTAX     Gauge32
        MAX-ACCESS read-only
        STATUS     current
        DESCRIPTION
        "The number of prefixes for a peer that are installed
         in the Adj-Ribs-In and are eligible to become active
         in the Loc-Rib."
        ::= { fsbgp4MpePrefixCountersEntry 10 }


    fsbgp4MpePrefixCountersInPrefixesRejected OBJECT-TYPE
        SYNTAX     Gauge32
        MAX-ACCESS read-only
        STATUS     current
        DESCRIPTION
        "The number of prefixes for a peer that are installed
         in the Adj-Ribs-In and are NOT eligible to become active
         in the Loc-Rib."
        ::= { fsbgp4MpePrefixCountersEntry 11 }

    fsbgp4MpePrefixCountersOutPrefixes OBJECT-TYPE
        SYNTAX     Gauge32
        MAX-ACCESS read-only
        STATUS     current
        DESCRIPTION
        "The number of prefixes for a peer that are installed
         in that peer's Adj-Ribs-Out."
        ::= { fsbgp4MpePrefixCountersEntry 12 }

--**************************************************************************
-- MIB for BGP/MPLS VPN starts.

fsbgp4MplsVpn OBJECT IDENTIFIER ::= {fsbgp 35} 

-- Fsbgp4MplsVpnRouteTargetTable

fsbgp4MplsVpnVrfRouteTargetTable OBJECT-TYPE
    SYNTAX        SEQUENCE OF Fsbgp4MplsVpnVrfRouteTargetEntry
    MAX-ACCESS    not-accessible
    STATUS        current
    DESCRIPTION
    "This table specifies per-VRF route target association.
     Each entry identifies a connectivity policy supported
     as part of a VPN."
   ::= { fsbgp4MplsVpn 1 }

fsbgp4MplsVpnVrfRouteTargetEntry OBJECT-TYPE
    SYNTAX        Fsbgp4MplsVpnVrfRouteTargetEntry
    MAX-ACCESS    not-accessible
    STATUS        current
    DESCRIPTION
    "An entry in this table is created by an LSR (PE router) 
     for each route target configured for a VRF supporting
     a MPLS/BGP VPN instance. The indexing provides an
     ordering per-VRF instance."
    INDEX  { fsbgp4MplsVpnVrfName,  fsbgp4MplsVpnVrfRouteTargetType,
             fsbgp4MplsVpnVrfRouteTarget }
    ::= { fsbgp4MplsVpnVrfRouteTargetTable 1 }

Fsbgp4MplsVpnVrfRouteTargetEntry ::= SEQUENCE {
    fsbgp4MplsVpnVrfName                  DisplayString,
    fsbgp4MplsVpnVrfRouteTargetType       INTEGER,
    fsbgp4MplsVpnVrfRouteTarget           DisplayString,
    fsbgp4MplsVpnVrfRouteTargetRowStatus  RowStatus
   }

fsbgp4MplsVpnVrfName OBJECT-TYPE
    SYNTAX          DisplayString(SIZE(0..16))
    MAX-ACCESS      not-accessible
    STATUS          current
    DESCRIPTION
    "The human-readable name of this VPN. This MAY be equivalent to the 
     RFC2685 VPN-ID, but may also vary. If it is set to the VPN ID, it MUST
     be equivalent to the value of mplsVpnVrfVpnId. It is strongly 
     recommended that all sites supporting VRFs that are part of the same 
     VPN use the same naming convention for VRFs as well as the same VPN ID."
   ::= { fsbgp4MplsVpnVrfRouteTargetEntry 1 }

fsbgp4MplsVpnVrfRouteTargetType OBJECT-TYPE
    SYNTAX          INTEGER { import(1), 
                              export(2), 
                              both(3) }
    MAX-ACCESS      not-accessible
    STATUS          current
    DESCRIPTION
    "The route target type. If set to both means, the route target will be
    assigned as import target and export target."
   ::= { fsbgp4MplsVpnVrfRouteTargetEntry 2 }

fsbgp4MplsVpnVrfRouteTarget OBJECT-TYPE
    SYNTAX          DisplayString(SIZE(0..8))
    MAX-ACCESS      not-accessible 
    STATUS          current
    DESCRIPTION
    "The route target distribution policy."
   ::= { fsbgp4MplsVpnVrfRouteTargetEntry 3 }

fsbgp4MplsVpnVrfRouteTargetRowStatus OBJECT-TYPE
    SYNTAX          RowStatus
    MAX-ACCESS      read-create
    STATUS          current
    DESCRIPTION
    "Row status for this entry."
   ::= { fsbgp4MplsVpnVrfRouteTargetEntry 4 }

-- Fsbgp4MplsVpnVrfRedistributeTable

fsbgp4MplsVpnVrfRedistributeTable OBJECT-TYPE
    SYNTAX          SEQUENCE OF Fsbgp4MplsVpnVrfRedistributeEntry
    MAX-ACCESS      not-accessible
    STATUS          current
    DESCRIPTION
    "This table specifies per-VRF ipv4 redistribution."
   ::= { fsbgp4MplsVpn 2 }

fsbgp4MplsVpnVrfRedistributeEntry OBJECT-TYPE
    SYNTAX          Fsbgp4MplsVpnVrfRedistributeEntry
    MAX-ACCESS      not-accessible
    STATUS          current
    DESCRIPTION
    "An entry in this table is created by an LSR (PE router) 
     for a VRF supporting a MPLS/BGP VPN instance. The indexing 
     provides an ordering per-VRF instance."
   INDEX  { fsbgp4MplsVpnVrfRedisAfi, fsbgp4MplsVpnVrfRedisSafi,
            fsbgp4MplsVpnVrfName}
   ::= { fsbgp4MplsVpnVrfRedistributeTable 1 }

Fsbgp4MplsVpnVrfRedistributeEntry ::= SEQUENCE {
    fsbgp4MplsVpnVrfRedisAfi           InetAddressType,
    fsbgp4MplsVpnVrfRedisSafi          BgpSafi,
    fsbgp4MplsVpnVrfRedisProtoMask     Integer32
}

fsbgp4MplsVpnVrfRedisAfi OBJECT-TYPE
    SYNTAX      InetAddressType
    MAX-ACCESS  not-accessible
    STATUS      current
    DESCRIPTION
    "Address Family Identifier of VPN VRF redistribution and it takes only ipv4"
    ::= { fsbgp4MplsVpnVrfRedistributeEntry 1 }

fsbgp4MplsVpnVrfRedisSafi OBJECT-TYPE
    SYNTAX      BgpSafi 
    MAX-ACCESS  not-accessible
    STATUS      current
    DESCRIPTION
    "Subsequent Address Family Identifier of VPN VRF redistribution and
     it takes only vpnv4" 
    ::= { fsbgp4MplsVpnVrfRedistributeEntry 2 }

fsbgp4MplsVpnVrfRedisProtoMask  OBJECT-TYPE
    SYNTAX      Integer32
    MAX-ACCESS  read-write
    STATUS      current
    DESCRIPTION
    "The bit mask of source protocols from which routes are
     imported to BGP.(LSB corresponds to Bit 0)

     Bit 1, if set, indicates that direct routes can be 
     redistributed into BGP. (value = 2)

     Bit 2, if set, indicates that static routes can be 
     redistributed into BGP. (value = 4)

     Bit 7, if set, indicates that routes from RIP can be 
     redistributed into  BGP. (value = 128)

     Bit 12, if set, indicates that OSPF routes can be 
     redistributed into BGP. (value = 4096)

     Other bits are reserved for future use. This object can be
     set only if VRF is created already.

     If different route protocols to be redistributed, then the
     value to be set must be the combination of (total) the 
     individual protocol redistribution values.
     
     Value of '0' indicates, disabling the redistribution completely"
    ::= { fsbgp4MplsVpnVrfRedistributeEntry 3 }

-- Fsbgp4MplsVpnRRRouteTargetSetTable

fsbgp4MplsVpnRRRouteTargetTable OBJECT-TYPE
    SYNTAX        SEQUENCE OF Fsbgp4MplsVpnRRRouteTargetEntry
    MAX-ACCESS    not-accessible
    STATUS        current
    DESCRIPTION
    "This table specifies Route Reflector Import Route Target set.
     If the speaker is a route reflector, the import targets that are 
     received from client peer, will be mainitained in a set. When there are
     no more routes assoiciated with a particular import route target,
     then some delay (few hours) will be allowed before deleting that route
     target from the set. This table gives the information about the route
     targets in the set, and the no.of routes associated individually and the
     time after which it will be deleted from the set"
   ::= { fsbgp4MplsVpn 3 }

fsbgp4MplsVpnRRRouteTargetEntry OBJECT-TYPE
    SYNTAX        Fsbgp4MplsVpnRRRouteTargetEntry
    MAX-ACCESS    not-accessible
    STATUS        current
    DESCRIPTION
    "An entry in this table is created whenever a new import route target
    is received along with a route from client peers.
    The index to the table is the import route target in the set itself."
    INDEX  { fsbgp4MplsVpnRRRouteTarget }
    ::= { fsbgp4MplsVpnRRRouteTargetTable 1 }

Fsbgp4MplsVpnRRRouteTargetEntry ::= SEQUENCE {
    fsbgp4MplsVpnRRRouteTarget            DisplayString,
    fsbgp4MplsVpnRRRouteTargetRtCnt       Integer32,
    fsbgp4MplsVpnRRRouteTargetTimeStamp   Integer32
   }

fsbgp4MplsVpnRRRouteTarget OBJECT-TYPE
    SYNTAX          DisplayString(SIZE(0..8))
    MAX-ACCESS      not-accessible 
    STATUS          current
    DESCRIPTION
    "The import route target in the set."
   ::= { fsbgp4MplsVpnRRRouteTargetEntry 1 }

fsbgp4MplsVpnRRRouteTargetRtCnt     OBJECT-TYPE
    SYNTAX                          Integer32
    MAX-ACCESS                      read-only
    STATUS                          current
    DESCRIPTION
    "The no.of routes received/associated with this route target. i.e no.of
    routes that are received with this import route target from client peers"
   ::= { fsbgp4MplsVpnRRRouteTargetEntry 2 }

fsbgp4MplsVpnRRRouteTargetTimeStamp OBJECT-TYPE
    SYNTAX                          Integer32
    MAX-ACCESS                      read-only
    STATUS                          current
    DESCRIPTION
    "The time after which the import route target will be removed from the set.
    A value of zero indicates, it is not to be deleted. When this value is
    a positive number, then the above mib object should be having a value of 0"
   ::= { fsbgp4MplsVpnRRRouteTargetEntry 3 }

-- FILTERING OBJECT DEFINITION BEGIN

 fsbgp4DistInOutRouteMap OBJECT IDENTIFIER ::= { fsbgp 36 }

    fsBgp4DistInOutRouteMapTable OBJECT-TYPE
        SYNTAX SEQUENCE OF FsBgp4DistInOutRouteMapEntry
        MAX-ACCESS          not-accessible
        STATUS              current
        DESCRIPTION
            "A table describing the configuration of filtering for route map."
    ::= { fsbgp4DistInOutRouteMap 1 }

    fsBgp4DistInOutRouteMapEntry OBJECT-TYPE
        SYNTAX FsBgp4DistInOutRouteMapEntry
        MAX-ACCESS          not-accessible
        STATUS              current
        DESCRIPTION
            "Information describing the filtering configuration of single entry."
        INDEX {fsBgp4DistInOutRouteMapName, fsBgp4DistInOutRouteMapType}
    ::=  { fsBgp4DistInOutRouteMapTable 1 }

    FsBgp4DistInOutRouteMapEntry ::= SEQUENCE {
        fsBgp4DistInOutRouteMapName         DisplayString,
        fsBgp4DistInOutRouteMapType         Integer32,
        fsBgp4DistInOutRouteMapValue        Integer32,
        fsBgp4DistInOutRouteMapRowStatus    RowStatus
    }

    fsBgp4DistInOutRouteMapName OBJECT-TYPE
        SYNTAX              DisplayString (SIZE(1..20))
        MAX-ACCESS          not-accessible
        STATUS              current
        DESCRIPTION
            "Route map name."
    ::=  { fsBgp4DistInOutRouteMapEntry 1 }

    fsBgp4DistInOutRouteMapType OBJECT-TYPE
        SYNTAX              Integer32(1..3)
        MAX-ACCESS          not-accessible
        STATUS              current
        DESCRIPTION
            "Type of route map to indicate the route map is for
            distribute in or for distribute out or for distance.
            1 - distance
            2 - distribute in
            3 - distribute out"
    ::=  { fsBgp4DistInOutRouteMapEntry 2 }

    fsBgp4DistInOutRouteMapValue  OBJECT-TYPE
        SYNTAX              Integer32(1..255)
        MAX-ACCESS          read-write
        STATUS              current
        DESCRIPTION
            "Distance value ( this will be unused for distribute list )"
    ::=  { fsBgp4DistInOutRouteMapEntry 3 }

    fsBgp4DistInOutRouteMapRowStatus OBJECT-TYPE
        SYNTAX              RowStatus
        MAX-ACCESS          read-write
        STATUS              current
        DESCRIPTION
            "The status of this row, by which new entries may be
            created, or old entries deleted from this table."
    ::=  { fsBgp4DistInOutRouteMapEntry 4 }

-- FILTERING OBJECT DEFINITION END

-- PREFERENCE OBJECT DEFINITION BEGIN

 fsbgp4PreferenceGroup OBJECT IDENTIFIER ::=  { fsbgp 37 }

   fsBgp4PreferenceValue OBJECT-TYPE
       SYNTAX Integer32 (0..255)
       MAX-ACCESS read-write
       STATUS current
       DESCRIPTION
           "Preference value for RIP routes. Use '0' to set default value"
       DEFVAL { 122 }
       ::= { fsbgp4PreferenceGroup 1 }

-- PREFERENCE OBJECT DEFINITION END


-- TRAP objects
fsbgp4Notification OBJECT IDENTIFIER ::= {fsbgp 38}
fsbgp4Trap         OBJECT IDENTIFIER ::= {fsbgp4Notification 0}
fsbgp4RestartStatusChange NOTIFICATION-TYPE
        OBJECTS  {
                   fsbgp4Identifier,	
                   fsbgp4RestartStatus,
                   fsbgp4GRRestartTimeInterval,
                   fsbgp4RestartExitReason
                 }
        STATUS             current
        DESCRIPTION
    "A fsbgp4RestartStatusChange trap signifies that there has 
    been a change in the graceful restart state for the router. 
    This trap should be generated when the router restart status changes."
    ::= {fsbgp4Trap 1}

-- ROUTE-MAP ON NEIGHBOUR 

fsbgp4NeighborRouteMap OBJECT IDENTIFIER ::= { fsbgp 39 }

    fsBgp4NeighborRouteMapTable OBJECT-TYPE
        SYNTAX SEQUENCE OF FsBgp4NeighborRouteMapEntry
        MAX-ACCESS          not-accessible
        STATUS              current
        DESCRIPTION
            "A table describing the configuration of route map on a neighbour."
    ::= { fsbgp4NeighborRouteMap 1 }

    fsBgp4NeighborRouteMapEntry OBJECT-TYPE
        SYNTAX FsBgp4NeighborRouteMapEntry
        MAX-ACCESS          not-accessible
        STATUS              current
        DESCRIPTION
            "Information describing the routemap configuration of single entry."
        INDEX {fsBgp4NeighborRouteMapPeerAddrType, fsBgp4NeighborRouteMapPeer, fsBgp4NeighborRouteMapDirection}
    ::=  { fsBgp4NeighborRouteMapTable 1 }

    FsBgp4NeighborRouteMapEntry ::= SEQUENCE {
        fsBgp4NeighborRouteMapPeerAddrType InetAddressType,
        fsBgp4NeighborRouteMapPeer         InetAddress,
        fsBgp4NeighborRouteMapDirection    INTEGER,
        fsBgp4NeighborRouteMapName         DisplayString,
        fsBgp4NeighborRouteMapRowStatus    RowStatus
    }

    fsBgp4NeighborRouteMapPeerAddrType OBJECT-TYPE
        SYNTAX              InetAddressType
        MAX-ACCESS          not-accessible
        STATUS              current
        DESCRIPTION
            "Adress type of the Neighbor."
    ::=  { fsBgp4NeighborRouteMapEntry 1 }

    fsBgp4NeighborRouteMapPeer OBJECT-TYPE
        SYNTAX              InetAddress
        MAX-ACCESS          not-accessible
        STATUS              current
        DESCRIPTION
            "IpAddress of the Neighbor."
    ::=  { fsBgp4NeighborRouteMapEntry 2 }

    fsBgp4NeighborRouteMapDirection OBJECT-TYPE
        SYNTAX              INTEGER{ in(1) ,
                                     out(2)
                                   }
        MAX-ACCESS          not-accessible  
        STATUS              current
        DESCRIPTION
            "Direction of route map to indicate the route map is for in or out.
             In direction routemap is to apply the routemap rules for incoming routes from
             the peer.Out direction routemap is to apply the routemap for on the 
             advertising routes to the peer.

            1 - in
            2 - out"
    ::=  { fsBgp4NeighborRouteMapEntry 3 }

    fsBgp4NeighborRouteMapName OBJECT-TYPE
        SYNTAX              DisplayString (SIZE(1..20))
        MAX-ACCESS          read-write
        STATUS              current
        DESCRIPTION
            "Route map name."
    ::=  { fsBgp4NeighborRouteMapEntry 4 }

    fsBgp4NeighborRouteMapRowStatus OBJECT-TYPE
        SYNTAX              RowStatus
        MAX-ACCESS          read-write
        STATUS              current
        DESCRIPTION
            "The status of this row, by which new entries may be
            created, or old entries deleted from this table."
    ::=  { fsBgp4NeighborRouteMapEntry 5 }


-- BGP Peer Group Table

    fsBgp4PeerGroupTable OBJECT-TYPE
    SYNTAX SEQUENCE OF  FsBgp4PeerGroupEntry
    MAX-ACCESS          not-accessible
    STATUS              current
    DESCRIPTION
        "A table for configuring the bgp peer groups. Configuring
         a property for the peer group copies it to all the peers 
         present in the peer group."
    ::= { fsbgp 40 }

    fsBgp4PeerGroupEntry OBJECT-TYPE
    SYNTAX      FsBgp4PeerGroupEntry
    MAX-ACCESS  not-accessible
    STATUS      current
    DESCRIPTION
        "An entry describing the bgp peer group."
        INDEX { fsBgp4PeerGroupName }
    ::=  { fsBgp4PeerGroupTable 1 }

    FsBgp4PeerGroupEntry ::= SEQUENCE {
        fsBgp4PeerGroupName          DisplayString,
        fsBgp4PeerGroupAddrType      InetAddressType,
        fsBgp4PeerGroupRemoteAs      Unsigned32,
        fsBgp4PeerGroupHoldTimeConfigured   Integer32,
        fsBgp4PeerGroupKeepAliveConfigured  Integer32,
        fsBgp4PeerGroupConnectRetryInterval Integer32,
        fsBgp4PeerGroupMinASOriginInterval Integer32,
        fsBgp4PeerGroupMinRouteAdvInterval Integer32,
        fsBgp4PeerGroupAllowAutomaticStart INTEGER,
        fsBgp4PeerGroupAllowAutomaticStop  INTEGER,
        fsBgp4PeerGroupIdleHoldTimeConfigured Integer32,
        fsBgp4PeerGroupDampPeerOscillations   INTEGER,
        fsBgp4PeerGroupDelayOpen     INTEGER,
        fsBgp4PeerGroupDelayOpenTimeConfigured Integer32,
        fsBgp4PeerGroupPrefixUpperLimit Integer32,
        fsBgp4PeerGroupTcpConnectRetryCnt Integer32,
        fsBgp4PeerGroupEBGPMultiHop  INTEGER,
        fsBgp4PeerGroupEBGPHopLimit  Integer32,
        fsBgp4PeerGroupNextHopSelf   INTEGER,
        fsBgp4PeerGroupRflClient       INTEGER,
        fsBgp4PeerGroupTcpSendBufSize  Integer32,
        fsBgp4PeerGroupTcpRcvBufSize   Integer32,
        fsBgp4PeerGroupCommSendStatus  INTEGER,
        fsBgp4PeerGroupECommSendStatus INTEGER,
        fsBgp4PeerGroupPassive         INTEGER,
        fsBgp4PeerGroupDefaultOriginate INTEGER,
        fsBgp4PeerGroupActivateMPCapability INTEGER,
        fsBgp4PeerGroupDeactivateMPCapability INTEGER,
        fsBgp4PeerGroupRouteMapNameIn   DisplayString,
        fsBgp4PeerGroupRouteMapNameOut  DisplayString,
        fsBgp4PeerGroupStatus        RowStatus,
        fsBgp4PeerGroupIpPrefixNameIn   DisplayString,
        fsBgp4PeerGroupIpPrefixNameOut  DisplayString,
        fsBgp4PeerGroupOrfType          Unsigned32,
        fsBgp4PeerGroupOrfCapMode       INTEGER,
        fsBgp4PeerGroupOrfRequest       INTEGER
    }

    fsBgp4PeerGroupName OBJECT-TYPE
    SYNTAX              DisplayString (SIZE(1..20))
    MAX-ACCESS          not-accessible
    STATUS              current
    DESCRIPTION
        "The group name for this peer group entry."
    ::= { fsBgp4PeerGroupEntry 1 }

    fsBgp4PeerGroupAddrType OBJECT-TYPE
    SYNTAX              InetAddressType
    MAX-ACCESS          read-only
    STATUS              current
    DESCRIPTION
        "The address type of the peers added to this peer group."
    ::= { fsBgp4PeerGroupEntry 2 }

    fsBgp4PeerGroupRemoteAs OBJECT-TYPE
    SYNTAX              Unsigned32 (0..4294967295) 
    MAX-ACCESS          read-write
    STATUS              current
    DESCRIPTION
        "The remote autonomous system number for this peer group."
    ::= { fsBgp4PeerGroupEntry 3 }

    fsBgp4PeerGroupHoldTimeConfigured OBJECT-TYPE
    SYNTAX              Integer32 ( 0 | 3..65535 )
    MAX-ACCESS          read-write
    STATUS              current
    DESCRIPTION
        "Time interval (in seconds) for the Hold Time configured for this 
         BGP speaker with all the peers configured for this group. 
         This value is placed in an OPEN message sent to the peers 
         by this BGP speaker. This value must not be less than three seconds 
         if it is not zero (0). If it is zero (0), the Hold Time is NOT to be 
         established with the peer. 
         The suggested value for this timer is 90 seconds."
    ::= { fsBgp4PeerGroupEntry 4 }

    fsBgp4PeerGroupKeepAliveConfigured OBJECT-TYPE
    SYNTAX              Integer32 ( 0 | 1..21845 )
    MAX-ACCESS          read-write
    STATUS              current
    DESCRIPTION
        "Time interval (in seconds) for the KeepAlive timer configured for this 
         BGP speaker with all the peers configured in this group. The value 
         of this object will only determine the KEEPALIVE messages frequency 
         relative to the value specified in fsBgp4PeerGroupCfgHoldTime. 
         A reasonable maximum value for this timer would be one third of that 
         of fsBgp4PeerGroupCfgHoldTime. If the value of this object is zero (0),
         no periodical KEEPALIVE messages are sent to the peers after the 
         BGP connection is established. 
         The suggested value for this timer is 30 seconds."
    ::= { fsBgp4PeerGroupEntry 5 }

    fsBgp4PeerGroupConnectRetryInterval OBJECT-TYPE
    SYNTAX              Integer32 (1..65535)
    MAX-ACCESS          read-write
    STATUS              current
    DESCRIPTION
        "Time interval in seconds for the ConnectRetry timer for the peers 
         in this group. The suggested value for this timer is 120 seconds."
    ::= { fsBgp4PeerGroupEntry 6 }

    fsBgp4PeerGroupMinASOriginInterval OBJECT-TYPE
    SYNTAX              Integer32 (1..65535) 
    MAX-ACCESS          read-write
    STATUS              current
    DESCRIPTION
        "Time interval (in seconds) for the MinASOriginationInterval 
         timer for all peers configured in this group.
         The suggested value for this timer is 15 seconds."
    ::= { fsBgp4PeerGroupEntry 7 }

    fsBgp4PeerGroupMinRouteAdvInterval OBJECT-TYPE
    SYNTAX              Integer32 (1..65535)
    MAX-ACCESS          read-write
    STATUS              current
    DESCRIPTION
        "Time interval (in seconds) for the MinRouteAdvertisementInterval timer. 
         The suggested value for this timer is 30 seconds for EBGP connections 
         and 5 seconds for IBGP connections."
    ::= { fsBgp4PeerGroupEntry 8 }

    fsBgp4PeerGroupAllowAutomaticStart OBJECT-TYPE
    SYNTAX              INTEGER
                        {
                            enable(1),
                            disable(2)
                        }
    MAX-ACCESS          read-write
    STATUS              current
    DESCRIPTION
        "This MIB object specifies whether BGP session with the peers in the 
         peer group can be started automatically. This object when set to
         'disabled', requires manual start for initiating BGP session with the peer via
          MIB object 'fsBgp4PeerGroupAdminStatus'. When set to 'enabled',
          the peer session can be automatically started in the IDLE state,
          after a BGP Peer session is brought down either by Autostop or via
          reception of invalid BGP message. The BGP session will be automatically
          started after an interval specified by
          'fsBgp4PeerGroupIdleHoldTimeConfigured'. If
          fsBgp4PeerGroupDampPeerOscillations is enabled, then automaticStart will not
          occur if peer is damped."
    DEFVAL { disable }
    ::= { fsBgp4PeerGroupEntry 9 }

    fsBgp4PeerGroupAllowAutomaticStop  OBJECT-TYPE
    SYNTAX              INTEGER
                        {
                            enable(1),
                            disable(2)
                        }
    MAX-ACCESS          read-write
    STATUS              current
    DESCRIPTION
        "This MIB object specifies whether BGP session with the peers in the 
         peer group need to be automatically stopped after a TCP connect-retry
         count value specified by 'fsBgp4PeerGroupTcpConnectRetryCnt'.
         The resources allocated for the BGP peers are released and it 
         continues to remain in IDLE state. After an automatic stop,
         the Peer connection needs to be re-intiated manually by the
         administrator. When AutomaticStop is disabled, the connect retry 
         count value is set to 0."
    DEFVAL { disable }
    ::= { fsBgp4PeerGroupEntry 10 }

    fsBgp4PeerGroupIdleHoldTimeConfigured OBJECT-TYPE
    SYNTAX              Integer32 ( 1..65535 )
    MAX-ACCESS          read-write
    STATUS              current
    DESCRIPTION
        "IdleHoldTime specifies the length of time the BGP peers in this
         peer group is held in Idle state prior to allowing the next 
         automatic restart. The IdleHoldTime is configured only when the
         fsBgp4PeerGroupAllowAutomaticStart is Enabled or when the
         fsBgp4PeerGroupDampPeerOscillations is Enabled. The configurable value
         differs based on the two options that are enabled.The Suggested default
         value is 60 secs for automatic start. After each dampening, the value
         of the IdleHoldTime is doubled consecutively."
    DEFVAL { 60 }
    ::= { fsBgp4PeerGroupEntry 11 }

    fsBgp4PeerGroupDampPeerOscillations  OBJECT-TYPE
    SYNTAX              INTEGER
                        {
                            enable(1),
                            disable(2)
                        }
    MAX-ACCESS          read-write
    STATUS              current
    DESCRIPTION
        "The DampPeerOscillations option specifies that the implementation
         engages additional logic to damp the oscillations of BGP peers in
         the face of series of automatic start and automatic stop operations
         in the IDLE state.The DampPeerOscillations option indicates that the
         BGP connection is using logic that damps BGP peer oscillations in
         states other than 'established' state."
    DEFVAL { disable }
    ::= { fsBgp4PeerGroupEntry 12 }

    fsBgp4PeerGroupDelayOpen          OBJECT-TYPE
    SYNTAX              INTEGER
                        {
                            enable(1),
                            disable(2)
                        }
    MAX-ACCESS          read-write
    STATUS              current
    DESCRIPTION
        "This MIB object allows configuration option to enable/disable delay
         in sending of OPEN messages to the BGP peers for a specific time period
         (DelayOpenTime). The delay allows the remote BGP Peers to send the first
         OPEN message."
    DEFVAL { disable }
    ::= { fsBgp4PeerGroupEntry 13 }

    fsBgp4PeerGroupDelayOpenTimeConfigured  OBJECT-TYPE
    SYNTAX              Integer32 ( 0..65535 )
    MAX-ACCESS          read-write
    STATUS              current
    DESCRIPTION
        "The DelayOpen time specifies the amount of time the BGP Peers should
         delay in sending the OPEN message to the remote peers. If the
         fsBgp4PeerGroupDelayOpen option is enabled, the DelayOpen time can be
         configured. The default value is kept as 0 secs, which implies that
         the BGP Peers can send an OPEN message without any delay to its
         neighbor."
    DEFVAL { 0 }
    ::= { fsBgp4PeerGroupEntry 14 }

    fsBgp4PeerGroupPrefixUpperLimit OBJECT-TYPE
    SYNTAX              Integer32 (1..2147483647)
    MAX-ACCESS          read-write
    STATUS              current
    DESCRIPTION
        "BGP speaker imposes a locally-configured, upper bound on the number of
        address prefixes the speaker is willing to accept from a neighbor. The
        default value is calculated as the following:
        fsbgp4MaxNoofRoutes / fsbgp4MaxPeerEntry
        Administrator can configure a value less than the default value at
        runtime. Prefixes exceeding the PrefixUpperLimit will not be processed
        by the system."
    DEFVAL { 100 }
    ::= { fsBgp4PeerGroupEntry 15 }

    fsBgp4PeerGroupTcpConnectRetryCnt  OBJECT-TYPE
    SYNTAX              Integer32 (1..50)
    MAX-ACCESS          read-write
    STATUS              current
    DESCRIPTION
        "This counter denotes the Maximum number of times the BGP Peers have
         tried to issue a TCP-Connect with its neighboring peers.
         The default value for the counter is set as 5."
        DEFVAL { 5 }
    ::= { fsBgp4PeerGroupEntry 16 }

    fsBgp4PeerGroupEBGPMultiHop OBJECT-TYPE
    SYNTAX              INTEGER
                        {
                            enable(1),
                            disable(2)
                        }
    MAX-ACCESS          read-write
    STATUS              current
    DESCRIPTION
        "This objects enables the BGP4 Speaker to accept or attempt
         connections to external peers residing on network that are not directly
         connected. By default, only directly connected EBGP peers are allowed.
         The configuration of this object has effect only when the peers added to 
         this peer group are of EBGP type."
    ::= { fsBgp4PeerGroupEntry 17 }

    fsBgp4PeerGroupEBGPHopLimit OBJECT-TYPE
    SYNTAX              Integer32 (1..255) 
    MAX-ACCESS          read-write
    STATUS              current
    DESCRIPTION
        "This objects enables the BGP4 Speaker to accept or attempt
         connections to external peers residing on network that are not directly
         connected and seperated by a maximum hop limit as configured by this
         object. The configuration of this object has effect only when the peers added to
         this peer group are of EBGP type."
    ::= { fsBgp4PeerGroupEntry 18 }

    fsBgp4PeerGroupNextHopSelf OBJECT-TYPE
    SYNTAX              INTEGER
                        {
                            automatic(1),
                            self(2)
                        }
    MAX-ACCESS          read-write
    STATUS              current
    DESCRIPTION
        "This object specifies how the next hop attribute sent in the update
         messages to the peers in this peer group.  When the object takes the
         value of self,the next Hop attribute will always be the sender Local
         Address else the next hop will be generated based on the IP address of
         the destination and the present next hop in the route information."
    DEFVAL { automatic }
    ::= { fsBgp4PeerGroupEntry 19 }

    fsBgp4PeerGroupRflClient OBJECT-TYPE
    SYNTAX              INTEGER
                        {
                            nonClient (1),
                            client (2)
                        }
    MAX-ACCESS          read-write
    STATUS              current
    DESCRIPTION
        "This object specifies whether the peers in this peer group are
         Client peers or Non-Client peers. By default, the peers are
         created as Non-Client Peer. "
    DEFVAL { nonClient }
    ::= { fsBgp4PeerGroupEntry 20 }

    fsBgp4PeerGroupTcpSendBufSize OBJECT-TYPE
    SYNTAX              Integer32 (4096..65536)
    MAX-ACCESS          read-write
    STATUS              current
    DESCRIPTION
        "This object configures the tcp window size on the sender side
         for all the peers in this peer group."
    DEFVAL { 65536 }
    ::= { fsBgp4PeerGroupEntry 21 }

    fsBgp4PeerGroupTcpRcvBufSize   OBJECT-TYPE
    SYNTAX              Integer32 (4096..65536)
    MAX-ACCESS          read-write
    STATUS              current
    DESCRIPTION
        "This object configures the tcp window size on the receiver side
         for all the peers in this peer group."
    DEFVAL { 65536 }
    ::= { fsBgp4PeerGroupEntry 22 }

    fsBgp4PeerGroupCommSendStatus OBJECT-TYPE
    SYNTAX              INTEGER 
                        {
                            none (1),
                            send (2),
                            donotsend (3)
                        }
    MAX-ACCESS          read-create
    STATUS              current
    DESCRIPTION
        "Community Send status for the peers in this peer group.
            o none       - is for read-only
            o send       - send communities to this peer
            o donotsend  - do not send communities to this peer."
    DEFVAL { send }
    ::= { fsBgp4PeerGroupEntry 23 }

    fsBgp4PeerGroupECommSendStatus OBJECT-TYPE
    SYNTAX              INTEGER
                        {
                            none       (1),
                            send       (2),
                            donotsend  (3)
                        }
    MAX-ACCESS          read-create
    STATUS              current
    DESCRIPTION
        "Extended Community Send status for the peers in this peer group.
           o none     - is for read-only
           o send       - send extended communities to this peer
           o donotsend  - do not send extended communities to this peer."
    DEFVAL { send }
    ::= { fsBgp4PeerGroupEntry 24 }

    fsBgp4PeerGroupPassive OBJECT-TYPE
    SYNTAX              INTEGER
                        {
                            enable (1),
                            disable (2)
                        }
    MAX-ACCESS          read-write
    STATUS              current
    DESCRIPTION
        "This object is used to set the peers in this group to be active,
         that means the speaker will not initiate the session with the peers
         instead it waits for the remote peers to initiate the session"
    ::= { fsBgp4PeerGroupEntry 25 }

    fsBgp4PeerGroupDefaultOriginate OBJECT-TYPE
    SYNTAX              INTEGER
                        {
                            enable(1),
                            disable(2)
                        }
    MAX-ACCESS          read-write
    STATUS              current
    DESCRIPTION
        "This object is used to enable/disable the advertisement 
         of the default route to all the peers in this peer group.
         This object overrides the global default route configuration
         (fsbgp4DefaultOriginate) and always send a default
         route to the peer with self next-hop. This advertisement occurs
         irrespective of the presence of default route in FDB. This object can
         be set only if the fsbgp4LocalAs is set."
    DEFVAL  { disable }
    ::= { fsBgp4PeerGroupEntry 26 }

    fsBgp4PeerGroupActivateMPCapability OBJECT-TYPE
    SYNTAX              INTEGER
                        {
                            ipv4unicast(1),
                            ipv6unicast(2)

                        }
    MAX-ACCESS          read-write
    STATUS              current
    DESCRIPTION
        "This object is set to activate the corresponding MP Capability.
         If any of MP Capability is activated, then this capability should
         be negotiated while establishing session with the peers in this group.
         Any get on this object will return only ZERO."
    ::= { fsBgp4PeerGroupEntry 27 }

    fsBgp4PeerGroupDeactivateMPCapability OBJECT-TYPE
    SYNTAX              INTEGER
                        {
                            ipv4unicast(1),
                            ipv6unicast(2)
                        }
    MAX-ACCESS          read-write
    STATUS              current
    DESCRIPTION
        "This object is set to deactivate the corresponding MP Capability.
         If any of MP Capability is deactivated, then this capability should
         not be negotiated while establishing session with the peers in this group.
         Any get on this object will return only ZERO."
    ::= { fsBgp4PeerGroupEntry 28 }
 
    fsBgp4PeerGroupRouteMapNameIn OBJECT-TYPE
    SYNTAX              DisplayString
    MAX-ACCESS          read-write
    STATUS              current
    DESCRIPTION
        "This object is used to configure the in routemap for this peer group entry."
    ::= { fsBgp4PeerGroupEntry 29 }

    fsBgp4PeerGroupRouteMapNameOut OBJECT-TYPE
    SYNTAX              DisplayString
    MAX-ACCESS          read-write
    STATUS              current
    DESCRIPTION
        "This object is used to configure the out routemap for this peer group entry."
    ::= { fsBgp4PeerGroupEntry 30 }

    fsBgp4PeerGroupStatus OBJECT-TYPE
    SYNTAX              RowStatus
    MAX-ACCESS          read-write
    STATUS              current
    DESCRIPTION
        "This object is used to create the peer group or delete the group."
    ::= { fsBgp4PeerGroupEntry 31 }

    fsBgp4PeerGroupIpPrefixNameIn OBJECT-TYPE
    SYNTAX              DisplayString
    MAX-ACCESS          read-write
    STATUS              current
    DESCRIPTION
        "This object is used to configure the IP Prefix list name in IN direction for this peer group entry."
    ::= { fsBgp4PeerGroupEntry 32 }

    fsBgp4PeerGroupIpPrefixNameOut OBJECT-TYPE
    SYNTAX              DisplayString
    MAX-ACCESS          read-write
    STATUS              current
    DESCRIPTION
        "This object is used to configure the IP Prefix list name in OUT direction for this peer group entry."
    ::= { fsBgp4PeerGroupEntry 33 }

    fsBgp4PeerGroupOrfType OBJECT-TYPE
    SYNTAX              Unsigned32
    MAX-ACCESS          read-write
    STATUS              current
    DESCRIPTION
        "This object is used to configure the ORF type supported for this peer group entry.
         This object should be set before enabling the ORF mode fsBgp4PeerGroupOrfCapMode.
         Now the Address Prefix ORF type (value 64) is only supported"
    ::= { fsBgp4PeerGroupEntry 34 }

    fsBgp4PeerGroupOrfCapMode OBJECT-TYPE
    SYNTAX              INTEGER {
                                    disable (0),
                                    receive (1),
                                    send (2),
                                    both (3)
                                }
    MAX-ACCESS          read-write
    STATUS              current
    DESCRIPTION
        "This object is used to configure the ORF Capability mode supported for this peer group entry.
         If it is set to ZERO, then the both ORF modes will be disabled"
    ::= { fsBgp4PeerGroupEntry 35 }

    fsBgp4PeerGroupOrfRequest OBJECT-TYPE
    SYNTAX              INTEGER {
                                  true (1)
                                 }
    MAX-ACCESS          read-write
    STATUS              current
    DESCRIPTION
        "This object is to trigger the ORF messages to the peers associated with this peer group entry.
         Once the ORF messags are transmitted, this object will be cleared.
         Get operation of this object will always return ZERO."
    ::= { fsBgp4PeerGroupEntry 36 }


    fsBgp4PeerGroupListTable OBJECT-TYPE
    SYNTAX SEQUENCE OF  FsBgp4PeerGroupListEntry
    MAX-ACCESS          not-accessible
    STATUS              current
    DESCRIPTION
        "A table for adding/removing the bgp peers to a peer group."
    ::= { fsbgp 41 }

    fsBgp4PeerGroupListEntry OBJECT-TYPE
    SYNTAX      FsBgp4PeerGroupListEntry
    MAX-ACCESS  not-accessible
    STATUS      current
    DESCRIPTION
        "An entry describing the bgp peer group list."
        INDEX { fsBgp4PeerGroupName, fsBgp4PeerAddrType, fsBgp4PeerAddress }
    ::=  { fsBgp4PeerGroupListTable 1 }

    FsBgp4PeerGroupListEntry ::= SEQUENCE {
        fsBgp4PeerAddrType      InetAddressType,
        fsBgp4PeerAddress       InetAddress,
        fsBgp4PeerAddStatus     INTEGER
    }

    fsBgp4PeerAddrType  OBJECT-TYPE
    SYNTAX              InetAddressType
    MAX-ACCESS          not-accessible
    STATUS              current
    DESCRIPTION
        "This object specifies the address type of the BGP peer entry 
         added to this peer group entry"
    ::= { fsBgp4PeerGroupListEntry 1 }

    fsBgp4PeerAddress   OBJECT-TYPE
    SYNTAX              InetAddress
    MAX-ACCESS          not-accessible
    STATUS              current
    DESCRIPTION
        "This object specifies the remote address of the BGP peer entry 
         added to this peer group entry"
    ::= { fsBgp4PeerGroupListEntry 2 }

    fsBgp4PeerAddStatus OBJECT-TYPE
    SYNTAX              INTEGER
                        {
                            add(1),
                            delete(2)
                        }
    MAX-ACCESS          read-write
    STATUS              current
    DESCRIPTION
        "This object is used to add or remove the bgp peer specified through
         fsBgp4PeerAddress to this bgp peer group entry."
    ::= { fsBgp4PeerGroupListEntry 3 }

fsBgp4TestGroup OBJECT IDENTIFIER ::= {fsbgp 45}

fsBgp4RmTestObject OBJECT-TYPE
    SYNTAX      INTEGER
    MAX-ACCESS  read-write
    STATUS      current
    DESCRIPTION
     "This object is used for testing of RM bulk update scenarios.
       users cannot set or retrive this object"
    ::= { fsBgp4TestGroup 1 }


-- MIB for TCP AO Authentication starts

fsbgp4TCPMKTAuth OBJECT IDENTIFIER ::= {fsbgp 42}

-- TCP MKT(Master Key Tuple) Authentication Table

    fsbgp4TCPMKTAuthTable OBJECT-TYPE
        SYNTAX     SEQUENCE OF Fsbgp4TCPMKTAuthEntry
        MAX-ACCESS not-accessible
        STATUS     current
        DESCRIPTION
        "TCP MKT Authentication Table, used for configuring MKT for TCP-AO 
         authentication, supported algorithms HMAC-SHA-1 and AES-128-CMAC"
        ::= { fsbgp4TCPMKTAuth 1 }

    fsbgp4TCPMKTAuthEntry OBJECT-TYPE
        SYNTAX     Fsbgp4TCPMKTAuthEntry
        MAX-ACCESS not-accessible
        STATUS     current
        DESCRIPTION
        "Entry corresponds to the TCP MKT parameters"
        INDEX {
                fsbgp4TCPMKTAuthKeyId
              }
        ::= { fsbgp4TCPMKTAuthTable 1 }

    Fsbgp4TCPMKTAuthEntry ::= SEQUENCE {
        fsbgp4TCPMKTAuthKeyId
            Integer32,
        fsbgp4TCPMKTAuthRecvKeyId
            Integer32,
        fsbgp4TCPMKTAuthMasterKey 
           OCTET STRING,
        fsbgp4TCPMKTAuthAlgo
            INTEGER,
        fsbgp4TCPMKTAuthTcpOptExc
            TruthValue,
        fsbgp4TCPMKTAuthRowStatus
            RowStatus
        }

    fsbgp4TCPMKTAuthKeyId OBJECT-TYPE
       SYNTAX      Integer32 (0..255)
       MAX-ACCESS  not-accessible
       STATUS      current
       DESCRIPTION
           "Send KeyID of the MKT. This object value is used to fill the key-id
            field in the TCP-AO option in the TCP header"
       ::=  { fsbgp4TCPMKTAuthEntry 1 }

    fsbgp4TCPMKTAuthRecvKeyId OBJECT-TYPE
       SYNTAX      Integer32 (0..255)
       MAX-ACCESS  read-write
       STATUS      current
       DESCRIPTION
           "Receive Key-id of the MKT. Receive Key-id of the MKT. 
            The MKT that is ready at the sender to 
            be used to authenticate received segments is indicated to the 
            peer by filling the receive key id of the MKT in the RNExtKeyId 
            field of the TCP-AO option in TCP header."
       ::=  { fsbgp4TCPMKTAuthEntry 2 }

    fsbgp4TCPMKTAuthMasterKey OBJECT-TYPE
       SYNTAX      OCTET STRING (SIZE (1..80))
       MAX-ACCESS  read-write
       STATUS      current
       DESCRIPTION
           "Master Key corresponding to the MKT"
       ::=  { fsbgp4TCPMKTAuthEntry 3 }

    fsbgp4TCPMKTAuthAlgo OBJECT-TYPE
       SYNTAX      INTEGER
                   {
                       hmacSha1(1),
                       aes128Cmac(2)
                   }
       MAX-ACCESS  read-write
       STATUS      current
       DESCRIPTION
           "Algorithm used for TCP-AO MAC or KDF calculation, allowed 
            algorithms are HMAC-SHA-1 & AES-128-CMAC, 
            default value is HMAC-SHA-1 "
       DEFVAL { hmacSha1 }       
       ::=  { fsbgp4TCPMKTAuthEntry 4 }

    fsbgp4TCPMKTAuthTcpOptExc OBJECT-TYPE
       SYNTAX      TruthValue
       MAX-ACCESS  read-write
       STATUS      current
       DESCRIPTION
           "Exclude TCP options other than TCP-AO during MAC calculation,
            if fsMIBgp4TCPMKTAuthTcpOptExc is not set TCP-AO MAC will
            be calculated on tcp segment including all other TCP options"
       ::=  { fsbgp4TCPMKTAuthEntry 5 }

    fsbgp4TCPMKTAuthRowStatus OBJECT-TYPE
       SYNTAX      RowStatus
       MAX-ACCESS  read-write
       STATUS      current
       DESCRIPTION
           "This variable represents the status of  the  MKT entry, can
            have values allowed for RowStatus, eg. createAndGo, destroy etc "
       ::=  { fsbgp4TCPMKTAuthEntry 6 }

--MIB for TCP-AO config  for  BGP peers

    fsbgp4TCPAOAuthPeer   OBJECT IDENTIFIER ::= {fsbgp 43}

--BGP TCP-AO config Table

    fsbgp4TCPAOAuthPeerTable  OBJECT-TYPE
        SYNTAX     SEQUENCE OF Fsbgp4TCPAOAuthPeerEntry
        MAX-ACCESS not-accessible
        STATUS     current
        DESCRIPTION
        "TCP-AO Peer config Table"
        ::= { fsbgp4TCPAOAuthPeer 1 }

    fsbgp4TCPAOAuthPeerEntry OBJECT-TYPE
        SYNTAX     Fsbgp4TCPAOAuthPeerEntry
        MAX-ACCESS not-accessible
        STATUS     current
        DESCRIPTION
        "Entry corresponds to the TCP-AO configs for peer, 
         Support for associating one keyId(MKT) per peer is available at
         present. If a new keyId/MKT is associated with a peer which 
         already has one associated keyId/MKT, existing values will 
         be overwritten with new one.
         Configuration support for start accept, start generate, stop accept 
         and stop generate are not available currently"
        INDEX {
                fsbgp4TCPAOAuthPeerType,
                fsbgp4TCPAOAuthPeerAddr,
                fsbgp4TCPAOAuthKeyId
              }
        ::= { fsbgp4TCPAOAuthPeerTable 1 }

    Fsbgp4TCPAOAuthPeerEntry ::= SEQUENCE {
        fsbgp4TCPAOAuthPeerType
            InetAddressType,
        fsbgp4TCPAOAuthPeerAddr
            InetAddress,
        fsbgp4TCPAOAuthKeyId
            Integer32,
        fsbgp4TCPAOAuthKeyStatus
            INTEGER,
        fsbgp4TCPAOAuthKeyStartAccept    
            DateAndTime,
        fsbgp4TCPAOAuthKeyStartGenerate  
            DateAndTime,
        fsbgp4TCPAOAuthKeyStopGenerate   
            DateAndTime,
        fsbgp4TCPAOAuthKeyStopAccept     
            DateAndTime
    }

    fsbgp4TCPAOAuthPeerType OBJECT-TYPE
        SYNTAX      InetAddressType 
        MAX-ACCESS  not-accessible
        STATUS      current
        DESCRIPTION
            "The IP address type of the peer IP address"
        ::=  { fsbgp4TCPAOAuthPeerEntry 1 }

    fsbgp4TCPAOAuthPeerAddr OBJECT-TYPE
        SYNTAX      InetAddress  (SIZE (1 .. 16))
        MAX-ACCESS  not-accessible
        STATUS      current
        DESCRIPTION
            "The IP address of this the peer for which TCP-AO config is done"
        ::=  { fsbgp4TCPAOAuthPeerEntry 2 }

    fsbgp4TCPAOAuthKeyId OBJECT-TYPE
        SYNTAX      Integer32 (0 .. 255)
        MAX-ACCESS  not-accessible
        STATUS      current
        DESCRIPTION
            "Key id of the MKT which need to be associated with the peer"
        ::=  { fsbgp4TCPAOAuthPeerEntry 3 }

    fsbgp4TCPAOAuthKeyStatus OBJECT-TYPE
        SYNTAX	    INTEGER
        {
            set (1),
            clear(2)
        } 
	MAX-ACCESS  read-write
	STATUS	    current
	DESCRIPTION 
        " While doing a write on the object(snmpset) the value 
             'set(1)'   will associate the MKT with KeyId mentioned
                        in the index to the peer
             'clear(2)' will clear/dissociate the keyId mentioned
                        in the index to the peer
          During read/snmpget on the ogject the value
             'set(1)'   will indicate TCP-AO is enabled and the value
                        returned by fsbgp4TCPAOAuthKeyId is valid
             Read on object will not display clear"
        ::= { fsbgp4TCPAOAuthPeerEntry 4 }

    
     fsbgp4TCPAOAuthKeyStartAccept OBJECT-TYPE
        SYNTAX      DateAndTime 
        MAX-ACCESS  read-write
        STATUS      current
        DESCRIPTION
           " The date & time the router will start accepting packets that have 
             been created with the MKT specified by the key-id"
       DEFVAL { "0000000000000000"  }
       ::=  { fsbgp4TCPAOAuthPeerEntry 5 }
   
     fsbgp4TCPAOAuthKeyStartGenerate OBJECT-TYPE
        SYNTAX      DateAndTime 
        MAX-ACCESS  read-write
        STATUS      current
        DESCRIPTION
           "The date & time the router will start using the MKT specified
            by the key-id for  packets generation"
        DEFVAL { "0000000000000000"  }
        ::=  { fsbgp4TCPAOAuthPeerEntry 6 }
   
     fsbgp4TCPAOAuthKeyStopGenerate OBJECT-TYPE
        SYNTAX      DateAndTime 
        MAX-ACCESS  read-write
        STATUS      current
        DESCRIPTION
           " The date & time the router will stop using the MKT specified by 
             the key-id for  packets generation."
       DEFVAL { "0000000000000000" }
       ::=  { fsbgp4TCPAOAuthPeerEntry 7 }
   
     fsbgp4TCPAOAuthKeyStopAccept OBJECT-TYPE
        SYNTAX      DateAndTime 
        MAX-ACCESS  read-write
        STATUS      current
        DESCRIPTION
           " The date & time the router will stop accepting packets that have 
             been created with the MKT specified by the key-id."
        DEFVAL { "0000000000000000" }
        ::=  { fsbgp4TCPAOAuthPeerEntry 8 }
-- ORF table 
    fsBgp4ORFListTable OBJECT-TYPE
    SYNTAX SEQUENCE OF  FsBgp4ORFListEntry
    MAX-ACCESS          not-accessible
    STATUS              current
    DESCRIPTION
        "A table for adding/removing Ooutbound Route Filter entries received from the peer"
    ::= { fsbgp 44 }

    fsBgp4ORFListEntry OBJECT-TYPE
    SYNTAX      FsBgp4ORFListEntry
    MAX-ACCESS  not-accessible
    STATUS      current
    DESCRIPTION
        "An entry describing the bgp ORF list."
        INDEX { fsBgp4ORFPeerAddrType,
                fsBgp4ORFPeerAddr, 
                fsBgp4ORFAfi,
                fsBgp4ORFSafi,
                fsBgp4ORFType,
                fsBgp4ORFSequence,
                fsBgp4ORFAddrPrefix,
                fsBgp4ORFAddrPrefixLen,
                fsBgp4ORFMinLength,
                fsBgp4ORFMaxLength,
                fsBgp4ORFAction
              }
    ::=  { fsBgp4ORFListTable 1 }

    FsBgp4ORFListEntry ::= SEQUENCE {
        fsBgp4ORFPeerAddrType   InetAddressType,
        fsBgp4ORFPeerAddr       InetAddress,
        fsBgp4ORFAfi            InetAddressType,
        fsBgp4ORFSafi           BgpSafi,
        fsBgp4ORFType           Unsigned32,
        fsBgp4ORFSequence       Unsigned32,
        fsBgp4ORFAddrPrefix     InetAddress,
        fsBgp4ORFAddrPrefixLen  Unsigned32,
        fsBgp4ORFMinLength      Unsigned32,
        fsBgp4ORFMaxLength      Unsigned32,
        fsBgp4ORFAction         INTEGER
    }

    fsBgp4ORFPeerAddrType OBJECT-TYPE
    SYNTAX                  InetAddressType
    MAX-ACCESS              not-accessible
    STATUS                  current
    DESCRIPTION
        "This object specifies the address type of the BGP peer 
         asspciated with this ORF entry"
    ::= { fsBgp4ORFListEntry 1 }

    fsBgp4ORFPeerAddr OBJECT-TYPE
    SYNTAX              InetAddress
    MAX-ACCESS          not-accessible
    STATUS              current
    DESCRIPTION
        "This object specifies the remote address of the BGP peer associated
         with this ORF entry"
    ::= { fsBgp4ORFListEntry 2 }

    fsBgp4ORFAfi      OBJECT-TYPE
    SYNTAX              InetAddressType
    MAX-ACCESS          not-accessible
    STATUS              current
    DESCRIPTION
        "This object specifies the type of IP address prefix in the ORF entry."
    ::= { fsBgp4ORFListEntry 3 }

    fsBgp4ORFSafi     OBJECT-TYPE
    SYNTAX              BgpSafi
    MAX-ACCESS          not-accessible
    STATUS              current
    DESCRIPTION
        "This object specifies the Sub-sequent address family of 
         IP address prefix in the ORF entry."
    ::= { fsBgp4ORFListEntry 4 }

    fsBgp4ORFType     OBJECT-TYPE
    SYNTAX              Unsigned32
    MAX-ACCESS          not-accessible
    STATUS              current
    DESCRIPTION
        "This object specifies the type of the ORF entry.
         Currently it supports only Address-Prefix based ORF type (64)"
    ::= { fsBgp4ORFListEntry 5 }

    fsBgp4ORFSequence OBJECT-TYPE
    SYNTAX              Unsigned32
    MAX-ACCESS          not-accessible
    STATUS              current
    DESCRIPTION
        "This object specifies the sequential order in which a route should be 
         matched against an ORF entry."
    ::= { fsBgp4ORFListEntry 6 }

    fsBgp4ORFAddrPrefix OBJECT-TYPE
    SYNTAX                InetAddress
    MAX-ACCESS            not-accessible
    STATUS                current
    DESCRIPTION
         "This object specifies the IP address prefix for which the ORF rule was specified."
    ::= { fsBgp4ORFListEntry 7 }

    fsBgp4ORFAddrPrefixLen OBJECT-TYPE
    SYNTAX                Unsigned32 (0..128)
    MAX-ACCESS            not-accessible
    STATUS                current
    DESCRIPTION
         "This object specifies the length of the IP address prefix length in bits which will be
          considered when matching a route with the ORF entry."
    ::= { fsBgp4ORFListEntry 8 }

    fsBgp4ORFMinLength OBJECT-TYPE
    SYNTAX               Unsigned32 (0..128)
    MAX-ACCESS           not-accessible
    STATUS               current
    DESCRIPTION
         "This object specifies the minimum prefix-length in bits for a IP address prefix.
          Any route with prefix-length equal to or greater than this length will be
          considered as a match, if fsBgp4ORFMaxLength is not specified.
          If it is ZERO, it will be considered as unspecified and it will not be considered
          while applying the rule. If both fsBgp4ORFMinLength and fsBgp4ORFMaxLength are specified, 
          then a route with prefix-length with in the range of fsBgp4ORFMinLength and 
          fsBgp4ORFMaxLength will be considered as a match"
    ::= { fsBgp4ORFListEntry 9 }

    fsBgp4ORFMaxLength OBJECT-TYPE
    SYNTAX               Unsigned32 (0..128)
    MAX-ACCESS           not-accessible
    STATUS               current
    DESCRIPTION
         "This object specifies the maximum prefix-length in bits for a IP address prefix.
          Any route with prefix-length equal to or less than this length will be
          considered as a match, if fsBgp4ORFMinLength is not specified.
          If it is ZERO, then it will be considered as unspecified and it will not be considered
          while applying the rule. If both fsBgp4ORFMaxLength and fsBgp4ORFMinLength are specified, 
          then a route with prefix-length with in the range of fsBgp4ORFMinLength and 
          fsBgp4ORFMaxLength will be considered as a match"
    ::= { fsBgp4ORFListEntry 10 }

    fsBgp4ORFAction OBJECT-TYPE  
    SYNTAX            INTEGER { 
                                permit (0), 
                                deny (1) 
                              }
    MAX-ACCESS        not-accessible
    STATUS            current
    DESCRIPTION
         "This object specifies the action to be taken for a particular route
          if it matches with the ORF rules defined in this particular ORF entry.
          If it is PERMIT, then the matched route will be advertised to the peer.
          Else if it is DENY, then the matched route will not be advertised to the peer"
    ::= { fsBgp4ORFListEntry 11 }

END

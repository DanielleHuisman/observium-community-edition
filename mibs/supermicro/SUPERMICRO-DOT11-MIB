--******************************************************************************
--Copyright (C) 2008-2014 Super Micro Computer Inc. All Rights Reserved
--
--$Id: fswlan.mib,v 1.1 2013/09/19 13:02:53 siva Exp $
--
--Description : This file contains MIB definitions for ISS module.
--
--******************************************************************************/

-- Supermicro WSS MIB Definition

-- MIB for 'Wireless Switch Solution'

-- The 'Wireless Switch Solution' MIB definition is as follows:


SUPERMICRO-DOT11-MIB DEFINITIONS ::= BEGIN

IMPORTS
   MODULE-IDENTITY, OBJECT-TYPE,
   enterprises, Integer32, Unsigned32 FROM SNMPv2-SMI
   ifIndex, InterfaceIndex FROM IF-MIB
   InetAddressType, InetAddress FROM INET-ADDRESS-MIB
   SnmpAdminString FROM SNMP-FRAMEWORK-MIB 
   DisplayString, TruthValue, RowStatus, 
   MacAddress, TEXTUAL-CONVENTION  FROM SNMPv2-TC;   

fsDot11 MODULE-IDENTITY
      LAST-UPDATED "201302150000Z"
      ORGANIZATION "Super Micro Computer Inc."
      CONTACT-INFO

        "Super Micro Computer Inc.
         E-mail:support@Supermicro.com"

      DESCRIPTION
       "The enterprise ID 10876 is originally assigned to Super Micro Computer Inc."
      REVISION "201302150000Z"

      DESCRIPTION
         "The MIB for AricentWSS."
   ::=  { enterprises supermicro-computer-inc(10876) super-switch(101) extended(2) 83 }

-- Textual conventions

CapwapBaseRadioIdTC ::= TEXTUAL-CONVENTION
    DISPLAY-HINT "d"
    STATUS      current
    DESCRIPTION
        "Represents the unique identifier of a radio on a WTP."
    SYNTAX      Unsigned32 (1..31)

CapwapDot11WlanIdTC ::= TEXTUAL-CONVENTION
    DISPLAY-HINT "d"
    STATUS      current
    DESCRIPTION
        "Represents the unique identifier of a Wireless Local Area
         Network (WLAN)."
    SYNTAX      Unsigned32 (1..16)

CapwapDot11WlanIdProfileTC ::= TEXTUAL-CONVENTION
    DISPLAY-HINT "d"
    STATUS      current
    DESCRIPTION
        "Represents the unique identifier of a WLAN profile."
    SYNTAX      Unsigned32 (0..512)

EnabledStatus ::= TEXTUAL-CONVENTION 
    STATUS      current 
    DESCRIPTION 
        "A simple status value for the object." 
    SYNTAX      INTEGER { enabled(1), disabled(2) } 

-- ----------------------------------------------------------------- --
-- groups in the MIB
-- ----------------------------------------------------------------- --
 
        fsDot11Radio            OBJECT IDENTIFIER ::= { fsDot11 1 }
        fsSecurityWebAuthParams OBJECT IDENTIFIER ::= { fsDot11 2 }
        fsDot11smt              OBJECT IDENTIFIER ::= { fsDot11 3 }
        fsDot11mac              OBJECT IDENTIFIER ::= { fsDot11 4 }
        fsDot11phy              OBJECT IDENTIFIER ::= { fsDot11 5 }
        fsWlanSystem            OBJECT IDENTIFIER ::= { fsDot11 6 }

fsDot11aNetworkEnable OBJECT-TYPE
    SYNTAX      EnabledStatus
    MAX-ACCESS  read-write
    STATUS      current
    DESCRIPTION
    "To disable or enable the radio transmission for an entire 802.11a network."
    DEFVAL { enabled }
    ::= { fsDot11Radio 1 }

fsDot11bNetworkEnable OBJECT-TYPE
    SYNTAX      EnabledStatus
    MAX-ACCESS  read-write
    STATUS      current
    DESCRIPTION
    "To disable or enable the radio transmission for an entire 802.11b network."
    DEFVAL { enabled }
    ::= { fsDot11Radio 2 }

fsDot11gSupport OBJECT-TYPE
    SYNTAX      EnabledStatus
    MAX-ACCESS  read-write
    STATUS      current
    DESCRIPTION
    "To enable or disable the 11g suppport for all dot11b radios."
    DEFVAL {disabled }
    ::= { fsDot11Radio 3 } 

fsDot11anSupport OBJECT-TYPE
    SYNTAX      EnabledStatus
    MAX-ACCESS  read-write
    STATUS      current
    DESCRIPTION
    "To disable or enable 11n support for dot11a radios in the network."
    DEFVAL { disabled }
    ::= { fsDot11Radio 4 }

fsDot11bnSupport OBJECT-TYPE
    SYNTAX      EnabledStatus
    MAX-ACCESS  read-write
    STATUS      current
    DESCRIPTION
    "To disable or enable 11n support for dot11b/g radios in the network."
    DEFVAL { disabled }
    ::= { fsDot11Radio 5 }

fsDot11ManagmentSSID OBJECT-TYPE
    SYNTAX      CapwapDot11WlanIdProfileTC
    MAX-ACCESS  read-write
    STATUS      current
    DESCRIPTION
    "Indicates the ssid used for management of AP and radio resource
     management."
    DEFVAL { 0 }
    ::= { fsDot11Radio 6 }    
     
fsDot11CountryString OBJECT-TYPE
    SYNTAX OCTET STRING (SIZE(3))
    MAX-ACCESS read-write
    STATUS current
    DESCRIPTION
    "This attribute identifies the country or non-country
    entity in which the station is operating. If it is a
    country, the first two octets of this
    string is the two character country code as described
    in document ISO/IEC 3166-1. The third octet shall
    be one of the following:
    1. an ASCII space character, if the regulations under
    which the station is operating encompass all
    environments in the country,
    2. an ASCII 'O' character, if the regulations under
    which the station is operating are for an Outdoor
    environment only, or
    3. an ASCII 'I' character, if the regulations under
    which the station is operating are for an Indoor
    environment only.
    4. an ASCII 'X' character, if the station is operating
    under a non-country entity. The first two octets of the
    non-country entity shall be two ASCII 'XX' characters."
    DEFVAL { "US" }
    ::= { fsDot11Radio 7 }    

fsSecurityWebAuthType OBJECT-TYPE
    SYNTAX INTEGER { internal(1), external(2) }
    MAX-ACCESS read-write
    STATUS current
    DESCRIPTION
    "This attribute shall be a set of all the Web authentication
    type supported by the WLC. The following are the
    default values and the associated type.
    Value = 1: Internal
    Value = 2: Customized
    Value = 3: External"
    DEFVAL { internal }
    ::= {fsSecurityWebAuthParams  1 }

fsSecurityWebAuthUrl OBJECT-TYPE
    SYNTAX DisplayString          
    MAX-ACCESS read-write
    STATUS current
    DESCRIPTION
    "This attribute shall be the URL  of the customised Webpage on 
     the external Web server. This is used in case of External Web 
     Authentication"
    ::= {fsSecurityWebAuthParams 2}

fsSecurityWebAuthRedirectUrl OBJECT-TYPE
    SYNTAX DisplayString
    MAX-ACCESS read-write
    STATUS current
    DESCRIPTION
    "This attribute shall be the Redirect URL to which the user will be
     redirected after successful authentication."
    ::= {fsSecurityWebAuthParams 3}

fsSecurityWebAddr OBJECT-TYPE
    SYNTAX Integer32
    MAX-ACCESS read-write
    STATUS current
    DESCRIPTION
    "This attribute shall be the IP Address of the External Web Server"
    ::= {fsSecurityWebAuthParams 4}

fsSecurityWebAuthWebTitle OBJECT-TYPE
    SYNTAX DisplayString
    MAX-ACCESS read-write
    STATUS current
    DESCRIPTION
    "This attribute shall be the customizable title in the web login 
    page."
    DEFVAL {"Web Authentication"}
    ::= {fsSecurityWebAuthParams 5}

fsSecurityWebAuthWebMessage OBJECT-TYPE
    SYNTAX DisplayString
    MAX-ACCESS read-write
    STATUS current
    DESCRIPTION
    "This attribute shall be the customizable message on the web login
    page."
    DEFVAL {"Hello welcome aboard!"}
    ::= {fsSecurityWebAuthParams 6}

fsSecurityWebAuthWebLogoFileName OBJECT-TYPE
    SYNTAX DisplayString
    MAX-ACCESS read-write
    STATUS current
    DESCRIPTION
    "This attribute shall be the filename containing the logo to be 
    displayed in the authentication page."
    DEFVAL {"smc_loginnewcr.jpg"}
    ::= {fsSecurityWebAuthParams 7}

fsSecurityWebAuthWebSuccMessage OBJECT-TYPE
    SYNTAX DisplayString
    MAX-ACCESS read-write
    STATUS current
    DESCRIPTION
    "This attribute shall be the customizable success message to be 
    displayed to user when successfully authenticated."
    DEFVAL {"Authenticated Successfully"}
    ::= {fsSecurityWebAuthParams 8}

fsSecurityWebAuthWebFailMessage OBJECT-TYPE
    SYNTAX DisplayString
    MAX-ACCESS read-write
    STATUS current
    DESCRIPTION
    "This attribute shall be the customizable Failure message to be 
    displayed to user when the authentication fails."
    DEFVAL {"Authentication Failed"}
    ::= {fsSecurityWebAuthParams 9}

fsSecurityWebAuthWebButtonText OBJECT-TYPE
    SYNTAX DisplayString
    MAX-ACCESS read-write
    STATUS current
    DESCRIPTION
    "This attribute shall be the customizable text message to be displayed 
     Submit button displayed in the login page." 
    DEFVAL {"Submit"}
    ::= {fsSecurityWebAuthParams 10}

fsSecurityWebAuthWebLoadBalInfo OBJECT-TYPE
    SYNTAX DisplayString
    MAX-ACCESS read-write
    STATUS current
    DESCRIPTION
    "This attribute shall be the customizable load balance message to be 
     displayed in the login page."
    ::= {fsSecurityWebAuthParams 11}

fsSecurityWebAuthDisplayLang OBJECT-TYPE
    SYNTAX Integer32
    MAX-ACCESS read-write
    STATUS current
    DESCRIPTION
    "This attribute shall be the customizable language option to be 
     displayed in the login page." 
    DEFVAL {1}
    ::= {fsSecurityWebAuthParams 12}

fsSecurityWebAuthColor OBJECT-TYPE
    SYNTAX Integer32
    MAX-ACCESS read-write
    STATUS current
    DESCRIPTION
    "This attribute shall be the customizable color option to be 
     displayed in the login page." 
    DEFVAL {1}
    ::= {fsSecurityWebAuthParams 13}


-- **********************************************************************
-- * fsDot11StationConfig TABLE
-- **********************************************************************
fsDot11StationConfigTable  OBJECT-TYPE
    SYNTAX          SEQUENCE OF FsDot11StationConfigEntry
    MAX-ACCESS      not-accessible
    STATUS          current
    DESCRIPTION     
    "Station Configuration Table in addition to
    dot11StationConfigTable."
    ::= { fsDot11smt 1 }

fsDot11StationConfigEntry  OBJECT-TYPE
    SYNTAX      FsDot11StationConfigEntry
    MAX-ACCESS  not-accessible
    STATUS      current
    DESCRIPTION
    "An entry in the fsDot11StationConfigTable. "
    INDEX { ifIndex }
    ::= { fsDot11StationConfigTable 1 }

FsDot11StationConfigEntry  ::=
    SEQUENCE {  fsDot11SupressSSID      TruthValue,
                fsDot11VlanId           Integer32
    }

fsDot11SupressSSID  OBJECT-TYPE
    SYNTAX      TruthValue
    MAX-ACCESS  read-write
    STATUS      current
    DESCRIPTION
    "This attribute, when FALSE, indicates that the
     SSID will be suppressed in 802.11 Beacon and Probe 
     Response frames."
    DEFVAL { false }
    ::= { fsDot11StationConfigEntry 1 }

fsDot11VlanId   OBJECT-TYPE
    SYNTAX      Integer32 (1..4094)
    MAX-ACCESS  read-write
    STATUS      current
    DESCRIPTION
    "Indicates the Vlan ID mapped to the corressponding
     WLAN Profile."
    DEFVAL { 1 }
    ::= { fsDot11StationConfigEntry 2 }

-- **********************************************************************
-- * fsDot11CapabilityProfile TABLE
-- **********************************************************************
fsDot11CapabilityProfileTable    OBJECT-TYPE
    SYNTAX      SEQUENCE OF FsDot11CapabilityProfileEntry
    MAX-ACCESS  not-accessible
    STATUS      current
    DESCRIPTION
    "A table containing the WTP capability profile Configuration in addition 
     to dot11."
    ::= { fsDot11smt 2 }

fsDot11CapabilityProfileEntry    OBJECT-TYPE
    SYNTAX      FsDot11CapabilityProfileEntry
    MAX-ACCESS  not-accessible
    STATUS      current
    DESCRIPTION
    "An entry appears in this table for each Capability profile. There can be
     upto 10 such instances."
    INDEX { fsDot11CapabilityProfileName }
    ::= { fsDot11CapabilityProfileTable 1 }

FsDot11CapabilityProfileEntry ::=
    SEQUENCE {  
		fsDot11CapabilityProfileName	             OCTET STRING,
        fsDot11CFPollable                            TruthValue,
		fsDot11CFPollRequest                         TruthValue,
		fsDot11PrivacyOptionImplemented              TruthValue,
		fsDot11ShortPreambleOptionImplemented        TruthValue,
		fsDot11PBCCOptionImplemented                 TruthValue,
		fsDot11ChannelAgilityPresent                 TruthValue, 
		fsDot11QosOptionImplemented                  TruthValue,
		fsDot11SpectrumManagementRequired            TruthValue,
		fsDot11ShortSlotTimeOptionImplemented        TruthValue,
		fsDot11APSDOptionImplemented                 TruthValue,
		fsDot11DSSSOFDMOptionEnabled                 TruthValue,
		fsDot11DelayedBlockAckOptionImplemented      TruthValue,
		fsDot11ImmediateBlockAckOptionImplemented    TruthValue,
		fsDot11QAckOptionImplemented                 TruthValue,
		fsDot11QueueRequestOptionImplemented         TruthValue,
		fsDot11TXOPRequestOptionImplemented          TruthValue,
		fsDot11RSNAOptionImplemented                 TruthValue,
		fsDot11RSNAPreauthenticationImplemented      TruthValue,
	    fsDot11CapabilityRowStatus  	    	     RowStatus  
    }

fsDot11CapabilityProfileName    OBJECT-TYPE
    SYNTAX      OCTET STRING (SIZE(0..32))
    MAX-ACCESS  not-accessible
    STATUS      current
    DESCRIPTION
    "Specify the index of the capabilities table."
    ::= { fsDot11CapabilityProfileEntry 1 }

fsDot11CFPollable OBJECT-TYPE
    SYNTAX      TruthValue
    MAX-ACCESS  read-write
    STATUS      current
    DESCRIPTION
    "When this attribute is TRUE, it shall indicate that
    the AP is able to respond to a CF-Poll with a data frame
    within a SIFS time. This attribute shall be FALSE if
    the AP is not able to respond to a CF-Poll with a data
    frame within a SIFS time."
    DEFVAL { false }
    ::= { fsDot11CapabilityProfileEntry 2 }

fsDot11CFPollRequest OBJECT-TYPE
    SYNTAX      TruthValue
    MAX-ACCESS  read-write
    STATUS      current
    DESCRIPTION
    "When this attribute is TRUE, it shall indiate that
     the AP is able to respond to CF-Poll but requesting
     not to be polled. When set to FALSE, the station will
     be able to respond to a CF-Poll with a data frame within 
     a SIFS time."
    DEFVAL { false }
    ::= { fsDot11CapabilityProfileEntry 3 }

fsDot11PrivacyOptionImplemented OBJECT-TYPE
    SYNTAX      TruthValue
    MAX-ACCESS  read-write
    STATUS      current
    DESCRIPTION
    "This attribute, when TRUE, shall indicate that the IEEE
    802.11 WEP option is implemented. The default value of
    this attribute shall be FALSE."
    DEFVAL { false }
    ::= { fsDot11CapabilityProfileEntry 4 }

fsDot11ShortPreambleOptionImplemented OBJECT-TYPE
    SYNTAX      TruthValue
    MAX-ACCESS  read-write
    STATUS      current
    DESCRIPTION
    "This attribute, when TRUE, shall indicate that the
    short preamble option as defined in 18.2.2.2
    is implemented. The default value of this attribute
    shall be FALSE."
    DEFVAL { false }
    ::= { fsDot11CapabilityProfileEntry 5 }
        
fsDot11PBCCOptionImplemented OBJECT-TYPE
    SYNTAX      TruthValue
    MAX-ACCESS  read-write
    STATUS      current
    DESCRIPTION
    "This attribute, when TRUE, shall indicate that the PBCC
    modulation option as defined in 18.4.6.6 is implemented. 
    The default value of this attribute shall be FALSE."
    DEFVAL { false }
    ::= { fsDot11CapabilityProfileEntry 6 }

fsDot11ChannelAgilityPresent OBJECT-TYPE
    SYNTAX      TruthValue
    MAX-ACCESS  read-write
    STATUS      current
    DESCRIPTION
    "This attribute indicates that the PHY is capable of
    channel agility."
    DEFVAL { false }
    ::= { fsDot11CapabilityProfileEntry 7 }

fsDot11QosOptionImplemented OBJECT-TYPE
    SYNTAX      TruthValue
    MAX-ACCESS  read-write
    STATUS      current
    DESCRIPTION
    "This attribute, when TRUE, indicates that the station
    implementation is capable of supporting QoS. The capability
    is disabled, otherwise. The default value of this attribute
    is FALSE."
    DEFVAL { false }
    ::= { fsDot11CapabilityProfileEntry 8 }
    
fsDot11SpectrumManagementRequired OBJECT-TYPE
    SYNTAX      TruthValue
    MAX-ACCESS  read-write
    STATUS      current
    DESCRIPTION
    "A AP will use the defined TPC and DFS procedures if and
    only if this attribute is TRUE. The default value of this
    attribute is FALSE."
    DEFVAL { false }
    ::= { fsDot11CapabilityProfileEntry 9 }

fsDot11ShortSlotTimeOptionImplemented OBJECT-TYPE
    SYNTAX      TruthValue
    MAX-ACCESS  read-write
    STATUS      current
    DESCRIPTION
    "This attribute, when TRUE, shall indicate that the Short
    Slot Time option as defined in 7.3.1.4 is implemented. The
    default value of this attribute is FALSE."
    DEFVAL { false }
    ::= { fsDot11CapabilityProfileEntry 10 }

fsDot11APSDOptionImplemented OBJECT-TYPE
    SYNTAX      TruthValue
    MAX-ACCESS  read-write
    STATUS      current
    DESCRIPTION
    "This attribute is available only at an AP. When TRUE,
    this attribute indicates that the AP implementation is
    capable of delivering data and polls to stations using
    APSD."
    DEFVAL { false }
    ::= { fsDot11CapabilityProfileEntry 11 }
    
fsDot11DSSSOFDMOptionEnabled OBJECT-TYPE
    SYNTAX      TruthValue
    MAX-ACCESS  read-write
    STATUS      current
    DESCRIPTION
    "This attribute, when TRUE, shall indicate that the
    DSSS-OFDM option as defined in 19.7 is
    enabled. The default value of this attribute is FALSE."
    DEFVAL { false }
    ::= { fsDot11CapabilityProfileEntry 12 }

fsDot11DelayedBlockAckOptionImplemented OBJECT-TYPE
    SYNTAX      TruthValue
    MAX-ACCESS  read-write
    STATUS      current
    DESCRIPTION
    "This attribute, when TRUE, indicates that the station
    implementation is capable of supporting Delayed Block Ack.
    The capability is disabled, otherwise. The default value of
    this attribute is FALSE."
    DEFVAL { false }
    ::= { fsDot11CapabilityProfileEntry 13 }
    
fsDot11ImmediateBlockAckOptionImplemented OBJECT-TYPE
    SYNTAX      TruthValue
    MAX-ACCESS  read-write
    STATUS      current
    DESCRIPTION
    "This attribute, when TRUE, indicates that the station
    implementation is capable of supporting Immediate Block Ack.
    The capability is disabled, otherwise. The default value of
    this attribute is FALSE."
    DEFVAL { false }
    ::= { fsDot11CapabilityProfileEntry 14 }
    
fsDot11QAckOptionImplemented OBJECT-TYPE
    SYNTAX      TruthValue
    MAX-ACCESS  read-write
    STATUS      current
    DESCRIPTION
    "This attribute, when TRUE, indicates that the station
    implementation is capable of interpreting the CF-Ack bit
    in a received frame of type data even if the frame is not
    directed to the QoS station. The capability is disabled,
    otherwise. A AP is capable of interpreting the CF-Ack bit
    in a received data frame if that station is the recipient
    of the data frame, regardless of the value of this MIB
    variable. The default value of this attribute is FALSE."
    DEFVAL { false }
    ::= { fsDot11CapabilityProfileEntry 15 }
    
fsDot11QueueRequestOptionImplemented OBJECT-TYPE
    SYNTAX      TruthValue
    MAX-ACCESS  read-write
    STATUS      current
    DESCRIPTION
    "This attribute is available only at an AP. This attribute,
    when TRUE, indicates that the AP is capable of processing
    the Queue Size field in QoS Control field of QoS Data type
    frames. The capability is disabled, otherwise. The default
    value of this attribute is FALSE."
    DEFVAL { false }
    ::= { fsDot11CapabilityProfileEntry 16 }
    
fsDot11TXOPRequestOptionImplemented OBJECT-TYPE
    SYNTAX      TruthValue
    MAX-ACCESS  read-write
    STATUS      current
    DESCRIPTION
    "This attribute is available only at an AP. This attribute,
    when TRUE, indicates that the AP is capable of processing
    the TXOP Duration requested field in QoS Control field of
    QoS Data type frames. The capability is disabled, otherwise.
    The default value of this attribute is FALSE."
    DEFVAL { false }
    ::= { fsDot11CapabilityProfileEntry 17 }
    
fsDot11RSNAOptionImplemented OBJECT-TYPE
    SYNTAX      TruthValue
    MAX-ACCESS  read-write
    STATUS      current
    DESCRIPTION
    "This variable indicates whether the entity is RSNA-capable."
    DEFVAL { false }
    ::= { fsDot11CapabilityProfileEntry 18 }

fsDot11RSNAPreauthenticationImplemented OBJECT-TYPE
    SYNTAX      TruthValue
    MAX-ACCESS  read-write
    STATUS      current
    DESCRIPTION
    "This variable indicates whether the entity supports RSNA
    preauthentication. This cannot be TRUE unless
    fsRSNAOptionImplemented is TRUE."
    DEFVAL { false }
    ::= { fsDot11CapabilityProfileEntry 19 }

fsDot11CapabilityRowStatus OBJECT-TYPE
    SYNTAX      RowStatus
    MAX-ACCESS  read-write
    STATUS      current
    DESCRIPTION
    "This variable is used to create, modify, and/or delete a row 
     in this table.
     All the objects in a row can be modified only when the value
     of this object in the corresponding conceptual row is not
     'active'.  Thus, to modify one or more of the objects in
     this conceptual row:
          a. change the row status to 'notInService',
          b. change the values of the row
          c. change the row status to 'active'
     The fsDot11ModelRowStatus may be changed to 'active'
     if all the managed objects in the conceptual row 
     have been assigned valid values."
    ::= { fsDot11CapabilityProfileEntry 20 }


-- **********************************************************************
-- * fsDot11AuthenticationProfile TABLE
-- **********************************************************************
fsDot11AuthenticationProfileTable    OBJECT-TYPE
    SYNTAX      SEQUENCE OF FsDot11AuthenticationProfileEntry
    MAX-ACCESS  not-accessible
    STATUS      current
    DESCRIPTION
    "A table containing the Authentication profile configured globally." 
    ::= { fsDot11smt 3 }

fsDot11AuthenticationProfileEntry    OBJECT-TYPE
    SYNTAX      FsDot11AuthenticationProfileEntry
    MAX-ACCESS  not-accessible
    STATUS      current
    DESCRIPTION
    "An entry appears in this table for each authentication profile. There can be
     upto 10 such instances."
    INDEX { fsDot11AuthenticationProfileName }
    ::= { fsDot11AuthenticationProfileTable 1 }

FsDot11AuthenticationProfileEntry ::=
    SEQUENCE {  fsDot11AuthenticationProfileName    OCTET STRING,
                fsDot11AuthenticationAlgorithm      INTEGER,
                fsDot11WepKeyIndex                  Integer32,
                fsDot11WepKeyType                   INTEGER,
                fsDot11WepKeyLength                 Integer32,
                fsDot11WepKey		                OCTET STRING,
                fsDot11WebAuthentication            Integer32,
                fsDot11AuthenticationRowStatus	    RowStatus  
    }

fsDot11AuthenticationProfileName    OBJECT-TYPE
    SYNTAX      OCTET STRING (SIZE(0..32))
    MAX-ACCESS  not-accessible
    STATUS      current
    DESCRIPTION
    "Specify the index of the Authentication Profile table."
    ::= { fsDot11AuthenticationProfileEntry 1 }
        
fsDot11AuthenticationAlgorithm OBJECT-TYPE
    SYNTAX INTEGER { openSystem(1), sharedKey(2) }
    MAX-ACCESS read-write
    STATUS current
    DESCRIPTION
    "This attribute shall be a set of all the authentication
    algorithms supported by the APs. The following are the
    default values and the associated algorithm.
    Value = 1: Open System
    Value = 2: Shared Key"
    DEFVAL { 1 }
    ::= { fsDot11AuthenticationProfileEntry 2 }

fsDot11WepKeyIndex OBJECT-TYPE
    SYNTAX Integer32 (1..4)
    MAX-ACCESS read-write
    STATUS current
    DESCRIPTION
    "The value of this variable indicates the WEP Key Index."
    ::= { fsDot11AuthenticationProfileEntry 3 }

fsDot11WepKeyType OBJECT-TYPE
    SYNTAX INTEGER { hex (1),
                     ascii (2)
                   }
    MAX-ACCESS read-write
    STATUS current
    DESCRIPTION
    "Wep Key type indicating HEX or ASCII value."
    ::= { fsDot11AuthenticationProfileEntry 4 }

fsDot11WepKeyLength OBJECT-TYPE
    SYNTAX Integer32 
    MAX-ACCESS read-write
    STATUS current
    DESCRIPTION
    "Wep Key Length which can be either 40 or 104."
    ::= { fsDot11AuthenticationProfileEntry 5 }

fsDot11WepKey OBJECT-TYPE
    SYNTAX OCTET STRING (SIZE(104))
    MAX-ACCESS read-write
    STATUS current
    DESCRIPTION
    "A WEP default secret key value. The length of the key can be 40 or 104." 
    ::= { fsDot11AuthenticationProfileEntry 6 }

fsDot11WebAuthentication OBJECT-TYPE
    SYNTAX INTEGER { enable (1),
                     disable (2)
    }
    MAX-ACCESS read-write
    STATUS current
    DESCRIPTION
    "Enable or disable the web authentication."
    DEFVAL { disable }
    ::= { fsDot11AuthenticationProfileEntry 7 }

fsDot11AuthenticationRowStatus OBJECT-TYPE
    SYNTAX      RowStatus
    MAX-ACCESS  read-write
    STATUS      current
    DESCRIPTION
    "This variable is used to create, modify, and/or delete a row 
     in this table.
     All the objects in a row can be modified only when the value
     of this object in the corresponding conceptual row is not
     'active'.  Thus, to modify one or more of the objects in
     this conceptual row:
          a. change the row status to 'notInService',
          b. change the values of the row
          c. change the row status to 'active'
     The fsDot11AuthenticationRowStatus may be changed to 'active'
     if all the managed objects in the conceptual row 
     have been assigned valid values."
    ::= { fsDot11AuthenticationProfileEntry 8 }

-- **********************************************************************
-- * End of fsDot11AuthenticationProfile TABLE
-- **********************************************************************

-- **********************************************************************
-- *	fsSecurityWebAuthGuestInfo TABLE
-- **********************************************************************
fsSecurityWebAuthGuestInfoTable OBJECT-TYPE
    SYNTAX SEQUENCE OF FsSecurityWebAuthGuestInfoEntry
    MAX-ACCESS not-accessible
    STATUS current
    DESCRIPTION
    "This (conceptual) table of attributes shall be a set of
    parameters related to the Guest users."
    ::= {fsDot11smt 4} 

fsSecurityWebAuthGuestInfoEntry OBJECT-TYPE
    SYNTAX FsSecurityWebAuthGuestInfoEntry
    MAX-ACCESS not-accessible
    STATUS current
    DESCRIPTION
    "An Entry (conceptual row) in the Web Authentication s
     credentials Table."
    INDEX { fsSecurityWebAuthUName}
    ::= { fsSecurityWebAuthGuestInfoTable 1 }

FsSecurityWebAuthGuestInfoEntry ::=
    SEQUENCE {fsSecurityWebAuthUName DisplayString,
              fsSecurityWlanProfileId Integer32,
              fsSecurityWebAuthUserLifetime Integer32,
              fsSecurityWebAuthUserEmailId DisplayString,
              fsSecurityWebAuthGuestInfoRowStatus RowStatus}

fsSecurityWebAuthUName OBJECT-TYPE
    SYNTAX DisplayString (SIZE(1..20))
    MAX-ACCESS not-accessible
    STATUS current
    DESCRIPTION
    "This attribute shall be the Guest user name to login through
     the Web Authentication"
    ::= {fsSecurityWebAuthGuestInfoEntry  1 }

fsSecurityWlanProfileId OBJECT-TYPE
    SYNTAX Integer32
    MAX-ACCESS read-write
    STATUS current
    DESCRIPTION
    "This attribute shall be the Wlan profileId for which the user 
     account is created for."
    ::= {fsSecurityWebAuthGuestInfoEntry 2 }
    
fsSecurityWebAuthUserLifetime OBJECT-TYPE
    SYNTAX Integer32
    MAX-ACCESS read-write
    STATUS current
    DESCRIPTION
    "This attribute shall be the lifetime(in seconds) of the Guest 
     user account . This value can be 60 to 2592000 seconds  and when set 
     to zero makes the account permanent"
    ::= {fsSecurityWebAuthGuestInfoEntry 3 }

fsSecurityWebAuthUserEmailId OBJECT-TYPE
    SYNTAX DisplayString
    MAX-ACCESS read-only
    STATUS current
    DESCRIPTION
    "This attribute shall be the Email address of the Guest
     user . This when set to zero makes the account permanent"
    ::= {fsSecurityWebAuthGuestInfoEntry 4 }

fsSecurityWebAuthGuestInfoRowStatus OBJECT-TYPE
    SYNTAX      RowStatus
    MAX-ACCESS  read-write
    STATUS      current
    DESCRIPTION
    "This variable is used to create, modify, and/or delete a row 
     in this table.
     All the objects in a row can be modified only when the value
     of this object in the corresponding conceptual row is not
     'active'.  Thus, to modify one or more of the objects in
     this conceptual row:
          a. change the row status to 'notInService',
          b. change the values of the row
          c. change the row status to 'active'
     The fsSecurityWebAuthGuestInfoRowStatus may be changed to 'active'
     if all the managed objects in the conceptual row 
     have been assigned valid values."
    ::= { fsSecurityWebAuthGuestInfoEntry 5 }
-- **********************************************************************
-- * End of fsSecurityWebAuthGuestInfo TABLE
-- **********************************************************************

-- **********************************************************************
-- *    fsStationQosParams TABLE
-- **********************************************************************
fsStationQosParamsTable OBJECT-TYPE
    SYNTAX SEQUENCE OF FsStationQosParamsEntry
    MAX-ACCESS not-accessible
    STATUS current
    DESCRIPTION
    "This (conceptual) table of attributes shall be a set of
    QoS parameters related to the Station QoS."
    ::= {fsDot11smt 5}

fsStationQosParamsEntry OBJECT-TYPE
    SYNTAX FsStationQosParamsEntry
    MAX-ACCESS not-accessible
    STATUS current
    DESCRIPTION
    "An Entry (conceptual row) in the Station QoS
     Table.
    ifIndex - Each IEEE 802.11 interface is represented by an
    ifEntry. Interface tables in this MIB module are indexed
    by ifIndex."
    INDEX { ifIndex,
	    fsStaMacAddress }
    ::= { fsStationQosParamsTable 1 }

FsStationQosParamsEntry ::=
    SEQUENCE {fsStaMacAddress MacAddress,
              fsStaQoSPriority Integer32,
              fsStaQoSDscp  Integer32 }

fsStaMacAddress OBJECT-TYPE
    SYNTAX MacAddress
    MAX-ACCESS not-accessible
    STATUS current
    DESCRIPTION
    "This attribute shall be Mac address of the Station"
    ::= {fsStationQosParamsEntry 1 }

fsStaQoSPriority OBJECT-TYPE
    SYNTAX Integer32
    MAX-ACCESS read-write
    STATUS current
    DESCRIPTION
    "This attribute shall be the priority values to be 
    used if the packets are to be IEEE 802.1p tagged 
    (3-bits)."
    ::= {fsStationQosParamsEntry 2 }

fsStaQoSDscp OBJECT-TYPE
    SYNTAX Integer32
    MAX-ACCESS read-write
    STATUS current
    DESCRIPTION
    "This attribute shall be the dscp label of 6-bits."
    ::= {fsStationQosParamsEntry 3 }

-- **********************************************************************
-- * End of fsStationQosParams TABLE
-- **********************************************************************
    
-- **********************************************************************
-- * fsVlanIsolation TABLE
-- **********************************************************************
fsVlanIsolationTable OBJECT-TYPE
    SYNTAX      SEQUENCE OF FsVlanIsolationEntry
    MAX-ACCESS  not-accessible
    STATUS      current
    DESCRIPTION
    "A table to determine whether the VLAN traffic for different SSID 
     needs to be isolated.This will be configured per WLAN profile"
    ::= { fsDot11smt 6 }

fsVlanIsolationEntry    OBJECT-TYPE
    SYNTAX      FsVlanIsolationEntry
    MAX-ACCESS  not-accessible
    STATUS      current
    DESCRIPTION
    "An entry in VLAN isolation table for each VLAN ID."
    INDEX { ifIndex }
    ::= { fsVlanIsolationTable 1 }

FsVlanIsolationEntry ::=
    SEQUENCE {  fsVlanIsolation INTEGER }

fsVlanIsolation OBJECT-TYPE
    SYNTAX      INTEGER {
                 enable (1),
                 disable (2)       
                }
    MAX-ACCESS  read-write
    STATUS      current
    DESCRIPTION
    "To enable or disable the VLAN isolation feature."
    DEFVAL { disable }
    ::= { fsVlanIsolationEntry 1 }


-- **********************************************************************
-- * fsDot11RadioConfig TABLE
-- **********************************************************************
fsDot11RadioConfigTable  OBJECT-TYPE
    SYNTAX          SEQUENCE OF FsDot11RadioConfigEntry
    MAX-ACCESS      not-accessible
    STATUS          current
    DESCRIPTION     
    "WTP Radio Configuration Information."
    ::= { fsDot11smt 7 }

fsDot11RadioConfigEntry  OBJECT-TYPE
    SYNTAX      FsDot11RadioConfigEntry
    MAX-ACCESS  not-accessible
    STATUS      current
    DESCRIPTION
    "An entry in the fsDot11RadioConfigTable, representing the radio configuration
     in addition to the configuration available in IEEE802dot11-MIB."
    INDEX { ifIndex }
    ::= { fsDot11RadioConfigTable 1 }	

FsDot11RadioConfigEntry  ::=
    SEQUENCE {  fsDot11RadioType               INTEGER,
                fsDot11RadioNoOfBssIdSupported Integer32,
                fsDot11RadioAntennaType        Integer32,
                fsDot11RadioFailureStatus      Integer32,
                fsDot11RowStatus               RowStatus     
    }

fsDot11RadioType     OBJECT-TYPE
    SYNTAX      INTEGER {
                dot11b (1),
                dot11a (2),
                dot11g (4),
                dot11bg (5),
                dot11an (10),
                dot11bgn (13)
    }
    MAX-ACCESS  read-write
    STATUS      current
    DESCRIPTION
    "Represents the current operating 802.11 a, b or g network."
    DEFVAL { dot11b }
    ::= { fsDot11RadioConfigEntry 1 }

fsDot11RadioNoOfBssIdSupported   OBJECT-TYPE
    SYNTAX      Integer32 (1..16)
    MAX-ACCESS  read-only
    STATUS      current
    DESCRIPTION
    "Number of BSSID supported by radio interface"
    ::= {fsDot11RadioConfigEntry 2 }

fsDot11RadioAntennaType      OBJECT-TYPE 
    SYNTAX      INTEGER {
                transmitter (1),
                receiver (2)           
            }
    MAX-ACCESS  read-only
    STATUS      current
    DESCRIPTION
    "Indicating the Antenna type in which the failure occured"
    ::= { fsDot11RadioConfigEntry 3 }

fsDot11RadioFailureStatus    OBJECT-TYPE
    SYNTAX      INTEGER {
                set (1),
                clear (2)
    }
    MAX-ACCESS  read-only
    STATUS      current
    DESCRIPTION
    "Indicates whether Radio failure occured or cleared"
    ::= { fsDot11RadioConfigEntry 4 }

fsDot11RowStatus OBJECT-TYPE
    SYNTAX      RowStatus
    MAX-ACCESS  read-write
    STATUS      current
    DESCRIPTION
    "This variable is used to create, modify, and/or delete a row 
     in this table.
     All the objects in a row can be modified only when the value
     of this object in the corresponding conceptual row is not
     'active'.  Thus, to modify one or more of the objects in
     this conceptual row:
          a. change the row status to 'notInService',
          b. change the values of the row
          c. change the row status to 'active'
     The fsDot11AuthenticationRowStatus may be changed to 'active'
     if all the managed objects in the conceptual row 
     have been assigned valid values."
    ::= { fsDot11RadioConfigEntry 15 }

-- **********************************************************************
-- * fsDot11QosProfile TABLE
-- **********************************************************************
fsDot11QosProfileTable    OBJECT-TYPE
    SYNTAX      SEQUENCE OF FsDot11QosProfileEntry
    MAX-ACCESS  not-accessible
    STATUS      current
    DESCRIPTION
    "A table containing the QoS profile configured globally." 
    ::= { fsDot11smt 8}

fsDot11QosProfileEntry    OBJECT-TYPE
    SYNTAX      FsDot11QosProfileEntry
    MAX-ACCESS  not-accessible
    STATUS      current
    DESCRIPTION
    "An entry appears in this table for each QoS profile. There can be
     upto 10 such instances."
    INDEX { fsDot11QosProfileName }
    ::= { fsDot11QosProfileTable 1 }

FsDot11QosProfileEntry ::=
    SEQUENCE {  fsDot11QosProfileName               OCTET STRING,
                fsDot11QosTraffic                   INTEGER,
                fsDot11QosPassengerTrustMode        INTEGER,
                fsDot11QosRateLimit		            INTEGER,
                fsDot11UpStreamCIR		            Integer32,	
                fsDot11UpStreamCBS		            Integer32,	
                fsDot11UpStreamEIR		            Integer32,
                fsDot11UpStreamEBS	                Integer32,
                fsDot11DownStreamCIR	            Integer32,	
                fsDot11DownStreamCBS	    	    Integer32,	
                fsDot11DownStreamEIR	    	    Integer32,
                fsDot11DownStreamEBS	 	        Integer32,
                fsDot11QosRowStatus         	    RowStatus  
    }

fsDot11QosProfileName  OBJECT-TYPE
    SYNTAX      OCTET STRING (SIZE(0..32))
    MAX-ACCESS  not-accessible
    STATUS      current
    DESCRIPTION
    "Specify the index of the Qos Profile table."
    ::= { fsDot11QosProfileEntry 1 }
        
fsDot11QosTraffic OBJECT-TYPE
    SYNTAX INTEGER { bestEffort (1), 
                     video (2),
                     voice (3), 
                     background (4)
    }
    MAX-ACCESS read-write
    STATUS current
    DESCRIPTION
    "This attribute indicates the type of Qos Traffic used by
     this profile"
    DEFVAL { bestEffort }
    ::= { fsDot11QosProfileEntry 2 }

fsDot11QosPassengerTrustMode OBJECT-TYPE
    SYNTAX INTEGER { enable (1),
                     disable (2)
    }
    MAX-ACCESS read-write
    STATUS current
    DESCRIPTION
    "Enable or disable the passenger trust mode."
    DEFVAL { disable }
    ::= { fsDot11QosProfileEntry 3 }

fsDot11QosRateLimit OBJECT-TYPE
    SYNTAX INTEGER { enable (1),
                     disable (2)
    }
    MAX-ACCESS read-write
    STATUS current
    DESCRIPTION
    "Enable or disable the Qos Rate Limit."
    DEFVAL { disable }
    ::= { fsDot11QosProfileEntry 4 }

fsDot11UpStreamCIR OBJECT-TYPE
    SYNTAX Integer32
    MAX-ACCESS read-write
    STATUS current
    DESCRIPTION
    "To configure CIR value for Upstream traffic."
    DEFVAL { 100 }
    ::= { fsDot11QosProfileEntry 5 }

fsDot11UpStreamCBS OBJECT-TYPE
    SYNTAX Integer32 
    MAX-ACCESS read-write
    STATUS current
    DESCRIPTION
    "To configure CBS value for Upstream traffic."
    DEFVAL { 1000 }
    ::= { fsDot11QosProfileEntry 6 }

fsDot11UpStreamEIR OBJECT-TYPE
    SYNTAX Integer32
    MAX-ACCESS read-write
    STATUS current
    DESCRIPTION
    "To configure EIR value for Upstream traffic."
    DEFVAL { 15000 }
    ::= { fsDot11QosProfileEntry 7 }

fsDot11UpStreamEBS OBJECT-TYPE
    SYNTAX Integer32 
    MAX-ACCESS read-write
    STATUS current
    DESCRIPTION
    "To configure EBS value for Upstream traffic."
    DEFVAL { 15000 }
    ::= { fsDot11QosProfileEntry 8 }

fsDot11DownStreamCIR OBJECT-TYPE
    SYNTAX Integer32
    MAX-ACCESS read-write
    STATUS current
    DESCRIPTION
    "To configure CIR value for Downstream traffic."
    DEFVAL { 100 }
    ::= { fsDot11QosProfileEntry 9 }

fsDot11DownStreamCBS OBJECT-TYPE
    SYNTAX Integer32 
    MAX-ACCESS read-write
    STATUS current
    DESCRIPTION
    "To configure CBS value for Downstream traffic."
    DEFVAL { 1000 }
    ::= { fsDot11QosProfileEntry 10 }

fsDot11DownStreamEIR OBJECT-TYPE
    SYNTAX Integer32
    MAX-ACCESS read-write
    STATUS current
    DESCRIPTION
    "To configure EIR value for Downstream traffic."
    DEFVAL { 15000 }
    ::= { fsDot11QosProfileEntry 11 }

fsDot11DownStreamEBS OBJECT-TYPE
    SYNTAX Integer32 
    MAX-ACCESS read-write
    STATUS current
    DESCRIPTION
    "To configure EBS value for Downstream traffic."
    DEFVAL { 15000 }
    ::= { fsDot11QosProfileEntry 12 }

fsDot11QosRowStatus OBJECT-TYPE
    SYNTAX      RowStatus
    MAX-ACCESS  read-write
    STATUS      current
    DESCRIPTION
    "This variable is used to create, modify, and/or delete a row 
     in this table.
     All the objects in a row can be modified only when the value
     of this object in the corresponding conceptual row is not
     'active'.  Thus, to modify one or more of the objects in
     this conceptual row:
          a. change the row status to 'notInService',
          b. change the values of the row
          c. change the row status to 'active'
     The fsDot11AuthenticationRowStatus may be changed to 'active'
     if all the managed objects in the conceptual row 
     have been assigned valid values."
    ::= { fsDot11QosProfileEntry 13 }

-- **********************************************************************
-- * fsDot11WlanCapabilityProfile TABLE
-- **********************************************************************
fsDot11WlanCapabilityProfileTable    OBJECT-TYPE
    SYNTAX      SEQUENCE OF FsDot11WlanCapabilityProfileEntry
    MAX-ACCESS  not-accessible
    STATUS      current
    DESCRIPTION
    "A table containing the WTP capability profile Configuration in addition 
     to dot11."
    ::= { fsDot11smt 9 }

fsDot11WlanCapabilityProfileEntry    OBJECT-TYPE
    SYNTAX      FsDot11WlanCapabilityProfileEntry
    MAX-ACCESS  not-accessible
    STATUS      current
    DESCRIPTION
    "An entry appears in this table for each Capability profile. There can be
     upto 10 such instances."
    INDEX { ifIndex }
    ::= { fsDot11WlanCapabilityProfileTable 1 }

FsDot11WlanCapabilityProfileEntry ::=
    SEQUENCE {  
        fsDot11WlanCFPollable                            TruthValue,
		fsDot11WlanCFPollRequest                         TruthValue,
		fsDot11WlanPrivacyOptionImplemented              TruthValue,
		fsDot11WlanShortPreambleOptionImplemented        TruthValue,
		fsDot11WlanPBCCOptionImplemented                 TruthValue,
		fsDot11WlanChannelAgilityPresent                 TruthValue, 
		fsDot11WlanQosOptionImplemented                  TruthValue,
		fsDot11WlanSpectrumManagementRequired            TruthValue,
		fsDot11WlanShortSlotTimeOptionImplemented        TruthValue,
		fsDot11WlanAPSDOptionImplemented                 TruthValue,
		fsDot11WlanDSSSOFDMOptionEnabled                 TruthValue,
		fsDot11WlanDelayedBlockAckOptionImplemented      TruthValue,
		fsDot11WlanImmediateBlockAckOptionImplemented    TruthValue,
		fsDot11WlanQAckOptionImplemented                 TruthValue,
		fsDot11WlanQueueRequestOptionImplemented         TruthValue,
		fsDot11WlanTXOPRequestOptionImplemented          TruthValue,
		fsDot11WlanRSNAOptionImplemented                 TruthValue,
		fsDot11WlanRSNAPreauthenticationImplemented      TruthValue,
	    fsDot11WlanCapabilityRowStatus  	    	     RowStatus  
    }

fsDot11WlanCFPollable OBJECT-TYPE
    SYNTAX      TruthValue
    MAX-ACCESS  read-write
    STATUS      current
    DESCRIPTION
    "When this attribute is TRUE, it shall indicate that
    the AP is able to respond to a CF-Poll with a data frame
    within a SIFS time. This attribute shall be FALSE if
    the AP is not able to respond to a CF-Poll with a data
    frame within a SIFS time."
    DEFVAL { false }
    ::= { fsDot11WlanCapabilityProfileEntry 1 }

fsDot11WlanCFPollRequest OBJECT-TYPE
    SYNTAX      TruthValue
    MAX-ACCESS  read-write
    STATUS      current
    DESCRIPTION
    "When this attribute is TRUE, it shall indiate that
     the AP is able to respond to CF-Poll but requesting
     not to be polled. When set to FALSE, the station will
     be able to respond to a CF-Poll with a data frame within 
     a SIFS time."
    DEFVAL { false }
    ::= { fsDot11WlanCapabilityProfileEntry 2 }

fsDot11WlanPrivacyOptionImplemented OBJECT-TYPE
    SYNTAX      TruthValue
    MAX-ACCESS  read-write
    STATUS      current
    DESCRIPTION
    "This attribute, when TRUE, shall indicate that the IEEE
    802.11 WEP option is implemented. The default value of
    this attribute shall be FALSE."
    DEFVAL { false }
    ::= { fsDot11WlanCapabilityProfileEntry 3 }

fsDot11WlanShortPreambleOptionImplemented OBJECT-TYPE
    SYNTAX      TruthValue
    MAX-ACCESS  read-write
    STATUS      current
    DESCRIPTION
    "This attribute, when TRUE, shall indicate that the
    short preamble option as defined in 18.2.2.2
    is implemented. The default value of this attribute
    shall be FALSE."
    DEFVAL { false }
    ::= { fsDot11WlanCapabilityProfileEntry 4 }
        
fsDot11WlanPBCCOptionImplemented OBJECT-TYPE
    SYNTAX      TruthValue
    MAX-ACCESS  read-write
    STATUS      current
    DESCRIPTION
    "This attribute, when TRUE, shall indicate that the PBCC
    modulation option as defined in 18.4.6.6 is implemented. 
    The default value of this attribute shall be FALSE."
    DEFVAL { false }
    ::= { fsDot11WlanCapabilityProfileEntry 5 }

fsDot11WlanChannelAgilityPresent OBJECT-TYPE
    SYNTAX      TruthValue
    MAX-ACCESS  read-write
    STATUS      current
    DESCRIPTION
    "This attribute indicates that the PHY is capable of
    channel agility."
    DEFVAL { false }
    ::= { fsDot11WlanCapabilityProfileEntry 6 }

fsDot11WlanQosOptionImplemented OBJECT-TYPE
    SYNTAX      TruthValue
    MAX-ACCESS  read-write
    STATUS      current
    DESCRIPTION
    "This attribute, when TRUE, indicates that the station
    implementation is capable of supporting QoS. The capability
    is disabled, otherwise. The default value of this attribute
    is FALSE."
    DEFVAL { false }
    ::= { fsDot11WlanCapabilityProfileEntry 7 }
    
fsDot11WlanSpectrumManagementRequired OBJECT-TYPE
    SYNTAX      TruthValue
    MAX-ACCESS  read-write
    STATUS      current
    DESCRIPTION
    "A AP will use the defined TPC and DFS procedures if and
    only if this attribute is TRUE. The default value of this
    attribute is FALSE."
    DEFVAL { false }
    ::= { fsDot11WlanCapabilityProfileEntry 8 }

fsDot11WlanShortSlotTimeOptionImplemented OBJECT-TYPE
    SYNTAX      TruthValue
    MAX-ACCESS  read-write
    STATUS      current
    DESCRIPTION
    "This attribute, when TRUE, shall indicate that the Short
    Slot Time option as defined in 7.3.1.4 is implemented. The
    default value of this attribute is FALSE."
    DEFVAL { false }
    ::= { fsDot11WlanCapabilityProfileEntry 9 }

fsDot11WlanAPSDOptionImplemented OBJECT-TYPE
    SYNTAX      TruthValue
    MAX-ACCESS  read-write
    STATUS      current
    DESCRIPTION
    "This attribute is available only at an AP. When TRUE,
    this attribute indicates that the AP implementation is
    capable of delivering data and polls to stations using
    APSD."
    DEFVAL { false }
    ::= { fsDot11WlanCapabilityProfileEntry 10 }
    
fsDot11WlanDSSSOFDMOptionEnabled OBJECT-TYPE
    SYNTAX      TruthValue
    MAX-ACCESS  read-write
    STATUS      current
    DESCRIPTION
    "This attribute, when TRUE, shall indicate that the
    DSSS-OFDM option as defined in 19.7 is
    enabled. The default value of this attribute is FALSE."
    DEFVAL { false }
    ::= { fsDot11WlanCapabilityProfileEntry 11 }

fsDot11WlanDelayedBlockAckOptionImplemented OBJECT-TYPE
    SYNTAX      TruthValue
    MAX-ACCESS  read-write
    STATUS      current
    DESCRIPTION
    "This attribute, when TRUE, indicates that the station
    implementation is capable of supporting Delayed Block Ack.
    The capability is disabled, otherwise. The default value of
    this attribute is FALSE."
    DEFVAL { false }
    ::= { fsDot11WlanCapabilityProfileEntry 12 }
    
fsDot11WlanImmediateBlockAckOptionImplemented OBJECT-TYPE
    SYNTAX      TruthValue
    MAX-ACCESS  read-write
    STATUS      current
    DESCRIPTION
    "This attribute, when TRUE, indicates that the station
    implementation is capable of supporting Immediate Block Ack.
    The capability is disabled, otherwise. The default value of
    this attribute is FALSE."
    DEFVAL { false }
    ::= { fsDot11WlanCapabilityProfileEntry 13 }
    
fsDot11WlanQAckOptionImplemented OBJECT-TYPE
    SYNTAX      TruthValue
    MAX-ACCESS  read-write
    STATUS      current
    DESCRIPTION
    "This attribute, when TRUE, indicates that the station
    implementation is capable of interpreting the CF-Ack bit
    in a received frame of type data even if the frame is not
    directed to the QoS station. The capability is disabled,
    otherwise. A AP is capable of interpreting the CF-Ack bit
    in a received data frame if that station is the recipient
    of the data frame, regardless of the value of this MIB
    variable. The default value of this attribute is FALSE."
    DEFVAL { false }
    ::= { fsDot11WlanCapabilityProfileEntry 14 }
    
fsDot11WlanQueueRequestOptionImplemented OBJECT-TYPE
    SYNTAX      TruthValue
    MAX-ACCESS  read-write
    STATUS      current
    DESCRIPTION
    "This attribute is available only at an AP. This attribute,
    when TRUE, indicates that the AP is capable of processing
    the Queue Size field in QoS Control field of QoS Data type
    frames. The capability is disabled, otherwise. The default
    value of this attribute is FALSE."
    DEFVAL { false }
    ::= { fsDot11WlanCapabilityProfileEntry 15 }
    
fsDot11WlanTXOPRequestOptionImplemented OBJECT-TYPE
    SYNTAX      TruthValue
    MAX-ACCESS  read-write
    STATUS      current
    DESCRIPTION
    "This attribute is available only at an AP. This attribute,
    when TRUE, indicates that the AP is capable of processing
    the TXOP Duration requested field in QoS Control field of
    QoS Data type frames. The capability is disabled, otherwise.
    The default value of this attribute is FALSE."
    DEFVAL { false }
    ::= { fsDot11WlanCapabilityProfileEntry 16 }
    
fsDot11WlanRSNAOptionImplemented OBJECT-TYPE
    SYNTAX      TruthValue
    MAX-ACCESS  read-write
    STATUS      current
    DESCRIPTION
    "This variable indicates whether the entity is RSNA-capable."
    DEFVAL { false }
    ::= { fsDot11WlanCapabilityProfileEntry 17 }

fsDot11WlanRSNAPreauthenticationImplemented OBJECT-TYPE
    SYNTAX      TruthValue
    MAX-ACCESS  read-write
    STATUS      current
    DESCRIPTION
    "This variable indicates whether the entity supports RSNA
    preauthentication. This cannot be TRUE unless
    fsRSNAOptionImplemented is TRUE."
    DEFVAL { false }
    ::= { fsDot11WlanCapabilityProfileEntry 18 }

fsDot11WlanCapabilityRowStatus OBJECT-TYPE
    SYNTAX      RowStatus
    MAX-ACCESS  read-write
    STATUS      current
    DESCRIPTION
    "This variable is used to create, modify, and/or delete a row 
     in this table.
     All the objects in a row can be modified only when the value
     of this object in the corresponding conceptual row is not
     'active'.  Thus, to modify one or more of the objects in
     this conceptual row:
          a. change the row status to 'notInService',
          b. change the values of the row
          c. change the row status to 'active'
     The fsDot11ModelRowStatus may be changed to 'active'
     if all the managed objects in the conceptual row 
     have been assigned valid values."
    ::= { fsDot11WlanCapabilityProfileEntry 19 }


-- **********************************************************************
-- * fsDot11AuthenticationProfile TABLE
-- **********************************************************************
fsDot11WlanAuthenticationProfileTable    OBJECT-TYPE
    SYNTAX      SEQUENCE OF FsDot11WlanAuthenticationProfileEntry
    MAX-ACCESS  not-accessible
    STATUS      current
    DESCRIPTION
    "A table containing the Authentication profile configured globally." 
    ::= { fsDot11smt 10 }

fsDot11WlanAuthenticationProfileEntry    OBJECT-TYPE
    SYNTAX      FsDot11WlanAuthenticationProfileEntry
    MAX-ACCESS  not-accessible
    STATUS      current
    DESCRIPTION
    "An entry appears in this table for each authentication profile. There can be
     upto 10 such instances."
    INDEX { ifIndex }
    ::= { fsDot11WlanAuthenticationProfileTable 1 }

FsDot11WlanAuthenticationProfileEntry ::=
    SEQUENCE {  fsDot11WlanAuthenticationAlgorithm      INTEGER,
                fsDot11WlanWepKeyIndex                  Integer32,
                fsDot11WlanWepKeyType	                INTEGER,
                fsDot11WlanWepKeyLength                 Integer32,
                fsDot11WlanWepKey                       OCTET STRING,
                fsDot11WlanWebAuthentication            INTEGER,
                fsDot11WlanAuthenticationRowStatus	    RowStatus  
    }

fsDot11WlanAuthenticationAlgorithm OBJECT-TYPE
    SYNTAX INTEGER { openSystem(1), sharedKey(2), webAuth(3) }
    MAX-ACCESS read-write
    STATUS current
    DESCRIPTION
    "This attribute shall be a set of all the authentication
    algorithms supported by the APs. The following are the
    default values and the associated algorithm.
    Value = 1: Open System
    Value = 2: Shared Key
    Value = 3: Web Auth"
    DEFVAL { 1 }
    ::= { fsDot11WlanAuthenticationProfileEntry 1 }

fsDot11WlanWepKeyIndex OBJECT-TYPE
    SYNTAX Integer32 (1..4)
    MAX-ACCESS read-write
    STATUS current
    DESCRIPTION
    "The value of this variable indicates the WEP Key Index."
    ::= { fsDot11WlanAuthenticationProfileEntry 2 }

fsDot11WlanWepKeyType OBJECT-TYPE
    SYNTAX INTEGER { hex (1),
                     ascii (2)
                   }
    MAX-ACCESS read-write
    STATUS current
    DESCRIPTION
    "Wep Key type indicating HEX or ASCII value."
    ::= { fsDot11WlanAuthenticationProfileEntry 3 }

fsDot11WlanWepKeyLength OBJECT-TYPE
    SYNTAX Integer32 
    MAX-ACCESS read-write
    STATUS current
    DESCRIPTION
    "Wep Key Length which can be either 40 or 104."
    ::= { fsDot11WlanAuthenticationProfileEntry 4 }

fsDot11WlanWepKey OBJECT-TYPE
    SYNTAX OCTET STRING (SIZE(104))
    MAX-ACCESS read-write
    STATUS current
    DESCRIPTION
    "A WEP default secret key value. The length of the key can be 40 or 104." 
    ::= { fsDot11WlanAuthenticationProfileEntry 5 }

fsDot11WlanWebAuthentication OBJECT-TYPE
    SYNTAX INTEGER { enabled (1),
                     disabled (2)
    }
    MAX-ACCESS read-write
    STATUS current
    DESCRIPTION
    "Enable or disable the web authentication."
    DEFVAL { disabled }
    ::= { fsDot11WlanAuthenticationProfileEntry 6 }

fsDot11WlanAuthenticationRowStatus OBJECT-TYPE
    SYNTAX      RowStatus
    MAX-ACCESS  read-write
    STATUS      current
    DESCRIPTION
    "This variable is used to create, modify, and/or delete a row 
     in this table.
     All the objects in a row can be modified only when the value
     of this object in the corresponding conceptual row is not
     'active'.  Thus, to modify one or more of the objects in
     this conceptual row:
          a. change the row status to 'notInService',
          b. change the values of the row
          c. change the row status to 'active'
     The fsDot11AuthenticationRowStatus may be changed to 'active'
     if all the managed objects in the conceptual row 
     have been assigned valid values."
    ::= { fsDot11WlanAuthenticationProfileEntry 7 }

-- **********************************************************************
-- * fsDot11WlanQosProfile TABLE
-- **********************************************************************
fsDot11WlanQosProfileTable    OBJECT-TYPE
    SYNTAX      SEQUENCE OF FsDot11WlanQosProfileEntry
    MAX-ACCESS  not-accessible
    STATUS      current
    DESCRIPTION
    "A table containing the QoS profile configured globally." 
    ::= { fsDot11smt 11 }

fsDot11WlanQosProfileEntry    OBJECT-TYPE
    SYNTAX      FsDot11WlanQosProfileEntry
    MAX-ACCESS  not-accessible
    STATUS      current
    DESCRIPTION
    "An entry appears in this table for each QoS profile. There can be
     upto 10 such instances."
    INDEX { ifIndex }
    ::= { fsDot11WlanQosProfileTable 1 }

FsDot11WlanQosProfileEntry ::=
    SEQUENCE {  
            fsDot11WlanQosTraffic                   INTEGER,
            fsDot11WlanQosPassengerTrustMode        INTEGER,
		    fsDot11WlanQosRateLimit		 	        INTEGER,
	        fsDot11WlanUpStreamCIR		            Integer32,	
	        fsDot11WlanUpStreamCBS		            Integer32,	
	        fsDot11WlanUpStreamEIR		            Integer32,
	        fsDot11WlanUpStreamEBS	                Integer32,
	        fsDot11WlanDownStreamCIR	            Integer32,	
	        fsDot11WlanDownStreamCBS	            Integer32,	
	        fsDot11WlanDownStreamEIR	            Integer32,
	        fsDot11WlanDownStreamEBS	            Integer32,
            fsDot11WlanQosRowStatus         	    RowStatus  
    }

fsDot11WlanQosTraffic OBJECT-TYPE
    SYNTAX INTEGER { bestEffort (1), 
                     video (2),
                     voice (3), 
                     background (4)
    }
    MAX-ACCESS read-write
    STATUS current
    DESCRIPTION
    "This attribute indicates the type of Qos Traffic used by
     this profile"
    DEFVAL { bestEffort }
    ::= { fsDot11WlanQosProfileEntry 1 }

fsDot11WlanQosPassengerTrustMode OBJECT-TYPE
    SYNTAX INTEGER { enabled (1),
                     disabled (2)
    }
    MAX-ACCESS read-write
    STATUS current
    DESCRIPTION
    "Enable or disable the passenger trust mode."
    DEFVAL { disabled }
    ::= { fsDot11WlanQosProfileEntry 2 }

fsDot11WlanQosRateLimit OBJECT-TYPE
    SYNTAX INTEGER { enabled (1),
                     disabled (2)
    }
    MAX-ACCESS read-write
    STATUS current
    DESCRIPTION
    "Enable or disable the Qos Rate Limit."
    DEFVAL { disabled }
    ::= { fsDot11WlanQosProfileEntry 3 }

fsDot11WlanUpStreamCIR OBJECT-TYPE
    SYNTAX Integer32
    MAX-ACCESS read-write
    STATUS current
    DESCRIPTION
    "To configure CIR value for Upstream traffic."
    DEFVAL { 100 }
    ::= { fsDot11WlanQosProfileEntry 4 }

fsDot11WlanUpStreamCBS OBJECT-TYPE
    SYNTAX Integer32 
    MAX-ACCESS read-write
    STATUS current
    DESCRIPTION
    "To configure CBS value for Upstream traffic."
    DEFVAL { 1000 }
    ::= { fsDot11WlanQosProfileEntry 5 }

fsDot11WlanUpStreamEIR OBJECT-TYPE
    SYNTAX Integer32
    MAX-ACCESS read-write
    STATUS current
    DESCRIPTION
    "To configure EIR value for Upstream traffic."
    DEFVAL { 15000 }
    ::= { fsDot11WlanQosProfileEntry 6 }

fsDot11WlanUpStreamEBS OBJECT-TYPE
    SYNTAX Integer32 
    MAX-ACCESS read-write
    STATUS current
    DESCRIPTION
    "To configure EBS value for Upstream traffic."
    DEFVAL { 15000 }
    ::= { fsDot11WlanQosProfileEntry 7 }

fsDot11WlanDownStreamCIR OBJECT-TYPE
    SYNTAX Integer32
    MAX-ACCESS read-write
    STATUS current
    DESCRIPTION
    "To configure CIR value for Downstream traffic."
    DEFVAL { 100 }
    ::= { fsDot11WlanQosProfileEntry 8 }

fsDot11WlanDownStreamCBS OBJECT-TYPE
    SYNTAX Integer32 
    MAX-ACCESS read-write
    STATUS current
    DESCRIPTION
    "To configure CBS value for Downstream traffic."
    DEFVAL { 1000 }
    ::= { fsDot11WlanQosProfileEntry 9 }

fsDot11WlanDownStreamEIR OBJECT-TYPE
    SYNTAX Integer32
    MAX-ACCESS read-write
    STATUS current
    DESCRIPTION
    "To configure EIR value for Downstream traffic."
    DEFVAL { 15000 }
    ::= { fsDot11WlanQosProfileEntry 10 }

fsDot11WlanDownStreamEBS OBJECT-TYPE
    SYNTAX Integer32 
    MAX-ACCESS read-write
    STATUS current
    DESCRIPTION
    "To configure EBS value for Downstream traffic."
    DEFVAL { 15000 }
    ::= { fsDot11WlanQosProfileEntry 11 }

fsDot11WlanQosRowStatus OBJECT-TYPE
    SYNTAX      RowStatus
    MAX-ACCESS  read-write
    STATUS      current
    DESCRIPTION
    "This variable is used to create, modify, and/or delete a row 
     in this table.
     All the objects in a row can be modified only when the value
     of this object in the corresponding conceptual row is not
     'active'.  Thus, to modify one or more of the objects in
     this conceptual row:
          a. change the row status to 'notInService',
          b. change the values of the row
          c. change the row status to 'active'
     The fsDot11AuthenticationRowStatus may be changed to 'active'
     if all the managed objects in the conceptual row 
     have been assigned valid values."
    ::= { fsDot11WlanQosProfileEntry 12 }

-- **********************************************************************
-- * fsDot11CapabilityMapping TABLE
-- **********************************************************************
fsDot11CapabilityMappingTable OBJECT-TYPE
    SYNTAX      SEQUENCE OF FsDot11CapabilityMappingEntry
    MAX-ACCESS  not-accessible
    STATUS      current
    DESCRIPTION
    "A table containing the QoS configuration information for the WTP.
     This table shall contain an entry for each virtual radio interface
     index."
    ::= { fsDot11smt 12 }

fsDot11CapabilityMappingEntry OBJECT-TYPE
    SYNTAX      FsDot11CapabilityMappingEntry
    MAX-ACCESS  not-accessible
    STATUS      current
    DESCRIPTION
    "An Entry (conceptual row) in the WTP Qos Configuration Table.
     ifIndex - Each IEEE 802.11 interface is represented by an
     ifEntry."
    INDEX { ifIndex }
    ::= { fsDot11CapabilityMappingTable 1 }

FsDot11CapabilityMappingEntry ::=
    SEQUENCE {
        fsDot11CapabilityMappingProfileName OCTET STRING,
        fsDot11CapabilityMappingRowStatus   RowStatus 
    }

fsDot11CapabilityMappingProfileName    OBJECT-TYPE
    SYNTAX      OCTET STRING (SIZE(0..32))
    MAX-ACCESS  not-accessible
    STATUS      current
    DESCRIPTION
    "Specify the index of the capabilities table."
    ::= { fsDot11CapabilityMappingEntry 1 }

fsDot11CapabilityMappingRowStatus   OBJECT-TYPE
    SYNTAX      RowStatus
    MAX-ACCESS  read-write
    STATUS      current
    DESCRIPTION
    "This variable is used to create or delete a row 
     in this table."
    ::= { fsDot11CapabilityMappingEntry 2 }


-- **********************************************************************
-- * fsDot11AuthMapping TABLE
-- **********************************************************************
fsDot11AuthMappingTable OBJECT-TYPE
    SYNTAX      SEQUENCE OF FsDot11AuthMappingEntry
    MAX-ACCESS  not-accessible
    STATUS      current
    DESCRIPTION
    "A table containing the QoS configuration information for the WTP.
     This table shall contain an entry for each virtual radio interface
     index."
    ::= { fsDot11smt 13 }

fsDot11AuthMappingEntry OBJECT-TYPE
    SYNTAX      FsDot11AuthMappingEntry
    MAX-ACCESS  not-accessible
    STATUS      current
    DESCRIPTION
    "An Entry (conceptual row) in the WTP Qos Configuration Table.
     ifIndex - Each IEEE 802.11 interface is represented by an
     ifEntry."
    INDEX { ifIndex }
    ::= { fsDot11AuthMappingTable 1 }

FsDot11AuthMappingEntry ::=
    SEQUENCE {
        fsDot11AuthMappingProfileName    OCTET STRING,
        fsDot11AuthMappingRowStatus   RowStatus 
    }

fsDot11AuthMappingProfileName    OBJECT-TYPE
    SYNTAX      OCTET STRING (SIZE(0..32))
    MAX-ACCESS  read-write
    STATUS      current
    DESCRIPTION
    "Specify the index of the Authentication Profile table."
    ::= { fsDot11AuthMappingEntry 1 }
        
fsDot11AuthMappingRowStatus   OBJECT-TYPE
    SYNTAX      RowStatus
    MAX-ACCESS  read-write
    STATUS      current
    DESCRIPTION
    "This variable is used to create or delete a row 
     in this table."
    ::= { fsDot11AuthMappingEntry 2 }

-- **********************************************************************
-- * fsDot11QosMapping TABLE
-- **********************************************************************
fsDot11QosMappingTable OBJECT-TYPE
    SYNTAX      SEQUENCE OF FsDot11QosMappingEntry
    MAX-ACCESS  not-accessible
    STATUS      current
    DESCRIPTION
    "A table containing the QoS configuration information for the WTP.
     This table shall contain an entry for each virtual radio interface
     index."
    ::= { fsDot11smt 14 }

fsDot11QosMappingEntry OBJECT-TYPE
    SYNTAX      FsDot11QosMappingEntry
    MAX-ACCESS  not-accessible
    STATUS      current
    DESCRIPTION
    "An Entry (conceptual row) in the WTP Qos Configuration Table.
     ifIndex - Each IEEE 802.11 interface is represented by an
     ifEntry."
    INDEX { ifIndex }
    ::= { fsDot11QosMappingTable 1 }

FsDot11QosMappingEntry ::=
    SEQUENCE {
        fsDot11QosMappingProfileName    OCTET STRING,
        fsDot11QosMappingRowStatus   RowStatus 
    }

fsDot11QosMappingProfileName  OBJECT-TYPE
    SYNTAX      OCTET STRING (SIZE(0..32))
    MAX-ACCESS  read-write
    STATUS      current
    DESCRIPTION
    "Specify the index of the Qos Profile table."
    ::= { fsDot11QosMappingEntry 1 }
        
fsDot11QosMappingRowStatus   OBJECT-TYPE
    SYNTAX      RowStatus
    MAX-ACCESS  read-write
    STATUS      current
    DESCRIPTION
    "This variable is used to create or delete a row 
     in this table."
    ::= { fsDot11QosMappingEntry 2 }


-- **********************************************************************
-- * fsDot11ClientSummary TABLE
-- **********************************************************************
fsDot11ClientSummaryTable OBJECT-TYPE
    SYNTAX      SEQUENCE OF FsDot11ClientSummaryEntry
    MAX-ACCESS  not-accessible
    STATUS      current
    DESCRIPTION
    "This table stores the station related information."
    ::= { fsDot11smt 15 }

fsDot11ClientSummaryEntry OBJECT-TYPE
    SYNTAX      FsDot11ClientSummaryEntry
    MAX-ACCESS  not-accessible
    STATUS      current
    DESCRIPTION
    "An Entry (conceptual row) in the Client related information.
     ifIndex - Each IEEE 802.11 interface is represented by an
     ifEntry."
    INDEX { fsDot11ClientMacAddress }
    ::= { fsDot11ClientSummaryTable 1 }

FsDot11ClientSummaryEntry ::=
    SEQUENCE {
        fsDot11ClientMacAddress      MacAddress,
        fsDot11WlanProfileId         CapwapDot11WlanIdProfileTC,
        fsDot11WtpProfileName        SnmpAdminString,
        fsDot11WtpRadioId            CapwapBaseRadioIdTC,
        fsDot11AuthStatus            TruthValue,
        fsDot11AssocStatus           TruthValue
    }

fsDot11ClientMacAddress  OBJECT-TYPE
    SYNTAX      MacAddress
    MAX-ACCESS  not-accessible
    STATUS      current
    DESCRIPTION
    "Specify the index of the Client summary Table."
    ::= { fsDot11ClientSummaryEntry 1 }
        
fsDot11WlanProfileId   OBJECT-TYPE
    SYNTAX      CapwapDot11WlanIdProfileTC
    MAX-ACCESS  read-only
    STATUS      current
    DESCRIPTION
    "This variable represents the WLAN profile for which the station
     is associated."
    ::= { fsDot11ClientSummaryEntry 2 }

fsDot11WtpProfileName   OBJECT-TYPE
    SYNTAX      SnmpAdminString
    MAX-ACCESS  read-only
    STATUS      current
    DESCRIPTION
    "This variable represents the WTP Profile for which the station
     is associated."
    ::= { fsDot11ClientSummaryEntry 3 }
        
fsDot11WtpRadioId   OBJECT-TYPE
    SYNTAX      CapwapBaseRadioIdTC
    MAX-ACCESS  read-only
    STATUS      current
    DESCRIPTION
    "This variable represents the WTP Radio Id in which the station
     is associated."
    ::= { fsDot11ClientSummaryEntry 4 }

fsDot11AuthStatus   OBJECT-TYPE
    SYNTAX      TruthValue
    MAX-ACCESS  read-only
    STATUS      current
    DESCRIPTION
    "This variable represents the Authentication status of the
     station."
    ::= { fsDot11ClientSummaryEntry 5 }

fsDot11AssocStatus   OBJECT-TYPE
    SYNTAX      TruthValue
    MAX-ACCESS  read-only
    STATUS      current
    DESCRIPTION
    "This variable represents the Association status of the
     station."
    ::= { fsDot11ClientSummaryEntry 6 }


-- **********************************************************************
-- * fsDot11RadioQoS TABLE
-- **********************************************************************

fsDot11RadioQosTable OBJECT-TYPE
    SYNTAX      SEQUENCE OF FsDot11RadioQosEntry
    MAX-ACCESS  not-accessible
    STATUS      current
    DESCRIPTION
    "A table containing the QoS configuration information for the WTP.
     This table shall contain an entry for each virtual radio interface
     index."
    ::= { fsDot11mac 1 }

fsDot11RadioQosEntry OBJECT-TYPE
    SYNTAX FsDot11RadioQosEntry
    MAX-ACCESS  not-accessible
    STATUS      current
    DESCRIPTION
    "An Entry (conceptual row) in the WTP Qos Configuration Table.
     ifIndex - Each IEEE 802.11 interface is represented by an
     ifEntry."
    INDEX { ifIndex }
    ::= {fsDot11RadioQosTable 1}

FsDot11RadioQosEntry ::=
    SEQUENCE { fsDot11TaggingPolicy  BITS
    }

fsDot11TaggingPolicy OBJECT-TYPE
    SYNTAX      BITS {
                dot1p (0),
                dot1q (1),
                dscp (2),
                outerHeader (3),
                innerHeader (4)
    }
    MAX-ACCESS  read-write
    STATUS      current
    DESCRIPTION
    "Represents the bit field indicating how the WTP is to mark
     packets for QoS purposes."
    DEFVAL { 0 }
    ::= {fsDot11RadioQosEntry 1}

-- **********************************************************************
-- * fsDot11QAP TABLE
-- **********************************************************************

fsDot11QAPTable OBJECT-TYPE
    SYNTAX      SEQUENCE OF FsDot11QAPEntry
    MAX-ACCESS  not-accessible
    STATUS      current
    DESCRIPTION
    "A table containing the QoS configuration information for the WTP.
     This table shall contain an entry for each virtual radio interface
     index."
    ::= { fsDot11mac 2 }

fsDot11QAPEntry OBJECT-TYPE
    SYNTAX FsDot11QAPEntry
    MAX-ACCESS  not-accessible
    STATUS      current
    DESCRIPTION
    "An Entry (conceptual row) in the WTP Qos Configuration Table.
     ifIndex - Each IEEE 802.11 interface is represented by an
     ifEntry."
    INDEX { ifIndex,
	    dot11EDCATableIndex }
    ::= {fsDot11QAPTable 1}

FsDot11QAPEntry ::=
    SEQUENCE { fsDot11QueueDepth     Integer32,
               fsDot11PriorityValue  Integer32,
               fsDot11DscpValue      Integer32
    }

fsDot11QueueDepth OBJECT-TYPE
    SYNTAX      Integer32 (1..255) 
    MAX-ACCESS  read-only
    STATUS      current
    DESCRIPTION
    "Represents the number of packets that can be on the specific
     QoS transmit queue at any given time."
    ::= {fsDot11QAPEntry 2}

fsDot11PriorityValue OBJECT-TYPE
    SYNTAX      Integer32 (0..7)
    MAX-ACCESS  read-write
    STATUS      current
    DESCRIPTION
    "Represents the priority value for incoming packets from station."
    DEFVAL { 0 }
    ::= {fsDot11QAPEntry 3}

fsDot11DscpValue OBJECT-TYPE
    SYNTAX      Integer32 (0..63)
    MAX-ACCESS  read-write
    STATUS      current
    DESCRIPTION
    "Represents the DSCP value marked for QoS purposes."
    DEFVAL { 0 }
    ::= {fsDot11QAPEntry 4}


-- **********************************************************************
-- * fsDot11QAP TABLE
-- **********************************************************************

fsQAPProfileTable OBJECT-TYPE
    SYNTAX      SEQUENCE OF FsQAPProfileEntry
    MAX-ACCESS  not-accessible
    STATUS      current
    DESCRIPTION
    "A table containing the QoS configuration information for the WTP.
     This table shall contain an entry for each virtual radio interface
     index."
    ::= { fsDot11mac 3 }

fsQAPProfileEntry OBJECT-TYPE
    SYNTAX FsQAPProfileEntry
    MAX-ACCESS  not-accessible
    STATUS      current
    DESCRIPTION
    "An Entry (conceptual row) in the WTP Qos Configuration Table.
     ifIndex - Each IEEE 802.11 interface is represented by an
     ifEntry."
    INDEX { fsQAPProfileName, fsQAPProfileIndex }
    ::= {fsQAPProfileTable 1}

FsQAPProfileEntry ::=
    SEQUENCE { fsQAPProfileName                 OCTET STRING,
               fsQAPProfileIndex                Integer32,
               fsQAPProfileCWmin                Integer32,
               fsQAPProfileCWmax                Integer32,
               fsQAPProfileAIFSN                Integer32,
               fsQAPProfileTXOPLimit            Integer32,
               fsQAPProfileQueueDepth           Integer32,
               fsQAPProfilePriorityValue        Integer32,
               fsQAPProfileDscpValue            Integer32,
               fsQAPProfileRowStatus            RowStatus
    }

fsQAPProfileName OBJECT-TYPE
    SYNTAX      OCTET STRING (SIZE(0..32))
    MAX-ACCESS  not-accessible
    STATUS      current
    DESCRIPTION
    "Represents the QoS Profile which will be default get applied to
     any WTP Profile when configured."
    ::= { fsQAPProfileEntry 1 }

fsQAPProfileIndex OBJECT-TYPE
    SYNTAX Integer32 (1..4)
    MAX-ACCESS not-accessible
    STATUS current
    DESCRIPTION
    "The auxiliary variable used to identify instances of the columnar
    objects in the EDCA Table. The value of this variable is
    1) 1, if the value of the AC is AC_BK.
    2) 2, if the value of the AC is AC_BE.
    3) 3, if the value of the AC is AC_VI.
    4) 4, if the value of the AC is AC_VO."
    ::= { fsQAPProfileEntry 2 }

fsQAPProfileCWmin OBJECT-TYPE
    SYNTAX Integer32 (0..255)
    MAX-ACCESS read-write
    STATUS current
    DESCRIPTION
    "This attribute shall specify the value of the minimum size of the
    window that shall be used by an AP for a particular AC for
    generating a random number for the backoff. The value of this
    attribute shall be such that it could always be expressed in the
    form of 2X - 1, where X is an integer. The default value for this
    attribute is
    1) aCWmin, if dot11QAPEDCATableIndex is 1 or 2.
    2) (aCWmin+1)/2 - 1, if dot11QAPEDCATableIndex is 3.
    3) (aCWmin+1)/4 - 1, if dot11QAPEDCATableIndex is 4."
    ::= { fsQAPProfileEntry 3 }

fsQAPProfileCWmax OBJECT-TYPE
    SYNTAX Integer32 (0..65535)
    MAX-ACCESS read-write
    STATUS current
    DESCRIPTION
    "This attribute shall specify the value of the maximum size of the
    window that shall be used by an AP for a particular AC for
    generating a random number for the backoff. The value of this
    attribute shall be such that it could always be expressed in the
    form of 2X - 1, where X is an integer. The default value for this
    attribute is
    1) aCWmax, if dot11QAPEDCATableIndex is 1.
    2) 4*(aCWmin+1) - 1, if dot11QAPEDCATableIndex is 2.
    3) aCWmin, if dot11QAPEDCATableIndex is 3.
    4) (aCWmin+1)/2 - 1, if dot11QAPEDCATableIndex is 4."
    ::= { fsQAPProfileEntry 4 }

fsQAPProfileAIFSN OBJECT-TYPE
    SYNTAX Integer32 (1..15)
    MAX-ACCESS read-write
    STATUS current
    DESCRIPTION
    "This attribute shall specify the number of slots, after a SIFS
    duration, that the AP, for a particular AC, shall sense the
    medium idle either before transmitting or executing a backoff. The
    default value for this attribute is
    1) 7, if dot11QAPEDCATableIndex is 1,
    2) 3, if dot11QAPEDCATableIndex is 2
    3) 1, otherwise."
    ::= { fsQAPProfileEntry 5 }

fsQAPProfileTXOPLimit OBJECT-TYPE
    SYNTAX Integer32 (0..65535)
    MAX-ACCESS read-write
    STATUS current
    DESCRIPTION
    "This attribute shall specify the maximum number of microseconds of
    an EDCA TXOP for a given AC at a non-AP STA. The default value for
    this attribute is
    1) 0 for all PHYs, if dot11EDCATableIndex is 1 or 2; this
    implies that the sender can send one MSDU in an EDCA TXOP,
    2) 3008 microseconds for Clause 17 and Clause 19 PHY and 6016
    microseconds for Clause 18 PHY, if dot11EDCATableIndex is 3,
    3) 1504 microseconds for Clause 17 and Clause 19 PHY and 3264
    microseconds for Clause 18 PHY, if dot11EDCATableIndex is 4."
    ::= { fsQAPProfileEntry 6 }

fsQAPProfileQueueDepth OBJECT-TYPE
    SYNTAX      Integer32 (1..255) 
    MAX-ACCESS  read-only
    STATUS      current
    DESCRIPTION
    "Represents the number of packets that can be on the specific
     QoS transmit queue at any given time."
    ::= { fsQAPProfileEntry 7 }

fsQAPProfilePriorityValue OBJECT-TYPE
    SYNTAX      Integer32 (0..7)
    MAX-ACCESS  read-write
    STATUS      current
    DESCRIPTION
    "Represents the priority value for incoming packets from station."
    DEFVAL { 0 }
    ::= { fsQAPProfileEntry 8 }

fsQAPProfileDscpValue OBJECT-TYPE
    SYNTAX      Integer32 (0..63)
    MAX-ACCESS  read-write
    STATUS      current
    DESCRIPTION
    "Represents the DSCP value marked for QoS purposes."
    DEFVAL { 0 }
    ::= { fsQAPProfileEntry 9 }

fsQAPProfileRowStatus OBJECT-TYPE
    SYNTAX      RowStatus
    MAX-ACCESS  read-write
    STATUS      current
    DESCRIPTION
    "This variable is used to create, modify, and/or delete a row 
     in this table.
     All the objects in a row can be modified only when the value
     of this object in the corresponding conceptual row is not
     'active'.  Thus, to modify one or more of the objects in
     this conceptual row:
          a. change the row status to 'notInService',
          b. change the values of the row
          c. change the row status to 'active'
     The fsDot11AuthenticationRowStatus may be changed to 'active'
     if all the managed objects in the conceptual row 
     have been assigned valid values."
    ::= { fsQAPProfileEntry 10 }


-- **********************************************************************
-- * fsDot11AntennaList TABLE
-- **********************************************************************
fsDot11AntennasListTable OBJECT-TYPE
    SYNTAX      SEQUENCE OF FsDot11AntennasListEntry
    MAX-ACCESS  not-accessible
    STATUS      current
    DESCRIPTION
    "This table represents the list of antennae. Each entry in this
    table represents a single antenna with its properties(antenna selection). 
    The maximum number of antennae that can be contained in this table is 255."
    ::= { fsDot11phy 1 }

fsDot11AntennasListEntry OBJECT-TYPE
    SYNTAX      FsDot11AntennasListEntry
    MAX-ACCESS  not-accessible
    STATUS      current
    DESCRIPTION
    "An entry in the fsDot11AntennasListTable, representing
    the properties of a single antenna. This table is
    an enhancement to the table in IEEE802dot11-MIB.
    ifIndex - Each IEEE 802.11 interface is represented by
    an ifEntry. Interface tables in this MIB module are indexed
    by ifIndex."
    INDEX { ifIndex,
        dot11AntennaListIndex }
    ::= { fsDot11AntennasListTable 1 }

FsDot11AntennasListEntry ::=
    SEQUENCE {  fsAntennaMode   INTEGER,
                fsAntennaSelection INTEGER }

fsAntennaMode OBJECT-TYPE
    SYNTAX      INTEGER {
                 sectorA (1),
                 sectorB (2),
                 omni (3),
                 mimo (4)
    }
    MAX-ACCESS  read-write
    STATUS      current
    DESCRIPTION
    "To configure an AP to use one internal antenna for an 802.11 sectorized
    180-degree coverage pattern or both internal antennas for an 802.11
    360-degree omnidirectional pattern. 
    
    sectorA - Specifies to use only the left internal antenna. 
    sectorB - Specifies to use only the right internal antenna
    omni - Specifies to use both internal antennas. 
    mimo -  Specifies to use multiple antennas at both transmitter and receiver."
    DEFVAL { omni }
    ::= { fsDot11AntennasListEntry 1 }

fsAntennaSelection OBJECT-TYPE
    SYNTAX      INTEGER {
                 internal(1),
                 external(2)
    }
    MAX-ACCESS  read-write
    STATUS      current
    DESCRIPTION
    "To select the internal or external antenna selection for an access point.
     There can be 255 antennas configured."
    DEFVAL { internal }
    ::= { fsDot11AntennasListEntry 2 }

-- fsDot11WlanTable Table
fsDot11WlanTable OBJECT-TYPE
    SYNTAX      SEQUENCE OF FsDot11WlanEntry
    MAX-ACCESS  not-accessible
    STATUS      current
    DESCRIPTION
        "A table that allows the operator to display and configure
         WLAN profiles, such as specifying the MAC type and tunnel mode
         for a WLAN.  Also, it helps the AC to configure a WLAN through
         the IEEE 802.11 MIB module.
         Values of all objects in this table are persistent at
         restart/reboot."
    ::= { fsDot11phy 2 }

fsDot11WlanEntry  OBJECT-TYPE
    SYNTAX      FsDot11WlanEntry
    MAX-ACCESS  not-accessible
    STATUS      current
    DESCRIPTION
        "A set of objects that stores the settings of a WLAN profile."
    INDEX { capwapDot11WlanProfileId }
    ::= { fsDot11WlanTable 1 }

FsDot11WlanEntry ::=
    SEQUENCE {
      fsDot11WlanProfileIfIndex     InterfaceIndex,
      fsDot11WlanRowStatus          RowStatus
    }

fsDot11WlanProfileIfIndex OBJECT-TYPE
    SYNTAX      InterfaceIndex
    MAX-ACCESS  read-write
    STATUS      current
    DESCRIPTION
        "Represents the index value that uniquely identifies a
         WLAN Profile Interface.  The interface identified by a
         particular value of this index is the same interface as
         identified by the same value of the ifIndex.
         The creation of a row object in the capwapDot11WlanTable
         triggers the AC to automatically create an WLAN Profile
         Interface identified by an ifIndex without manual
         intervention.
         Most MIB tables in the IEEE 802.11 MIB module
         [IEEE.802-11.2007] use an ifIndex to identify an interface
         to facilitate the configuration and maintenance, for example,
         dot11AuthenticationAlgorithmsTable.
         Using the ifIndex of a WLAN Profile Interface, the Operator
         could configure a WLAN through the IEEE 802.11 MIB module."
    ::= { fsDot11WlanEntry 1 }

fsDot11WlanRowStatus OBJECT-TYPE
    SYNTAX      RowStatus
    MAX-ACCESS  read-create
    STATUS      current
    DESCRIPTION
        "This variable is used to create, modify, and/or delete a row
         in this table.
         All the objects in a row can be modified only when the value
         of this object in the corresponding conceptual row is not
         'active'.  Thus, to modify one or more of the objects in
         this conceptual row:
              a. change the row status to 'notInService',
              b. change the values of the row
              c. change the row status to 'active'
         The capwapDot11WlanRowStatus may be changed to 'active'
         if all the managed objects in the conceptual row with
         MAX-ACCESS read-create have been assigned valid values.

         When the operator deletes a WLAN profile, the AC SHOULD
         check whether the WLAN profile is bound with a radio.
         If yes, the value of the Response-PDU's error-status field
         is set to 'inconsistentValue', and the value of its
         error-index field is set to the index of the failed variable
         binding.  If not, the row object could be deleted."
    ::= { fsDot11WlanEntry 2 }

-- End of capwapDot11WlanTable Table

-- fsDot11WlanBindTable Table

fsDot11WlanBindTable OBJECT-TYPE
    SYNTAX      SEQUENCE OF FsDot11WlanBindEntry
    MAX-ACCESS  not-accessible
    STATUS      current
    DESCRIPTION
        "A table that stores bindings between WLAN profiles
         (identified by capwapDot11WlanProfileId) and WTP Virtual Radio
         Interfaces.  The WTP Virtual Radio Interfaces on the AC
         correspond to physical layer (PHY) radios on the WTPs.
         It also stores the mappings between WLAN IDs and WLAN
         Basic Service Set (BSS) Interfaces.
         Values of all objects in this table are persistent at
         restart/reboot."
    ::= { fsDot11phy 3 }

fsDot11WlanBindEntry OBJECT-TYPE
    SYNTAX      FsDot11WlanBindEntry
    MAX-ACCESS  not-accessible
    STATUS      current
    DESCRIPTION
        "A set of objects that stores the binding of a WLAN profile
         to a WTP Virtual Radio Interface.  It also stores the mapping
         between WLAN ID and WLAN BSS Interface.
         The INDEX object ifIndex is the ifIndex of a WTP Virtual
         Radio Interface."
    INDEX { ifIndex, capwapDot11WlanProfileId }
    ::= { fsDot11WlanBindTable 1 }

FsDot11WlanBindEntry ::=
    SEQUENCE { fsDot11WlanBindWlanId        CapwapDot11WlanIdTC,
      fsDot11WlanBindBssIfIndex    InterfaceIndex,
      fsDot11WlanBindRowStatus     RowStatus
    }

fsDot11WlanBindWlanId OBJECT-TYPE
    SYNTAX      CapwapDot11WlanIdTC
    MAX-ACCESS  read-write
    STATUS      current
    DESCRIPTION
        "Represents the WLAN ID of a WLAN.
         During a binding operation, the AC MUST select an unused
         WLAN ID from between 1 and 16 [RFC5416].  For example, to bind
         another WLAN profile to a radio that has been bound with
         a WLAN profile, WLAN ID 2 should be assigned."
    REFERENCE
        "Section 6.1 of CAPWAP Protocol Binding for IEEE 802.11,
         RFC 5416."
    ::= { fsDot11WlanBindEntry 1 }

fsDot11WlanBindBssIfIndex OBJECT-TYPE
    SYNTAX      InterfaceIndex
    MAX-ACCESS  read-write
    STATUS      current
    DESCRIPTION
        "Represents the index value that uniquely identifies a
         WLAN BSS Interface.  The interface identified by a
         particular value of this index is the same interface as
         identified by the same value of the ifIndex.
         The ifIndex here is for a WLAN BSS Interface.
         The creation of a row object in the capwapDot11WlanBindTable
         triggers the AC to automatically create a WLAN BSS Interface
         identified by an ifIndex without manual intervention.
         The PHY address of the capwapDot11WlanBindBssIfIndex is the
         BSSID.  While manufacturers are free to assign BSSIDs by using
         any arbitrary mechanism, it is advised that where possible the
         BSSIDs are assigned as a contiguous block.
         When assigned as a block, implementations can still assign
         any of the available BSSIDs to any WLAN.  One possible method
         is for the WTP to assign the address using the following
         algorithm: base BSSID address + WLAN ID."
    REFERENCE
        "Section 2.4 of CAPWAP Protocol Binding for IEEE 802.11,
         RFC 5416."
    ::= { fsDot11WlanBindEntry 2 }

fsDot11WlanBindRowStatus OBJECT-TYPE
    SYNTAX      RowStatus
    MAX-ACCESS  read-create
    STATUS      current
    DESCRIPTION
        "This variable is used to create, modify, and/or delete a row
         in this table.
         All the objects in a row can be modified only when the value
         of this object in the corresponding conceptual row is not
         'active'.  Thus, to modify one or more of the objects in
         this conceptual row:
              a. change the row status to 'notInService',
              b. change the values of the row
              c. change the row status to 'active'"
    ::= { fsDot11WlanBindEntry 3 }
-- End of fsDot11WlanBindTable Table

-- fsWtpImageUpgrade Table
fsWtpImageUpgradeTable      OBJECT-TYPE
    SYNTAX      SEQUENCE OF FsWtpImageUpgradeEntry
    MAX-ACCESS  not-accessible
    STATUS      current
    DESCRIPTION
        "A table that stores the WTP upgrade related information"
    ::= { fsWlanSystem 1 }

fsWtpImageUpgradeEntry      OBJECT-TYPE
    SYNTAX      FsWtpImageUpgradeEntry
    MAX-ACCESS  not-accessible
    STATUS      current
    DESCRIPTION
    "A set of objects that stores the upgrade related information for
     a particular WTP model."
    INDEX { capwapBaseWtpProfileWtpModelNumber }
    ::= { fsWtpImageUpgradeTable 1 }

FsWtpImageUpgradeEntry ::=
    SEQUENCE { 
        fsWtpImageVersion           OCTET STRING,
        fsWtpUpgradeDev             INTEGER,
        fsWtpName                   SnmpAdminString,
        fsWtpImageName              OCTET STRING,
        fsWtpAddressType            InetAddressType,
        fsWtpServerIP               InetAddress,
        fsWtpRowStatus              RowStatus               
    }

fsWtpImageVersion  OBJECT-TYPE
    SYNTAX      OCTET STRING
    MAX-ACCESS  read-write
    STATUS      current
    DESCRIPTION
        "Indicates the Software Image version number available in the 
        server"
    ::= { fsWtpImageUpgradeEntry 1 }

fsWtpUpgradeDev  OBJECT-TYPE
    SYNTAX      INTEGER {
                none (1),
                perAP (2),
                allAP (3)
    }
    MAX-ACCESS  read-write
    STATUS      current
    DESCRIPTION
        "Indicates whether to upgrade a specific AP or all AP's or only  
        download the image"
    DEFVAL { none }
    ::= { fsWtpImageUpgradeEntry 2 }

fsWtpName  OBJECT-TYPE
    SYNTAX      SnmpAdminString
    MAX-ACCESS  read-write
    STATUS      current
    DESCRIPTION
        "The configured WTP name is applicable only if fsWtpUpgradeDev is set to
        perAP."
    ::= { fsWtpImageUpgradeEntry 3 }

fsWtpImageName  OBJECT-TYPE
    SYNTAX      OCTET STRING
    MAX-ACCESS  read-write
    STATUS      current
    DESCRIPTION
        "Indicates the Software Image name  to be downloaded from the server."
    ::= { fsWtpImageUpgradeEntry 4 }

fsWtpAddressType  OBJECT-TYPE
    SYNTAX      InetAddressType
    MAX-ACCESS  read-write
    STATUS      current
    DESCRIPTION
        "Specifies the Address type of server.Address type shall be ipv4(1) or
        ipv6(2)."
    DEFVAL { 1 }    
    ::= { fsWtpImageUpgradeEntry 5 }

fsWtpServerIP  OBJECT-TYPE
    SYNTAX      InetAddress(SIZE(4|16))
    MAX-ACCESS  read-write
    STATUS      current
    DESCRIPTION
        "Specifies the ServerIP from which the image shall be downloaded."
    ::= { fsWtpImageUpgradeEntry 6 }

fsWtpRowStatus  OBJECT-TYPE
    SYNTAX      RowStatus
    MAX-ACCESS  read-write
    STATUS      current
    DESCRIPTION
        "The status of the entry"
    ::= { fsWtpImageUpgradeEntry 7 }

-- End of fsWtpImageUpgrade Table

-- fsDot11nConfigTable Table

fsDot11nConfigTable OBJECT-TYPE
    SYNTAX      SEQUENCE OF FsDot11nConfigEntry
    MAX-ACCESS  not-accessible
    STATUS      current
    DESCRIPTION
    "This table represents the dot11n config params."
    ::= { fsDot11phy 4 }

fsDot11nConfigEntry OBJECT-TYPE
    SYNTAX      FsDot11nConfigEntry
    MAX-ACCESS  not-accessible
    STATUS      current
    DESCRIPTION
    " "
    INDEX { ifIndex }
    ::= { fsDot11nConfigTable 1 }

FsDot11nConfigEntry ::=
SEQUENCE { 
    fsDot11nConfigShortGIfor20MHz TruthValue,
    fsDot11nConfigShortGIfor40MHz TruthValue,
    fsDot11nConfigChannelWidth INTEGER
}

fsDot11nConfigShortGIfor20MHz OBJECT-TYPE
    SYNTAX      TruthValue
    MAX-ACCESS  read-write
    STATUS      current
    DESCRIPTION
    "This is a status variable.It is written by the SME when a measurement 
     report is completed.The HT Short GI for 20 MHZ indicates short GI support
     for the reception of 20 MHz packets, equal to false if not supported, 
     equal to true if supported See 8.4.2.58.2"
    DEFVAL { false } 
    ::= { fsDot11nConfigEntry 1 }

fsDot11nConfigShortGIfor40MHz OBJECT-TYPE
    SYNTAX      TruthValue
    MAX-ACCESS  read-write
    STATUS      current
    DESCRIPTION
    "This is a status variable. It is written by the SME when a measurement
     report is completed. The HT Short GI for 20 MHZ indicates short GI support
     for the reception of 40 MHz packets, equal to false if not supported, 
     equal to true if supported See 8.4.2.58.2"
    DEFVAL { false } 
    ::= { fsDot11nConfigEntry 2 }  

fsDot11nConfigChannelWidth OBJECT-TYPE
    SYNTAX       INTEGER { width20MHz(1), width40MHz(2)}
    MAX-ACCESS  read-write
    STATUS      current
    DESCRIPTION
    "This is a control variable. It is written by the SME.Changes take effect
     as soon as practical in the implementation. This is an 8-bit integer value
     that identifies the Dot11n Config channel width. Currently defined values
     and their corresponding Channel widths are: 10MHz = 01, 20MHz = 02"
    DEFVAL { 1 } 
     ::= { fsDot11nConfigEntry 3 }

-- End of fsDot11nConfigTable Table

-- fsDot11nMCSDataRateTable Table

fsDot11nMCSDataRateTable OBJECT-TYPE
    SYNTAX      SEQUENCE OF FsDot11nMCSDataRateEntry
    MAX-ACCESS  not-accessible
    STATUS      current
    DESCRIPTION
    "This table configures the Data rate for 11n params."
    ::= { fsDot11phy 5 }

fsDot11nMCSDataRateEntry OBJECT-TYPE
    SYNTAX      FsDot11nMCSDataRateEntry
    MAX-ACCESS  not-accessible
    STATUS      current
    DESCRIPTION
    " ."
    INDEX { ifIndex,
            fsDot11nMCSDataRateIndex  }
    ::= { fsDot11nMCSDataRateTable 1 }

FsDot11nMCSDataRateEntry ::=
    SEQUENCE { 
    fsDot11nMCSDataRateIndex Integer32,
    fsDot11nMCSDataRate TruthValue
    } 

fsDot11nMCSDataRateIndex OBJECT-TYPE
    SYNTAX      Integer32 (0..15)
    MAX-ACCESS  not-accessible 
    STATUS      current
    DESCRIPTION
    "Table index."
    ::= { fsDot11nMCSDataRateEntry 1 }

fsDot11nMCSDataRate OBJECT-TYPE
    SYNTAX      TruthValue
    MAX-ACCESS  read-write
    STATUS      current
    DESCRIPTION
    "Represents whether the rate is enabled or disabled."
    DEFVAL { false } 
    ::= { fsDot11nMCSDataRateEntry 2 }

-- End of fsDot11nMCSDataRateTable Table

END

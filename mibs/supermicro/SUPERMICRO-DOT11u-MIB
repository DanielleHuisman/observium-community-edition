--SupermicroDOT11u Proprietary MIB Definition
-- /*****************************************************************
--  *                                                               *
--  * $RCSfile: dot11u.mib,v $                                      *
--  *                                                               *
--  * $Date: 2013/04/06 13:16:44 $                                  *
--  *                                                               *
--  * $Revision: 1.2 $                                              *
--  *                                                               *
--  ****************************************************************/

-- SupermicroDOT11 and DOT11u MIBs.

-- The MIB contains scalars used to configure SupermicroDOT11 functionally.

 SUPERMICRO-DOT11u-MIB DEFINITIONS ::= BEGIN

 IMPORTS
    OBJECT-TYPE, MODULE-IDENTITY, IpAddress,
    Counter32, Integer32,
    enterprises            FROM SNMPv2-SMI
    DisplayString,
    TruthValue, RowStatus, MacAddress  FROM SNMPv2-TC;


    dot11MIB MODULE-IDENTITY
    LAST-UPDATED "201212200000Z"
    ORGANIZATION "Super Micro Computer Inc."
    CONTACT-INFO

         "Super Micro Computer Inc.
          E-mail:support@Supermicro.com"

          DESCRIPTION
        "This proprietary MIB for Supermicro Dot11u is for
         IEEE 802.11u standard entities."
          REVISION "201212200000Z"
    DESCRIPTION " This mib module is for Supermicro Dot11u module"
::= { enterprises supermicro-computer-inc(10876) super-switch(101) basic(2) 78}

   dot11MIBObjects OBJECT IDENTIFIER ::= { dot11MIB 1 }

-- -------------------------------------------------------------
-- groups in the dot11u MIB
-- -------------------------------------------------------------

dot11GASAdvertisement    OBJECT IDENTIFIER ::= { dot11MIBObjects 1 }
dot11StationConfig       OBJECT IDENTIFIER ::= { dot11MIBObjects 2 }

-- -------------------------------------------------------------


dot11StationConfigTable OBJECT-TYPE
        SYNTAX SEQUENCE OF Dot11StationConfigEntry
        MAX-ACCESS not-accessible
        STATUS current
        DESCRIPTION
            "Station Configuration attributes.  In tablular form to
            allow for multiple instances on an agent."
	::= { dot11StationConfig 1 }

dot11StationConfigEntry OBJECT-TYPE
        SYNTAX Dot11StationConfigEntry
        MAX-ACCESS not-accessible
        STATUS current
        DESCRIPTION
            "An entry in the dot11StationConfigTable.  It is
            possible for there to be multiple IEEE 802.11 interfaces
            on one agent, each with its unique MAC address. The
            relationship between an IEEE 802.11 interface and an
            interface in the context of the Internet-standard MIB is
            one-to-one.  As such, the value of an ifIndex object
            instance can be directly used to identify corresponding
            instances of the objects defined herein.

            ifIndex - Each IEEE 802.11 interface is represented by an
            ifEntry.  Interface tables in this MIB module are indexed
            by ifIndex."
        INDEX { ifIndex }
    ::= { dot11StationConfigTable 1 }

Dot11StationConfigEntry ::=
        SEQUENCE {
	ifIndex                 INTEGER,
	dot11InterworkingServiceImplemented                 TruthValue,
	dot11InterworkingServiceActivated                 TruthValue,
	dot11QosmapImplemented                 TruthValue,
	dot11QosMapActivated                 TruthValue,
	dot11EBRImplemented                 TruthValue,
	dot11EBRActivated                 TruthValue,
	dot11ESNetwork                 TruthValue,
	dot11SSPNInterfaceImplemented            TruthValue,
	dot11SSPNInterfaceActivated                 TruthValue,
	dot11HESSID                 MacAddress,
	dot11EASImplemented                 TruthValue,
	dot11EASActivated                 TruthValue,
	dot11MSGCFImplemented                 TruthValue,
	dot11MSGCFActivated                 TruthValue,
	dot11StationID                 MacAddress,
	dot11MediumOccupancyLimit                INTEGER ,
	dot11CFPollable                 TruthValue,
	dot11CFPPeriod                 INTEGER,
	dot11CFPMaxDuration                 INTEGER,
	dot11AuthenticationResponseTimeOut                 Unsigned32,
	dot11PrivacyOptionImplemented                 TruthValue,
	dot11PowerManagementMode                 INTEGER,
	dot11DesiredSSID                 OCTET STRING,
	dot11DesiredBSSType                 INTEGER,
	dot11OperationalRateSet                 OCTET STRING,
	dot11BeaconPeriod                 INTEGER,
	dot11DTIMPeriod                 INTEGER,
	dot11AssociationResponseTimeOut                   Unsigned32,
	dot11DisassociateReason                 INTEGER,
	dot11DisassociateStation                 MacAddress,
	dot11DeauthenticateReason                 INTEGER,
	dot11DeauthenticateStation                 MacAddress,
	dot11AuthenticateFailStatus                 INTEGER,
	dot11AuthenticateFailStation                 MacAddress,
	dot11MultiDomainCapabilityImplemented                 TruthValue,
	dot11MultiDomainCapabilityEnabled                 TruthValue,
	dot11CountryString                 OCTET STRING
}
-- HS Group
-- This group defines objects for DOT11 and DOT11u.

ifIndex OBJECT-TYPE
 SYNTAX INTEGER (0..255)
 MAX-ACCESS not-accessible
 STATUS current
 DESCRIPTION
 "This is a control variable.
 It is written by an external management entity or the SME.
 Changes take effect as soon as practical in the implementation.
 The one octet identification number for the GAS Advertisement
 Protocol, as defined in Table7-43bi, for which statistics are
 stored the logical row of the GASAdvertisement table."
 ::= { dot11StationConfigEntry  1 }

dot11InterworkingServiceImplemented OBJECT-TYPE
	SYNTAX TruthValue
	MAX-ACCESS read-only
	STATUS current
	DESCRIPTION
	"This is a capability variable.
	Its value is determined by device capabilities.
	This attribute when true, indicates the STA is capable of
	interworking with external networks. A STA setting this to
	TRUE implements Interworking Service. When this is false, the
	STA does not implement Interworking Service."
	DEFVAL {true}
	::= { dot11StationConfigEntry  2 }  


dot11InterworkingServiceActivated OBJECT-TYPE
	SYNTAX TruthValue
	MAX-ACCESS read-write
	STATUS current
	DESCRIPTION
	"This is a capability variable.
	Its value is determined by device capabilities.
	This attribute when true, indicates the STA is capable of
	interworking with external networks. A STA setting this to
	TRUE implements Interworking Service. When this is false, the
	STA does not implement Interworking Service."
	DEFVAL {true}
	::= { dot11StationConfigEntry  3 }  


dot11QosmapImplemented OBJECT-TYPE
	SYNTAX TruthValue
	MAX-ACCESS read-only
	STATUS current
	DESCRIPTION
	"This is a capability variable.
	Its value is determined by device capabilities.
	This attribute available at STAs, when true, indicates the
	STA is capable of supporting the QoS Map procedures. When
	this is set to FALSE, the STA does not implement QoS Map
	procedures.."
	DEFVAL {false}
	::= { dot11StationConfigEntry 4 }


dot11QosMapActivated OBJECT-TYPE
	SYNTAX TruthValue
	MAX-ACCESS read-write
	STATUS current
	DESCRIPTION
	".This is a control variable.
	It is written by an external management entity or the SME. Changes take effect as soon as practical in the implementation.
	This attribute, when true, indicates the capability of the
	TA to support QoS Map procedures is enabled. The capability
	s disabled otherwise.."
	DEFVAL {false}
	::= { dot11StationConfigEntry 5 }


dot11EBRImplemented OBJECT-TYPE
	SYNTAX TruthValue
	MAX-ACCESS read-only
	STATUS current
	DESCRIPTION
	"This is a capability variable.
	ts value is determined by device capabilities.
	his attribute available at STAs, when true, indicates the
	TA is capable of supporting Expedited Bandwidth Request
	rocedures. When this is false, the STA does not implement
	xpedited Bandwidth Request procedures.."
	DEFVAL {false}
	::= { dot11StationConfigEntry 6 }


dot11EBRActivated OBJECT-TYPE
	SYNTAX TruthValue
	MAX-ACCESS read-write
	STATUS current
	DESCRIPTION
	"This is a control variable.
	t is written by an external management entity or the SME. Changes take effect as soon as practical in the implementation.
	his attribute, when true, indicates the capability of the
	TA to support Expedited Bandwidth Request procedures is
	nabled. The capability is disabled otherwise.."
	DEFVAL {false}
	::= { dot11StationConfigEntry 7}


dot11ESNetwork OBJECT-TYPE
	SYNTAX TruthValue
	MAX-ACCESS read-write
	STATUS current
	DESCRIPTION
	"This is a control variable.
	t is written by an external management entity or the SME. Changes take effect as soon as practical in the implementation.
	he Emergency Services Access Network Type set to TRUE
	ndicates that the BSS is used exclusively for the purposes of accessing emergency services. This object is not used by non-AP STAs.."
	::= { dot11StationConfigEntry 8 }


dot11SSPNInterfaceImplemented OBJECT-TYPE
	SYNTAX TruthValue
	MAX-ACCESS read-only
	STATUS current
	DESCRIPTION
	".This is a capability variable.
	Its value is determined by device capabilities.
	This attribute when true, indicates the AP is capable of SSPN
	Interface service. When this is false, the STA does not
	implement SSPN Interface Service. This object is not used by
	non-AP STAs. The default value of this attribute is false.."
	DEFVAL {false}
	::= { dot11StationConfigEntry 9 }


dot11SSPNInterfaceActivated OBJECT-TYPE
	SYNTAX TruthValue
	MAX-ACCESS read-write
	STATUS current
	DESCRIPTION
	".This is a control variable.
	It is written by an external management entity or the SME.
	Changes take effect as soon as practical in the implementation.
	This attribute, when true, indicates the capability of the AP
	to provide SSPN Interface service is enabled. The capability is
	disabled, otherwise. The default value of this attribute is
	false.."
	DEFVAL {false}
	::= { dot11StationConfigEntry 10 }


dot11HESSID OBJECT-TYPE
	SYNTAX MacAddress
	MAX-ACCESS read-write
	STATUS current
	DESCRIPTION
	".This is a control variable.
	It is written by an external management entity or the SME. Changes take effect for the next MLME-Start.request
	primitive.
	This attribute is used by an AP and is the 6-octet
	homogeneous ESS identifier field, whose value is set to one of the BSSIDs in the ESS. It is required that the same value
	of HESSID be used for all BSSs in the homogeneous ESS.."
	::= { dot11StationConfigEntry 11 }


dot11EASImplemented OBJECT-TYPE
	SYNTAX TruthValue
	MAX-ACCESS read-only
	STATUS current
	DESCRIPTION
	".This is a capability variable.
	Its value is determined by device capabilities.
	This attribute when true, indicates the STA is capable of
	emergency alert system notification with external networks. A
	STA setting this to TRUE implements emergency alert system
	notification. When this is false, the STA does not implement
	emergency alert system notification.."
	DEFVAL {false}
	::= { dot11StationConfigEntry 12 }


dot11EASActivated OBJECT-TYPE
	SYNTAX TruthValue
	MAX-ACCESS read-write
	STATUS current
	DESCRIPTION
	"This is a control variable.
	It is written by an external management entity or the SME.
	Changes take effect as soon as practical
	This attribute when true, indicates the STA is capable of
	supporting emergency alert system. The capability is disabled
	otherwise.."
	DEFVAL {false}
	::= { dot11StationConfigEntry 13 }


dot11MSGCFImplemented OBJECT-TYPE
	SYNTAX TruthValue
	MAX-ACCESS read-only
	STATUS current
	DESCRIPTION
	"This is a capability variable.
	Its value is determined by device capabilities.
	This attribute when true, indicates the non-AP STA is capable
	of supporting the MSGCF procedures defined in 11B. When false,
	the non-AP STA does not implement MSGCF procedures. This object
	is not used by APs. The default value of this attribute is
	false.."
	DEFVAL {false}
	::= { dot11StationConfigEntry 14 }


dot11MSGCFActivated OBJECT-TYPE
	SYNTAX TruthValue
	MAX-ACCESS read-write
	STATUS current
	DESCRIPTION
	"This is a control variable.
	It is written by an external management entity or the SME.
	Changes take effect as soon as practical in the implementation.
	This attribute, when true, indicates the capability of the non-
	AP STA to provide the MSGCF is enabled. The capability is
	disabled, otherwise. The default value of this attribute is
	false.."
	DEFVAL {false}
	::= { dot11StationConfigEntry 15 }


dot11StationID OBJECT-TYPE
       SYNTAX MacAddress
       MAX-ACCESS read-write
       STATUS deprecated
       DESCRIPTION
           "The purpose of dot11StationID is to allow a manager to identify
           a station for its own purposes.  This attribute provides
           for that eventuality while keeping the true MAC address
           independent.  Its syntax is MAC address and default value
           is the station's assigned, unique MAC address."

	::= { dot11StationConfigEntry 16 }

dot11MediumOccupancyLimit OBJECT-TYPE
       SYNTAX INTEGER(0..1000)
       MAX-ACCESS read-write
       STATUS current
       DESCRIPTION
           "This attribute shall indicate the maximum amount of time,
           in TU, that a point coordinator may control the usage of
           the wireless medium without relinquishing control for long
           enough to allow at least one instance of DCF access to the
           medium.  The default value of this attribute shall be 100,
           and the maximum value shall be 1000."

	::= { dot11StationConfigEntry 17 }

dot11CFPollable OBJECT-TYPE
       SYNTAX TruthValue
       MAX-ACCESS read-only
       STATUS current
       DESCRIPTION

       "When this attribute is true, it shall indicate that the STA
       is able to respond to a CF-Poll with a data frame within a
       SIFS time. This attribute shall be false if the STA is not
       able to respond to a CF-Poll with a data frame within a SIFS
       time."

	::= { dot11StationConfigEntry 18  }

dot11CFPPeriod OBJECT-TYPE
       SYNTAX INTEGER (0..255)
       MAX-ACCESS read-write
       STATUS current
       DESCRIPTION

           "The attribute shall describe the number of DTIM intervals
           between the start of CFPs.  It is modified by
           MLME-START.request primitive."

	::= {  dot11StationConfigEntry 19 }

dot11CFPMaxDuration OBJECT-TYPE
       SYNTAX INTEGER (0..65535)
       MAX-ACCESS read-write
       STATUS current
       DESCRIPTION

       "The attribute shall describe the maximum duration of the CFP
       in TU that may be generated by the PCF. It is modified by
       MLME-START.request primitive."

	::= { dot11StationConfigEntry 20 }

dot11AuthenticationResponseTimeOut OBJECT-TYPE
--        SYNTAX INTEGER (1..4294967295)
       SYNTAX Unsigned32 (1..4294967295)
       MAX-ACCESS read-write
       STATUS current
       DESCRIPTION

           "This attribute shall specify the number of TU that a
           responding STA should wait for the next frame in the
           authentication sequence."

	::= {  dot11StationConfigEntry 21 }

dot11PrivacyOptionImplemented OBJECT-TYPE
       SYNTAX TruthValue
       MAX-ACCESS read-only
       STATUS current
       DESCRIPTION

           "This attribute, when true, shall indicate that the IEEE
            802.11 WEP option is implemented.  The default value of
            this attribute shall be false."

	::= {  dot11StationConfigEntry 22 }

dot11PowerManagementMode OBJECT-TYPE
       SYNTAX INTEGER { active(1), powersave(2) }
       MAX-ACCESS read-write
       STATUS current
       DESCRIPTION
            "This attribute shall specify the power management
             mode of the STA. When set to active, it shall indicate
             that the station is not in power-save mode. When set
             to powersave, it shall indicate that the station is
             in power-save mode. The power management mode is
             transmitted in all frames according to the rules
             in  7.1.3.1.7."
	::= { dot11StationConfigEntry 23 }

dot11DesiredSSID OBJECT-TYPE
       SYNTAX OCTET STRING (SIZE(0..32))
       MAX-ACCESS read-write
       STATUS current
       DESCRIPTION
             "This attribute reflects the Service Set ID used
              in the DesiredSSID parameter of the most recent
              MLME_Scan.request.  This value may be modified
              by an external management entity and used by the
              local SME to make decisions about the Scanning process."
	::= { dot11StationConfigEntry 24 }

dot11DesiredBSSType OBJECT-TYPE
        SYNTAX INTEGER { infrastructure(1), independent(2), any(3) }
        MAX-ACCESS read-write
        STATUS current
        DESCRIPTION
              "This attribute shall specify the type of BSS the
               station shall use when scanning for a BSS with which
               to synchronize. This value is used to filter Probe
               Response frames and Beacons. When set to infrastructure,
               the station shall only synchronize with a BSS whose
               Capability Information field has the ESS subfield set
               to 1. When set to independent, the station shall only
               synchronize with a BSS whose Capability Information
               field has the IBSS subfield set to 1. When set to
               any, the station may synchronize to either type of  BSS."	
	::= { dot11StationConfigEntry 25 }

dot11OperationalRateSet OBJECT-TYPE
        SYNTAX OCTET STRING (SIZE(1..126))
        MAX-ACCESS read-write
        STATUS current
        DESCRIPTION
               "This attribute shall specify the set of data rates
                at which the station may transmit data.  Each octet
		contains a value representing a rate.  Each rate
                shall be within the range from 2 to 127,
                corresponding to data rates in increments of
                500 kb/s from 1 Mb/s to 63.5 Mb/s, and shall be
                supported (as indicated in the supported rates
                table) for receiving data. This value is reported in
                transmitted Beacon, Probe Request, Probe Response,
                Association Request, Association Response,
                Reassociation Request, and Reassociation Response
                frames, and is used to determine whether a BSS
                with which the station desires to synchronize is
                suitable. It is also used when starting a BSS,
                as specified in  10.3."
	::= { dot11StationConfigEntry 26 }

dot11BeaconPeriod OBJECT-TYPE
        SYNTAX INTEGER (1..65535)
        MAX-ACCESS read-write
        STATUS current
        DESCRIPTION
                "This attribute shall specify the number of TU that a
                station shall use for scheduling Beacon transmissions.
                This value is transmitted in Beacon and Probe Response
                frames."
	::= { dot11StationConfigEntry 27 }

dot11DTIMPeriod OBJECT-TYPE
        SYNTAX INTEGER(1..255)
        MAX-ACCESS read-write
        STATUS current
        DESCRIPTION
                "This attribute shall specify the number of beacon
                intervals that shall elapse between transmission of
                Beacons frames containing a TIM element whose DTIM
                Count field is 0. This value is transmitted in
                the DTIM Period field of Beacon frames."
	::= { dot11StationConfigEntry 28 }

dot11AssociationResponseTimeOut OBJECT-TYPE
--      SYNTAX INTEGER(1..4294967295)
        SYNTAX Unsigned32(1..4294967295)
        MAX-ACCESS read-write
        STATUS current
        DESCRIPTION
                "This attribute shall specify the number of TU that a
                requesting STA should wait for a response to a
                transmitted association-request MMPDU."
	::= { dot11StationConfigEntry 29 }

dot11DisassociateReason OBJECT-TYPE
        SYNTAX INTEGER(0..65535)
        MAX-ACCESS read-only
        STATUS current
        DESCRIPTION
                "This attribute holds the most recently transmitted Reason
                Code in a Disassociation frame.  If no Disassociation frame
                has been transmitted, the value of this attribute shall be 0."
-- REFERENCE "IEEE Std 802.11-1997, 7.3.1.7"
	::= { dot11StationConfigEntry 30 }

dot11DisassociateStation OBJECT-TYPE
        SYNTAX MacAddress
        MAX-ACCESS read-only
        STATUS current
        DESCRIPTION
                "This attribute holds the MAC address from the Address 1 field
                of the most recently transmitted Disassociation frame.  If no
                Disassociation frame has been transmitted, the value of this
                attribute shall be 0."
	::= { dot11StationConfigEntry 31 }

dot11DeauthenticateReason OBJECT-TYPE
        SYNTAX INTEGER(0..65535)
        MAX-ACCESS read-only
        STATUS current
        DESCRIPTION
                "This attribute holds the most recently transmitted Reason
                Code in a Deauthentication frame.  If no Deauthentication
                frame has been transmitted, the value of this attribute shall be 0."
-- REFERENCE "IEEE Std 802.11-1997, 7.3.1.7"
	::= { dot11StationConfigEntry 32 }

dot11DeauthenticateStation OBJECT-TYPE
        SYNTAX MacAddress
        MAX-ACCESS read-only
        STATUS current
        DESCRIPTION
                "This attribute holds the MAC address from the Address 1 field
                of the most recently transmitted Deauthentication frame.  If no
                Deauthentication frame has been transmitted, the value of this
                attribute shall be 0."
	::= { dot11StationConfigEntry 33 }

dot11AuthenticateFailStatus OBJECT-TYPE
        SYNTAX INTEGER(0..65535)
        MAX-ACCESS read-only
        STATUS current
        DESCRIPTION
                "This attribute holds the most recently transmitted Status
                Code in a failed Authentication frame.  If no failed
                Athentication frame has been transmitted, the value of this
                attribute shall be 0."
-- REFERENCE "IEEE Std 802.11-1997, 7.3.1.9"
	::= { dot11StationConfigEntry 34 }

dot11AuthenticateFailStation OBJECT-TYPE
        SYNTAX MacAddress
        MAX-ACCESS read-only
        STATUS current
        DESCRIPTION
                "This attribute holds the MAC address from the Address 1 field
                of the most recently transmitted failed Authentication frame.
                If no failed Authentication frame has been transmitted, the
                value of this attribute shall be 0."
	::= { dot11StationConfigEntry 35 }

dot11MultiDomainCapabilityImplemented OBJECT-TYPE
        SYNTAX TruthValue
        MAX-ACCESS read-only
        STATUS current
        DESCRIPTION
                "This attribute, when TRUE, indicates that the station implementation is capable of supporting multiple re                 gulatory domains. The capability is
                 disabled, otherwise. The default value of this attribute is FALSE."
	::= { dot11StationConfigEntry 36 }

dot11MultiDomainCapabilityEnabled OBJECT-TYPE
        SYNTAX TruthValue
        MAX-ACCESS read-write
        STATUS current
        DESCRIPTION
                "This attribute, when TRUE, indicates that the capability of the station to
                operate in multiple regulatory domains is enabled. The capability is
                disabled, otherwise. The default value of this attribute is FALSE."
	::= { dot11StationConfigEntry 37 }

dot11CountryString OBJECT-TYPE
        SYNTAX OCTET STRING (SIZE(3))
        MAX-ACCESS read-only
        STATUS current
        DESCRIPTION
               "This attribute identifies the country in which the station is operating.
               The first two octets if this string is the two character country code as
               described in document ISO/IEC 3166-1. The third octet shall be one of the
               following:
                   1. an ASCII space character, if the regulations under which the
                   station is operating encompass all environments in the country,
                   2. an ASCII Ocharacter, if the regulations under which the
                   station is operating are for an Outdoor environment only, or
                   3. an ASCII Icharacter, if the regulations under which the
                   station is operating are for an Indoor environment only."
	::= { dot11StationConfigEntry 38 }

-- -------------------------------------------------------------
-- the dot11GASAdvertisementTable group
-- -------------------------------------------------------------

dot11GASAdvertisementTable OBJECT-TYPE
        SYNTAX SEQUENCE OF Dot11GASAdvertisementEntry
        MAX-ACCESS not-accessible
        STATUS current
        DESCRIPTION
            "This object is a table of GAS counters that allows for
	            multiple instantiations of those counters on an STA."
	::= { dot11GASAdvertisement 1 }

dot11GASAdvertisementEntry OBJECT-TYPE
        SYNTAX Dot11GASAdvertisementEntry
        MAX-ACCESS not-accessible
        STATUS current
        DESCRIPTION
            "This object provides the attributes identifying a GAS counter within an STA."
        INDEX { dot11GASAdvertisementId }
    ::= { dot11GASAdvertisementTable 1 }

Dot11GASAdvertisementEntry ::=
        SEQUENCE {
	dot11GASAdvertisementId                 INTEGER,
	dot11GASPauseForServerResponse                 TruthValue,
	dot11GASResponseTimeout                 INTEGER,
	dot11GASComebackDelay                 INTEGER,
	dot11GASResponseBufferingTime                 INTEGER,
	dot11GASQueryResponseLengthLimit                 INTEGER,
	dot11GASQueries            Counter32,
	dot11GASQueryRate                 Unsigned32,
	dot11GASResponses                 Counter32,
	dot11GASResponseRate                 Unsigned32,
	dot11GASTransmittedFragmentCount                 Counter32,
	dot11GASReceivedFragmentCount                 Counter32,
	dot11GASNoRequestOutstanding                 Counter32,
	dot11GASResponsesDiscarded                 Counter32,
	dot11GASFailedResponses                Counter32 
}

-- HS Group
-- This group defines objects for DOT11 and DOT11u.


dot11GASAdvertisementId OBJECT-TYPE
	SYNTAX INTEGER (0..255)
	MAX-ACCESS not-accessible
	STATUS current
	DESCRIPTION
	"This is a control variable.
	It is written by an external management entity or the SME.
	Changes take effect as soon as practical in the implementation.
	The one octet identification number for the GAS Advertisement
	Protocol, as defined in Table7-43bi, for which statistics are
	stored the logical row of the GASAdvertisement table."
	::= { dot11GASAdvertisementEntry  1 }  


dot11GASPauseForServerResponse OBJECT-TYPE
	SYNTAX TruthValue
	MAX-ACCESS read-write
	STATUS current
	DESCRIPTION
	"This is a control variable.
	It is written by an external management entity or the SME.
	Changes take effect as soon as practical in the implementation.
	This attribute is only used by the responding STA in a GAS
	exchange. When true, it indicates that the responding STA will
	not transmit a GAS Initial Response frame until it receives the
	query response from the Advertisement Server or a timeout
	occurs. When false, the STA will not wait for a response from
	the Advertisement Server before transmiting the GAS Initial
	Response frame." 
	DEFVAL {false}
	::= { dot11GASAdvertisementEntry  2 }  


dot11GASResponseTimeout OBJECT-TYPE
	SYNTAX INTEGER (1000..65535)
	MAX-ACCESS read-write
	STATUS current
	DESCRIPTION
	"This is a control variable.
	It is written by an external management entity or the SME.
 Changes take effect as soon as practical in the implementation.
	This parameter shall indicate the GAS response timeout value in
	TUs."
	DEFVAL {5000}
	::= { dot11GASAdvertisementEntry  3 }  


dot11GASComebackDelay OBJECT-TYPE
	SYNTAX INTEGER (0..65535)
	MAX-ACCESS read-write
	STATUS current
	DESCRIPTION
	"This is a control variable.
	It is written by an external management entity or the SME.
	Changes take effect as soon as practical in the implementation.
	This object identifies the GAS Comeback Delay (in TUs) to be
	used for this Advertisement Protocol"
	DEFVAL {1000}
	::= { dot11GASAdvertisementEntry  4 }  


dot11GASResponseBufferingTime OBJECT-TYPE
	SYNTAX INTEGER (0..65535)
	MAX-ACCESS read-write
	STATUS current
	DESCRIPTION
	"This is a control variable.
	It is written by an external management entity or the SME.
	Changes take effect as soon as practical in the implementation.
	This object defines the time duration after the expiry of the
	GAS Comeback Delay that an STA will buffer a Query Response.
	The units of this MIB object are TUs. Upon expiry of this time,
	the STA may discard the Query Response."
	DEFVAL {1000}
	::= { dot11GASAdvertisementEntry  5 }  


dot11GASQueryResponseLengthLimit OBJECT-TYPE
 SYNTAX INTEGER (1..127)
 MAX-ACCESS read-write
 STATUS current
 DESCRIPTION
 "This is a control variable.
 It is written by an external management entity or the SME.
 Changes take effect as soon as practical in the implementation.
 This object indicates the maximum number of octets an AP will
 transmit in one or more Query Response fields contained within
 GAS Comeback Response frame(s). A value of 127 means the
 maximum limit enforced is contained by the maximum allowable
 number of fragments in the GAS Query Fragment Response ID"
 ::= { dot11GASAdvertisementEntry 6 }


dot11GASQueries OBJECT-TYPE
 SYNTAX Counter32
 MAX-ACCESS read-only
 STATUS current
 DESCRIPTION
 "This is a status variable.
 It is written by the SME after transmission of a MLME-
 GAS.request or MLME-PDGAS.request or receipt of an MLME-
 GAS.indication or MLME-PDGAS.indication primitive.
 The number of GAS queries sent or received for the protocol
 identified by dot11GASAdvertisementId."
 ::= { dot11GASAdvertisementEntry 7 }


dot11GASQueryRate OBJECT-TYPE
 SYNTAX Unsigned32
 MAX-ACCESS read-only
 STATUS current
 DESCRIPTION
 "This is a status variable.
 It is updated by the SME after receipt of an MLME-
 GAS.indication or MLME-PDGAS.indication primitive.
 The number of GAS queries per minute received for the protocol
 identified by dot11GASAdvertisementId, averaged over the
 previous ten minutes."
::= { dot11GASAdvertisementEntry 8 }


dot11GASResponses OBJECT-TYPE
 SYNTAX Counter32
 MAX-ACCESS read-only
 STATUS current
 DESCRIPTION
 "This is a status variable.
 It is written by the SME after transmission of a MLME-
 GAS.response or MLME-PDGAS.response or receipt of an MLME-
 GAS.confirm or MLME-PDGAS.confirm primitive.
 The number of GAS responses sent or received for the protocol
 identified by dot11GASAdvertisementId."
 ::= { dot11GASAdvertisementEntry 9 }


dot11GASResponseRate OBJECT-TYPE
 SYNTAX Unsigned32
 MAX-ACCESS read-only
 STATUS current
 DESCRIPTION
 "This is a status variable.
 It is updated by the SME after transmission of an MLME-
 GAS.response or MLME-PDGAS.response primitive.
 The number of responses to GAS queries per minute transmitted
 by an AP for the protocol identified by dot11GASAdvertisementId,
	averaged over the previous ten
	minutes. This MIB variable is not used in non-AP STAs."
	::= { dot11GASAdvertisementEntry 10 }


dot11GASTransmittedFragmentCount OBJECT-TYPE
 SYNTAX Counter32
 MAX-ACCESS read-only
 STATUS current
 DESCRIPTION
 "This is a status variable.
 It is updated by the SME after transmission of an MLME-
 GAS.response or MLME-PDGAS.response primitive.
 This counter shall be incremented for an acknowledged GAS MMPDU
 for the protocol identified by dot11GASAdvertisementId."
 ::= { dot11GASAdvertisementEntry 11 }


dot11GASReceivedFragmentCount OBJECT-TYPE
 SYNTAX Counter32
 MAX-ACCESS read-only
 STATUS current
 DESCRIPTION
 "This is a status variable.
 It is updated by the MAC after transmission of an MLME-
 GAS.confirm or MLME-PDGAS.confirm primitive.
 This counter shall be incremented for each successfully
 received MMPDU of type Data"
 ::= { dot11GASAdvertisementEntry 12 }


dot11GASNoRequestOutstanding OBJECT-TYPE
 SYNTAX Counter32
 MAX-ACCESS read-only
 STATUS current
 DESCRIPTION
 "This is a status variable.
 It is updated by the SME after transmission of an MLME-GAS.response
 or MLME-PDGAS.response primitive.
 This counter shall be incremented each time a STA returns a status
 code of no request outstanding in a GAS Initial Response or GAS
 Comeback Response frame for the protocol identified by
 dot11GASAdvertisementId."
 ::= { dot11GASAdvertisementEntry 13 }


dot11GASResponsesDiscarded OBJECT-TYPE
 SYNTAX Counter32
 MAX-ACCESS read-only
 STATUS current
 DESCRIPTION
 "This is a status variable.
 It is updated by the SME after transmission of an MLME-GAS.response
 or MLME-PDGAS.response primitive.
 This counter shall be incremented each a STA discards a GAS
 response due to the expiry of the dot11GASResponseBufferingTime
 timer for the protocol identified by dot11GASAdvertisementId."
 ::= { dot11GASAdvertisementEntry 14 }


dot11GASFailedResponses OBJECT-TYPE
 SYNTAX Counter32
 MAX-ACCESS read-only
 STATUS current
 DESCRIPTION
 "This is a status variable.
 It is updated by the SME after transmission of an MLME-GAS.response
 or MLME-PDGAS.response primitive.
 This counter shall be incremented each time a STA commences
	transmitting a GAS response but fails to successfully complete the
 transmission of all GAS fragments in that response due to the expiry of the dot11GASResponseTimeout timer for the protocol
 identified by dot11GASAdvertisementId."
 ::= { dot11GASAdvertisementEntry 15 }


   END

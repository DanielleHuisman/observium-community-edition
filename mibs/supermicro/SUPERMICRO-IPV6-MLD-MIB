-- Copyright (C) 2008-2014 Super Micro Computer Inc. All Rights Reserved

-- $Id: fsmld.mib,v 1.7 2012/09/07 09:52:05 siva Exp $

SUPERMICRO-IPV6-MLD-MIB DEFINITIONS ::= BEGIN

   IMPORTS
       MODULE-IDENTITY, OBJECT-TYPE,enterprises, 
       Unsigned32 FROM SNMPv2-SMI;

   futuremld MODULE-IDENTITY
       LAST-UPDATED "201209050000Z" 
       ORGANIZATION "Super Micro Computer Inc."
       CONTACT-INFO "support@Supermicro.com"
       DESCRIPTION
               "The MIB module for MLD Management."
       REVISION "201209050000Z"
       DESCRIPTION
               "The MIB module for MLD Management."
       ::={ enterprises supermicro-computer-inc(10876) super-switch(101) basic(1) 70 }

fsmldScalars OBJECT IDENTIFIER ::= { futuremld 1 }

        fsmldNoOfCacheEntries OBJECT-TYPE
             SYNTAX  Unsigned32 
             MAX-ACCESS  read-write
             STATUS  deprecated
             DESCRIPTION
                "Maximun number of multicast address per interface."
             ::= { fsmldScalars 1 }

        fsmldNoOfRoutingProtocols OBJECT-TYPE
             SYNTAX  Unsigned32 
             MAX-ACCESS  read-write
             STATUS  deprecated
             DESCRIPTION
                "Maximum number of Routing Protocols that can register
                 with MLD."
             ::= { fsmldScalars 2 }


        fsmldTraceDebug OBJECT-TYPE
             SYNTAX  Unsigned32 
             MAX-ACCESS  read-write
             STATUS  current
             DESCRIPTION
                "This is used to enable Trace Statements in MLD Module"
             ::= { fsmldScalars 3 }

        fsmldMode OBJECT-TYPE
             SYNTAX  INTEGER{
                    mldrouter(1),
                    mldhost(2),
                    mldrouterhost (3)
                    }
             MAX-ACCESS  read-write
             STATUS  current
             DESCRIPTION
                "This is used to enable Router or Host mode for MLD"
             DEFVAL { mldrouter }
             ::= { fsmldScalars 4 }

        fsmldProtocolUpDown OBJECT-TYPE
             SYNTAX  INTEGER{
                    mldinit(1),
                    mldshutdown(2)
                    }
             MAX-ACCESS  read-write
             STATUS  current
             DESCRIPTION
                "This is used to bring the MLD Protocol up/down during
                 runtime."
             ::= { fsmldScalars 5 }

   END

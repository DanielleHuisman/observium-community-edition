-- Copyright (C) 2008-2014 Super Micro Computer Inc. All Rights Reserved

-- $Id: fsmvlext.mib,v 1.11 2012/09/07 09:52:05 siva Exp $

SUPERMICRO-MIVLAN-EXT-MIB DEFINITIONS ::= BEGIN 
 
IMPORTS 
 
    OBJECT-TYPE,MODULE-IDENTITY, Integer32,
    enterprises,Counter32 FROM SNMPv2-SMI 
    TEXTUAL-CONVENTION,MacAddress FROM SNMPv2-TC
    EnabledStatus  FROM SUPERMICROP-BRIDGE-MIB;


 
futureMIVlanExtMIB MODULE-IDENTITY 
    LAST-UPDATED "201209050000Z" 
    ORGANIZATION "Super Micro Computer Inc." 
    CONTACT-INFO "support@Supermicro.com" 
    DESCRIPTION "||||||" 
    REVISION "201209050000Z"
    DESCRIPTION "||||||" 
::= { enterprises supermicro-computer-inc(10876) super-switch(101) basic(1) 138}

TunnelStatus ::= TEXTUAL-CONVENTION
    STATUS      current
    DESCRIPTION
        "To specify how to handle the L2 protocol packets received on a
         particular port.
         
         When the option is set to 'peer', the L2 protocol packets received
         on a particular port will be processed in the Bridge.
         
         When the option is set to 'tunnel', the L2 protocol packets received
         on a particular port will be transparently transmitted in the provider
         network and will not be processed in Bridges.
         
         When the option is set to 'discard', the L2 protocol packets
         received over a particular port will not be processed and discarded."

    SYNTAX      INTEGER { peer(1), tunnel(2), discard(3) }

--fsMIVlanTunnelObjects - This sub group contains mib objects for 
-- configuring Tunneling feature in VLAN.

fsMIVlanSystemConfig OBJECT IDENTIFIER  ::= { futureMIVlanExtMIB 1 }
fsMIVlanTunnelObjects OBJECT IDENTIFIER  ::= { futureMIVlanExtMIB 2 }
fsMIVlanDiscardObjects OBJECT IDENTIFIER  ::= { futureMIVlanExtMIB 3 }

-- ---------------------------------------------------------------------------- 
-- Future Vlan Bridge Info Table 
-- ----------------------------------------------------------------------------

fsMIVlanBridgeInfoTable OBJECT-TYPE
   SYNTAX        SEQUENCE OF FsMIVlanBridgeInfoEntry
   MAX-ACCESS    not-accessible
   STATUS        current
   DESCRIPTION
      "List of Tunneling related objects that can be configured
      per Virtual Context in the system."
   ::= { fsMIVlanSystemConfig 1 }

fsMIVlanBridgeInfoEntry OBJECT-TYPE
   SYNTAX        FsMIVlanBridgeInfoEntry
   MAX-ACCESS    not-accessible
   STATUS        current
   DESCRIPTION
      "Virtual Context based Provider Bridge objects."
   INDEX { fsMIVlanContextId }
   ::= { fsMIVlanBridgeInfoTable 1 }

FsMIVlanBridgeInfoEntry ::=
    SEQUENCE {
        fsMIVlanContextId
           Integer32,
        fsMIVlanBridgeMode  
           INTEGER
}

fsMIVlanContextId OBJECT-TYPE
   SYNTAX       Integer32 (0..65535)
   MAX-ACCESS   not-accessible
   STATUS       current
   DESCRIPTION
      "Identifies a Virtual Context."
   ::= { fsMIVlanBridgeInfoEntry 1 }
 

fsMIVlanBridgeMode OBJECT-TYPE
   SYNTAX      INTEGER {
                  customerBridge (1),
                  providerBridge (2),
                  providerEdgeBridge (3),
                  providerCoreBridge (4),
                  providerBackoneICompBridge (5),
                  providerBackoneBCompBridge (6),
                  invalidBridgeMode  (7)
               }
   MAX-ACCESS  read-write
   STATUS      current
   DESCRIPTION
      
      "This object indicates the Bridge mode of the switch.
      
      Setting this to 'customerBridge' means that the switch will operate 
      as a 802.1Q VLAN Bridge.

      Setting this to 'providerBridge' means that the Bridge will operate as 
      a normal Q-in-Q Bridge.

      Setting this to 'providerCoreBridge' means that the switch will operate 
      as a 802.1ad compliant provider bridge with only S-VLAN component.

      Setting this to 'providerEdgeBridge' means that the switch will operate 
      as a 802.1ad provider edge bridge with S-VLAN component and atleast 
      one C-VLAN component.
   
      Setting this to 'providerBackoneICompBridge' means that the switch will operate 
      as a 802.1ah provider backone bridge as an I component.

      Setting this to 'providerBackoneBCompBridge' means that the switch will operate 
      as a 802.1ah provider backone bridge as a B component.
 
      Setting this to 'invalidBridgeMode` is not allowed. 
	  Whenever a context is created by default it will be set to `customerBridge`.
      
      For changing the bridge mode, GARP and STP modules should be shutdown."

   DEFVAL  { customerBridge } 
   ::= { fsMIVlanBridgeInfoEntry 2 }

-- ----------------------------------------------------------------------------
-- Future Vlan Tunnel Context Info Table 
-- ----------------------------------------------------------------------------
fsMIVlanTunnelContextInfoTable OBJECT-TYPE
   SYNTAX        SEQUENCE OF FsMIVlanTunnelContextInfoEntry
   MAX-ACCESS    not-accessible
   STATUS        current
   DESCRIPTION
      "List of Tunneling related objects that can be configured
      per Virtual Context in the system."
   ::= { fsMIVlanTunnelObjects 1 }

fsMIVlanTunnelContextInfoEntry OBJECT-TYPE
   SYNTAX        FsMIVlanTunnelContextInfoEntry
   MAX-ACCESS    not-accessible
   STATUS        current
   DESCRIPTION
      "Virtual Context based Provider Bridge objects."
   INDEX { fsMIVlanContextId }
   ::= { fsMIVlanTunnelContextInfoTable 1 }

FsMIVlanTunnelContextInfoEntry ::=
    SEQUENCE {
        fsMIVlanTunnelBpduPri  
           Integer32,
        fsMIVlanTunnelStpAddress
           MacAddress,
        fsMIVlanTunnelLacpAddress
           MacAddress,
        fsMIVlanTunnelDot1xAddress
           MacAddress,
        fsMIVlanTunnelGvrpAddress
           MacAddress,
        fsMIVlanTunnelGmrpAddress
           MacAddress,
        fsMIVlanTunnelMvrpAddress
           MacAddress,
        fsMIVlanTunnelMmrpAddress
           MacAddress,
        fsMIVlanTunnelElmiAddress
           MacAddress,
        fsMIVlanTunnelLldpAddress
           MacAddress
}

fsMIVlanTunnelBpduPri OBJECT-TYPE
    SYNTAX      Integer32 (0..7)
    MAX-ACCESS  read-write
    STATUS      current
    DESCRIPTION
        "Specifies the default User Priority for all the tunneled Layer 2
        BPDU's received on tunnel ports per virtual context."

    DEFVAL { 7 }
    ::= { fsMIVlanTunnelContextInfoEntry 1 }

fsMIVlanTunnelStpAddress OBJECT-TYPE
    SYNTAX      MacAddress
    MAX-ACCESS  read-write
    STATUS      current
    DESCRIPTION
        " The MAC address to be used for Customer STP BPDUs tunneling.

        When STP tunneling is enabled on a port, this MAC address will be
        used as the the destination MAC address of the customer BPDUs received.
        This is the default behaviour in Provider (Q-in-Q) Bridges and customer 
        network. In case of 802.1ad bridges, this will be done only when the 
        outgoing port type is proprietary PNP.
        
        Inside a given Network,BPDUs received with this MAC address will be 
        treated as data packets and not processed. This is the default
        behaviour in case of Provider (Q-in-Q) and customer Bridges.In case 
        of 802.1ad Bridges, when the outgoing port type is not proprietary
        PNP, the destination address will be replaced with the reserved address 
        defined for customer STP BPDU.Otherwise, they will be treated as 
        data packets.
        
        When the BPDU is sent out of the given Network, this MAC address
        will be replaced with the reserved address defined for Customer STP
        BPDU. This is done only when when STP protocol tunnel status is set to 
        Tunnel on the outgoing port.Dropped otherwise."

        ::= { fsMIVlanTunnelContextInfoEntry 2 }

fsMIVlanTunnelLacpAddress OBJECT-TYPE
    SYNTAX      MacAddress 
    MAX-ACCESS  read-write
    STATUS      current
    DESCRIPTION
        "The MAC address to be used for LACP packets tunneling . When
        LACP tunneling is enabled on a port, this MAC address will be
        used as the the destination MAC address of the customer LACP packets
        received over this port.
        
        Inside a given Network, LACP packets received with this MAC address 
        will be treated as data packets and not processed.
        
        When the tunneled LACP packets are sent out of the given Network, 
        this MAC address will be replaced with the reserved address defined 
        for LACP packets. This is done only when LACP protocol tunnel status 
        is set to Tunnel on the outgoing port.Dropped otherwise."

        ::= { fsMIVlanTunnelContextInfoEntry 3 }

fsMIVlanTunnelDot1xAddress OBJECT-TYPE
    SYNTAX      MacAddress 
    MAX-ACCESS  read-write
    STATUS      current
    DESCRIPTION

        "The MAC address to be used for Dot1x packets tunneling . When
        Dot1x tunneling is enabled on a port, this MAC address will 
        be used as the the destination MAC address for the customer Dot1x 
        packets received with reserved address over this port. 
        
        Inside a given Network, Dot1x packets received with this MAC address 
        will be treated as data packets and not processed.
        
        When the tunneled Dot1x packets are sent out of the given Network, 
        this MAC address will be replaced with the reserved address defined 
        for Dot1x packets. This is done only when Dot1x protocol tunnel
        status is set to Tunnel on the outgoing port.Dropped otherwise."
        
    ::= { fsMIVlanTunnelContextInfoEntry 4 }

fsMIVlanTunnelGvrpAddress OBJECT-TYPE
    SYNTAX      MacAddress 
    MAX-ACCESS  read-write
    STATUS      current
    DESCRIPTION
         " The MAC address to be used for Customer GVRP PDUs tunneling.
        When GVRP tunneling is enabled on a port, this MAC address will be
        used as the the destination MAC address of the customer GVRP PDUs
        received. This is the default behaviour in Provider (Q-in-Q) Bridges
        and customer bridges. In case of 802.1ad bridges, this will be done 
        only when the outgoing port type is proprietary PNP.
        
        Inside a given Network,packets received with this MAC address will be 
        treated as data packets and not processed. This is the default
        behaviour in case of Provider (Q-in-Q) Bridges and customer bridges. 
        In case of 802.1ad Bridges, when the outgoing port type is not 
        proprietary PNP, the destination address will be replaced with the
        reserved address defined for customer GVRP PDUs.Otherwise, they will
        be treated as data packets.
        
        When the GVRP PDU is sent out of the given Network, this MAC address
        will be replaced with the reserved address defined for Customer GVRP
        PDU. This is done only when when GVRP protocol tunnel status is set to 
        Tunnel on the outgoing port.Dropped otherwise."
       
    ::= { fsMIVlanTunnelContextInfoEntry 5 }

fsMIVlanTunnelGmrpAddress OBJECT-TYPE
    SYNTAX      MacAddress 
    MAX-ACCESS  read-write
    STATUS      current
    DESCRIPTION
         "The MAC address to be used for GMRP PDUs tunneling. When GMRP
         tunneling is enabled on a port, this MAC address will be 
        used as the the destination MAC address of the customer GMRP PDUs 
        received over this port. 
        
        Inside a given Network, GMRP PDUs received with this MAC address 
        will be treated as data packets and not processed.
        
        When the tunneled GMRP PDUs are sent out of the given Network, 
        this MAC address will be replaced with the reserved address defined 
        for GMRP PDUs.This is done only when GMRP protocol tunnel status is 
        set to Tunnel on the outgoing port.Dropped otherwise."
       
    ::= { fsMIVlanTunnelContextInfoEntry 6 }

fsMIVlanTunnelMvrpAddress OBJECT-TYPE
    SYNTAX      MacAddress
    MAX-ACCESS  read-write
    STATUS      current
    DESCRIPTION
      " The MAC address to be used for MVRP PDUs tunneling.
        When MVRP tunneling is enabled on a port, this MAC address will be
        used as the the destination MAC address of the received MVRP PDUs.

        Inside a given Network, packets received with this MAC address will be 
        treated as data packets and not processed. This is the default
        behaviour in case of Provider (Q-in-Q) Bridges and customer bridges. 
        In case of 802.1ad Bridges, when the outgoing port type is not 
        proprietary PNP, the destination address will be replaced with the
        reserved address defined for customer MVRP PDUs.Otherwise, they 
        will be treated as data packets.

        When the MVRP PDU is sent out of the given Network, this MAC address
        will be replaced with the reserved address defined for Customer MVRP
        PDU. This is done only when when MVRP protocol tunnel status is set to
        Tunnel on the outgoing port. Dropped otherwise."

    ::= { fsMIVlanTunnelContextInfoEntry 7 }

fsMIVlanTunnelMmrpAddress OBJECT-TYPE
    SYNTAX      MacAddress
    MAX-ACCESS  read-write
    STATUS      current
    DESCRIPTION
      " The MAC address to be used for MMRP PDUs tunneling.
        When MMRP tunneling is enabled on a port, this MAC address will be
        used as the the destination MAC address of the MMRP PDUs received 
        over this port.

        Inside a given Network, MMRP PDUs received with this MAC address
        will be treated as data packets and not processed.

        When the tunneled MMRP PDUs are sent out of the given Network,
        this MAC address will be replaced with the reserved address defined
        for MMRP PDUs.This is done only when MMRP protocol tunnel status is
        set to Tunnel on the outgoing port.Dropped otherwise."

    ::= { fsMIVlanTunnelContextInfoEntry 8 }

fsMIVlanTunnelElmiAddress OBJECT-TYPE
    SYNTAX      MacAddress
    MAX-ACCESS  read-write
    STATUS      current
    DESCRIPTION
        "The MAC address to be used for ELMI packets tunneling . When
        ELMI tunneling is enabled on a port, this MAC address will be
        used as the the destination MAC address of the ELMI packets
        received over this port. ELMI packets received with this MAC
        address will be treated as data packets and not processed.

        When the tunneled ELMI packets are sent out of the given Network,
        this MAC address will be replaced with the reserved address defined
        for ELMI packets. This is done only when ELMI protocol tunnel status
        is set to Tunnel on the outgoing port.Dropped otherwise."

    ::= { fsMIVlanTunnelContextInfoEntry 9 }

fsMIVlanTunnelLldpAddress OBJECT-TYPE
    SYNTAX      MacAddress
    MAX-ACCESS  read-write
    STATUS      current
    DESCRIPTION
        "The MAC address to be used for LLDP packets tunneling . When
        LLDP tunneling is enabled on a port, this MAC address will be
        used as the the destination MAC address of the LLDP packets
        received over this port.

        LLDP packets received with this MAC address will be treated as
        data packets and not processed.

        When the tunneled LLDP packets are sent out of the given Network,
        this MAC address will be replaced with the reserved address defined
        for LLDP packets. This is done only when LLDP protocol tunnel status
        is set to Tunnel on the outgoing port.Dropped otherwise."

    ::= { fsMIVlanTunnelContextInfoEntry 10 }

-- ---------------------------------------------------------------------------- 
-- Future Vlan Tunnel Table 
-- ---------------------------------------------------------------------------- 
 
fsMIVlanTunnelTable OBJECT-TYPE 
   SYNTAX      SEQUENCE OF FsMIVlanTunnelEntry 
   MAX-ACCESS  not-accessible 
   STATUS      current 
   DESCRIPTION 
      "This table contains information about the tunnel ports. A walk on 
      this table will show only those interfaces that are configured for
      tunneling.
      This table is supported only when the Bridge is configured in Provider
      Bridge (Q-in-Q) mode."
      
   ::= { fsMIVlanTunnelObjects 2 } 
 
fsMIVlanTunnelEntry OBJECT-TYPE 
   SYNTAX      FsMIVlanTunnelEntry 
   MAX-ACCESS  not-accessible 
   STATUS      current 
   DESCRIPTION 
      "Entry indicating the tunnel information of the port."
   INDEX { fsMIVlanPort } 
   ::= { fsMIVlanTunnelTable 1 } 
    
FsMIVlanTunnelEntry ::= 
   SEQUENCE { 
      fsMIVlanPort         Integer32,
      fsMIVlanTunnelStatus EnabledStatus 
   } 

fsMIVlanPort OBJECT-TYPE
   SYNTAX      Integer32 (1..65535)
   MAX-ACCESS  not-accessible
   STATUS      current
   DESCRIPTION
      "The Index value of the port in the system for which this entry
      applies. The maximum index value of the port is defined by the
      system."
   ::= { fsMIVlanTunnelEntry 1 }


fsMIVlanTunnelStatus OBJECT-TYPE 
   SYNTAX      EnabledStatus
   MAX-ACCESS  read-write
   STATUS      current 
   DESCRIPTION 
      "Indicates whether Tunnelling is enabled or disabled on this port.
      fsMIVlanTunnelStatus can be set to `enabled` if and only if the
      Bridge mode is set to be `Provider Bridge Mode / Customer Bridge Mode`
      and Future VLAN port type is set to 'accessPort'.  Tunnelling can be
      enabled only on ports which are in 'dot1x force-authorised' state."
   DEFVAL      { disabled }
   ::= { fsMIVlanTunnelEntry 2 } 


-- ----------------------------------------------------------------
-- Tunnel protocol configuration table
-- ----------------------------------------------------------------
fsMIVlanTunnelProtocolTable OBJECT-TYPE
   SYNTAX      SEQUENCE OF FsMIVlanTunnelProtocolEntry
   MAX-ACCESS  not-accessible
   STATUS      current
   DESCRIPTION
      "This table contains information about the handling (Tunnel/Peer/
      Discard)of customer Layer 2 protocols (STP/GVRP/GMRP/LACP/Dot1x/
      IGMP/MVRP/MMRP/ELMI and LLDP) inside service provider network."
      
   ::= { fsMIVlanTunnelObjects 3 }
 
fsMIVlanTunnelProtocolEntry OBJECT-TYPE
   SYNTAX      FsMIVlanTunnelProtocolEntry
   MAX-ACCESS  not-accessible
   STATUS      current
   DESCRIPTION 
      "Entry indicating the handling (Tunnel/Peer/Discard) of Layer 2
      protocols (STP/GVRP/GMRP/LACP/Dot1x/IGMP/MVRP/MMRP/ELMI and LLDP) on this 
      port.
      
      Tunnel Status cannot be set to `tunnel/discard`, if the protocol
      is enabled on the port.Exception, Igmp and dot1x should be disabled 
      globally for setting the tunnel status to `tunnel/discard`."
   INDEX { fsMIVlanPort }
   ::= { fsMIVlanTunnelProtocolTable 1 }
    
 FsMIVlanTunnelProtocolEntry ::=
 SEQUENCE {
    fsMIVlanTunnelProtocolDot1x      TunnelStatus,
    fsMIVlanTunnelProtocolLacp       TunnelStatus,
    fsMIVlanTunnelProtocolStp        TunnelStatus,
    fsMIVlanTunnelProtocolGvrp       TunnelStatus,
    fsMIVlanTunnelProtocolGmrp       TunnelStatus,
    fsMIVlanTunnelProtocolIgmp       TunnelStatus,
    fsMIVlanTunnelProtocolMvrp       TunnelStatus,
    fsMIVlanTunnelProtocolMmrp       TunnelStatus,
    fsMIVlanTunnelProtocolElmi       TunnelStatus,
    fsMIVlanTunnelProtocolLldp       TunnelStatus
 }

fsMIVlanTunnelProtocolDot1x OBJECT-TYPE
   SYNTAX      TunnelStatus
   MAX-ACCESS  read-write
   STATUS      current
   DESCRIPTION
      "The object to specify whether to peer/tunnel/discard the Dot1x packets
            received on this port."
   ::= { fsMIVlanTunnelProtocolEntry  1 }

fsMIVlanTunnelProtocolLacp OBJECT-TYPE
   SYNTAX      TunnelStatus
   MAX-ACCESS  read-write
   STATUS      current
   DESCRIPTION
      "The object to specify whether to peer/tunnel/discard the LACP packets
            received on this port."
   ::= { fsMIVlanTunnelProtocolEntry 2 }

fsMIVlanTunnelProtocolStp OBJECT-TYPE
   SYNTAX      TunnelStatus
   MAX-ACCESS  read-write
   STATUS      current
   DESCRIPTION
      "The object to specify whether to peer/tunnel/discard the STP packets
            received on this port."
   ::= { fsMIVlanTunnelProtocolEntry 3 }

fsMIVlanTunnelProtocolGvrp OBJECT-TYPE
   SYNTAX      TunnelStatus
   MAX-ACCESS  read-write
   STATUS      current 
   DESCRIPTION 
      "The object to specify whether to peer/tunnel/discard the GVRP packets
            received on this port."
   ::= { fsMIVlanTunnelProtocolEntry 4 } 

fsMIVlanTunnelProtocolGmrp OBJECT-TYPE
   SYNTAX      TunnelStatus
   MAX-ACCESS  read-write
   STATUS      current
   DESCRIPTION
      "The object to specify whether to peer/tunnel/discard the GMRP packets
            received on this port."
   ::= { fsMIVlanTunnelProtocolEntry 5 }

fsMIVlanTunnelProtocolIgmp OBJECT-TYPE
   SYNTAX      TunnelStatus
   MAX-ACCESS  read-write
   STATUS      current
   DESCRIPTION
      "The object to specify whether to peer/tunnel/discard the IGMP packets
            received on this port."
   ::= { fsMIVlanTunnelProtocolEntry 6 }

fsMIVlanTunnelProtocolMvrp OBJECT-TYPE
   SYNTAX      TunnelStatus
   MAX-ACCESS  read-write
   STATUS      current
   DESCRIPTION
      "The object to specify whether to peer/tunnel/discard the MVRP packets
            received on this port."
   ::= { fsMIVlanTunnelProtocolEntry 7 }

fsMIVlanTunnelProtocolMmrp OBJECT-TYPE
   SYNTAX      TunnelStatus
   MAX-ACCESS  read-write
   STATUS      current
   DESCRIPTION
      "The object to specify whether to peer/tunnel/discard the MMRP packets
            received on this port."
   ::= { fsMIVlanTunnelProtocolEntry 8 }

fsMIVlanTunnelProtocolElmi OBJECT-TYPE
   SYNTAX      TunnelStatus
   MAX-ACCESS  read-write
   STATUS      current
   DESCRIPTION
      "The object to specify whether to peer/tunnel/discard the ELMI packets
            received on this port."
   ::= { fsMIVlanTunnelProtocolEntry 9 }

fsMIVlanTunnelProtocolLldp OBJECT-TYPE
   SYNTAX      TunnelStatus
   MAX-ACCESS  read-write
   STATUS      current
   DESCRIPTION
      "The object to specify whether to peer/tunnel/discard the LLDP packets
            received on this port."
   ::= { fsMIVlanTunnelProtocolEntry 10 }

-- ----------------------------------------------------------------
-- Tunnel protocol statistics table
-- ----------------------------------------------------------------
fsMIVlanTunnelProtocolStatsTable OBJECT-TYPE
   SYNTAX      SEQUENCE OF FsMIVlanTunnelProtocolStatsEntry
   MAX-ACCESS  not-accessible
   STATUS      current
   DESCRIPTION
      "This table contains statistics information about the tunneled 
       Layer 2 protocols (STP/GVRP/GMRP/LACP/Dot1x/IGMP/MVRP and MMRP) 
       received and transmitted over a port.

       This table is supported only for Provider (Q-in-Q) and 802.1ad 
       Bridges. This is not supported for customer bridges."

       
   ::= { fsMIVlanTunnelObjects 4 }
 
fsMIVlanTunnelProtocolStatsEntry OBJECT-TYPE
   SYNTAX      FsMIVlanTunnelProtocolStatsEntry
   MAX-ACCESS  not-accessible
   STATUS      current
   DESCRIPTION 
      "Entry indicating the handling (Tunnel/Peer/Discard) of Layer 2
      protocols (STP/GVRP/GMRP/LACP/Dot1x/IGMP/MVRP and MMRP) on this port."

      
   INDEX { fsMIVlanPort }
   ::= { fsMIVlanTunnelProtocolStatsTable 1 }
    
FsMIVlanTunnelProtocolStatsEntry ::=
 SEQUENCE {
      fsMIVlanTunnelProtocolDot1xPktsRecvd Counter32,
      fsMIVlanTunnelProtocolDot1xPktsSent  Counter32,
      fsMIVlanTunnelProtocolLacpPktsRecvd  Counter32,
      fsMIVlanTunnelProtocolLacpPktsSent   Counter32,
      fsMIVlanTunnelProtocolStpPDUsRecvd   Counter32,
      fsMIVlanTunnelProtocolStpPDUsSent    Counter32,
      fsMIVlanTunnelProtocolGvrpPDUsRecvd  Counter32,
      fsMIVlanTunnelProtocolGvrpPDUsSent   Counter32,
      fsMIVlanTunnelProtocolGmrpPktsRecvd  Counter32,
      fsMIVlanTunnelProtocolGmrpPktsSent   Counter32,
      fsMIVlanTunnelProtocolIgmpPktsRecvd  Counter32,
      fsMIVlanTunnelProtocolIgmpPktsSent   Counter32,
      fsMIVlanTunnelProtocolMvrpPktsRecvd  Counter32,
      fsMIVlanTunnelProtocolMvrpPktsSent   Counter32,
      fsMIVlanTunnelProtocolMmrpPktsRecvd  Counter32,
      fsMIVlanTunnelProtocolMmrpPktsSent   Counter32
   }

fsMIVlanTunnelProtocolDot1xPktsRecvd OBJECT-TYPE
   SYNTAX      Counter32
   MAX-ACCESS  read-only
   STATUS      current
   DESCRIPTION
      "The number of tunneled Dot1x Packets received."
   ::= { fsMIVlanTunnelProtocolStatsEntry 1 }

fsMIVlanTunnelProtocolDot1xPktsSent OBJECT-TYPE
   SYNTAX      Counter32
   MAX-ACCESS  read-only
   STATUS      current 
   DESCRIPTION 
      "The number of tunneled Dot1x Packets transmitted."
   ::= { fsMIVlanTunnelProtocolStatsEntry 2 }

fsMIVlanTunnelProtocolLacpPktsRecvd OBJECT-TYPE 
   SYNTAX      Counter32
   MAX-ACCESS  read-only
   STATUS      current 
   DESCRIPTION 
      "The number of tunneled LACP Packets received."
   ::= { fsMIVlanTunnelProtocolStatsEntry 3 } 

fsMIVlanTunnelProtocolLacpPktsSent OBJECT-TYPE 
   SYNTAX      Counter32
   MAX-ACCESS  read-only
   STATUS      current 
   DESCRIPTION 
      "The number of tunneled LACP packets transmitted."
   ::= { fsMIVlanTunnelProtocolStatsEntry 4 } 

fsMIVlanTunnelProtocolStpPDUsRecvd OBJECT-TYPE
   SYNTAX      Counter32
   MAX-ACCESS  read-only
   STATUS      current 
   DESCRIPTION 
      "The number of tunneled STP PDUs received."
   ::= { fsMIVlanTunnelProtocolStatsEntry 5 } 

fsMIVlanTunnelProtocolStpPDUsSent OBJECT-TYPE 
   SYNTAX      Counter32
   MAX-ACCESS  read-only
   STATUS      current 
   DESCRIPTION 
      "The number of tunneled STP PDUs transmitted."
   ::= { fsMIVlanTunnelProtocolStatsEntry 6 } 

fsMIVlanTunnelProtocolGvrpPDUsRecvd OBJECT-TYPE 
   SYNTAX      Counter32
   MAX-ACCESS  read-only
   STATUS      current 
   DESCRIPTION 
      "The number of tunneled  GVRP PDUs received."
   ::= { fsMIVlanTunnelProtocolStatsEntry 7 } 

fsMIVlanTunnelProtocolGvrpPDUsSent OBJECT-TYPE 
   SYNTAX      Counter32
   MAX-ACCESS  read-only
   STATUS      current 
   DESCRIPTION 
      "The number of tunneled GVRP PDUs transmitted."
   ::= { fsMIVlanTunnelProtocolStatsEntry 8 } 

fsMIVlanTunnelProtocolGmrpPktsRecvd OBJECT-TYPE
   SYNTAX      Counter32
   MAX-ACCESS  read-only
   STATUS      current
   DESCRIPTION
      "The number of tunneled GMRP PDUs packets received."
   ::= { fsMIVlanTunnelProtocolStatsEntry 9 }

fsMIVlanTunnelProtocolGmrpPktsSent OBJECT-TYPE
   SYNTAX      Counter32
   MAX-ACCESS  read-only
   STATUS      current 
   DESCRIPTION 
      "The number of tunneled GMRP packets transmitted."
   ::= { fsMIVlanTunnelProtocolStatsEntry 10 }

fsMIVlanTunnelProtocolIgmpPktsRecvd OBJECT-TYPE 
   SYNTAX      Counter32
   MAX-ACCESS  read-only
   STATUS      current 
   DESCRIPTION 
      "The number of tunneled IGMP packets received."
   ::= { fsMIVlanTunnelProtocolStatsEntry 11 } 

fsMIVlanTunnelProtocolIgmpPktsSent OBJECT-TYPE 
   SYNTAX      Counter32
   MAX-ACCESS  read-only
   STATUS      current 
   DESCRIPTION 
      "The number of tunneled  IGMP packets transmitted."
   ::= { fsMIVlanTunnelProtocolStatsEntry 12 }

fsMIVlanTunnelProtocolMvrpPktsRecvd OBJECT-TYPE
   SYNTAX      Counter32
   MAX-ACCESS  read-only
   STATUS      current
   DESCRIPTION
      "The number of MVRPDUs received on a port for which the MVRP tunneling 
       status is enabled."
   ::= { fsMIVlanTunnelProtocolStatsEntry 13 }

fsMIVlanTunnelProtocolMvrpPktsSent OBJECT-TYPE
   SYNTAX      Counter32
   MAX-ACCESS  read-only
   STATUS      current
   DESCRIPTION
      "The number of MVRPDUs transmitted on a port on which the MVRP tunneling 
       status is enabled."
   ::= { fsMIVlanTunnelProtocolStatsEntry 14 }

fsMIVlanTunnelProtocolMmrpPktsRecvd OBJECT-TYPE
   SYNTAX      Counter32
   MAX-ACCESS  read-only
   STATUS      current
   DESCRIPTION
      "The number of MMRPDUs received on a port for which the MMRP tunneling 
       status is enabled."
   ::= { fsMIVlanTunnelProtocolStatsEntry 15 }

fsMIVlanTunnelProtocolMmrpPktsSent OBJECT-TYPE
   SYNTAX      Counter32
   MAX-ACCESS  read-only
   STATUS      current
   DESCRIPTION
      "The number of MMRPDUs transmitted on a port on which the MMRP tunneling 
       status is enabled."
   ::= { fsMIVlanTunnelProtocolStatsEntry 16 } 

-- ----------------------------------------------------------------
-- VLAN Discard statistics table
-- ----------------------------------------------------------------
fsMIVlanDiscardStatsTable OBJECT-TYPE
   SYNTAX      SEQUENCE OF FsMIVlanDiscardStatsEntry
   MAX-ACCESS  not-accessible
   STATUS      current
   DESCRIPTION
      "This table contains statistics information about the L2 protocol   
       packets (STP/GVRP/GMRP/LACP/Dot1x/IGMP/MVRP and MMRP) discarded 
       on reception and transmission side due to 'Discard' tunnel protocol 
       status."

   ::= { fsMIVlanDiscardObjects 1 }
 
fsMIVlanDiscardStatsEntry OBJECT-TYPE
   SYNTAX      FsMIVlanDiscardStatsEntry
   MAX-ACCESS  not-accessible
   STATUS      current
   DESCRIPTION 
      "Entry indicating the Discard statistics for L2 protocol packets.
      This table is supported only for Provider(Q-in-Q) and 802.1ad Bridges."

   INDEX { fsMIVlanPort }
   ::= { fsMIVlanDiscardStatsTable 1 }
    
FsMIVlanDiscardStatsEntry ::=
 SEQUENCE {
      fsMIVlanDiscardDot1xPktsRx   Counter32,
      fsMIVlanDiscardDot1xPktsTx   Counter32,
      fsMIVlanDiscardLacpPktsRx    Counter32,
      fsMIVlanDiscardLacpPktsTx    Counter32,
      fsMIVlanDiscardStpPDUsRx     Counter32,
      fsMIVlanDiscardStpPDUsTx     Counter32,
      fsMIVlanDiscardGvrpPktsRx    Counter32,
      fsMIVlanDiscardGvrpPktsTx    Counter32,
      fsMIVlanDiscardGmrpPktsRx    Counter32,
      fsMIVlanDiscardGmrpPktsTx    Counter32,
      fsMIVlanDiscardIgmpPktsRx    Counter32,
      fsMIVlanDiscardIgmpPktsTx    Counter32,
      fsMIVlanDiscardMvrpPktsRx    Counter32,
      fsMIVlanDiscardMvrpPktsTx    Counter32,
      fsMIVlanDiscardMmrpPktsRx    Counter32,
      fsMIVlanDiscardMmrpPktsTx    Counter32
   }

fsMIVlanDiscardDot1xPktsRx OBJECT-TYPE
   SYNTAX      Counter32
   MAX-ACCESS  read-only
   STATUS      current
   DESCRIPTION
      "The number of Dot1x packets discarded on the reception side 
       due to Discard option."
   ::= { fsMIVlanDiscardStatsEntry 1 }

fsMIVlanDiscardDot1xPktsTx OBJECT-TYPE
   SYNTAX      Counter32
   MAX-ACCESS  read-only
   STATUS      current
   DESCRIPTION
      "The number of Dot1x packets discarded on the transmission side 
       due to Discard option."
   ::= { fsMIVlanDiscardStatsEntry 2 }

fsMIVlanDiscardLacpPktsRx OBJECT-TYPE
   SYNTAX      Counter32
   MAX-ACCESS  read-only
   STATUS      current
   DESCRIPTION
      "The number of LACP packets discarded on the reception side 
       due to Discard option."
   ::= { fsMIVlanDiscardStatsEntry 3 }

fsMIVlanDiscardLacpPktsTx OBJECT-TYPE
   SYNTAX      Counter32
   MAX-ACCESS  read-only
   STATUS      current
   DESCRIPTION
      "The number of LACP packets discarded on the transmission side 
       due to Discard option."
   ::= { fsMIVlanDiscardStatsEntry 4 }

fsMIVlanDiscardStpPDUsRx OBJECT-TYPE
   SYNTAX      Counter32
   MAX-ACCESS  read-only
   STATUS      current
   DESCRIPTION
      "The number of STP BPDUs discarded on the reception side 
       due to Discard option."
   ::= { fsMIVlanDiscardStatsEntry 5 }

fsMIVlanDiscardStpPDUsTx OBJECT-TYPE
   SYNTAX      Counter32
   MAX-ACCESS  read-only
   STATUS      current
   DESCRIPTION
      "The number of STP BPDUs discarded on the transmission side 
       due to Discard option."
   ::= { fsMIVlanDiscardStatsEntry 6 }

fsMIVlanDiscardGvrpPktsRx OBJECT-TYPE
   SYNTAX      Counter32
   MAX-ACCESS  read-only
   STATUS      current
   DESCRIPTION
      "The number of GVRP packets discarded on the reception side 
       due to Discard option."
   ::= { fsMIVlanDiscardStatsEntry 7 }

fsMIVlanDiscardGvrpPktsTx OBJECT-TYPE
   SYNTAX      Counter32
   MAX-ACCESS  read-only
   STATUS      current
   DESCRIPTION
      "The number of GVRP packets discarded on the transmission side 
       due to Discard option."
   ::= { fsMIVlanDiscardStatsEntry 8 }

fsMIVlanDiscardGmrpPktsRx OBJECT-TYPE
   SYNTAX      Counter32
   MAX-ACCESS  read-only
   STATUS      current
   DESCRIPTION
      "The number of GMRP packets discarded on the reception side 
       due to Discard option."
   ::= { fsMIVlanDiscardStatsEntry 9 }

fsMIVlanDiscardGmrpPktsTx OBJECT-TYPE
   SYNTAX      Counter32
   MAX-ACCESS  read-only
   STATUS      current
   DESCRIPTION
      "The number of GMRP packets discarded on the transmission side 
       due to Discard option."
   ::= { fsMIVlanDiscardStatsEntry 10 }

fsMIVlanDiscardIgmpPktsRx OBJECT-TYPE
   SYNTAX      Counter32
   MAX-ACCESS  read-only
   STATUS      current
   DESCRIPTION
      "The number of IGMP packets discarded on the reception side 
       due to Discard option."
   ::= { fsMIVlanDiscardStatsEntry 11 }

fsMIVlanDiscardIgmpPktsTx OBJECT-TYPE
   SYNTAX      Counter32
   MAX-ACCESS  read-only
   STATUS      current
   DESCRIPTION
      "The number of IGMP packets discarded on the transmission side 
       due to Discard option."
   ::= { fsMIVlanDiscardStatsEntry 12 }

fsMIVlanDiscardMvrpPktsRx OBJECT-TYPE
   SYNTAX      Counter32
   MAX-ACCESS  read-only
   STATUS      current
   DESCRIPTION
      "The number of MVRP packets discarded on the reception side
       due to Discard option."
   ::= { fsMIVlanDiscardStatsEntry 13 }

fsMIVlanDiscardMvrpPktsTx OBJECT-TYPE
   SYNTAX      Counter32
   MAX-ACCESS  read-only
   STATUS      current
   DESCRIPTION
      "The number of MVRP packets discarded on the transmission side
       due to Discard option."
   ::= { fsMIVlanDiscardStatsEntry 14 }

fsMIVlanDiscardMmrpPktsRx OBJECT-TYPE
   SYNTAX      Counter32
   MAX-ACCESS  read-only
   STATUS      current
   DESCRIPTION
      "The number of MMRP packets discarded on the receiption side
       due to Discard option."
   ::= { fsMIVlanDiscardStatsEntry 15 }

fsMIVlanDiscardMmrpPktsTx OBJECT-TYPE
   SYNTAX      Counter32
   MAX-ACCESS  read-only
   STATUS      current
   DESCRIPTION
      "The number of MMRP packets discarded on the transmission side
       due to Discard option."
   ::= { fsMIVlanDiscardStatsEntry 16 }        

END

-- Copyright (C) 2008-2014 Super Micro Computer Inc. All Rights Reserved

-- $Id: fsmpvlan.mib,v 1.30 2013/07/09 12:59:42 siva Exp $

SUPERMICRO-MIVlan-MIB DEFINITIONS ::= BEGIN 

IMPORTS 
 
    OBJECT-TYPE,MODULE-IDENTITY, Integer32, Unsigned32,
    NOTIFICATION-TYPE,
    enterprises,Counter32,IpAddress  FROM SNMPv2-SMI 
    RowStatus, TEXTUAL-CONVENTION, MacAddress, 
    TruthValue,DisplayString  FROM SNMPv2-TC
    fsDot1qTpFdbPort FROM SUPERMICROQ-BRIDGE-MIB
    fsDot1qTpFdbEntry FROM SUPERMICROQ-BRIDGE-MIB
    fsDot1qStaticUnicastEntry FROM SUPERMICROQ-BRIDGE-MIB
    fsDot1qVlanStaticEntry FROM SUPERMICROQ-BRIDGE-MIB
    VlanIdOrNone FROM Q-BRIDGE-MIB
    fsDot1qTpPort FROM SUPERMICROQ-BRIDGE-MIB
    fsDot1qVlanStaticPortConfigEntry FROM SUPERMICROQ-BRIDGE-MIB;

 
futureMIVlanMIB MODULE-IDENTITY 
    LAST-UPDATED "201209050000Z" 
    ORGANIZATION "Super Micro Computer Inc." 
    CONTACT-INFO "support@Supermicro.com" 
    DESCRIPTION "This mib module is for Proprietary
       Multiple Instance VLAN mib" 
    REVISION "201209050000Z"
    DESCRIPTION "This mib module is for Proprietary
       Multiple Instance VLAN mib" 
::= { enterprises supermicro-computer-inc(10876) super-switch(101) basic(1) 120 } 
 
VlanId ::= TEXTUAL-CONVENTION 
    STATUS      current 
    DESCRIPTION 
        "A 12-bit VLAN ID used in the VLAN Tag header." 
    SYNTAX      Integer32 (1..4094) 
 
EnabledStatus ::= TEXTUAL-CONVENTION 
    STATUS      current 
    DESCRIPTION 
        "A simple status value for the object." 
    SYNTAX      INTEGER { enabled(1), disabled(2) } 
 
 
MacLearningStatus ::= TEXTUAL-CONVENTION
    STATUS      current
    DESCRIPTION
        "A simple MAC learning status value specific to VLAN."
    SYNTAX      INTEGER { enabled(1), disabled(2), default(3) }

fsMIDot1qFutureVlan     OBJECT IDENTIFIER   ::= { futureMIVlanMIB 1 } 
 
-- fsMIDot1qFutureVlanTunnelConfig - This sub group contains mib objects for 
-- configuring VLAN Stacking (also known 802.1q in 802.1q) feature 
-- in FutureVLAN.
fsMIDot1qFutureVlanTunnelConfig OBJECT IDENTIFIER  ::= { futureMIVlanMIB 2 }
fsMIDot1qFutureVlanTraps  OBJECT IDENTIFIER  ::= { futureMIVlanMIB 3 }
fsMIDot1qFutureVlanTrapControl OBJECT IDENTIFIER  ::= { futureMIVlanMIB 4 }

 
-- fsMIDot1qFutureVlan group 
 
fsMIDot1qFutureVlanGlobalTrace OBJECT-TYPE
   SYNTAX        TruthValue
   MAX-ACCESS    read-write
   STATUS        current
   DESCRIPTION
      "Enable/Disable the global trace in VLAN."
   ::= { fsMIDot1qFutureVlan 1 }

fsMIDot1qFutureVlanGlobalsTable OBJECT-TYPE
   SYNTAX        SEQUENCE OF FsMIDot1qFutureVlanGlobalsEntry
   MAX-ACCESS    not-accessible
   STATUS        current
   DESCRIPTION
      "List of per virtual context Vlan Module Parameters."
   ::= { fsMIDot1qFutureVlan 2 }

fsMIDot1qFutureVlanGlobalsEntry OBJECT-TYPE
   SYNTAX       FsMIDot1qFutureVlanGlobalsEntry
   MAX-ACCESS   not-accessible
   STATUS       current
   DESCRIPTION
      "Per virtual context Vlan module parmaters."
   INDEX { fsMIDot1qFutureVlanContextId }
   ::= { fsMIDot1qFutureVlanGlobalsTable 1 }

FsMIDot1qFutureVlanGlobalsEntry ::=
   SEQUENCE {
       fsMIDot1qFutureVlanContextId
          Integer32,
       fsMIDot1qFutureVlanStatus 
          EnabledStatus,
       fsMIDot1qFutureVlanMacBasedOnAllPorts 
          EnabledStatus,
       fsMIDot1qFutureVlanPortProtoBasedOnAllPorts 
          EnabledStatus,
       fsMIDot1qFutureVlanShutdownStatus 
          TruthValue,
       fsMIDot1qFutureGarpShutdownStatus 
          TruthValue,
       fsMIDot1qFutureVlanDebug 
          Integer32,
       fsMIDot1qFutureVlanLearningMode 
          INTEGER,
       fsMIDot1qFutureVlanHybridTypeDefault 
          INTEGER,
       fsMIDot1qFutureVlanOperStatus
          EnabledStatus,
       fsMIDot1qFutureGvrpOperStatus
          EnabledStatus,
       fsMIDot1qFutureGmrpOperStatus
          EnabledStatus,
       fsMIDot1qFutureVlanContextName
          DisplayString,
       fsMIDot1qFutureGarpDebug 
          Integer32,
       fsMIDot1qFutureUnicastMacLearningLimit
          Unsigned32,
       fsMIDot1qFutureBaseBridgeMode
          INTEGER,
       fsMIDot1qFutureVlanSubnetBasedOnAllPorts 
          EnabledStatus,
       fsMIDot1qFutureVlanGlobalMacLearningStatus
          EnabledStatus,
       fsMIDot1qFutureVlanApplyEnhancedFilteringCriteria
          TruthValue,
       fsMIDot1qFutureVlanGlobalsFdbFlush
          TruthValue
   }

fsMIDot1qFutureVlanContextId OBJECT-TYPE
   SYNTAX        Integer32 (0..65535)
   MAX-ACCESS    not-accessible
   STATUS        current
   DESCRIPTION
      "Identifies the virtual context in the system."
   ::= { fsMIDot1qFutureVlanGlobalsEntry 1 }

fsMIDot1qFutureVlanStatus OBJECT-TYPE 
   SYNTAX      EnabledStatus 
   MAX-ACCESS  read-write 
   STATUS      current 
   DESCRIPTION 
      "The administrative status requested by management for the Vlan 
      feature. The value enabled(1) indicates that Vlan should be enabled  
      in the device on all ports. The value disabled(2) indicates that 
      Vlan should be disabled in the device on all ports. The object can 
      be set to disabled if and only if, fsMIDot1qGvrpStatus and 
      fsMIDot1dGmrpStatus are disabled. The object should NOT be enabled 
      before setting 'fsMIDot1qFutureVlanType'. Setting this object will 
      affect the operational status of the VLAN module 
      (fsMIDot1qFutureVlanOperStatus)." 
   ::= { fsMIDot1qFutureVlanGlobalsEntry 2 } 
 
fsMIDot1qFutureVlanMacBasedOnAllPorts OBJECT-TYPE 
   SYNTAX      EnabledStatus
   MAX-ACCESS  read-write
   STATUS      current
   DESCRIPTION 
      "This object is only used to enable/disable the mac based type on all 
      ports of fsMIDot1qFutureVlanPortMacBasedClassification"
   ::= { fsMIDot1qFutureVlanGlobalsEntry 3 } 

fsMIDot1qFutureVlanPortProtoBasedOnAllPorts OBJECT-TYPE 
   SYNTAX      EnabledStatus
   MAX-ACCESS  read-write
   STATUS      current
   DESCRIPTION 
      "This object is only used to enable/disable the port protocol based 
      type on all ports of 
      fsMIDot1qFutureVlanPortPortProtoBasedClassification"
   ::= { fsMIDot1qFutureVlanGlobalsEntry 4 } 
 
fsMIDot1qFutureVlanShutdownStatus OBJECT-TYPE 
   SYNTAX      TruthValue 
   MAX-ACCESS  read-write 
   STATUS      current 
   DESCRIPTION 
      "The administrative shutdown status requested by management for Vlan  
      The value true(1) indicates that Vlan should be shutdown  
      in the device on all ports. All memory will be released. 
      The value false(2) indicates that Vlan should be active in the device  
      on all ports."
   DEFVAL   { false }       
   ::= { fsMIDot1qFutureVlanGlobalsEntry 5 } 
 
fsMIDot1qFutureGarpShutdownStatus OBJECT-TYPE 
   SYNTAX      TruthValue 
   MAX-ACCESS  read-write 
   STATUS      current 
   DESCRIPTION 
      "The administrative status requested by management for GARP  
      The value true(1) indicates that GARP should be shutdown  
      in the device on all ports. All memory will be released. 
      The value false(2) indicates that GARP should be active in  
      the device on all ports. This object can be set to true only  
      when none of the Garp applications (GVRP, GMRP) are enabled. 
      Whenever Garp is enabled after shutdown, Gvrp and Gmrp must 
      be enabled explicitly.By default this value is false(2) for default 
      context and is true for other contexts." 
   ::= { fsMIDot1qFutureVlanGlobalsEntry 6 } 
 
fsMIDot1qFutureVlanDebug OBJECT-TYPE 
   SYNTAX      Integer32 (0..524287)
   MAX-ACCESS  read-write 
   STATUS      current 
   DESCRIPTION 
      "Enables the tracing in the selected submodule in VLAN. A 32 bit 
      integer is used to store the Tracing level in the specified module.
       Different Tracing Levels -
         BIT 0 - Initialisation and Shutdown Trace.
         BIT 1 - Management trace.
         BIT 2 - Data path trace.
         BIT 3 - Control Plane trace.
         BIT 4 - Packet Dump.
         BIT 5 - OS Resource trace.
         BIT 6 - All Failure trace (All failures including Packet Validation)
         BIT 7 - Buffer Trace.

       Different submodule Tracing -
         BIT 16 - Tracing in VLAN module.
         BIT 17 - Tracing in VLAN Priority module.
         BIT 18 - Tracing in VLAN Redundancy module.

       The remaining bits are reserved. The combination of levels and 
       submodules are allowed i.e. Tracing can be allowed at all failure 
       and data path level in All submodules by setting the BIT 
       appropriately.
       For Example, setting the debug value to the following bit stream, 
          00000000000000010000000000000100 will enable data path trace 
       prints in VLAN module. Multiple submodules and multiple levels can
       be combined by setting the corresponding bits.
       For Example, setting the debug value to the following bit stream,
          00000000000000110000000000001100 will enable data path and 
       control plane trace prints in VLAN and VLAN Priority modules.
       
       Note : BIT0 is the least significant bit and BIT31 is the most
       significant bit."
   ::= { fsMIDot1qFutureVlanGlobalsEntry 7 } 
 
fsMIDot1qFutureVlanLearningMode OBJECT-TYPE
   SYNTAX      INTEGER {
               ivl (1),
               svl (2),
               hybrid (3)
               }
   MAX-ACCESS read-only
   STATUS      current
   DESCRIPTION
         "The Type of VLAN learning mode.
          When the object value is modified, the static
          fid-vlan mappings and static unicast entries
          need to be reconfigured. Static unicast configurations 
          associated with old fid will get deleted." 
   DEFVAL  { ivl }
   ::= { fsMIDot1qFutureVlanGlobalsEntry 8 }

fsMIDot1qFutureVlanHybridTypeDefault OBJECT-TYPE
   SYNTAX      INTEGER {
               ivl(1),
               svl(2)
               }
   MAX-ACCESS  read-only
   STATUS      current
   DESCRIPTION
         "The default learning mode of the switch if 
          fsMIDot1qFutureVlanLearningMode is hvl (3).
          When the object value is modified, the static
          fid-vlan mappings and static unicast entries
          need to be reconfigured. Static unicast configurations 
          associated with old fid will get deleted."
   DEFVAL  { ivl }
   ::= { fsMIDot1qFutureVlanGlobalsEntry 9 }

fsMIDot1qFutureVlanOperStatus OBJECT-TYPE 
   SYNTAX      EnabledStatus 
   MAX-ACCESS  read-only 
   STATUS      current 
   DESCRIPTION 
      "The operational status of the Vlan module. 
      The value enabled(1) indicates that Vlan module is currently enabled  
      in the device. 
      The value disabled(2) indicates that Vlan module is currently disabled 
      in the device." 
   ::= { fsMIDot1qFutureVlanGlobalsEntry 10 } 

fsMIDot1qFutureGvrpOperStatus OBJECT-TYPE 
   SYNTAX      EnabledStatus 
   MAX-ACCESS  read-only 
   STATUS      current 
   DESCRIPTION 
      "The operational status of the GVRP module. 
      The value enabled(1) indicates that GVRP module is currently enabled  
      in the device. 
      The value disabled(2) indicates that GVRP module is currently disabled 
      in the device." 
   ::= { fsMIDot1qFutureVlanGlobalsEntry 11 } 

fsMIDot1qFutureGmrpOperStatus OBJECT-TYPE 
   SYNTAX      EnabledStatus 
   MAX-ACCESS  read-only 
   STATUS      current 
   DESCRIPTION 
      "The operational status of the GMRP module. 
      The value enabled(1) indicates that GMRP module is currently enabled  
      in the device. 
      The value disabled(2) indicates that GMRP module is currently disabled 
      in the device." 
   ::= { fsMIDot1qFutureVlanGlobalsEntry 12 } 

fsMIDot1qFutureVlanContextName OBJECT-TYPE
    SYNTAX      DisplayString (SIZE (1..32))
    MAX-ACCESS  read-only
    STATUS      current
    DESCRIPTION
              "The name of the virtual context."
    ::= { fsMIDot1qFutureVlanGlobalsEntry 13 }
 
fsMIDot1qFutureGarpDebug OBJECT-TYPE 
   SYNTAX      Integer32 (0..1048575)
   MAX-ACCESS  read-write 
   STATUS      current 
   DESCRIPTION 
      "Enables the tracing in the selected submodule in GARP. A 32 bit 
      integer is used to store the Tracing level in the specified module.
       Different Tracing Levels -
         BIT 0 - Initialisation and Shutdown Trace.
         BIT 1 - Management trace.
         BIT 2 - Data path trace.
         BIT 3 - Control Plane trace.
         BIT 4 - Packet Dump.
         BIT 5 - OS Resource trace.
         BIT 6 - All Failure trace (All failures including Packet Validation)
         BIT 7 - Buffer Trace.

       Different submodule Tracing -
         BIT 16 - Tracing in GARP module.   
         BIT 17 - Tracing in GMRP module.  
         BIT 18 - Tracing in GVRP module.   
         BIT 19 - Tracing in GARP Redundancy module.   

       The remaining bits are reserved. The combination of levels and 
       submodules are allowed i.e. Tracing can be allowed at all failure 
       and data path level in All submodules by setting the BIT 
       appropriately.
       For Example, setting the debug value to the following bit stream, 
          00000000000000010000000000000100 will enable data path trace 
       prints in GARP module. Multiple submodules and multiple levels can
       be combined by setting the corresponding bits.
       For Example, setting the debug value to the following bit stream,
          00000000000001010000000000001100 will enable data path and 
       control plane trace prints in GARP and GVRP modules.
       
       Note : BIT0 is the least significant bit and BIT31 is the most
       significant bit."
   ::= { fsMIDot1qFutureVlanGlobalsEntry 14 } 
 
fsMIDot1qFutureUnicastMacLearningLimit OBJECT-TYPE
   SYNTAX      Unsigned32 (0..4294967295) 
   MAX-ACCESS  read-write
   STATUS      current
   DESCRIPTION
      "The Limiting value on the number of distinct unicast MAC addresses
       that can be learnt in the specified virtual context.

       The upper limit value that can be SET for this object is determined 
       by the underlying hardware. The value that can be SET for this object 
       cannot be less than the value set for the UnicastMacLimit per vlan for 
       any of the vlans in the specified virtual context."
   ::= { fsMIDot1qFutureVlanGlobalsEntry 15 }

fsMIDot1qFutureBaseBridgeMode OBJECT-TYPE
   SYNTAX      INTEGER
                {
                 dot1dTransparentMode(1),
                 dot1qVlanMode(2)
                }

   MAX-ACCESS  read-write
   STATUS      current
   DESCRIPTION
     "This object indicates Base Bridge-Mode of the Switch.
      Setting the value to transparent mode will make
      switch behave according to IEEE 802.1d implementation.
      Setting the value to VLAN mode will make switch behave
      according to IEEE 802.1q Implementation"
   ::= { fsMIDot1qFutureVlanGlobalsEntry 16 }

fsMIDot1qFutureVlanSubnetBasedOnAllPorts OBJECT-TYPE 
   SYNTAX      EnabledStatus
   MAX-ACCESS  read-write
   STATUS      current
   DESCRIPTION 
      "This object is used to enable/disable the subnet based VLAN Classification
       on all ports of dot1qFutureVlanPortSubnetBasedClassification. On setting
       this object to enable/disable status, Subnet based VLAN classification 
       will be enabled/disabled on all the ports."
   ::= { fsMIDot1qFutureVlanGlobalsEntry 17 } 

fsMIDot1qFutureVlanGlobalMacLearningStatus OBJECT-TYPE 
   SYNTAX      EnabledStatus
   MAX-ACCESS  read-write
   STATUS      current
   DESCRIPTION 
         "This object specifies the global  MAC learning status of the
          switch. The default value of global mac learning status of
          the switch is enabled.
          This object can take only two values enabled or disabled.
          The value as specified by this object will be applied
          for a newly created VLAN. The configuration of this object 
          will override the value of fsMIDot1qFutureVlanAdminMacLearningStatus 
          provided  the value of fsMIDot1qFutureVlanAdminMacLearningStatus is 
          default only."
   DEFVAL  {enabled}
   ::= { fsMIDot1qFutureVlanGlobalsEntry 18 } 

fsMIDot1qFutureVlanApplyEnhancedFilteringCriteria OBJECT-TYPE
   SYNTAX      TruthValue 
   MAX-ACCESS  read-write
   STATUS      current
   DESCRIPTION
   "If this object is set as 'false', then only default filtering
   utility criteria will be applied on all ports in this context.
   Otherwise the filtering criteria to be used for the ports in this
   context will be taken from fsMIDot1qFutureVlanFilteringUtilityCriteria 
   for the respective ports.
    - It is recommended to configure this object before doing any port
    to virtual context mapping in the system."
   DEFVAL  {true}
   ::= { fsMIDot1qFutureVlanGlobalsEntry 19 }

fsMIDot1qFutureVlanGlobalsFdbFlush OBJECT-TYPE
   SYNTAX      TruthValue 
   MAX-ACCESS  read-write
   STATUS      current
   DESCRIPTION
   "If this object is set as 'true', then all the dynamically learnt 
    MAC addresses in this context are removed.After flush this object 
    is set to 'false'"
   DEFVAL  {false}
   ::= { fsMIDot1qFutureVlanGlobalsEntry 20 }



-- ------------------------------------------------------------------------- 
-- Future Vlan Port Table 
-- ------------------------------------------------------------------------- 
 
fsMIDot1qFutureVlanPortTable OBJECT-TYPE 
   SYNTAX      SEQUENCE OF FsMIDot1qFutureVlanPortEntry 
   MAX-ACCESS  not-accessible 
   STATUS      current 
   DESCRIPTION 
      "Table containing the port type information." 
   ::= { fsMIDot1qFutureVlan 3 } 
 
fsMIDot1qFutureVlanPortEntry OBJECT-TYPE 
   SYNTAX      FsMIDot1qFutureVlanPortEntry 
   MAX-ACCESS  not-accessible 
   STATUS      current 
   DESCRIPTION 
      "Entry indicating the type of the port." 
   INDEX { fsMIDot1qFutureVlanPort } 
   ::= { fsMIDot1qFutureVlanPortTable 1 } 
   
-- 2014/09/05 Chung : Global mapping and control for MAC-based and Subnet-base VLAN.
-- fsMIDot1qFutureVlanPortMacBasedClassification and
-- fsMIDot1qFutureVlanPortSubnetBasedClassification are invalid.

FsMIDot1qFutureVlanPortEntry ::= 
   SEQUENCE { 
      fsMIDot1qFutureVlanPort Integer32, 
      fsMIDot1qFutureVlanPortType INTEGER, 
--      fsMIDot1qFutureVlanPortMacBasedClassification EnabledStatus,
      fsMIDot1qFutureVlanPortPortProtoBasedClassification EnabledStatus,
      fsMIDot1qFutureVlanFilteringUtilityCriteria INTEGER,
      fsMIDot1qFutureVlanPortProtected TruthValue, 
--      fsMIDot1qFutureVlanPortSubnetBasedClassification EnabledStatus,
      fsMIDot1qFutureVlanPortUnicastMacLearning EnabledStatus,
      fsMIDot1qFutureVlanPortGmrpJoinEmptyTxCount Counter32,
      fsMIDot1qFutureVlanPortGmrpJoinEmptyRxCount Counter32,
      fsMIDot1qFutureVlanPortGmrpJoinInTxCount Counter32,
      fsMIDot1qFutureVlanPortGmrpJoinInRxCount Counter32,
      fsMIDot1qFutureVlanPortGmrpLeaveInTxCount Counter32,
      fsMIDot1qFutureVlanPortGmrpLeaveInRxCount Counter32,
      fsMIDot1qFutureVlanPortGmrpLeaveEmptyTxCount Counter32,
      fsMIDot1qFutureVlanPortGmrpLeaveEmptyRxCount Counter32,
      fsMIDot1qFutureVlanPortGmrpEmptyTxCount Counter32,
      fsMIDot1qFutureVlanPortGmrpEmptyRxCount Counter32,
      fsMIDot1qFutureVlanPortGmrpLeaveAllTxCount Counter32,
      fsMIDot1qFutureVlanPortGmrpLeaveAllRxCount Counter32,
      fsMIDot1qFutureVlanPortGmrpDiscardCount Counter32,
      fsMIDot1qFutureVlanPortGvrpJoinEmptyTxCount Counter32,
      fsMIDot1qFutureVlanPortGvrpJoinEmptyRxCount Counter32,
      fsMIDot1qFutureVlanPortGvrpJoinInTxCount Counter32,
      fsMIDot1qFutureVlanPortGvrpJoinInRxCount Counter32,
      fsMIDot1qFutureVlanPortGvrpLeaveInTxCount Counter32,
      fsMIDot1qFutureVlanPortGvrpLeaveInRxCount Counter32,
      fsMIDot1qFutureVlanPortGvrpLeaveEmptyTxCount Counter32,
      fsMIDot1qFutureVlanPortGvrpLeaveEmptyRxCount Counter32,
      fsMIDot1qFutureVlanPortGvrpEmptyTxCount Counter32,
      fsMIDot1qFutureVlanPortGvrpEmptyRxCount Counter32,
      fsMIDot1qFutureVlanPortGvrpLeaveAllTxCount Counter32,
      fsMIDot1qFutureVlanPortGvrpLeaveAllRxCount Counter32,
      fsMIDot1qFutureVlanPortGvrpDiscardCount Counter32,
      fsMIDot1qFutureVlanPortFdbFlush TruthValue,
	  fsMIDot1qFutureVlanPortAllowedVlanList OCTET STRING
   } 
 
fsMIDot1qFutureVlanPort OBJECT-TYPE 
   SYNTAX      Integer32 (1..65535) 
   MAX-ACCESS  not-accessible 
   STATUS      current 
   DESCRIPTION 
      "The port number of the port for which this entry applies." 
   ::= { fsMIDot1qFutureVlanPortEntry 1 } 
 
fsMIDot1qFutureVlanPortType OBJECT-TYPE 
   SYNTAX      INTEGER { 
                  accessPort (1), 
                  trunkPort (2), 
                  hybridPort (3),
                  hostPort (4), 
                  promiscuousPort (5)
               } 
   MAX-ACCESS  read-write 
   STATUS      current 
   DESCRIPTION 
      "The type of the port is by default hybrid port. 
       When configured as access port, the port can accept and send 
       only untagged frames.
       When configured as a trunk port, port is added as 
       member of all the existing Vlans and also for any new vlan
       created. 
       When configured as hybrid port, the port can send or accept both 
       tagged and untagged frames.  
       
       hostPort, promiscuousPort are types of port in PVLAN domain.
       Behaviour of host port varies based on the secondary vlan to which
       it is configured as member port.

       If a host port is a member port of an isolated VLAN, traffic from the 
       host port is sent only to the promiscuous port of the Private VLAN and 
       the trunk port.

       If a host port is a member port of the community VLAN, traffic from the 
       port can be sent only to other ports of the community VLAN , trunk port 
       and promiscuous port of the private VLAN.

       A host port can be associated with only one secondary vlan and with
       the associated primary vlan.

       The PVID of host port will be set the ID of the secondary vlan
       to which it belongs to.
       If a host port is member port of primary vlan, but is not member port 
       of any secondary vlan, then its PVID will be set to primary vlan id.

       Promiscuous ports should be configured as member port of primary vlan 
       and member port of all(some) secondary vlans associated with that 
       primary vlan.

       The PVID of promiscuous port will be set as the ID of the primary 
       vlan to which it belongs to.

       Host and  promiscuous ports should be configured as untagged members
       of primary/secondary vlans.

       When a access/hybrid port is configured as a member port of a
       primary/secondary vlan, it becomes a hostPort automatically."

   DEFVAL   { hybridPort } 
   ::= { fsMIDot1qFutureVlanPortEntry 2 } 

-- fsMIDot1qFutureVlanPortMacBasedClassification OBJECT-TYPE 
--    SYNTAX      EnabledStatus
--    MAX-ACCESS  read-write 
--    STATUS      current 
--    DESCRIPTION 
--       "Object to expilicitly enable/disable the Mac based Classification 
--       on port. This can be independently set without 
--       any dependency in available configuration of
--        fsMIDot1qFutureVlanMacBasedOnAllPorts " 
--    ::= { fsMIDot1qFutureVlanPortEntry 3 } 

fsMIDot1qFutureVlanPortPortProtoBasedClassification OBJECT-TYPE 
   SYNTAX      EnabledStatus
   MAX-ACCESS  read-write 
   STATUS      current 
   DESCRIPTION 
      "Object to expilicitly enable/disable the port and protocol
      Classification on port. This can be independently set without 
      any dependency in available configuration of
       fsMIDot1qFutureVlanPortProtoBasedOnAllPorts " 
   ::= { fsMIDot1qFutureVlanPortEntry 4 } 
 
fsMIDot1qFutureVlanFilteringUtilityCriteria OBJECT-TYPE 
   SYNTAX      INTEGER { 
                  default  (1), 
                  enhanced (2)
               } 
   MAX-ACCESS  read-write 
   STATUS      current 
   DESCRIPTION 
      "Based on this object, learning on a port is decided.
      
      If default filtering utility Criteria is selected on a port, then
      learning of source mac from a received packet on that port will be
      done only if there is atleast on member port in that vlan.

      If enhanced filtering utility criteria is selected on a port,then
      learning of source mac from a received packet on that port will be
      done if the following are satisfied: 
      
      -    if at least one VLAN that uses the FID includes the reception
      Port and at least one other Port with a Port State of Learning or
      Forwarding in its member set, and:
       
       o The operPointToPointMAC parameter is false for the reception Port; or
       o Ingress to the VLAN is permitted through a third Port.
       
       The third port can, but is not required to, be in the member set."
   DEFVAL   { default } 
   ::= { fsMIDot1qFutureVlanPortEntry 5 } 
 
fsMIDot1qFutureVlanPortProtected  OBJECT-TYPE
   SYNTAX      TruthValue
   MAX-ACCESS  read-write
   STATUS      current
   DESCRIPTION
      "The Split Horizon property of the port. If set to true, frames that 
       are received on any other port, that has the same property set to true,
       will not be forwarded on this port."
   DEFVAL   { false }
   ::= { fsMIDot1qFutureVlanPortEntry 6 }
 
-- fsMIDot1qFutureVlanPortSubnetBasedClassification OBJECT-TYPE 
--    SYNTAX      EnabledStatus
--    MAX-ACCESS  read-write 
--    STATUS      current 
--    DESCRIPTION 
--       "Object to expilicitly enable/disable the Subnet based Vlan Classification 
--       on port. This can be independently set without any dependency in 
--       available configuration of dot1qFutureVlanSubnetBasedOnAllPorts. This
--       object is not used in case of BCM chipsets." 
--    ::= { fsMIDot1qFutureVlanPortEntry 7 } 

fsMIDot1qFutureVlanPortUnicastMacLearning OBJECT-TYPE
   SYNTAX      EnabledStatus
   MAX-ACCESS  read-write
   STATUS      current
   DESCRIPTION
      "A Truth value indicating the unicast MAC learning enabled/disabled
       status for this port. 
       When Unicast Mac Learning is disabled, 
       no unicast mac entry will be learnt on this port.
       When Mac Learning is enabled, unicast mac entries will be learnt on this 
       port. Configuration of this object will not get affected by the value
       configured for fsMIDot1qFutureVlanGlobalMacLearningStatus "
   DEFVAL   { enabled }
   ::= { fsMIDot1qFutureVlanPortEntry 8 }

fsMIDot1qFutureVlanPortGmrpJoinEmptyTxCount OBJECT-TYPE
   SYNTAX      Counter32
   MAX-ACCESS  read-only
   STATUS      current
   DESCRIPTION
            " Number of Gmrp Join Empty packets transmitted by this port."
   ::= { fsMIDot1qFutureVlanPortEntry 9 }

fsMIDot1qFutureVlanPortGmrpJoinEmptyRxCount OBJECT-TYPE
   SYNTAX      Counter32
   MAX-ACCESS  read-only
   STATUS      current
   DESCRIPTION
            " Number of Gmrp Join Empty packets received on this port."
   ::= { fsMIDot1qFutureVlanPortEntry 10 }

fsMIDot1qFutureVlanPortGmrpJoinInTxCount OBJECT-TYPE
   SYNTAX      Counter32
   MAX-ACCESS  read-only
   STATUS      current
   DESCRIPTION
            " Number of Gmrp Join In packets transmitted by this port."
   ::= { fsMIDot1qFutureVlanPortEntry 11 }

fsMIDot1qFutureVlanPortGmrpJoinInRxCount OBJECT-TYPE
   SYNTAX      Counter32
   MAX-ACCESS  read-only
   STATUS      current
   DESCRIPTION
            " Number of Gmrp Join In packets received on this port."
   ::= { fsMIDot1qFutureVlanPortEntry 12 }

fsMIDot1qFutureVlanPortGmrpLeaveInTxCount OBJECT-TYPE
   SYNTAX      Counter32
   MAX-ACCESS  read-only
   STATUS      current
   DESCRIPTION
            " Number of Gmrp Leave In packets transmitted by this port."
   ::= { fsMIDot1qFutureVlanPortEntry 13 }

fsMIDot1qFutureVlanPortGmrpLeaveInRxCount OBJECT-TYPE
   SYNTAX      Counter32
   MAX-ACCESS  read-only
   STATUS      current
   DESCRIPTION
            " Number of Gmrp Leave In packets received on this port."
   ::= { fsMIDot1qFutureVlanPortEntry 14 }

fsMIDot1qFutureVlanPortGmrpLeaveEmptyTxCount OBJECT-TYPE
   SYNTAX      Counter32
   MAX-ACCESS  read-only
   STATUS      current
   DESCRIPTION
            " Number of Gmrp Leave Empty packets transmitted by this port."
   ::= { fsMIDot1qFutureVlanPortEntry 15 }

fsMIDot1qFutureVlanPortGmrpLeaveEmptyRxCount OBJECT-TYPE
   SYNTAX      Counter32
   MAX-ACCESS  read-only
   STATUS      current
   DESCRIPTION
            " Number of Gmrp Leave Empty packets received on this port."
   ::= { fsMIDot1qFutureVlanPortEntry 16 }

fsMIDot1qFutureVlanPortGmrpEmptyTxCount OBJECT-TYPE
   SYNTAX      Counter32
   MAX-ACCESS  read-only
   STATUS      current
   DESCRIPTION
            " Number of Gmrp Empty packets transmitted by this port."
   ::= { fsMIDot1qFutureVlanPortEntry 17 }

fsMIDot1qFutureVlanPortGmrpEmptyRxCount OBJECT-TYPE
   SYNTAX      Counter32
   MAX-ACCESS  read-only
   STATUS      current
   DESCRIPTION
            " Number of Gmrp Empty packets received on this port."
   ::= { fsMIDot1qFutureVlanPortEntry 18 }

fsMIDot1qFutureVlanPortGmrpLeaveAllTxCount OBJECT-TYPE
   SYNTAX      Counter32
   MAX-ACCESS  read-only
   STATUS      current
   DESCRIPTION
            " Number of Gmrp Leave All packets transmitted by this port."
   ::= { fsMIDot1qFutureVlanPortEntry 19 }

fsMIDot1qFutureVlanPortGmrpLeaveAllRxCount OBJECT-TYPE
   SYNTAX      Counter32
   MAX-ACCESS  read-only
   STATUS      current
   DESCRIPTION
            " Number of Gmrp Leave All packets received on this port."
   ::= { fsMIDot1qFutureVlanPortEntry 20 }

fsMIDot1qFutureVlanPortGmrpDiscardCount OBJECT-TYPE
   SYNTAX      Counter32
   MAX-ACCESS  read-only
   STATUS      current
   DESCRIPTION
            " Number of Gmrp packets discarded in this port."
   ::= { fsMIDot1qFutureVlanPortEntry 21 }

fsMIDot1qFutureVlanPortGvrpJoinEmptyTxCount OBJECT-TYPE
   SYNTAX      Counter32
   MAX-ACCESS  read-only
   STATUS      current
   DESCRIPTION
            " Number of Gvrp Join Empty packets transmitted by this port."
   ::= { fsMIDot1qFutureVlanPortEntry 22 }

fsMIDot1qFutureVlanPortGvrpJoinEmptyRxCount OBJECT-TYPE
   SYNTAX      Counter32
   MAX-ACCESS  read-only
   STATUS      current
   DESCRIPTION
            " Number of Gvrp Join Empty packets received on this port."
   ::= { fsMIDot1qFutureVlanPortEntry 23 }

fsMIDot1qFutureVlanPortGvrpJoinInTxCount OBJECT-TYPE
   SYNTAX      Counter32
   MAX-ACCESS  read-only
   STATUS      current
   DESCRIPTION
            " Number of Gvrp Join In packets transmitted by this port."
   ::= { fsMIDot1qFutureVlanPortEntry 24 }

fsMIDot1qFutureVlanPortGvrpJoinInRxCount OBJECT-TYPE
   SYNTAX      Counter32
   MAX-ACCESS  read-only
   STATUS      current
   DESCRIPTION
            " Number of Gvrp Join In packets received on this port."
   ::= { fsMIDot1qFutureVlanPortEntry 25 }

fsMIDot1qFutureVlanPortGvrpLeaveInTxCount OBJECT-TYPE
   SYNTAX      Counter32
   MAX-ACCESS  read-only
   STATUS      current
   DESCRIPTION
            " Number of Gvrp Leave In packets transmitted by this port."
   ::= { fsMIDot1qFutureVlanPortEntry 26 }

fsMIDot1qFutureVlanPortGvrpLeaveInRxCount OBJECT-TYPE
   SYNTAX      Counter32
   MAX-ACCESS  read-only
   STATUS      current
   DESCRIPTION
            " Number of Gvrp Leave In packets received on this port."
   ::= { fsMIDot1qFutureVlanPortEntry 27 }

fsMIDot1qFutureVlanPortGvrpLeaveEmptyTxCount OBJECT-TYPE
   SYNTAX      Counter32
   MAX-ACCESS  read-only
   STATUS      current
   DESCRIPTION
            " Number of Gvrp Leave Empty packets transmitted by this port."
   ::= { fsMIDot1qFutureVlanPortEntry 28 }

fsMIDot1qFutureVlanPortGvrpLeaveEmptyRxCount OBJECT-TYPE
   SYNTAX      Counter32
   MAX-ACCESS  read-only
   STATUS      current
   DESCRIPTION
            " Number of Gvrp Leave Empty packets received on this port."
   ::= { fsMIDot1qFutureVlanPortEntry 29 }

fsMIDot1qFutureVlanPortGvrpEmptyTxCount OBJECT-TYPE
   SYNTAX      Counter32
   MAX-ACCESS  read-only
   STATUS      current
   DESCRIPTION
            " Number of Gvrp Empty packets transmitted by this port."
   ::= { fsMIDot1qFutureVlanPortEntry 30 }

fsMIDot1qFutureVlanPortGvrpEmptyRxCount OBJECT-TYPE
   SYNTAX      Counter32
   MAX-ACCESS  read-only
   STATUS      current
   DESCRIPTION
            " Number of Gvrp Empty packets received on this port."
   ::= { fsMIDot1qFutureVlanPortEntry 31 }

fsMIDot1qFutureVlanPortGvrpLeaveAllTxCount OBJECT-TYPE
   SYNTAX      Counter32
   MAX-ACCESS  read-only
   STATUS      current
   DESCRIPTION
            " Number of Gvrp Leave All packets transmitted by this port."
   ::= { fsMIDot1qFutureVlanPortEntry 32 }

fsMIDot1qFutureVlanPortGvrpLeaveAllRxCount OBJECT-TYPE
   SYNTAX      Counter32
   MAX-ACCESS  read-only
   STATUS      current
   DESCRIPTION
            " Number of Gvrp Leave All packets received on this port."
   ::= { fsMIDot1qFutureVlanPortEntry 33 }

fsMIDot1qFutureVlanPortGvrpDiscardCount OBJECT-TYPE
   SYNTAX      Counter32
   MAX-ACCESS  read-only
   STATUS      current
   DESCRIPTION
            " Number of Gvrp packets discarded in this port."
   ::= { fsMIDot1qFutureVlanPortEntry 34 }

fsMIDot1qFutureVlanPortFdbFlush  OBJECT-TYPE
   SYNTAX      TruthValue
   MAX-ACCESS  read-write
   STATUS      current
   DESCRIPTION
      "If this object is set as 'true', then all the dynamically 
       learnt MAC addresses on the specified interface are removed.
       After flush this object is set to 'false'"
   DEFVAL   { false }
   ::= { fsMIDot1qFutureVlanPortEntry 35 }

-- ----------------------------------------------------------------------------
-- JC Add allowed vlan list for trunk ports
-- ----------------------------------------------------------------------------
fsMIDot1qFutureVlanPortAllowedVlanList OBJECT-TYPE 
   SYNTAX      OCTET STRING (SIZE (0..512))
   MAX-ACCESS  read-write 
   STATUS      current 
   DESCRIPTION 
      "A string of octets containing one bit per vlan.
	   Specifies the vlans which the trunk port can add to.
	   By default all vlans are allowed to add the trunk ports.
	   
	   If a set of vlans are configured in the 'VlanList', the trunk port can
	   reside only in the configured vlan set. The native vlan or port vlan 
	   id must be in the list."

   ::= { fsMIDot1qFutureVlanPortEntry 36 } 
   
-- ------------------------------------------------------------------------- 
-- Future Vlan Mac Map Table 
-- ------------------------------------------------------------------------- 
 
fsMIDot1qFutureVlanPortMacMapTable OBJECT-TYPE 
   SYNTAX      SEQUENCE OF FsMIDot1qFutureVlanPortMacMapEntry 
   MAX-ACCESS  not-accessible 
   STATUS      current 
   DESCRIPTION 
      "A table that contains information on Vlan-MAC address 
      mapping. This table maintains context ID as one more 
      index to support Multiple Instances." 
   ::= { fsMIDot1qFutureVlan 4 } 

   -- 2014/09/05 Chung. System-wide config Mac Map.
fsMIDot1qFutureVlanPortMacMapEntry OBJECT-TYPE 
   SYNTAX      FsMIDot1qFutureVlanPortMacMapEntry 
   MAX-ACCESS  not-accessible 
   STATUS      current 
   DESCRIPTION 
      "Entry that contains Vlan-MAC address mapping." 
--   INDEX { fsMIDot1qFutureVlanPort, 
--           fsMIDot1qFutureVlanPortMacMapAddr } 
   INDEX { fsMIDot1qFutureVlanPortMacMapAddr } 

           ::= { fsMIDot1qFutureVlanPortMacMapTable 1 } 

-- 2014/09/05 Chung. No support Map name and McastBcastOption
FsMIDot1qFutureVlanPortMacMapEntry ::= 
   SEQUENCE { 
      fsMIDot1qFutureVlanPortMacMapAddr MacAddress, 
      fsMIDot1qFutureVlanPortMacMapVid VlanId, 
--      fsMIDot1qFutureVlanPortMacMapName DisplayString, 
--      fsMIDot1qFutureVlanPortMacMapMcastBcastOption INTEGER,
      fsMIDot1qFutureVlanPortMacMapRowStatus RowStatus 
   } 
 
fsMIDot1qFutureVlanPortMacMapAddr OBJECT-TYPE 
   SYNTAX      MacAddress  
   MAX-ACCESS  not-accessible 
   STATUS      current 
   DESCRIPTION 
      "The Mac address for which the Vlan mapping is present in the entry." 
   ::= { fsMIDot1qFutureVlanPortMacMapEntry 1 } 
 
fsMIDot1qFutureVlanPortMacMapVid OBJECT-TYPE 
   SYNTAX      VlanId 
   MAX-ACCESS  read-write 
   STATUS      current 
   DESCRIPTION 
      "The Vlan to which the mac address of this entry is mapped to." 
   ::= { fsMIDot1qFutureVlanPortMacMapEntry 2 } 
 
-- fsMIDot1qFutureVlanPortMacMapName OBJECT-TYPE 
--    SYNTAX      DisplayString 
--    MAX-ACCESS  read-write 
--    STATUS      current 
--    DESCRIPTION 
--       "The name given to the mac-vlan entry." 
--    ::= { fsMIDot1qFutureVlanPortMacMapEntry 3 } 
 
-- fsMIDot1qFutureVlanPortMacMapMcastBcastOption OBJECT-TYPE
--    SYNTAX      INTEGER { allow(1), supress(2) }
--    MAX-ACCESS  read-write
--    STATUS      current
--    DESCRIPTION 
--        "Configurable option for discarding/allowing Multicast/Broadcast Untagged
--         frames. The value allow (1) indicates that Multicast/Broadcast frames
--         with source Mac address as in the Mac Vlan entry will be dropped if mac
--         based vlan is enabled on that port.The value suppress (2) indicates that
--         Multicast/Broadcast frames with source Mac address as in the Mac Vlan
--         entry will be processed if mac based vlan is enabled on that port"
--     DEFVAL { allow }
--     ::= { fsMIDot1qFutureVlanPortMacMapEntry 4 }
 
fsMIDot1qFutureVlanPortMacMapRowStatus OBJECT-TYPE 
   SYNTAX      RowStatus 
   MAX-ACCESS  read-write 
   STATUS      current 
   DESCRIPTION 
      "The row status of the entry."  
   ::= { fsMIDot1qFutureVlanPortMacMapEntry 5 } 

-- ------------------------------------------------------------------------- 
-- Future Vlan Vlan-Fid Map Table 
-- ------------------------------------------------------------------------- 
 
fsMIDot1qFutureVlanFidMapTable OBJECT-TYPE 
   SYNTAX      SEQUENCE OF FsMIDot1qFutureVlanFidMapEntry 
   MAX-ACCESS  not-accessible 
   STATUS      current 
   DESCRIPTION 
      "This table contains information about the Filtering database 
      identifier (FID) used by vlan's to make forwarding decisions. Vlan's 
      can be mapped to use the same FID to share filtering information among 
      them. This will cause the mapped vlan's to operate in shared vlan 
      learning (SVL) mode. Vlan's mapped to a unique FID will operate in 
      independent vlan learning mode (IVL). A SET operation on this table is 
      allowed only when fsMIDot1qFutureVlanLearningMode is hybrid. By 
      default all vlan's will be mapped to the FID equal to their vlan id 
      when fsMIDot1qFutureVlanHybridTypeDefault is IVL. If the value of 
      fsMIDot1qFutureVlanHybridTypeDefault is SVL all vlan's are mapped to 
      filtering database id 1. This table maintains context ID as one more 
      index to support Multiple Instances."

   ::= { fsMIDot1qFutureVlan 5 } 
 
fsMIDot1qFutureVlanFidMapEntry OBJECT-TYPE 
   SYNTAX      FsMIDot1qFutureVlanFidMapEntry 
   MAX-ACCESS  not-accessible 
   STATUS      current 
   DESCRIPTION 
      "Entry mapping VlanId to Filtering database id."
   INDEX { fsMIDot1qFutureVlanContextId, fsMIDot1qFutureVlanIndex } 
   ::= { fsMIDot1qFutureVlanFidMapTable 1 } 
    
FsMIDot1qFutureVlanFidMapEntry ::= 
   SEQUENCE { 
      fsMIDot1qFutureVlanIndex Unsigned32,
      fsMIDot1qFutureVlanFid Unsigned32
   } 
   
 fsMIDot1qFutureVlanIndex OBJECT-TYPE
    SYNTAX      Unsigned32 (1..4094)
    MAX-ACCESS  read-only
    STATUS      current
    DESCRIPTION
        "VLAN ID for which filtering database information is available."
    ::= { fsMIDot1qFutureVlanFidMapEntry 1 }

 fsMIDot1qFutureVlanFid OBJECT-TYPE 
    SYNTAX      Unsigned32 (1..4094)
    MAX-ACCESS  read-write
    STATUS      current 
    DESCRIPTION 
       "The Filtering database id (FID) that will be used by the vlan."
    ::= { fsMIDot1qFutureVlanFidMapEntry 2 } 

 -- fsMIDot1qFutureVlanTunnelConfig group 
 
fsMIDot1qFutureVlanTunnelConfigTable OBJECT-TYPE
   SYNTAX       SEQUENCE OF FsMIDot1qFutureVlanTunnelConfigEntry
   MAX-ACCESS   not-accessible
   STATUS      deprecated
   DESCRIPTION
      "List of per virtual context Vlan Tunnel config parameters."
   ::= { fsMIDot1qFutureVlanTunnelConfig 1 }

fsMIDot1qFutureVlanTunnelConfigEntry OBJECT-TYPE
   SYNTAX       FsMIDot1qFutureVlanTunnelConfigEntry
   MAX-ACCESS   not-accessible
   STATUS      deprecated
   DESCRIPTION
      "Per virtual context Vlan Tunnel config parameters.

      "
      
   INDEX { fsMIDot1qFutureVlanContextId }
   ::= { fsMIDot1qFutureVlanTunnelConfigTable 1 }

FsMIDot1qFutureVlanTunnelConfigEntry ::=
   SEQUENCE {
       fsMIDot1qFutureVlanBridgeMode
           INTEGER,
       fsMIDot1qFutureVlanTunnelBpduPri
           Integer32
   }

fsMIDot1qFutureVlanBridgeMode OBJECT-TYPE
   SYNTAX      INTEGER {
                  customerBridge (1),
                  providerBridge (2),
                  providerCoreBridge (3),
                  providerEdgeBridge (4),
                  invalidBridgeMode  (5)
               }
   MAX-ACCESS  read-write
   STATUS      deprecated
   DESCRIPTION
      
      "This object indicates the Bridge mode of the switch.
      
      Setting this to 'customerBridge' means that the switch will operate 
      as a 802.1Q VLAN Bridge.

      Setting this to 'providerBridge' means that the Bridge will operate as 
      a normal Q-in-Q Bridge.

      Setting this to 'providerCoreBridge' means that the switch will operate 
      as a 802.1ad compliant provider bridge with only S-VLAN component.

      Setting this to 'providerEdgeBridge' means that the switch will operate 
      as a 802.1ad provider edge bridge with S-VLAN component and atleast 
      one C-VLAN component.
      
      For changing the bridge mode, GARP and STP modules should be shutdown."

   ::= { fsMIDot1qFutureVlanTunnelConfigEntry 1 } 


fsMIDot1qFutureVlanTunnelBpduPri OBJECT-TYPE
    SYNTAX      Integer32 (0..7)
    MAX-ACCESS  read-write
    STATUS      deprecated
    DESCRIPTION
        "Specifies the default User Priority for all the tunneled Layer 2
        BPDU's received on tunnel ports."
    DEFVAL { 7 }
    ::= { fsMIDot1qFutureVlanTunnelConfigEntry 2 }


-- ------------------------------------------------------------------------- 
-- Future Vlan Tunnel Table 
-- ------------------------------------------------------------------------- 
 
fsMIDot1qFutureVlanTunnelTable OBJECT-TYPE 
   SYNTAX      SEQUENCE OF FsMIDot1qFutureVlanTunnelEntry 
   MAX-ACCESS  not-accessible 
   STATUS      deprecated
   DESCRIPTION 
      "This table contains information about the fsMIDot1q tunnel ports. A 
      walk on this table will show only those interfaces that are configured 
      for tunneling.
      This table is supported only when the Bridge is configured in Provider 
      Bridge (Q-in-Q) mode.
      For Provider Core or Edge bridges, the tunnel protocol configuration
      objects are defined in fspb.mib."
   ::= { fsMIDot1qFutureVlanTunnelConfig 2 } 
 
fsMIDot1qFutureVlanTunnelEntry OBJECT-TYPE 
   SYNTAX      FsMIDot1qFutureVlanTunnelEntry 
   MAX-ACCESS  not-accessible 
   STATUS      deprecated
   DESCRIPTION 
      "Entry indicating the tunnel information of the port."
   INDEX { fsMIDot1qFutureVlanPort } 
   ::= { fsMIDot1qFutureVlanTunnelTable 1 } 
    
FsMIDot1qFutureVlanTunnelEntry ::= 
   SEQUENCE { 
      fsMIDot1qFutureVlanTunnelStatus EnabledStatus 
   } 
 
fsMIDot1qFutureVlanTunnelStatus OBJECT-TYPE 
   SYNTAX      EnabledStatus
   MAX-ACCESS  read-write
   STATUS      deprecated
   DESCRIPTION 
      "Indicates whether fsMIDot1qTunnelling is enabled or disabled on this 
      port. fsMIDot1qFutureVlanTunnelStatus can be set to `enabled` 
      only if the Bridge mode is set to be `Provider Bridge Mode` and 
      Future VLAN port type is set to 'accessPort'and GVRP,GMRP,STP Protocols
      are disabled on this port. All tunnel ports should be set as 
      untagged members for the access VLAN's configured for that customer."
   DEFVAL      { disabled }
   ::= { fsMIDot1qFutureVlanTunnelEntry 1 } 


-- ------------------------------------------------------------------------- 
-- Future Vlan Tunnel Protocol Table 
-- ------------------------------------------------------------------------- 
 
fsMIDot1qFutureVlanTunnelProtocolTable OBJECT-TYPE 
   SYNTAX      SEQUENCE OF FsMIDot1qFutureVlanTunnelProtocolEntry 
   MAX-ACCESS  not-accessible 
   STATUS      deprecated
   DESCRIPTION 
      "This table contains information/statistics about the customer STP 
      BPDU's being tunneled inside the service provider network. A walk on 
      this table will show only those interfaces in which tunneling of STP 
      BPDU's is enabled.
      This table is supported only when the Bridge is configured in Provider 
      Bridge (Q-in-Q) mode.
      For Provider Core or Edge bridges, the tunnel protocol configuration
      objects are defined in fspb.mib."

   ::= { fsMIDot1qFutureVlanTunnelConfig 3 } 
 
fsMIDot1qFutureVlanTunnelProtocolEntry OBJECT-TYPE 
   SYNTAX      FsMIDot1qFutureVlanTunnelProtocolEntry 
   MAX-ACCESS  not-accessible 
   STATUS      deprecated
   DESCRIPTION 
      "Entry indicating the tunneling of STP BPDU's on this port."
   INDEX { fsMIDot1qFutureVlanPort } 
   ::= { fsMIDot1qFutureVlanTunnelProtocolTable 1 } 
    
FsMIDot1qFutureVlanTunnelProtocolEntry ::= 
   SEQUENCE { 
      fsMIDot1qFutureVlanTunnelStpPDUs      EnabledStatus,
      fsMIDot1qFutureVlanTunnelStpPDUsRecvd Counter32,
      fsMIDot1qFutureVlanTunnelStpPDUsSent      Counter32,
      fsMIDot1qFutureVlanTunnelGvrpPDUs         EnabledStatus,
      fsMIDot1qFutureVlanTunnelGvrpPDUsRecvd    Counter32,
      fsMIDot1qFutureVlanTunnelGvrpPDUsSent     Counter32,
      fsMIDot1qFutureVlanTunnelIgmpPkts         EnabledStatus,
      fsMIDot1qFutureVlanTunnelIgmpPktsRecvd    Counter32,
      fsMIDot1qFutureVlanTunnelIgmpPktsSent     Counter32

   } 
 
fsMIDot1qFutureVlanTunnelStpPDUs OBJECT-TYPE 
   SYNTAX      EnabledStatus
   MAX-ACCESS  read-write
   STATUS      deprecated
   DESCRIPTION 
      "Indicates whether tunneling of STP BPDUs is enabled or not."
   DEFVAL      { disabled }
   ::= { fsMIDot1qFutureVlanTunnelProtocolEntry 1 } 

fsMIDot1qFutureVlanTunnelStpPDUsRecvd OBJECT-TYPE 
   SYNTAX      Counter32
   MAX-ACCESS  read-only
   STATUS      deprecated
   DESCRIPTION 
      "The number of tunneled ingress STP PDU's."
   ::= { fsMIDot1qFutureVlanTunnelProtocolEntry 2 } 

fsMIDot1qFutureVlanTunnelStpPDUsSent OBJECT-TYPE 
   SYNTAX      Counter32
   MAX-ACCESS  read-only
   STATUS      deprecated
   DESCRIPTION 
      "The number of tunneled egress STP PDU's."
   ::= { fsMIDot1qFutureVlanTunnelProtocolEntry 3 } 

fsMIDot1qFutureVlanTunnelGvrpPDUs OBJECT-TYPE 
   SYNTAX      EnabledStatus
   MAX-ACCESS  read-write
   STATUS      deprecated
   DESCRIPTION 
      "Indicates whether tunneling of GVRP BPDUs is enabled or not."
   DEFVAL      { enabled }
   ::= { fsMIDot1qFutureVlanTunnelProtocolEntry 4 } 

fsMIDot1qFutureVlanTunnelGvrpPDUsRecvd OBJECT-TYPE 
   SYNTAX      Counter32
   MAX-ACCESS  read-only
   STATUS      deprecated
   DESCRIPTION 
      "The number of tunneled ingress GVRP PDU's."
   ::= { fsMIDot1qFutureVlanTunnelProtocolEntry 5 } 

fsMIDot1qFutureVlanTunnelGvrpPDUsSent OBJECT-TYPE 
   SYNTAX      Counter32
   MAX-ACCESS  read-only
   STATUS      deprecated
   DESCRIPTION 
      "The number of tunneled egress GVRP PDU's."
   ::= { fsMIDot1qFutureVlanTunnelProtocolEntry 6 } 

fsMIDot1qFutureVlanTunnelIgmpPkts OBJECT-TYPE 
   SYNTAX      EnabledStatus
   MAX-ACCESS  read-write
   STATUS      deprecated
   DESCRIPTION 
      "Indicates whether tunneling of IGMP Packets is enabled or not."
   DEFVAL      { enabled }
   ::= { fsMIDot1qFutureVlanTunnelProtocolEntry 7 } 

fsMIDot1qFutureVlanTunnelIgmpPktsRecvd OBJECT-TYPE 
   SYNTAX      Counter32
   MAX-ACCESS  read-only
   STATUS      deprecated
   DESCRIPTION 
      "The number of tunneled ingress IGMP Packets."
   ::= { fsMIDot1qFutureVlanTunnelProtocolEntry 8 } 

fsMIDot1qFutureVlanTunnelIgmpPktsSent OBJECT-TYPE 
   SYNTAX      Counter32
   MAX-ACCESS  read-only
   STATUS      deprecated
   DESCRIPTION 
      "The number of tunneled egress IGMP Packets."
   ::= { fsMIDot1qFutureVlanTunnelProtocolEntry 9 } 

fsMIDot1qFutureVlanCounterTable OBJECT-TYPE
   SYNTAX      SEQUENCE OF FsMIDot1qFutureVlanCounterEntry
   MAX-ACCESS  not-accessible
   STATUS      current
   DESCRIPTION
             "The table contains the statistics on a per VLAN basis.
              It contains number of unicast, broadcast and unknown unicast
              packets flooded per VLAN."
   ::= { fsMIDot1qFutureVlan 6 }

fsMIDot1qFutureVlanCounterEntry OBJECT-TYPE
   SYNTAX      FsMIDot1qFutureVlanCounterEntry
   MAX-ACCESS  not-accessible
   STATUS      current
   DESCRIPTION
              "The entry contains the VLAN statistics"
   INDEX { fsMIDot1qFutureVlanContextId, fsMIDot1qFutureVlanIndex }
   ::= { fsMIDot1qFutureVlanCounterTable 1 }

FsMIDot1qFutureVlanCounterEntry ::=
   SEQUENCE {
             fsMIDot1qFutureVlanCounterRxUcast         Counter32,
             fsMIDot1qFutureVlanCounterRxMcastBcast    Counter32,
             fsMIDot1qFutureVlanCounterTxUnknUcast     Counter32,
             fsMIDot1qFutureVlanCounterTxUcast         Counter32,
             fsMIDot1qFutureVlanCounterTxBcast         Counter32,
             fsMIDot1qFutureVlanCounterStatus          EnabledStatus
            }

fsMIDot1qFutureVlanCounterRxUcast OBJECT-TYPE
   SYNTAX      Counter32
   MAX-ACCESS  read-only
   STATUS      current
   DESCRIPTION
            " Number of unicast packets received in this VLAN."
   ::= { fsMIDot1qFutureVlanCounterEntry 1 }

fsMIDot1qFutureVlanCounterRxMcastBcast OBJECT-TYPE
   SYNTAX      Counter32
   MAX-ACCESS  read-only
   STATUS      current
   DESCRIPTION
            " Number of multicast/broadcast packets received in this VLAN."
   ::= { fsMIDot1qFutureVlanCounterEntry 2 }

fsMIDot1qFutureVlanCounterTxUnknUcast OBJECT-TYPE
   SYNTAX      Counter32
   MAX-ACCESS  read-only
   STATUS      current
   DESCRIPTION
             " Number of unknown unicast packets flooded in this VLAN."
   ::= { fsMIDot1qFutureVlanCounterEntry 3 }

fsMIDot1qFutureVlanCounterTxUcast OBJECT-TYPE
   SYNTAX      Counter32
   MAX-ACCESS  read-only
   STATUS      current
   DESCRIPTION
            " Number of known unicast packets forwarded in this VLAN."
   ::= { fsMIDot1qFutureVlanCounterEntry 4 }

fsMIDot1qFutureVlanCounterTxBcast OBJECT-TYPE
   SYNTAX      Counter32
   MAX-ACCESS  read-only
   STATUS      current
   DESCRIPTION
            " Number of broadcast packets forwarded in this VLAN."
   ::= { fsMIDot1qFutureVlanCounterEntry 5 }

fsMIDot1qFutureVlanCounterStatus OBJECT-TYPE
   SYNTAX      EnabledStatus
   MAX-ACCESS  read-write
   STATUS      current
   DESCRIPTION
      "A Truth value indicating the statistics collection is enabled/disabled
       for this vlan.

       When statistics collection is set to disabled, Vlan stops collecting
       statistics on this specific vlan.
       When statistics collection is set to enabled, Vlan start collecting
       statistics on this specific vlan"
   DEFVAL   { disabled }       
   ::= {fsMIDot1qFutureVlanCounterEntry 6 }

fsMIDot1qFutureVlanUnicastMacControlTable OBJECT-TYPE
    SYNTAX      SEQUENCE OF FsMIDot1qFutureVlanUnicastMacControlEntry
    MAX-ACCESS  not-accessible
    STATUS      current
    DESCRIPTION
        "A table containing per VLAN Unicast MAC address control information. 
        The control information includes the status of unicast MAC address 
        learning as well as restricting the number of unique entries learnt to 
        a specified limit for the specified VLAN. The control set for the VLAN 
        is applicable only for the virtual context identified by the virtual 
        context identifier in this entry."
    ::= { fsMIDot1qFutureVlan 7 }

fsMIDot1qFutureVlanUnicastMacControlEntry OBJECT-TYPE
    SYNTAX      FsMIDot1qFutureVlanUnicastMacControlEntry
    MAX-ACCESS  not-accessible
    STATUS      current
    DESCRIPTION
       "Information controlling the number of distinct unicast MAC addresses 
        that can be learnt in a VLAN for a virtual context depending on whether
        learning is enabled or disabled for the VLAN. The virtual 
        context is identified by an unique virtual context identifier."
    INDEX { fsMIDot1qFutureVlanContextId, fsMIDot1qFutureVlanIndex }
    ::= { fsMIDot1qFutureVlanUnicastMacControlTable 1 }

FsMIDot1qFutureVlanUnicastMacControlEntry ::=
    SEQUENCE {
        fsMIDot1qFutureVlanUnicastMacLimit              Unsigned32,
        fsMIDot1qFutureVlanAdminMacLearningStatus       MacLearningStatus,
        fsMIDot1qFutureVlanOperMacLearningStatus        EnabledStatus
    }

fsMIDot1qFutureVlanUnicastMacLimit OBJECT-TYPE
    SYNTAX      Unsigned32 (0..4294967295)
    MAX-ACCESS  read-write
    STATUS      current
    DESCRIPTION
       "The Limiting value on the number of distinct unicast MAC addresses 
        learned in the VLAN in this specified virtual context.

        The lower limit and upper limit value that can be SET for this object
        is determined by the underlying hardware.

        Value 0 means unlimited and is the maximal limit the hardware supports."
    ::= { fsMIDot1qFutureVlanUnicastMacControlEntry 1 }

fsMIDot1qFutureVlanAdminMacLearningStatus OBJECT-TYPE
    SYNTAX      MacLearningStatus
    MAX-ACCESS  read-write
    STATUS      current
    DESCRIPTION
        "A Truth value used to configure the unicast MAC learning Admin status 
         for the VLAN in this specified virtual context to either be enabled (1)
         or disabled (2) or default (3), Configuring this object to default 
         behaviour is governed by value configured for dot1qFutureVlanGlobalMacLearningStatus."
    DEFVAL  { default }
    ::= { fsMIDot1qFutureVlanUnicastMacControlEntry 2 }

fsMIDot1qFutureVlanOperMacLearningStatus OBJECT-TYPE
    SYNTAX      EnabledStatus
    MAX-ACCESS  read-only
    STATUS      current
    DESCRIPTION
        "A Truth value indicating the unicast MAC learning enabled/disabled
         Operational status for the VLAN in this specified virtual context.
         If the VLAN is a Point-point service, then the Mac Learning Status 
         for this VLAN will always be disabled. If the VLAN is a Multipoint 
         service, then the Mac Learning status for this VLAN will take value 
         from Admin Mac Learning status."
    ::= { fsMIDot1qFutureVlanUnicastMacControlEntry 3 }

fsMIDot1qFutureGarpGlobalTrace OBJECT-TYPE
   SYNTAX        TruthValue
   MAX-ACCESS    read-write
   STATUS        current
   DESCRIPTION
      "Enable/Disable the global trace in GARP."
   ::= { fsMIDot1qFutureVlan 8 }

-- -------------------------------------------------------------
-- fsDot1qTpFdbTable
-- -------------------------------------------------------------

fsMIDot1qFutureVlanTpFdbTable OBJECT-TYPE
    SYNTAX      SEQUENCE OF FsMIDot1qFutureVlanTpFdbEntry
    MAX-ACCESS  not-accessible
    STATUS      current
    DESCRIPTION
        "A table that contains information about unicast entries
        for which the device has forwarding and/or filtering
        information.  This information is used by the
        transparent bridging function in determining how to
        propagate a received frame. This table maintains context ID
        as one more index to support Multiple Instances."
    REFERENCE
        "IEEE 802.1Q/D11 Section 12.7.7"
    ::= { fsMIDot1qFutureVlan 9 }

fsMIDot1qFutureVlanTpFdbEntry OBJECT-TYPE
    SYNTAX      FsMIDot1qFutureVlanTpFdbEntry
    MAX-ACCESS  not-accessible
    STATUS      current
    DESCRIPTION
        "Information about a specific unicast MAC address for
        which the device has some forwarding and/or filtering
        information."
    AUGMENTS { fsDot1qTpFdbEntry }
    ::= { fsMIDot1qFutureVlanTpFdbTable 1 }

FsMIDot1qFutureVlanTpFdbEntry ::=
    SEQUENCE {
        fsMIDot1qFutureVlanOldTpFdbPort
            Integer32,
        fsMIDot1qFutureConnectionIdentifier
            MacAddress
    }

fsMIDot1qFutureVlanOldTpFdbPort OBJECT-TYPE
    SYNTAX     Integer32 (0..65535)
    MAX-ACCESS  read-only
    STATUS      current
    DESCRIPTION
         "This object is useful for generating the source relearning trap.
         When a get is performed on this object, it returns the value of
         Zero(0), so that ISS walk doesn't break. It indicates the port 
         through which the mac-address was learnt previously, while generating
         the source relearning trap."
    ::= { fsMIDot1qFutureVlanTpFdbEntry 1 }

fsMIDot1qFutureConnectionIdentifier OBJECT-TYPE
    SYNTAX      MacAddress
    MAX-ACCESS  read-only
    STATUS      current
    DESCRIPTION
         "This object is to associate the backbone MAC address of the peer 
         backbone edge brige with customer Mac addresses that can be reached 
         through the peer backbone edge bridge."
    ::= { fsMIDot1qFutureVlanTpFdbEntry 2 }

fsMIDot1qFutureVlanWildCardTable OBJECT-TYPE
    SYNTAX      SEQUENCE OF FsMIDot1qFutureVlanWildCardEntry
    MAX-ACCESS  not-accessible
    STATUS      current
    DESCRIPTION
        "Wild card vlan (Id : 0xFFF) static filtering information 
        will be used for all Vlans for which there is no specific 
        Static filtering exists in dot1qStaticUnicastTable or 
        dot1qStaticMulticastTable."
    ::= { fsMIDot1qFutureVlan 10 }
    
fsMIDot1qFutureVlanWildCardEntry OBJECT-TYPE
    SYNTAX      FsMIDot1qFutureVlanWildCardEntry
    MAX-ACCESS  not-accessible
    STATUS      current
    DESCRIPTION
    "WildCard vlan filtering Information configured into device by
    management to which frames received from any port and for any
    vlan containing this wild card mac address as destination address
    and for which there is no static filtering information are allowed
    to be forwarded."

    INDEX { fsMIDot1qFutureVlanContextId,
            fsMIDot1qFutureVlanWildCardMacAddress
            }
    ::= { fsMIDot1qFutureVlanWildCardTable 1 }

FsMIDot1qFutureVlanWildCardEntry ::=
    SEQUENCE {
        fsMIDot1qFutureVlanWildCardMacAddress
        MacAddress,
        fsMIDot1qFutureVlanWildCardRowStatus
        RowStatus
    }

fsMIDot1qFutureVlanWildCardMacAddress OBJECT-TYPE
    SYNTAX      MacAddress
    MAX-ACCESS  not-accessible 
    STATUS      current
    DESCRIPTION
        "The destination MAC address in a frame to which this entry's 
        filtering information applies. This object must take the 
        value of a Unicast, Multicast or Broadcast address."
    ::= { fsMIDot1qFutureVlanWildCardEntry 1 }


fsMIDot1qFutureVlanWildCardRowStatus OBJECT-TYPE
   SYNTAX      RowStatus 
   MAX-ACCESS  read-write 
   STATUS      current 
   DESCRIPTION 
      "The row status of the entry."  
   ::= { fsMIDot1qFutureVlanWildCardEntry 2 }

fsMIDot1qFutureVlanWildCardPortTable OBJECT-TYPE
    SYNTAX      SEQUENCE OF FsMIDot1qFutureVlanWildCardPortEntry
    MAX-ACCESS  not-accessible
    STATUS      current
    DESCRIPTION
    "A Table containing ports to which frames received from a specific
    port and destined for fsMIDot1qFutureVlanWildCardMacAddress must be
    forwarded, if there is no specific static filtering entry exist
    for this MAC."
    ::= { fsMIDot1qFutureVlan 11 }
    
fsMIDot1qFutureVlanWildCardPortEntry OBJECT-TYPE
    SYNTAX      FsMIDot1qFutureVlanWildCardPortEntry
    MAX-ACCESS  not-accessible
    STATUS      current
    DESCRIPTION
    "WildCard vlan filtering Information configured into device by
    management specifying set of ports to which frames received
    from any port and for any vlan containing
    fsMIDot1qFutureVlanWildCardMacAddress mac address as destination
    address and for which there is no static filtering information
    are allowed to be forwarded."

    INDEX { fsMIDot1qFutureVlanContextId,
            fsMIDot1qFutureVlanWildCardMacAddress,
            fsDot1qTpPort }
    ::= { fsMIDot1qFutureVlanWildCardPortTable 1 }

FsMIDot1qFutureVlanWildCardPortEntry ::=
    SEQUENCE {
        fsMIDot1qFutureVlanIsWildCardEgressPort
        TruthValue
    }

fsMIDot1qFutureVlanIsWildCardEgressPort OBJECT-TYPE
    SYNTAX      TruthValue
    MAX-ACCESS  read-write
    STATUS      current
    DESCRIPTION
        "Indicates whether the port is an egress port of wildcard entry."
    ::= { fsMIDot1qFutureVlanWildCardPortEntry 1 }

-- -------------------------------------------------------------
-- The Static (Destination-Address Filtering) Database
-- -------------------------------------------------------------

fsMIDot1qFutureStaticUnicastExtnTable OBJECT-TYPE
    SYNTAX      SEQUENCE OF FsMIDot1qFutureStaticUnicastExtnEntry
    MAX-ACCESS  not-accessible
    STATUS      current
    DESCRIPTION
        "A table containing filtering information for Unicast
        MAC addresses for each Filtering Database, configured
        into the device by (local or network) management
        specifying the set of ports to which frames received
        from specific ports and containing specific unicast
        destination addresses are allowed to be forwarded.  A
        value of zero in this table as the port number from
        which frames with a specific destination address are
        received, is used to specify all ports for which there
        is no specific entry in this table for that particular
        destination address.  Entries are valid for unicast
        addresses only. This table maintains context ID as
    one more index to support Multiple Instances."
    REFERENCE
        "IEEE 802.1Q/D11 Section 12.7.7,
        ISO/IEC 15802-3 Section 7.9.1"
    ::= { fsMIDot1qFutureVlan 12 }

fsMIDot1qFutureStaticUnicastExtnEntry OBJECT-TYPE
    SYNTAX      FsMIDot1qFutureStaticUnicastExtnEntry
    MAX-ACCESS  not-accessible
    STATUS      current
    DESCRIPTION
        "Filtering information configured into the device by
        (local or network) management specifying the set of
        ports to which frames received from a specific port and
        containing a specific unicast destination address are
        allowed to be forwarded."
    AUGMENTS { fsDot1qStaticUnicastEntry }
    ::= { fsMIDot1qFutureStaticUnicastExtnTable 1 }

FsMIDot1qFutureStaticUnicastExtnEntry ::=
    SEQUENCE {
        fsMIDot1qFutureStaticConnectionIdentifier
            MacAddress
    }

fsMIDot1qFutureStaticConnectionIdentifier OBJECT-TYPE
    SYNTAX      MacAddress
    MAX-ACCESS  read-write
    STATUS      current
    DESCRIPTION
         "This object is to associate the backbone MAC address of the 
         peer backbone edge bridge with customer Mac addresses that 
         can be reached through the peer backbone edge bridge."
    ::= { fsMIDot1qFutureStaticUnicastExtnEntry 1 }

-- ------------------------------------------------------------------------- 
-- Future Vlan Subnet Map Table 
-- ------------------------------------------------------------------------- 
 
fsMIDot1qFutureVlanPortSubnetMapTable OBJECT-TYPE 
   SYNTAX      SEQUENCE OF FsMIDot1qFutureVlanPortSubnetMapEntry 
   MAX-ACCESS  not-accessible 
   STATUS      current 
   DESCRIPTION
      "Subnet based VLAN classification - The source IP-subnet address in
       the incoming packets is used to classify VLAN membership. 
       Subnet based VLAN is applied only on IP/ARP packets.
       This table contains information on Subnet-VlanId address mapping.
       This table maintains context ID as one more index to support 
       Multiple Instances. In case of BCM, the dot1qFutureVlanPort index 
       should always be 0 since BCM supports Subnet based VLAN 
       globally (not on per port)" 
   ::= { fsMIDot1qFutureVlan 13 } 
 
-- 2014/09/05 Chung. System-wide config Subnet Map. 
 fsMIDot1qFutureVlanPortSubnetMapEntry OBJECT-TYPE 
   SYNTAX      FsMIDot1qFutureVlanPortSubnetMapEntry 
   MAX-ACCESS  not-accessible 
   STATUS      current 
   DESCRIPTION 
      "Entry that contains Vlan-Subnet address mapping." 
--   INDEX { fsMIDot1qFutureVlanPort, fsMIDot1qFutureVlanPortSubnetMapAddr } 
  INDEX { fsMIDot1qFutureVlanPortSubnetMapAddr } 
 
   ::= { fsMIDot1qFutureVlanPortSubnetMapTable 1 } 

-- 2014/09/05 Chung. System-wide config Subnet Map. 
    FsMIDot1qFutureVlanPortSubnetMapEntry ::= 
   SEQUENCE { 
      fsMIDot1qFutureVlanPortSubnetMapAddr IpAddress, 
      fsMIDot1qFutureVlanPortSubnetMapVid VlanId, 
--      fsMIDot1qFutureVlanPortSubnetMapARPOption INTEGER,
      fsMIDot1qFutureVlanPortSubnetMapRowStatus RowStatus 
   } 
 
fsMIDot1qFutureVlanPortSubnetMapAddr OBJECT-TYPE 
   SYNTAX      IpAddress  
   MAX-ACCESS  not-accessible 
   STATUS      current 
   DESCRIPTION
      "The Source IP-Subnet address for which the Vlan mapping is present
       in the entry." 
   ::= { fsMIDot1qFutureVlanPortSubnetMapEntry 1 } 
 
fsMIDot1qFutureVlanPortSubnetMapVid OBJECT-TYPE 
   SYNTAX      VlanId 
   MAX-ACCESS  read-write 
   STATUS      current 
   DESCRIPTION 
      "The Vlan to which the source IP-Subnet address of this entry is mapped to." 
   ::= { fsMIDot1qFutureVlanPortSubnetMapEntry 2 } 
 
-- fsMIDot1qFutureVlanPortSubnetMapARPOption OBJECT-TYPE
--    SYNTAX      INTEGER { allow(1), suppress(2) }
--    MAX-ACCESS  read-write
--    STATUS      current
--    DESCRIPTION
--        "Configurable option for discarding/allowing ARP Untagged frames on
--         the vlan. The value allow (1) indicates that ARP frames with source 
--         IP-subnet address matching the dot1qFutureVlanPortSubnetMapEntry 
--         will be classified to vlan based on dot1qFutureVlanPortSubnetMapEntry.
--         The value suppress (2) indicates that ARP frames with source IP-Subnet
--         address matching the dot1qFutureVlanPortSubnetMapEntry will not be
--         classified to vlan based on dot1qFutureVlanPortSubnetMapEntry. The
--         VLAN classification will be based on next subsequent classification 
--         mechanism."
--     DEFVAL { allow }
--     ::= { fsMIDot1qFutureVlanPortSubnetMapEntry 3 }
 
fsMIDot1qFutureVlanPortSubnetMapRowStatus OBJECT-TYPE 
   SYNTAX      RowStatus 
   MAX-ACCESS  read-write 
   STATUS      current 
   DESCRIPTION 
      "The row status of the entry."  
   ::= { fsMIDot1qFutureVlanPortSubnetMapEntry 4 }

fsMIDot1qFutureVlanSwStatsEnabled OBJECT-TYPE
   SYNTAX      TruthValue 
   MAX-ACCESS  read-write 
   STATUS      current 
   DESCRIPTION 
   "If set to 'true', statistics collection will be done and stored in 
    software. This object can be set to 'true' only if the data switching
    is done by software.
    If set to 'false', the statistics collection will be done by the 
    hardware and will not be stored in software.
    If data switching is done by software, then the default value of this
    object will be 'true'. Otherwise, the default value will be 'false'.
    - It is recommended to configure this object before doing any port
    to virtual context mapping in the system."

   ::= { fsMIDot1qFutureVlan 14 }

-- ---------------------------------------------------------------------------- 
-- Future Vlan Extension Table
-- ---------------------------------------------------------------------------- 

fsMIDot1qFutureStVlanExtTable OBJECT-TYPE 
   SYNTAX      SEQUENCE OF FsMIDot1qFutureStVlanExtEntry 
   MAX-ACCESS  not-accessible 
   STATUS      current 
   DESCRIPTION 
        "An extension to fsDot1qVlanStaticTable VLAN table.
         This table contains the Private Vlan (PVLAN) related
         configurations."
   ::= { fsMIDot1qFutureVlan 15 } 
 
fsMIDot1qFutureStVlanExtEntry OBJECT-TYPE
   SYNTAX      FsMIDot1qFutureStVlanExtEntry
   MAX-ACCESS  not-accessible 
   STATUS      current 
   DESCRIPTION 
        "Each entry specifies the Private Vlan configuration done for
         a given Vlan."
   AUGMENTS { fsDot1qVlanStaticEntry }
   ::= { fsMIDot1qFutureStVlanExtTable 1 }
    
FsMIDot1qFutureStVlanExtEntry ::=
   SEQUENCE { 
      fsMIDot1qFutureStVlanPVlanType INTEGER,
      fsMIDot1qFutureStVlanPrimaryVid VlanIdOrNone,
      fsMIDot1qFutureStVlanFdbFlush TruthValue
   } 
 
fsMIDot1qFutureStVlanPVlanType OBJECT-TYPE
    SYNTAX      INTEGER {
                          normal (1),
                          primary (2),
                          isolated (3),
                          community (4) 
                        }
   MAX-ACCESS  read-write 
   STATUS      current 
   DESCRIPTION 
        "This object identifies the Private vlan type for this vlan.
         normal    - Vlan does not belong to any Private VLAN domain.
         primary   - Primary vlan in a Private VLAN domain.
         isolated  - Isolated vlan in a Private VLAN domain.
                     Devices connected to host ports of this vlan, can not
                     communicate with each other.
                     For every isolated vlan, one primary vlan id should be
                     configured.
         community - Community Vlan in a Private VLAN domain. Layer 2 
                     behaviour for a community and normal vlan is same.
                     For every community vlan, one primary vlan id should be
                     configured.
         Configuration of this object is allowed only when VLAN is not
         active."
    DEFVAL { normal }
    ::= { fsMIDot1qFutureStVlanExtEntry 1 }

fsMIDot1qFutureStVlanPrimaryVid OBJECT-TYPE
   SYNTAX      VlanIdOrNone
   MAX-ACCESS  read-write 
   STATUS      current 
   DESCRIPTION 
      "This object identifies the primary vlan assoicated with this
       vlan. 
       For primary and normal vlans, this object will have the value zero 
       and configuring this object to non-zero value will not be allowed for 
       them.
       For secondary vlans, this object identifies the associated
       primary vlan."
    DEFVAL { 0 }
   ::= { fsMIDot1qFutureStVlanExtEntry 2 }

fsMIDot1qFutureStVlanFdbFlush OBJECT-TYPE
   SYNTAX      TruthValue
   MAX-ACCESS  read-write
   STATUS      current
   DESCRIPTION
      "If this object is set as 'true', then all the dynamically
       learnt MAC addresses in this Vlan are removed.After flush
       this object is set to 'false'"
   DEFVAL  {false}
   ::= { fsMIDot1qFutureStVlanExtEntry 3 }

--table ends

fsMIDot1qVlanTraps OBJECT IDENTIFIER ::= { fsMIDot1qFutureVlanTraps 0 }

fsMIDot1qFutureMacThresholdTrap  NOTIFICATION-TYPE
    OBJECTS {
        fsMIDot1qFutureVlanContextName,
        fsMIDot1qFutureVlanIndex,
        fsMIDot1qFutureVlanUnicastMacLimit
        }
    STATUS     current
    DESCRIPTION
         "This trap is generated when the unicast mac limit threshold is 
         exceeded for a particular VLAN in a virtual context.The generated 
         trap will carry information regarding the Virtual context Id, 
         the Vlan Id whose Mac address limit has exceeded and the Mac 
         address threshold that was configured for this VLAN."
    ::= { fsMIDot1qVlanTraps 1 }

fsMIDot1qFutureSrcRelearnTrap NOTIFICATION-TYPE
    OBJECTS {
        fsMIDot1qFutureVlanContextName,
        fsMIDot1qFutureVlanFid,
        fsDot1qTpFdbPort,
        fsMIDot1qFutureVlanOldTpFdbPort
        }
    STATUS     current
    DESCRIPTION
         "This trap is generated whenever Source relearning happens in a VLAN.
          The generated trap will contain information about the VLAN for which 
          the Source relearning happened, MAC Address and port number through
          which this MAC address has been learnt now."
    ::= { fsMIDot1qVlanTraps 2 }

fsMIDot1qFutureSwitchMacLimitTrap  NOTIFICATION-TYPE
    OBJECTS {
        fsMIDot1qFutureVlanContextName,
        fsMIDot1qFutureUnicastMacLearningLimit
        }
    STATUS     current
    DESCRIPTION
         "This trap is generated when the unicast mac limit threshold is
         exceeded for a virtual context.The generated trap will carry
         information regarding the Virtual context Id, and the mac
         address threshold that was configured for this virtual context."
    ::= { fsMIDot1qVlanTraps 3 }

-- ----------------------------------------------------------------------------
-- Vlan Subnet Extension Table
-- ----------------------------------------------------------------------------

fsMIDot1qFutureVlanPortSubnetMapExtTable OBJECT-TYPE
   SYNTAX      SEQUENCE OF FsMIDot1qFutureVlanPortSubnetMapExtEntry
   MAX-ACCESS  not-accessible
   STATUS      current
   DESCRIPTION
      "Subnet based VLAN classification - The source IP-subnet address in
      the incoming packets is used to classify VLAN membership.
      Subnet based VLAN is applied only on IP/ARP packets.
      This table contains information on Subnet-VlanId address mapping."
   ::= { fsMIDot1qFutureVlan 16 }

-- 2014/09/05 Chung. System-wide config Subnet Map. 
fsMIDot1qFutureVlanPortSubnetMapExtEntry OBJECT-TYPE
   SYNTAX      FsMIDot1qFutureVlanPortSubnetMapExtEntry
   MAX-ACCESS  not-accessible
   STATUS      current
   DESCRIPTION
      "Entry that contains Vlan-Subnet address mapping."
--   INDEX { fsMIDot1qFutureVlanPort,
--           fsMIDot1qFutureVlanPortSubnetMapExtAddr,
--           fsMIDot1qFutureVlanPortSubnetMapExtMask }
   INDEX { fsMIDot1qFutureVlanPortSubnetMapExtAddr,
          fsMIDot1qFutureVlanPortSubnetMapExtMask }
   ::= { fsMIDot1qFutureVlanPortSubnetMapExtTable 1 }

-- 2014/09/05 Chung. System-wide config Subnet Map. 
FsMIDot1qFutureVlanPortSubnetMapExtEntry ::=
   SEQUENCE { 
      fsMIDot1qFutureVlanPortSubnetMapExtAddr IpAddress,
      fsMIDot1qFutureVlanPortSubnetMapExtMask IpAddress,
      fsMIDot1qFutureVlanPortSubnetMapExtVid  VlanId,
--      fsMIDot1qFutureVlanPortSubnetMapExtARPOption INTEGER,
      fsMIDot1qFutureVlanPortSubnetMapExtRowStatus RowStatus
   } 

fsMIDot1qFutureVlanPortSubnetMapExtAddr OBJECT-TYPE
   SYNTAX      IpAddress
   MAX-ACCESS  not-accessible
   STATUS      current 
   DESCRIPTION 
      "The Source IP address for which the Vlan mapping is present
       in the entry." 
   ::= { fsMIDot1qFutureVlanPortSubnetMapExtEntry 1 }       

fsMIDot1qFutureVlanPortSubnetMapExtMask OBJECT-TYPE
   SYNTAX      IpAddress
   MAX-ACCESS  not-accessible 
   STATUS      current 
   DESCRIPTION 
      "The Subnet Mask for which the Vlan mapping is present
       in the entry." 
   ::= { fsMIDot1qFutureVlanPortSubnetMapExtEntry 2 }

fsMIDot1qFutureVlanPortSubnetMapExtVid OBJECT-TYPE
   SYNTAX      VlanId 
   MAX-ACCESS  read-write 
   STATUS      current
   DESCRIPTION 
      "The Vlan to which the Source IP-Subnet address of this entry is mapped to." 
   ::= { fsMIDot1qFutureVlanPortSubnetMapExtEntry 3 }

-- fsMIDot1qFutureVlanPortSubnetMapExtARPOption OBJECT-TYPE
--    SYNTAX      INTEGER { allow(1), suppress(2) }
--    MAX-ACCESS  read-write
--    STATUS      current
--    DESCRIPTION 
--        "Configurable option for discarding/allowing ARP Untagged frames on
--         the vlan. The value allow (1) indicates that ARP frames with source 
--         IP-subnet address matching the fsMIDot1qFutureVlanPortSubnetMapExtEntry         will be classified to vlan based on 
--         fsMIDot1qFutureVlanPortSubnetMapExtEntry.The value suppress (2) 
--         indicates that ARP frames with source IP-Subnet address matching the 
--         fsMIDot1qFutureVlanPortSubnetMapExtEntry will not be classified to vlan
--         based on fsMIDot1qFutureVlanPortSubnetMapExtEntry. The VLAN 
--         classification will be based on next subsequent classification 
--         mechanism."
--     DEFVAL { allow }
--     ::= { fsMIDot1qFutureVlanPortSubnetMapExtEntry 4 }

fsMIDot1qFutureVlanPortSubnetMapExtRowStatus OBJECT-TYPE
   SYNTAX      RowStatus 
   MAX-ACCESS  read-write 
   STATUS      current 
   DESCRIPTION 
      "The row status of the entry."  
   ::= { fsMIDot1qFutureVlanPortSubnetMapExtEntry 5 }

-- ----------------------------------------------------------------------------
-- Port Vlan Extension Table
-- ----------------------------------------------------------------------------

fsMIDot1qFuturePortVlanExtTable OBJECT-TYPE 
   SYNTAX      SEQUENCE OF FsMIDot1qFuturePortVlanExtEntry 
   MAX-ACCESS  not-accessible 
   STATUS      current 
   DESCRIPTION 
        "An extension to fsDot1qVlanStaticPortConfigEntry VLAN table.
         This table contains the FDB Flush related
         configurations."
   ::= { fsMIDot1qFutureVlan 17 } 
 
fsMIDot1qFuturePortVlanExtEntry OBJECT-TYPE
   SYNTAX      FsMIDot1qFuturePortVlanExtEntry
   MAX-ACCESS  not-accessible 
   STATUS      current 
   DESCRIPTION 
        "Each entry specifies the Vlan configuration done for
         a given Vlan and Port."
   AUGMENTS { fsDot1qVlanStaticPortConfigEntry }
   ::= { fsMIDot1qFuturePortVlanExtTable 1 }
    
FsMIDot1qFuturePortVlanExtEntry ::=
   SEQUENCE { 
      fsMIDot1qFuturePortVlanFdbFlush TruthValue
   }

fsMIDot1qFuturePortVlanFdbFlush OBJECT-TYPE
   SYNTAX      TruthValue
   MAX-ACCESS  read-write
   STATUS      current
   DESCRIPTION
      "If this object is set to 'true', then all the dynamically 
       learnt MAC addresses on the specified interface and vlan 
       are removed.After flush this object is set to 'false'"
   DEFVAL  {false}
   ::= { fsMIDot1qFuturePortVlanExtEntry 1 }
 
END

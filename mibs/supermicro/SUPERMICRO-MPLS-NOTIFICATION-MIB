-- Copyright (C) 2008-2014 Super Micro Computer Inc. All Rights Reserved

-- $Id: fsmpnotif.mib,v 1.4 2012/09/07 09:52:05 siva Exp $
SUPERMICRO-MPLS-NOTIFICATION-MIB DEFINITIONS ::= BEGIN

IMPORTS
    DisplayString
        FROM SNMPv2-TC               -- [RFC2579]
    MODULE-IDENTITY, OBJECT-TYPE, enterprises, NOTIFICATION-TYPE
        FROM SNMPv2-SMI
    TruthValue
        FROM SNMPv2-TC
    PwIndexType
        FROM PW-TC-STD-MIB;

fsMplsNotificationMIB MODULE-IDENTITY
    LAST-UPDATED "201209050000Z"   
    ORGANIZATION "Super Micro Computer Inc."
    CONTACT-INFO "support@Supermicro.com" 

    DESCRIPTION  "All rights reserved"
    REVISION     "201209050000Z" 
    DESCRIPTION  "The Proprietary MIB for MPLS NOTIFICATION module"

    ::= { enterprises supermicro-computer-inc(10876) super-switch(101) basic(1) futureMpls (13) 10}

fsMplsNotifications            OBJECT IDENTIFIER ::= { fsMplsNotificationMIB 0 }
fsMplsNotifConfig              OBJECT IDENTIFIER ::= { fsMplsNotificationMIB 1 }

-- Definitions of Pw Notification config objects - Starts

fsMplsPwStatusNotifEnable OBJECT-TYPE
    SYNTAX      TruthValue
    MAX-ACCESS  read-write
    STATUS      current
    DESCRIPTION
         "If this object is set to true(1), then it enables
          the generation of pseudowire status notifications; 
          otherwise these notifications are not generated."
    DEFVAL { false }
    ::= { fsMplsNotifConfig 1 }

fsMplsPwOAMStatusNotifEnable OBJECT-TYPE
    SYNTAX      TruthValue
    MAX-ACCESS  read-write
    STATUS      deprecated
    DESCRIPTION
         "If this object is set to true(1), then it enables
          the generation of pw OAM Up and pw OAM Down
          notifications; otherwise these notifications are not
          generated. This object is not supported."
    DEFVAL { false } 
    ::= { fsMplsNotifConfig 2 }
-- Definitions of Pw Notification config objects - Ends

-- Definitions of Pw Notification objects - Starts
 fsMplsPwNotifStatusStr OBJECT-TYPE   
     SYNTAX       DisplayString(SIZE(1..50))
     MAX-ACCESS   accessible-for-notify
     STATUS       current
     DESCRIPTION
         "A human-readable text string indicating the details of 
          information sent in the notification message.

	  'PseudowireStatusUp' will be indicated when the pseudowire status is UP.
	  'PseudowireStatusDown' will be indicated when the pseudowire status is DOWN."

     ::= { fsMplsNotifications 1 }

 fsMplsPwIndex    OBJECT-TYPE   
     SYNTAX       PwIndexType
     MAX-ACCESS   accessible-for-notify
     STATUS       current
     DESCRIPTION
	   "pwIndex is of type not-accessible and it cannot be used as object 
	    for notifications. So this object is defined to use for notifications. 
	    The value of this object is same as that of pwIndex."

     ::= { fsMplsNotifications 2 }

fsMplsPwOamStatus NOTIFICATION-TYPE
    OBJECTS {
             fsMplsPwIndex,
             fsMplsPwNotifStatusStr
            } 
   STATUS   deprecated
   DESCRIPTION
        "This notification is generated when OAM is enabled/disabled/when an OAM message is 
	 received before VCCV capablility selection. 
         fsMplsPwNotifStatusStr is a string that denotes the details of OAM status on a 
	 particular pseudowire. This object is not supported." 
    ::= { fsMplsNotifications 3 }  

fsMplsPwStatus NOTIFICATION-TYPE
    OBJECTS {
             fsMplsPwIndex,
             fsMplsPwNotifStatusStr
            }
   STATUS   current
   DESCRIPTION
        "This notification is generated when Pseudowire is UP/DOWN. 
         fsMplsPwNotifStatusStr is a string that denotes the details of Pseudowire status"
    ::= { fsMplsNotifications 4 }

-- Definitions of Pw Notification - Ends

END

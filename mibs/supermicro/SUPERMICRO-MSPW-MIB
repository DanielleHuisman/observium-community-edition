-- Copyright (C) 2008-2014 Super Micro Computer Inc. All Rights Reserved

-- $Id: fsmspw.mib,v 1.2 2012/09/07 09:52:05 siva Exp $

SUPERMICRO-MSPW-MIB DEFINITIONS ::= BEGIN

IMPORTS
    PwIndexType, PwOperStatusTC
           FROM PW-TC-STD-MIB
    MODULE-IDENTITY, OBJECT-TYPE, enterprises,Unsigned32 
           FROM SNMPv2-SMI
    RowStatus
           FROM SNMPv2-TC;
   
fsMspwMIB MODULE-IDENTITY
    LAST-UPDATED "201209050000Z"   
    ORGANIZATION "Super Micro Computer Inc."
    CONTACT-INFO "support@Supermicro.com" 

    DESCRIPTION  "All rights reserved"
    REVISION     "201209050000Z"    --  15 March 2006 10:00:00 IST
    DESCRIPTION  "The Proprietary MIB for MSPW module"

    ::= { enterprises supermicro-computer-inc(10876) super-switch(101) extended(2) 57} 

fsMsPwConfigObjects               OBJECT IDENTIFIER ::= { fsMspwMIB 1 }

-- Multi Segment Pseudo Wire Table(MS-PW) starts


fsMsPwMaxEntries OBJECT-TYPE
    SYNTAX        Unsigned32 (1..32766)
    MAX-ACCESS    read-write
    STATUS        current
    DESCRIPTION
         "The maximum number of MS-PW entries are supported."
    DEFVAL        { 64 }
    ::= { fsMsPwConfigObjects 1 }

fsMsPwConfigTable OBJECT-TYPE 
    SYNTAX          SEQUENCE OF FsMsPwConfigEntry 
    MAX-ACCESS      not-accessible 
    STATUS          current 
    DESCRIPTION     
      "This table specifies information for configuring
      and monitoring Multi Segment Pseudo Wire at S-PE." 
    ::= { fsMsPwConfigObjects 2 } 
       
fsMsPwConfigEntry OBJECT-TYPE 
    SYNTAX          FsMsPwConfigEntry 
    MAX-ACCESS      not-accessible 
    STATUS          current 
    DESCRIPTION     
      
      "A row in this table represents Pseudo Wire cross connection 
      between packet switched network domains. It is indexed by  
      fsMsPwIndex1 and fsMsPwIndex2 which uniquely identifies
      a single Pseudo wire cross connection.   
      
      None of the read-create objects values can be 
      changed when fsMsPwRowStatus is in the active(1) 
      state. Changes are allowed when the fsMsPwRowStatus 
      is in notInService(2) or notReady(3) states only.   
      If the operator need to change one of the values 
      for an active row the fsMsPwRowStatus should be 
      first changed to notInService(2), the objects may 
      be changed now, and later to active(1) in order to 
      re-initiate the signaling process with the new 
      values in effect.  
      "  
    INDEX   { fsMsPwIndex1,fsMsPwIndex2} 
    ::= { fsMsPwConfigTable 1 } 
               
FsMsPwConfigEntry ::= SEQUENCE { 
    fsMsPwIndex1  	        PwIndexType,
    fsMsPwIndex2                PwIndexType,
    fsMsPwOperStatus            PwOperStatusTC, 
    fsMsPwRowStatus             RowStatus
  } 

fsMsPwIndex1   OBJECT-TYPE 
    SYNTAX          PwIndexType
    MAX-ACCESS      not-accessible 
    STATUS          current 
    DESCRIPTION     
      "Primay Index for the conceptual row identifying received pseudo wire at S-PE.
       It is referred to a received pwIndex in the pwTable" 
    ::= { fsMsPwConfigEntry 1 } 

fsMsPwIndex2  OBJECT-TYPE 
    SYNTAX          PwIndexType
    MAX-ACCESS      not-accessible 
    STATUS          current 
    DESCRIPTION     
      " Seconday Index for the conceptual row identifying the transmitted pseudowire at S-PE.
       It is referred to a transmitted pwIndex in the pwTable " 
    ::= { fsMsPwConfigEntry 2 } 

fsMsPwOperStatus  OBJECT-TYPE  
   SYNTAX        PwOperStatusTC  
   MAX-ACCESS    read-only  
   STATUS        current  
   DESCRIPTION  
        "This object indicates the operational status of the PW cross
         connection,It is said to be UP only when both segment of the 
         cross connected pseudo wire is UP,otherwise it will be Down.  
         "  
   ::= { fsMsPwConfigEntry 3 }  

fsMsPwRowStatus OBJECT-TYPE 
    SYNTAX          RowStatus
    MAX-ACCESS      read-write
    STATUS          current 
    DESCRIPTION     
      "For creating, modifying, and deleting this row. 
       For making a row available for use [Active State],
       valid PWIndices are Mandatory."
    ::= { fsMsPwConfigEntry 4 } 


-- Multi Segment Pseudo Wire Table(MS-PW) ends 

END

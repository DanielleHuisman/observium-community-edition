-- Copyright (C) 2008-2014 Super Micro Computer Inc. All Rights Reserved

-- $Id: fso3test.mib,v 1.5 2012/09/07 09:52:05 siva Exp $

SUPERMICRO-OSPFV3-TEST-MIB DEFINITIONS ::= BEGIN

-- Enterprises MIB for testing OSPFv3.


   IMPORTS
      MODULE-IDENTITY, OBJECT-TYPE, 
      enterprises 
                                                 FROM SNMPv2-SMI
      RowStatus
                                                 FROM SNMPv2-TC
      InetAddressType, InetAddress, InetAddressPrefixLength 
      			              		FROM INET-ADDRESS-MIB
      InterfaceIndex	
      						FROM IF-MIB;
                                                 
--    org         OBJECT IDENTIFIER ::=  { iso(1) 3 }
--    dod         OBJECT IDENTIFIER ::=  { org 6 }
--    internet    OBJECT IDENTIFIER ::=  { dod 1 }
--    mgmt        OBJECT IDENTIFIER ::=  { internet 2 }
--    private     OBJECT IDENTIFIER ::= { internet 4 }
--    enterprises OBJECT IDENTIFIER ::=  { iso(1) org(3) dod(6) internet(1)  private(4) 1 }
--      mib-2      OBJECT IDENTIFIER ::= { mgmt 1 }


futOspfv3TestGroup  MODULE-IDENTITY
      LAST-UPDATED "201209050000Z" 
      ORGANIZATION "Super Micro Computer Inc."
      CONTACT-INFO "support@Supermicro.com"
      DESCRIPTION
          " OSPFv3 test MIB"
      REVISION "201209050000Z"
      DESCRIPTION
          " OSPFv3 test MIB"

         ::= { enterprises supermicro-computer-inc(10876) super-switch(101) basic(1) 301 }

--future              OBJECT IDENTIFIER ::= { enterprises supermicro-computer-inc(10876) super-switch(101) futuresoftware(1)}
--futOspfv3TestGroup     OBJECT IDENTIFIER ::= { future 301 }
--::=  { 1 3 6 1 4 1 2076 301}


    -- Future OSPFv3 Test Interface Table 
 
    futOspfv3TestIfTable OBJECT-TYPE 
            SYNTAX          SEQUENCE OF FutOspfv3TestIfEntry 
            MAX-ACCESS      not-accessible 
            STATUS          current 
            DESCRIPTION 
                "The OSPFv3 Interface Table describes the  inter- 
                faces from the viewpoint of OSPFv3." 
            REFERENCE 
                "OSPF Version 2, Appendix C.3  Router  interface 
                parameters" 
            ::= { futOspfv3TestGroup 1 } 
 
    futOspfv3TestIfEntry OBJECT-TYPE 
            SYNTAX          FutOspfv3TestIfEntry 
            MAX-ACCESS      not-accessible 
            STATUS          current 
            DESCRIPTION 
                "The OSPFv3 Interface Entry describes one  inter- 
                face from the viewpoint of OSPFv3." 
            INDEX           { futOspfv3TestIfIndex } 
            ::= { futOspfv3TestIfTable 1 } 
 
 
    FutOspfv3TestIfEntry ::= SEQUENCE { 
            futOspfv3TestIfIndex 
                    InterfaceIndex, 
   	    futOspfv3TestDemandTraffic
	    	    INTEGER
            } 
 
    futOspfv3TestIfIndex OBJECT-TYPE 
            SYNTAX          InterfaceIndex 
            MAX-ACCESS      not-accessible 
            STATUS          current 
            DESCRIPTION 
                "The interface index of this OSPFv3 interface. 
                 It corresponds to the interface index of the 
                 IPv6 interface on which OSPFv3 is configured." 
            ::= { futOspfv3TestIfEntry 1 } 
   futOspfv3TestDemandTraffic OBJECT-TYPE
       SYNTAX   INTEGER {
                   open (1),
                   close (2)
                   }
       MAX-ACCESS  read-write
       STATUS      current
       DESCRIPTION
           "Simulation for indicating the data traffic open/close 
	    indication from lower layer for demand circuit
	    neighbor probing feature."
       DEFVAL { close }
       ::=  { futOspfv3TestIfEntry 2 }



--  Future OSPF External Route Table
   futOspfv3ExtRouteTable OBJECT-TYPE
       SYNTAX 	SEQUENCE OF FutOspfv3ExtRouteEntry
       MAX-ACCESS not-accessible
       STATUS     current
       DESCRIPTION
           "The OSPFv3 External Route Table describes the  
              External Routes information."
       ::=  { futOspfv3TestGroup 2 }
   
   futOspfv3ExtRouteEntry OBJECT-TYPE
       SYNTAX FutOspfv3ExtRouteEntry
       MAX-ACCESS not-accessible
       STATUS      current
       DESCRIPTION
           "The OSPFv3 External Route Table describes the  
              External Routes information."
       INDEX { futOspfv3ExtRouteDestType, 
	       futOspfv3ExtRouteDest,
	       futOspfv3ExtRoutePfxLength,
	       futOspfv3ExtRouteNextHopType,  
	       futOspfv3ExtRouteNextHop
	}
       ::=  { futOspfv3ExtRouteTable 1 }
   
   FutOspfv3ExtRouteEntry ::= SEQUENCE {
       futOspfv3ExtRouteDestType        InetAddressType,
       futOspfv3ExtRouteDest            InetAddress,
       futOspfv3ExtRoutePfxLength       InetAddressPrefixLength,
       futOspfv3ExtRouteNextHopType     InetAddressType,
       futOspfv3ExtRouteNextHop         InetAddress,
       futOspfv3ExtRouteStatus          RowStatus
       }

   futOspfv3ExtRouteDestType OBJECT-TYPE 
       SYNTAX          InetAddressType 
       MAX-ACCESS      not-accessible 
       STATUS          current 
       DESCRIPTION 
           "The prefix type of futOspfv3ExtRouteDestType. Only 
           IPv6 addresses are expected." 
       ::= { futOspfv3ExtRouteEntry 1 } 

   futOspfv3ExtRouteDest OBJECT-TYPE
       SYNTAX      InetAddress (SIZE(16))
       MAX-ACCESS  not-accessible
       STATUS      current
       DESCRIPTION
           " The Desitnation IPv6 Address of this route."
       ::=  { futOspfv3ExtRouteEntry 2 }
   
   futOspfv3ExtRoutePfxLength OBJECT-TYPE
       SYNTAX      InetAddressPrefixLength
       MAX-ACCESS  not-accessible
       STATUS      current
       DESCRIPTION
           " Indicates the prefix length of the destination Address."
       ::=  { futOspfv3ExtRouteEntry 3 }
   
   futOspfv3ExtRouteNextHopType OBJECT-TYPE 
       SYNTAX          InetAddressType 
       MAX-ACCESS      not-accessible 
       STATUS          current 
       DESCRIPTION 
           "The prefix type offutOspfv3ExtRouteNextHopType. Only 
           IPv6 addresses are expected." 
       ::= { futOspfv3ExtRouteEntry 4 } 

   futOspfv3ExtRouteNextHop OBJECT-TYPE
       SYNTAX      InetAddress (SIZE(16))
       MAX-ACCESS  not-accessible
       STATUS      current
       DESCRIPTION
           " Next Hop IPv6 Address for this route. For direct routes it has the
           value ::0."
       ::=  { futOspfv3ExtRouteEntry 5 }

   futOspfv3ExtRouteStatus OBJECT-TYPE
       SYNTAX RowStatus
       MAX-ACCESS read-create
       STATUS current
       DESCRIPTION
           "The variable dispalys the status of the entry. Only createAndGo (4) and Destroy (6) are supported"
       ::=  { futOspfv3ExtRouteEntry 6 }

END

-- Copyright (C) 2008-2014 Super Micro Computer Inc. All Rights Reserved

-- $Id: fsmitos3.mib,v 1.2 2012/09/07 09:52:05 siva Exp $

SUPERMICRO-OSPFV3MI-TEST-MIB DEFINITIONS ::= BEGIN

-- Enterprises MIB for testing OSPFv3.


   IMPORTS
      MODULE-IDENTITY, OBJECT-TYPE, Integer32, enterprises 
                                                 FROM SNMPv2-SMI
      RowStatus
                                                 FROM SNMPv2-TC
      InetAddressType, InetAddress, InetAddressPrefixLength 
      			              		FROM INET-ADDRESS-MIB
      InterfaceIndex	
      						FROM IF-MIB
      fsMIStdOspfv3ContextId  
				                FROM SUPERMICRO-MISTDOSPFV3-MIB; 
                                                 
--    org         OBJECT IDENTIFIER ::=  { iso(1) 3 }
--    dod         OBJECT IDENTIFIER ::=  { org 6 }
--    internet    OBJECT IDENTIFIER ::=  { dod 1 }
--    mgmt        OBJECT IDENTIFIER ::=  { internet 2 }
--    private     OBJECT IDENTIFIER ::= { internet 4 }
--    enterprises OBJECT IDENTIFIER ::=  { iso(1) org(3) dod(6) internet(1)  private(4) 1 }
--      mib-2      OBJECT IDENTIFIER ::= { mgmt 1 }


fsMIOspfv3TestGroup  MODULE-IDENTITY
        LAST-UPDATED "201209050000Z" 
        ORGANIZATION "Super Micro Computer Inc."
        CONTACT-INFO "support@Supermicro.com"
      DESCRIPTION
          " OSPFv3 MI test MIB"
      REVISION "201209050000Z"
      DESCRIPTION
          " OSPFv3 MI test MIB"

         ::= { enterprises supermicro-computer-inc(10876) super-switch(101) basic(2) fsMIOspfv3 (24) 100 }

-- fsMI                   OBJECT IDENTIFIER ::= { enterprises 2076}
-- fsMIOspfv3             OBJECT IDENTIFIER ::= { fsMI 90 } 
-- fsMIOspfv3TestGroup    OBJECT IDENTIFIER ::= { fsMIOspfv3 100 }
-- ::=  { 1 3 6 1 4 1 2076 90 100}


    -- Future OSPFv3 Test Interface Table 
 
    fsMIOspfv3TestIfTable OBJECT-TYPE 
        SYNTAX          SEQUENCE OF FsMIOspfv3TestIfEntry 
        MAX-ACCESS      not-accessible 
        STATUS          current 
        DESCRIPTION 
            "The OSPFv3 Interface Table describes the  inter- 
            faces from the viewpoint of OSPFv3." 
        REFERENCE 
            "OSPF Version 2, Appendix C.3  Router  interface 
            parameters" 
      ::= { fsMIOspfv3TestGroup 1 } 
 
    fsMIOspfv3TestIfEntry OBJECT-TYPE 
        SYNTAX          FsMIOspfv3TestIfEntry 
        MAX-ACCESS      not-accessible 
        STATUS          current 
        DESCRIPTION 
            "The OSPFv3 Interface Entry describes one  inter- 
            face from the viewpoint of OSPFv3." 
        INDEX { fsMIOspfv3TestIfIndex } 
      ::= { fsMIOspfv3TestIfTable 1 } 
 
 
    FsMIOspfv3TestIfEntry ::= SEQUENCE { 
        fsMIOspfv3TestIfIndex 
            InterfaceIndex, 
   	    fsMIOspfv3TestDemandTraffic
	        INTEGER,
        fsMIOspfv3TestIfContextId
            Integer32
        } 
 
    fsMIOspfv3TestIfIndex OBJECT-TYPE 
        SYNTAX          InterfaceIndex 
        MAX-ACCESS      not-accessible 
        STATUS          current 
        DESCRIPTION 
            "The interface index of this OSPFv3 interface. 
            It corresponds to the interface index of the 
            IPv6 interface on which OSPFv3 is configured." 
      ::= { fsMIOspfv3TestIfEntry 1 } 
      
    fsMIOspfv3TestDemandTraffic OBJECT-TYPE
        SYNTAX   INTEGER {
                   open (1),
                   close (2)
                   }
        MAX-ACCESS  read-write
        STATUS      current
        DESCRIPTION
            "Simulation for indicating the data traffic open/close 
	     indication from lower layer for demand circuit
	     neighbor probing feature."
        DEFVAL { close }
      ::=  { fsMIOspfv3TestIfEntry 2 }

    fsMIOspfv3TestIfContextId OBJECT-TYPE
        SYNTAX          Integer32
	    MAX-ACCESS      read-only
	    STATUS          current
	    DESCRIPTION
	        "A 32-bit unique context id for each entry. 
             Minimum value is 0 and Maximum depends upon system 
             configuration. Default value is 0 which will be initialized 
             during bootup"
      ::= { fsMIOspfv3TestIfEntry 3 }

--  Future OSPF External Route Table

    fsMIOspfv3ExtRouteTable OBJECT-TYPE
        SYNTAX 	SEQUENCE OF FsMIOspfv3ExtRouteEntry
        MAX-ACCESS not-accessible
        STATUS     current
        DESCRIPTION
            "The OSPFv3 External Route Table describes the  
            External Routes information."
      ::=  { fsMIOspfv3TestGroup 2 }
   
    fsMIOspfv3ExtRouteEntry OBJECT-TYPE
        SYNTAX FsMIOspfv3ExtRouteEntry
        MAX-ACCESS not-accessible
        STATUS      current
        DESCRIPTION
            "The OSPFv3 External Route Table describes the  
            External Routes information."
        INDEX { fsMIStdOspfv3ContextId,
                fsMIOspfv3ExtRouteDestType, 
	        fsMIOspfv3ExtRouteDest,
	        fsMIOspfv3ExtRoutePfxLength,
	        fsMIOspfv3ExtRouteNextHopType,  
	        fsMIOspfv3ExtRouteNextHop
	      }
      ::=  { fsMIOspfv3ExtRouteTable 1 }
   
    FsMIOspfv3ExtRouteEntry ::= SEQUENCE {
        fsMIOspfv3ExtRouteDestType        InetAddressType,
        fsMIOspfv3ExtRouteDest            InetAddress,
        fsMIOspfv3ExtRoutePfxLength       InetAddressPrefixLength,
        fsMIOspfv3ExtRouteNextHopType     InetAddressType,
        fsMIOspfv3ExtRouteNextHop         InetAddress,
        fsMIOspfv3ExtRouteStatus          RowStatus
        }

    fsMIOspfv3ExtRouteDestType OBJECT-TYPE 
        SYNTAX          InetAddressType 
        MAX-ACCESS      not-accessible 
        STATUS          current 
        DESCRIPTION 
            "The prefix type of fsMIOspfv3ExtRouteDestType. Only 
            IPv6 addresses are expected." 
      ::= { fsMIOspfv3ExtRouteEntry 1 } 

    fsMIOspfv3ExtRouteDest OBJECT-TYPE
        SYNTAX      InetAddress (SIZE(16))
        MAX-ACCESS  not-accessible
        STATUS      current
        DESCRIPTION
            " The Desitnation IPv6 Address of this route."
      ::=  { fsMIOspfv3ExtRouteEntry 2 }
   
    fsMIOspfv3ExtRoutePfxLength OBJECT-TYPE
        SYNTAX      InetAddressPrefixLength
        MAX-ACCESS  not-accessible
        STATUS      current
        DESCRIPTION
            " Indicates the prefix length of the destination Address."
      ::=  { fsMIOspfv3ExtRouteEntry 3 }
   
    fsMIOspfv3ExtRouteNextHopType OBJECT-TYPE 
        SYNTAX          InetAddressType 
        MAX-ACCESS      not-accessible 
        STATUS          current 
        DESCRIPTION 
            "The prefix type of fsMIOspfv3ExtRouteNextHopType. Only 
            IPv6 addresses are expected." 
      ::= { fsMIOspfv3ExtRouteEntry 4 } 

    fsMIOspfv3ExtRouteNextHop OBJECT-TYPE
        SYNTAX      InetAddress (SIZE(16))
        MAX-ACCESS  not-accessible
        STATUS      current
        DESCRIPTION
            " Next Hop IPv6 Address for this route. For direct routes it has the
            value ::0."
      ::=  { fsMIOspfv3ExtRouteEntry 5 }

    fsMIOspfv3ExtRouteStatus OBJECT-TYPE
        SYNTAX RowStatus
        MAX-ACCESS read-create
        STATUS current
        DESCRIPTION
            "The variable dispalys the status of the entry. Only createAndGo (4) and Destroy (6) are supported"
      ::=  { fsMIOspfv3ExtRouteEntry 6 }

END

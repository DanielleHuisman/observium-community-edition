-- Copyright (C) 2008-2014 Super Micro Computer Inc. All Rights Reserved

-- $Id: fsrip6.mib,v 1.13 2013/07/01 12:52:09 siva Exp $

SUPERMICRO-RIP6-MIB DEFINITIONS ::= BEGIN

   IMPORTS
      DisplayString,RowStatus              FROM SNMPv2-TC
      MODULE-IDENTITY, OBJECT-TYPE, 
      Counter32, Integer32, enterprises                    FROM SNMPv2-SMI;

fsrip6 MODULE-IDENTITY
      LAST-UPDATED "201209050000Z"
      ORGANIZATION "Super Micro Computer Inc."
      CONTACT-INFO "support@Supermicro.com"
      DESCRIPTION
            " The MIB module for RIP6. "
      REVISION "201209050000Z"
      DESCRIPTION
            " The MIB module for RIP6. "

      ::=  { enterprises supermicro-computer-inc(10876) super-switch(101) basic(1) 3 }


-- fsrip6 GROUP

fsrip6Scalars  OBJECT IDENTIFIER ::= { fsrip6 1 }
fsrip6Tables   OBJECT IDENTIFIER ::= { fsrip6 2 }
fsRip6Test OBJECT IDENTIFIER ::=  { fsrip6 5 }

-- rip6Scalars BEGIN


    fsrip6RoutePreference OBJECT-TYPE
              SYNTAX   INTEGER {
                                static(1),
                                dynamic(2),
                                bestmetric(3)
                               }
              MAX-ACCESS   read-write
              STATUS   current
              DESCRIPTION
                 "The route prefered for forwarding a packet to a 
                  destination when a statically configured route, 
                  as well as a dynamically learnt route exists for 
                  a particular destination. If the value is set
                  to bestmetric(3), the route with the best metric 
                  is the one to be used. Note that, this object would
                  be referred only if both a static route and a 
                  dynamic route exists to the same destination."
              DEFVAL { bestmetric }
              ::= { fsrip6Scalars 1 }

    fsrip6GlobalDebug OBJECT-TYPE
              SYNTAX  Integer32 (0..255)
              MAX-ACCESS read-write
              STATUS  current
              DESCRIPTION
                   "Enables the tracing in RIP6. A 32 bit
              integer is used to store the Tracing level.  
              Different Tracing Levels -
                 BIT 0 - Initialisation and Shutdown Trace.
                 BIT 1 - Management trace.
                 BIT 2 - Data path trace.
                 BIT 3 - Control Plane trace.
                 BIT 4 - Packet Dump.
                 BIT 5 - OS Resource trace.
                 BIT 6 - All Failure trace (including Packet Validation)
                 BIT 7 - Buffer Trace.

              The remaining bits are unused. If a Particular Bit 
              is set, the corresponding trace would be enabled. For
              Example, setting the debug value to 00000001000000000000000000000000 
              would enable all failure trace prints in RIP6 SubSystem."
              ::= { fsrip6Scalars 2 }

    fsrip6GlobalInstanceIndex OBJECT-TYPE
              SYNTAX Integer32 
              MAX-ACCESS read-write
              STATUS current
              DESCRIPTION
                    "This object specifes Instance Index, used to 
                     indicate the instance w.r.t which all the 
                     configuration will be performed. Before any 
                     configuration this object has to be set to the 
                     specific Instance Index. This object will be of use 
                     only in case the RIPng module is supporting Multiple
                     Instance. Ripng comes up with 0 as the default instance."
              ::= { fsrip6Scalars 3 }

    fsrip6PeerFilter OBJECT-TYPE
              SYNTAX INTEGER
                           {
                              allow (1),
                              deny (2)
                           }
              MAX-ACCESS read-write
              STATUS current
              DESCRIPTION
                    "Flag to set peer list to allow or deny.
                     if the flag set to allow, then responses from the 
                     peers in the list can be allowed to be processed.
                     If the flag is set to deny, the responses from the 
                     peers in the list are not allowed to be processed."
              DEFVAL { deny }
              ::= { fsrip6Scalars 4 }

    fsrip6AdvFilter OBJECT-TYPE
              SYNTAX INTEGER
                           {
                               enable (1),
                               disable (2)
                           }
              MAX-ACCESS read-write
              STATUS current
              DESCRIPTION
                    "Flag to enable filtering of routes in the Ripng 
                     responses to be advertised. Setting the flag to 
                     enable(1) will filter the corresponding routing 
                     entries in the response, that are matching with 
                     the AdvFilter list. Setting it to disable(2) 
                     will disable the filter, meaning that all the 
                     entries in the response message are going to be 
                     advertised."
              DEFVAL { disable }
              ::= { fsrip6Scalars 5 }


    fsRip6RRDAdminStatus         OBJECT-TYPE
              SYNTAX                   INTEGER {
                                            enable(1),
                                            disable(2)
                                       }
              MAX-ACCESS               read-write
              STATUS                   current
              DESCRIPTION
                    "Controls redistribution of Direct, Static, OSPF and BGP
                     routes into RIP. If this object is set to enable, then
                     routes from protocols as specified by
                     fsrip6RRDProtoMaskForEnable will be imported into RIP and
                     the RIP learnt routes will be distributed to BGP and OSPF.
                     If this object is set as disable, then the routes learned
                     from protocols specified by fsrip6RRDProtoMaskForEnable
                     will be removed from RIP and no route will be either
                     distributed to or imported from OSPF anf BGP. This object
                     can be set only if fsrip6GlobalAdminStatus is up. When the
                     global admin state changes the fsRip6RRDAdminStatus also
                     changes."
              DEFVAL { enable }
              ::= { fsrip6Scalars 6 }

 
    fsrip6RRDProtoMaskForEnable       OBJECT-TYPE
              SYNTAX                       Integer32
                                               -- See the description
              MAX-ACCESS                   read-write
              STATUS                       current
              DESCRIPTION
                    "The bit mask of source protocols from which routes are
                     imported to RIP.(LSB corresponds to Bit 0)

                     Bit 1, if set, indicates that direct routes can be
                     redistributed into RIP. (value = 2)

                     Bit 2, if set, indicates that static routes can be
                     redistributed into RIP. (value = 4)

                     Bit 5, if set to 1, indicates that routes from OSPF can be
                     redistributed into  RIP. (value = 32)

                     Bit 6, if set to 2, indicates that BGP routes can be
                     redistributed into RIP. (value = 64)

                     Other bits are reserved for future use."
              ::= { fsrip6Scalars 7 }


    fsrip6RRDSrcProtoMaskForDisable      OBJECT-TYPE
              SYNTAX                           Integer32
                                                    -- See the description
              MAX-ACCESS                       read-write
              STATUS                           current
              DESCRIPTION
                    "The bit mask of source protocols from which redistribution
                     to BGP is disabled.(LSB corresponds to Bit 0)

                     Bit 1, if set, indicates that direct routes cannot be
                     redistributed into RIP. (value = 2)

                     Bit 2, if set, indicates that static routes cannot be
                     redistributed into RIP. (value = 4)

                     Bit 5, if set to 1, indicates that routes from OSPF cannot
                     be redistributed into RIP. (value = 32)

                     Bit 6, if set to 2, indicates that BGP routes cannot be
                     redistributed into RIP. (value = 64)

                     Other bits are reserved for future use."
              ::= { fsrip6Scalars 8 }
 
      fsrip6RRDRouteDefMetric            OBJECT-TYPE
              SYNTAX                           Integer32 (0..16)
              MAX-ACCESS                       read-write
              STATUS                           current
              DESCRIPTION
                    "The default metric to be used for the imported routes
                     from RTM6. If 0, then metric value from the RTM6 will
                     be used."
              DEFVAL { 0 }
              ::= { fsrip6Scalars 9 }

      fsrip6RRDRouteMapName              OBJECT-TYPE
              SYNTAX             OCTET STRING (SIZE (0..20))
              MAX-ACCESS         read-write
              STATUS             current
              DESCRIPTION        "Name  Identifies the  specified route-map
                                  in the list of route-maps. If this Object needs to be
                                  changed, first reset this object and then configure the
                                  new value."
              ::= { fsrip6Scalars 10 }

      fsrip6RouteCount              OBJECT-TYPE
              SYNTAX             Integer32
              MAX-ACCESS         read-only
              STATUS             current
              DESCRIPTION        "Indicates the number of route entries."
              ::= { fsrip6Scalars 11 }


-- ripngScalars END

-- ripngTable BEGIN

-- IPv6 RIP Instance Table
      -- This table is relevent only when RIPng is supporting Multiple
      -- Instance Feature.

      -- This table contains Instance related parameters.

      -- The entry is created or deleted whenever a new Instance is to 
      -- be created or deleted. 

    fsrip6InstanceTable   OBJECT-TYPE
        SYNTAX   SEQUENCE OF Fsrip6InstanceEntry
        MAX-ACCESS not-accessible
        STATUS   current
        DESCRIPTION
           "The table contains Instance related parameters. This table is
            a global table i.e. its not instance specific."
        ::= { fsrip6Tables 1 }

    fsrip6InstanceEntry   OBJECT-TYPE
        SYNTAX   Fsrip6InstanceEntry
        MAX-ACCESS   not-accessible
        STATUS   current
        DESCRIPTION
           "The entry in the IPv6 RIP Instance Table. An entry is
            created/deleted in this table when the corresponding
            RIP6 instance is created/deleted."
        INDEX  { fsrip6InstanceIndex }
        ::= { fsrip6InstanceTable 1 }

    Fsrip6InstanceEntry  ::=
              SEQUENCE {
                 fsrip6InstanceIndex
                     Integer32,
                 fsrip6InstanceStatus
                     INTEGER
              }

          fsrip6InstanceIndex    OBJECT-TYPE
              SYNTAX          Integer32 (0..100)
              MAX-ACCESS      not-accessible
              STATUS          current
              DESCRIPTION
                 "The index value which uniquely identifies the RIPng Instance."
              ::= { fsrip6InstanceEntry 1 }


          fsrip6InstanceStatus    OBJECT-TYPE
              SYNTAX        INTEGER   {
                                       down(0), -- Instance Deleted
                                       up(1)    -- Instance Created
                                      }
              MAX-ACCESS    read-write
              STATUS        current
              DESCRIPTION
                 "The status of the specific Instance whether UP or DOWN."
              DEFVAL { 1 }
              ::= { fsrip6InstanceEntry 2 }

-- End of Instance Table

-- IPv6 RIP Instance Interface Map Table
      -- This table is relevent only when RIPng is supporting Multiple
      -- Instance Feature.

      -- This table contains Instance-Interface Mapping parameters.

      -- The entry in this table is created whenever an Interface gets 
      -- attached to an Instance and deleted whenever and Instance get 
      -- deleted or an Interface gets detached from an Instance.

    fsrip6InstIfMapTable   OBJECT-TYPE
        SYNTAX   SEQUENCE OF Fsrip6InstIfMapEntry
        MAX-ACCESS not-accessible
        STATUS   current
        DESCRIPTION
            "The table contains Instance-If mapping parametersits. This is 
             a global table ie its not instance specific."
        ::= { fsrip6Tables 2 }

    fsrip6InstIfMapEntry  OBJECT-TYPE
        SYNTAX   Fsrip6InstIfMapEntry  
        MAX-ACCESS   not-accessible
        STATUS   current
        DESCRIPTION
            "The entry in this table is created whenever an Interface gets 
             attached to an Instance and deleted whenever and Instance get 
             deleted or an Interface gets detached from an Instance."
        INDEX  { fsrip6IfIndex }
        ::= { fsrip6InstIfMapTable 1 }

    Fsrip6InstIfMapEntry  ::=
              SEQUENCE {
                 fsrip6IfIndex
                     Integer32,
                 fsrip6InstIfMapInstId
                     Integer32,
                 fsrip6InstIfMapIfAtchStatus
                     INTEGER
              }

          fsrip6IfIndex    OBJECT-TYPE
              SYNTAX          Integer32 (1..2147483647)
              MAX-ACCESS      not-accessible
              STATUS          current
              DESCRIPTION
                 "The index value which uniquely identifies 
                 the RIPng Interface."
              ::= { fsrip6InstIfMapEntry  1 }

          fsrip6InstIfMapInstId    OBJECT-TYPE
              SYNTAX          Integer32
              MAX-ACCESS      read-only
              STATUS          current
              DESCRIPTION
                 "The index value which uniquely identifies the 
                 RIPng Instance to which a RIPng Interface is 
                 attached. When a row is created in this table
                 this object is assigned the value of 
                 fsrip6GlobalInstanceIndex "
              ::= { fsrip6InstIfMapEntry  2 }

          fsrip6InstIfMapIfAtchStatus    OBJECT-TYPE
              SYNTAX        INTEGER   {
                                       detached(0),  -- Interface is detached
                                                     -- from Instance
                                       attached(1)   -- Interface attached 
                                                     -- to an Instance

                                      }
              MAX-ACCESS    read-write
              STATUS        current
              DESCRIPTION
                 "The attachment status of a RIPng Interface, whether attached 
                  to an instance or not."
              ::= { fsrip6InstIfMapEntry  3 }

-- END of Instance Interface Map Table.

-- IPv6 RIP Interface Table

          -- This table contains interface-based RIPng parameters

          -- Entries created/deleted in this table when corresponding
          -- IPv6 interface is created/deleted.

          -- Entries exist in this table even if RIPng protocol is not
          -- running on the interface as static routes are also maintained
          -- in the RIP routing table.

    fsrip6RipIfTable   OBJECT-TYPE
        SYNTAX   SEQUENCE OF Fsrip6RipIfEntry
        MAX-ACCESS   not-accessible
        STATUS   current
        DESCRIPTION
            "The table containing interface-related RIPng parameters."
        ::= { fsrip6Tables 3 }


    fsrip6RipIfEntry   OBJECT-TYPE
        SYNTAX   Fsrip6RipIfEntry
        MAX-ACCESS   not-accessible
        STATUS   current
        DESCRIPTION
            "The entry in the IPv6 RIP Interface Table. An entry is
             created/deleted in this table when corresponding
             IPv6 interface is created/deleted."
        INDEX  { fsrip6RipIfIndex }
        ::= { fsrip6RipIfTable 1 }

    Fsrip6RipIfEntry  ::=
              SEQUENCE {
                 fsrip6RipIfIndex
                     Integer32,
                 fsrip6RipIfProfileIndex
                     Integer32,
                 fsrip6RipIfCost
                     Integer32,
                 fsrip6RipIfOperStatus
                     INTEGER,
                 fsrip6RipIfProtocolEnable
                     INTEGER,
                 fsrip6RipIfInMessages
                     Counter32,
                 fsrip6RipIfInRequests
                     Counter32,
                 fsrip6RipIfInResponses
                     Counter32,
                 fsrip6RipIfUnknownCmds
                     Counter32,
                 fsrip6RipIfInOtherVer
                     Counter32,
                 fsrip6RipIfInDiscards
                     Counter32,
                 fsrip6RipIfOutMessages
                     Counter32,
                 fsrip6RipIfOutRequests
                     Counter32,
                 fsrip6RipIfOutResponses
                     Counter32,
                 fsrip6RipIfOutTrigUpdates
                     Counter32,
                 fsrip6RipIfDefRouteAdvt
                     INTEGER
              }

          fsrip6RipIfIndex    OBJECT-TYPE
              SYNTAX          Integer32 (1..2147483647)
              MAX-ACCESS      not-accessible
              STATUS          current
              DESCRIPTION
                 "The index value which uniquely identifies the IPv6
                 interface on which this fsrip6RipIfEntry exists.
                 The interface identified by a particular value of this
                 index is the same interface as identified by the same
                 value of fsrip6IfIndex."
              ::= { fsrip6RipIfEntry 1 }


          fsrip6RipIfProfileIndex    OBJECT-TYPE
              SYNTAX        Integer32 (0..9)
              MAX-ACCESS    read-write
              STATUS        current
              DESCRIPTION
                 "Index into the RIPng Profile Table which contains the
                 RIPng parameters for this interface." 
              DEFVAL { 0 }
              ::= { fsrip6RipIfEntry 2 }

          fsrip6RipIfCost   OBJECT-TYPE
              SYNTAX        Integer32 (1..15)
              MAX-ACCESS    read-write
              STATUS        current
              DESCRIPTION
              "The 'cost' associated with this interface. This 'cost'
                 is added to the metric of all routes learnt over this
                 interface before they are installed in the routing table."
              DEFVAL { 1 }
              ::= { fsrip6RipIfEntry 3 }

	  fsrip6RipIfOperStatus    OBJECT-TYPE
              SYNTAX        INTEGER {
                                     enabledup(1),-- Interface operational
                                                  -- and RIPng is enabled on it

                                     enableddown(2),-- Interface not operational
                                                   -- but RIPng is enabled on it

                                     disabledup(3),-- Interface operational
                                                  -- and RIPng not enabled on it

                                     disableddown(4)-- Interface not operational
                                                  -- and RIPng not enabled on it
                                    }
              MAX-ACCESS        read-only
              STATUS            current
              DESCRIPTION
                 "The operational status of this interface and whether
                 RIPng is enabled/disabled on it."
              ::= { fsrip6RipIfEntry 4 }


          fsrip6RipIfProtocolEnable   OBJECT-TYPE
              SYNTAX        INTEGER {
                                     enable(1), -- RIPng is Enabled 
                                                -- Over this Interface

                                     disable(2) --RIPng is Disabled
                                                 --Over this Interface
                                     } 
              MAX-ACCESS    read-write
              STATUS        current
              DESCRIPTION
              "RIPng is enabled over this Interface or Not."
              DEFVAL { disable }
              ::= { fsrip6RipIfEntry 5 }

          fsrip6RipIfInMessages  OBJECT-TYPE
              SYNTAX        Counter32
              MAX-ACCESS    read-only
              STATUS        current
              DESCRIPTION
                  "Number of RIPng messages received on this interface. "
              ::= { fsrip6RipIfEntry 6 }


          fsrip6RipIfInRequests  OBJECT-TYPE
              SYNTAX        Counter32
              MAX-ACCESS    read-only
              STATUS        current
              DESCRIPTION
                  "Number of RIPng Requests received on this interface. "
              ::= { fsrip6RipIfEntry 7 }


          fsrip6RipIfInResponses OBJECT-TYPE
              SYNTAX        Counter32
              MAX-ACCESS    read-only
              STATUS        current
              DESCRIPTION
                  "Number of RIPng Responses received on this interface. "
              ::= { fsrip6RipIfEntry 8 }


          fsrip6RipIfUnknownCmds  OBJECT-TYPE
              SYNTAX        Counter32
              MAX-ACCESS    read-only
              STATUS        current
              DESCRIPTION
                 "Number of RIPng packets with unknown command received
                 on this interface."
              ::= { fsrip6RipIfEntry 9 }

          fsrip6RipIfInOtherVer  OBJECT-TYPE
              SYNTAX        Counter32
              MAX-ACCESS    read-only
              STATUS        current
              DESCRIPTION
                 "Number of RIPng packets received with other version
                 on this interface."
              ::= { fsrip6RipIfEntry 10 }


         fsrip6RipIfInDiscards  OBJECT-TYPE
              SYNTAX        Counter32
              MAX-ACCESS    read-only
              STATUS        current
              DESCRIPTION
                 "Number of received RIPng packets that were discarded."
              ::= { fsrip6RipIfEntry 11 }

         fsrip6RipIfOutMessages  OBJECT-TYPE
              SYNTAX        Counter32
              MAX-ACCESS    read-only
              STATUS        current
              DESCRIPTION
                  "Number of RIPng messages sent out on this interface."
              ::= { fsrip6RipIfEntry 12 }


          fsrip6RipIfOutRequests  OBJECT-TYPE
              SYNTAX        Counter32
              MAX-ACCESS    read-only
              STATUS        current
              DESCRIPTION
                  "Number of RIPng Requests sent out on this interface."
              ::= { fsrip6RipIfEntry 13 }


          fsrip6RipIfOutResponses OBJECT-TYPE
              SYNTAX        Counter32
              MAX-ACCESS    read-only
              STATUS        current
              DESCRIPTION
                  "Number of RIPng Responses sent out on this interface."
              ::= { fsrip6RipIfEntry 14 }


          fsrip6RipIfOutTrigUpdates  OBJECT-TYPE
              SYNTAX        Counter32
              MAX-ACCESS    read-only
              STATUS        current
              DESCRIPTION
                  "Number of triggered updates sent out on this interface."
              ::= { fsrip6RipIfEntry 15 }

          fsrip6RipIfDefRouteAdvt OBJECT-TYPE
             SYNTAX                   INTEGER {
                                            disable(0),
                                            enable(1)
                                       }
              MAX-ACCESS               read-write
              STATUS                   current
              DESCRIPTION
                  "This Object controls the advertisement of default route
                   over this interface."
              DEFVAL { 0 }
              ::= { fsrip6RipIfEntry 16 }
 
-- IPv6 RIP Profile Table

          -- This table specifies the RIPng related parameters which are
          -- referred by interfaces on which RIPng protocol is enabled.

          -- Entries are created/deleted from SNMP except for the first profile
          -- entry which is autocreated and cannot be deleted.


          fsrip6RipProfileTable   OBJECT-TYPE
              SYNTAX   SEQUENCE OF Fsrip6RipProfileEntry
              MAX-ACCESS   not-accessible
              STATUS       current
              DESCRIPTION
                 "The table containing RIPng related configurable parameters
                 which are maintained as a profile and referred by the
                 fsrip6RipIfTable."
              ::= { fsrip6Tables 4 }

          fsrip6RipProfileEntry   OBJECT-TYPE
              SYNTAX       Fsrip6RipProfileEntry
              MAX-ACCESS   not-accessible
              STATUS       current
              DESCRIPTION
                 "The entry in the IPv6 Address Profile Table which contains
                 RIPng parameters. One or more RIP interfaces refer to this
                 profile through the object fsrip6RipIfProfileIndex in the
                 fsrip6RipIfTable. An entry of this table other than the first
                 entry is created/deleted from SNMP."
              INDEX  { fsrip6RipProfileIndex }
              ::= { fsrip6RipProfileTable 1 }


          Fsrip6RipProfileEntry  ::=
              SEQUENCE {
                 fsrip6RipProfileIndex
                     Integer32,
                 fsrip6RipProfileStatus
                     INTEGER,
                 fsrip6RipProfileHorizon
                     INTEGER,
                 fsrip6RipProfilePeriodicUpdTime
                     Integer32,
                 fsrip6RipProfileTrigDelayTime
                     Integer32,
                 fsrip6RipProfileRouteAge
                     Integer32,
                 fsrip6RipProfileGarbageCollectTime
                     Integer32
              }


          fsrip6RipProfileIndex OBJECT-TYPE
              SYNTAX       Integer32 (0..9)
              MAX-ACCESS   not-accessible
              STATUS       current
              DESCRIPTION
                 "A unique value identifying the particular IPv6
                 RIP profile. This is referred by fsrip6RipIfProfileIndex of
                 the IPv6 RIP interface Table."
              ::= { fsrip6RipProfileEntry 1 }


          fsrip6RipProfileStatus  OBJECT-TYPE
              SYNTAX   INTEGER {
                                valid (1),
                                invalid (2)
                               }
              MAX-ACCESS   read-write
              STATUS       current
              DESCRIPTION
                 "Indicates that the entry is valid or not. An entry other
                 than the first entry can be deleted by setting this object
                 to invalid(2)."
              ::= { fsrip6RipProfileEntry 2 }


          fsrip6RipProfileHorizon  OBJECT-TYPE
              SYNTAX   INTEGER {
                                              -- indicates that no-horizoning
                                              -- be done on the interface
                            nohorizon(1) ,    -- while sending updates

                                              -- indicates that split-
                                              -- horizoning be done on the
                                              -- interface while sending
                            splithorizon(2),  -- updates

                                              -- indicates that poison
                                              -- reverse be done on the
                                              -- interface while sending
                            poisonreverse(3) -- updates
              }
              MAX-ACCESS   read-write
              STATUS   current
              DESCRIPTION
                 "Indicates the type of horizoning to be done while sending
                  routing informations (learnt on that interface) over that
                  interface. If the configured value is split-horizon(2) then
                  routes learnt on a interface are not sent over that
                  interface. If the configured value is poison-reverse(3) then
                  such routes are sent with a metric of 16."
              DEFVAL { poisonreverse }
              ::= { fsrip6RipProfileEntry 3 }

          fsrip6RipProfilePeriodicUpdTime    OBJECT-TYPE
              SYNTAX       Integer32 (30..500)
              MAX-ACCESS   read-write
              STATUS       current
              DESCRIPTION
                 "Indicates the interval in seconds between the periodic
                 RIPng updates."
              DEFVAL { 30 }
              ::= { fsrip6RipProfileEntry 4 }


          fsrip6RipProfileTrigDelayTime  OBJECT-TYPE
              SYNTAX       Integer32 (1..10)
              MAX-ACCESS   read-write
              STATUS       current
              DESCRIPTION
                 "Indicates the time interval in seconds by which further
                 triggered updates are delayed after one triggered update
                 is sent."
              DEFVAL { 5 }
              ::= { fsrip6RipProfileEntry 5 }

          fsrip6RipProfileRouteAge  OBJECT-TYPE
              SYNTAX       Integer32 (180..500)
              MAX-ACCESS   read-write
              STATUS       current
              DESCRIPTION
                 "Indicates the period in seconds for which a dynamic route
                 will be kept in the IPv6 RIP routing table without receiving
                 any updates for the route. After this time interval, the
                 route will not be valid and will be aged out."
              DEFVAL { 180 }
              ::= { fsrip6RipProfileEntry 6 }


          fsrip6RipProfileGarbageCollectTime OBJECT-TYPE
              SYNTAX       Integer32 (120..180)
              MAX-ACCESS   read-write
              STATUS       current
              DESCRIPTION
                 "Indicates the period in seconds for which a route which
                 has aged out is retained in the IPv6 RIP Routing Table. After
                 this time interval the route is deleted from the IPv6
                 RIP Routing Table."
              DEFVAL { 120 }
              ::= { fsrip6RipProfileEntry 7 }

-- RIPng Routing Table

          -- The RIPng routing table contains an entry for each
          -- valid IPv6 unicast routes that can be used for packet
          -- forwarding. There are no entries for Multicast and
          -- Link-Local addresses.

          -- This table contains non-RIPng routes learnt via redistribution
          -- from IPv6 and dynamic routes (updated by RIPng). 

          -- Entries are created/deleted to this table through 
          --             1. Redistributed from IPv6
          --             2. routes learnt from other RIPng Peers

	 fsrip6RipRouteTable   OBJECT-TYPE
              SYNTAX   SEQUENCE OF Fsrip6RipRouteEntry
              MAX-ACCESS   not-accessible
              STATUS       current
              DESCRIPTION
                 "This table contains dynamic routes that are learnt
                 through RIPng protocol as well as non-RIPng routes learnt
                 via redistribution."
              ::= { fsrip6Tables 5 }


         fsrip6RipRouteEntry   OBJECT-TYPE
              SYNTAX   Fsrip6RipRouteEntry
              MAX-ACCESS   not-accessible
              STATUS       current
              DESCRIPTION
                 "An entry in the RIPng Routing Table. An entry can be created
                 by means of the RIPng protocol and redistributed routes from
                 IPv6. There can be a non-RIPng route as well as a RIPng route
                 with the same destination and prefix length."
              INDEX  { fsrip6RipRouteDest,
                       fsrip6RipRoutePfxLength,
                       fsrip6RipRouteProtocol,
                       fsrip6RipRouteIfIndex
                     }
              ::= { fsrip6RipRouteTable 1 }


         Fsrip6RipRouteEntry  ::=
              SEQUENCE {
                 fsrip6RipRouteDest
                     OCTET STRING, 
                 fsrip6RipRoutePfxLength
                     Integer32,
                 fsrip6RipRouteProtocol
                     INTEGER,
                 fsrip6RipRouteIfIndex
                     Integer32,
                 fsrip6RipRouteNextHop
                     OCTET STRING ,
                 fsrip6RipRouteMetric
                     Integer32,
                 fsrip6RipRouteTag
                     Integer32,
                 fsrip6RipRouteAge
                     Integer32
              }


          fsrip6RipRouteDest  OBJECT-TYPE
              SYNTAX       OCTET STRING (SIZE (16))
              MAX-ACCESS   not-accessible
              STATUS       current
              DESCRIPTION
                 "The destination IPv6 address of this route.
                  This object will not take a Link-Local or Multicast address
                  value."
              ::= { fsrip6RipRouteEntry 1 }


          fsrip6RipRoutePfxLength OBJECT-TYPE
              SYNTAX       Integer32 (1..128)
              MAX-ACCESS   not-accessible
              STATUS       current
              DESCRIPTION
                 "Indicates the prefix length of the destination
                  address."
              ::= { fsrip6RipRouteEntry 2 }


          fsrip6RipRouteProtocol OBJECT-TYPE
              SYNTAX     INTEGER {
                            other(1),        -- none of the following


                            local(2),        -- non-protocol information,
                                             -- e.g., manually configured
                                             -- entries

                            netmgmt(3),      -- static route

                            ndisc(4),        -- e.g., Redirect
                                             -- the following are all
                                             -- dynamic routing protocols

                            rip(5),          -- RIPng

                            ospf(6),         -- Open Shortest Path First

                            idrp(7)          -- InterDomain Routing Protocol

                         }
              MAX-ACCESS   not-accessible
              STATUS       current
              DESCRIPTION
                 "The routing mechanism via which this route was
                 learned. If it has value local(2), it indicates this
                 route was derived from a configured address prefix."
              ::= { fsrip6RipRouteEntry 3 }


          fsrip6RipRouteIfIndex  OBJECT-TYPE
              SYNTAX       Integer32 (1..2147483647)
              MAX-ACCESS   not-accessible
              STATUS       current
              DESCRIPTION
                 "The index value which uniquely identifies the local
                 interface through which the next hop of this
                 route should be reached.  The interface identified
                 by a particular value of this index is the same
                 interface as identified by the same value of fsrip6IfIndex."
              ::= { fsrip6RipRouteEntry 4 }


          fsrip6RipRouteNextHop  OBJECT-TYPE
              SYNTAX       OCTET STRING (SIZE (16))
              MAX-ACCESS   read-only
              STATUS       current
              DESCRIPTION
                 "Next hop IPv6 Address for this route. For direct routes
                 it has the value ::0."
              ::= { fsrip6RipRouteEntry 5 }


          fsrip6RipRouteMetric  OBJECT-TYPE
              SYNTAX       Integer32 (1..16)
              MAX-ACCESS   read-write
              STATUS       current
              DESCRIPTION
                 "The routing metric associated with this route. A metric
                 of 16 indicates infinity implying the route is no longer
                 valid."
              DEFVAL { 1 }
              ::= { fsrip6RipRouteEntry 6 }


          fsrip6RipRouteTag OBJECT-TYPE
              SYNTAX     Integer32 (0..65535)
              MAX-ACCESS   read-write
              STATUS   current
              DESCRIPTION
                 "This object specifies whether this route is an internal
                 or external route. Value 0 represent routes are internal
                 to the routing domain and Value > 0 represent routes
                 are external to the routing domain."
              ::= { fsrip6RipRouteEntry 7 }


          fsrip6RipRouteAge  OBJECT-TYPE
              SYNTAX       Integer32
              MAX-ACCESS   read-only
              STATUS       current
              DESCRIPTION
                "The number of seconds since this route was last
                updated or otherwise determined to be correct. For
                statically configured routes and locally derived routes,
                this object has value 0."
              ::= { fsrip6RipRouteEntry 8 }

-- Fsrip6PeerTable
          fsrip6RipPeerTable OBJECT-TYPE
              SYNTAX SEQUENCE OF Fsrip6RipPeerEntry
              MAX-ACCESS not-accessible
              STATUS current
              DESCRIPTION
                 "This table contains the Addresses of those Peers  
                  whose RIPng Responses are to be accepted or denied"
              ::= { fsrip6Tables  6 }
          
          fsrip6RipPeerEntry OBJECT-TYPE
              SYNTAX Fsrip6RipPeerEntry
              MAX-ACCESS not-accessible
              STATUS current
              DESCRIPTION
                     "Single entity in the fsrip6RipPeerTable."
              INDEX 
                   { fsrip6RipPeerAddr }
              ::= { fsrip6RipPeerTable 1 } 

          Fsrip6RipPeerEntry ::=
              SEQUENCE {
                           fsrip6RipPeerAddr
                                OCTET STRING, 
                           fsrip6RipPeerEntryStatus
                                INTEGER
                       }
           
          fsrip6RipPeerAddr OBJECT-TYPE
              SYNTAX       OCTET STRING (SIZE (16))
              MAX-ACCESS   not-accessible
              STATUS       current
              DESCRIPTION 
                     "The Address of the Peer, from whom Responses are 
                      to be Allowed or Denied"
              ::= { fsrip6RipPeerEntry 1 }
 
          fsrip6RipPeerEntryStatus OBJECT-TYPE
              SYNTAX  INTEGER
                            {
                               valid (1),
                               invalid (2)
                            }
              MAX-ACCESS read-write
              STATUS     current
              DESCRIPTION
                     "'valid' indicated presence of the entry. 
                      'invalid' means the entry is unavailable. "
              ::= { fsrip6RipPeerEntry 2}

          
-- Fsrip6RipAdvFilterTable

          fsrip6RipAdvFilterTable  OBJECT-TYPE
              SYNTAX SEQUENCE OF Fsrip6RipAdvFilterEntry
              MAX-ACCESS not-accessible
              STATUS current
              DESCRIPTION
                 "This table contains the routes which are 
                  NOT to be advertised in the RIPng Responses sent
                  by the router, if fsrip6AdvFilter is enabled"
              ::= { fsrip6Tables 7 }

          fsrip6RipAdvFilterEntry OBJECT-TYPE
              SYNTAX Fsrip6RipAdvFilterEntry
              MAX-ACCESS not-accessible
              STATUS current
              DESCRIPTION 
                     "Single entity in the fsrip6RipAdvFilterTable"
              INDEX 
                  {
                      fsrip6RipAdvFilterAddress
                  }
              ::= { fsrip6RipAdvFilterTable 1 }
 
           Fsrip6RipAdvFilterEntry ::=
              SEQUENCE {
                         fsrip6RipAdvFilterAddress
                               OCTET STRING,
                         fsrip6RipAdvFilterStatus
                               INTEGER
                       }

           fsrip6RipAdvFilterAddress OBJECT-TYPE
               SYNTAX OCTET STRING (SIZE(16))
               MAX-ACCESS not-accessible
               STATUS current
               DESCRIPTION
                      "The route(s) with this address is NOT to be 
                      advertised to the Peers, if fsrip6AdvFilter 
                      is enabled"
                      
               ::= { fsrip6RipAdvFilterEntry 1 }
 
           fsrip6RipAdvFilterStatus OBJECT-TYPE
               SYNTAX INTEGER
                            {
                               valid (1),
                               invalid(2)
                            }
               MAX-ACCESS read-write
               STATUS current
               DESCRIPTION
                     "'valid' indicated presence of the entry. 
                      'invalid' means the entry is unavailable. "
              ::= { fsrip6RipAdvFilterEntry 2 }

--ripngTable END

-- FILTERING OBJECT DEFINITION BEGIN

 fsrip6DistInOutRouteMap OBJECT IDENTIFIER ::= { fsrip6 3 }

    fsRip6DistInOutRouteMapTable OBJECT-TYPE
        SYNTAX SEQUENCE OF FsRip6DistInOutRouteMapEntry
        MAX-ACCESS          not-accessible
        STATUS              current
        DESCRIPTION
            "A table describing the configuration of filtering for route map."
    ::= { fsrip6DistInOutRouteMap 1 }

    fsRip6DistInOutRouteMapEntry OBJECT-TYPE
        SYNTAX FsRip6DistInOutRouteMapEntry
        MAX-ACCESS          not-accessible
        STATUS              current
        DESCRIPTION
            "Information describing the filtering configuration of single entry."
        INDEX {fsRip6DistInOutRouteMapName, fsRip6DistInOutRouteMapType}
    ::=  { fsRip6DistInOutRouteMapTable 1 }

    FsRip6DistInOutRouteMapEntry ::= SEQUENCE {
        fsRip6DistInOutRouteMapName         DisplayString,
        fsRip6DistInOutRouteMapType         Integer32,
        fsRip6DistInOutRouteMapValue        Integer32,
        fsRip6DistInOutRouteMapRowStatus    RowStatus
    }

    fsRip6DistInOutRouteMapName OBJECT-TYPE
        SYNTAX              DisplayString (SIZE(1..20))
        MAX-ACCESS          not-accessible
        STATUS              current
        DESCRIPTION
            "Route map name."
    ::=  { fsRip6DistInOutRouteMapEntry 1 }

    fsRip6DistInOutRouteMapType OBJECT-TYPE
        SYNTAX              Integer32(1..3)
        MAX-ACCESS          not-accessible
        STATUS              current
        DESCRIPTION
            "Type of route map to indicate the route map is for
            distribute in or for distribute out or for distance.
            1 - distance
            2 - distribute in
            3 - distribute out"
    ::=  { fsRip6DistInOutRouteMapEntry 3 }

    fsRip6DistInOutRouteMapValue  OBJECT-TYPE
        SYNTAX              Integer32(1..255)
        MAX-ACCESS          read-write
        STATUS              current
        DESCRIPTION
            "Distance value ( this will be unused for distribute list )"
    ::=  { fsRip6DistInOutRouteMapEntry 4 }

    fsRip6DistInOutRouteMapRowStatus OBJECT-TYPE
        SYNTAX              RowStatus
        MAX-ACCESS          read-write
        STATUS              current
        DESCRIPTION
            "The status of this row, by which new entries may be
            created, or old entries deleted from this table."
    ::=  { fsRip6DistInOutRouteMapEntry 5 }

-- FILTERING OBJECT DEFINITION END

-- PREFERENCE OBJECT DEFINITION BEGIN


 fsrip6PreferenceGroup OBJECT IDENTIFIER ::=  { fsrip6 4 }

   fsRip6PreferenceValue OBJECT-TYPE
       SYNTAX Integer32 (0..255)
       MAX-ACCESS read-write
       STATUS current
       DESCRIPTION
           "Preference value for RIP6 routes. If the value is set as '0',it
            will inturn be mapped to default value "
       DEFVAL { 120 }
       ::= { fsrip6PreferenceGroup 1 }

-- PREFERENCE OBJECT DEFINITION END

fsRip6TestBulkUpd OBJECT-TYPE
    SYNTAX INTEGER {
        enabled	      (1),
        disabled	  (2)
    }
    MAX-ACCESS read-write
    STATUS current
    DESCRIPTION
        "This is disabled to crash the active node during
        bulk update."
    ::= { fsRip6Test 1 }

fsRip6TestDynamicUpd OBJECT-TYPE
    SYNTAX INTEGER {
        enabled	      (1),
        disabled	  (2)
    }
    MAX-ACCESS read-write
    STATUS current
    DESCRIPTION
        "This is disabled to make the active node drop the
                dynamic update to standby node."
    ::= { fsRip6Test 2 }

END

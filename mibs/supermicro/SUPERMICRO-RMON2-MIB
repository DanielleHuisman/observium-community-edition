-- Copyright (C) 2008-2014 Super Micro Computer Inc. All Rights Reserved

-- $Id: fsrmon2.mib,v 1.3 2012/09/07 09:52:06 siva Exp $

SUPERMICRO-RMON2-MIB DEFINITIONS ::= BEGIN

-- Remote Network Monitoring Management Information Base Version 2

-- Enterprises MIB for RMON2 product (for Trace).

IMPORTS 
    MODULE-IDENTITY, OBJECT-TYPE,
    enterprises, Unsigned32        FROM SNMPv2-SMI;


fsrmon2 MODULE-IDENTITY
     LAST-UPDATED "201209050000Z"
     ORGANIZATION "Super Micro Computer Inc."
     CONTACT-INFO "support@Supermicro.com" 
         DESCRIPTION
             "This MIB module is for managing RMON2 implementations."
	 REVISION "201209050000Z"
         DESCRIPTION
             "This MIB module is for managing RMON2 implementations."
                  ::= { enterprises supermicro-computer-inc(10876) super-switch(101) extended(2) 19 }
    
-- fsRmon2 Trace object
         fsRmon2Trace OBJECT-TYPE
              SYNTAX  Unsigned32 
              MAX-ACCESS read-write
              STATUS current
              DESCRIPTION
		  "This object defines the traces that are defined for rmon2.
	          Bit 1 - Function Entry
        	  Bit 2 - Function Exit
	          Bit 3 - Critical
        	  Bit 4 - Memory failures
	          Bit 5 - Debug"
         ::=  { fsrmon2  1 }

-- fsRmon2 Admin Status object
         fsRmon2AdminStatus OBJECT-TYPE
              SYNTAX  INTEGER { 
                      enabled(1),
                      disabled(2)
                      } 
              MAX-ACCESS read-write
              STATUS current
              DESCRIPTION
		  "This object defines the admin status for rmon2." 
              DEFVAL  { disabled }
         ::=  { fsrmon2  2 }
 
END

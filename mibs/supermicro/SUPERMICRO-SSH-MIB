-- Copyright (C) 2008-2014 Super Micro Computer Inc. All Rights Reserved

-- $Id: fssshmib.mib,v 1.9 2012/12/12 15:09:56 siva Exp $

-- SSH proprietary MIB Definition
 
SUPERMICRO-SSH-MIB DEFINITIONS ::= BEGIN

IMPORTS 
   MODULE-IDENTITY, OBJECT-TYPE, 
   enterprises, Integer32, Unsigned32   
   FROM SNMPv2-SMI 
   TruthValue 
   FROM SNMPv2-TC; 

   ssh MODULE-IDENTITY 
      LAST-UPDATED "202102190000Z"
      ORGANIZATION "Super Micro Computer Inc." 
      CONTACT-INFO "support@Supermicro.com" 
      DESCRIPTION
         "The proprietary MIB for SSH."
      REVISION "202102190000Z"
      DESCRIPTION 
         "The proprietary MIB for SSH." 
   ::= { enterprises supermicro-computer-inc(10876) super-switch(101) basic(1) 97 }


-- ----------------------------------------------------------------- --
-- groups in the MIB
-- ----------------------------------------------------------------- --
 
      sshGeneralGroup             OBJECT IDENTIFIER ::= { ssh 1 }
 
-- ---------------------------------------------------------------- --

-- General Group 

sshVersionCompatibility      OBJECT-TYPE
   SYNTAX      TruthValue 
   MAX-ACCESS  read-write 
   STATUS      current 
   DESCRIPTION 

   "This object is to configure the SSH version compatibility mode.
   When set to TRUE, both SSH version-1 and SSH Version-2 will be supported.
   When set to FALSE, SSH version-2 only will be supported.

   By default SSH version-2 is supported."

   DEFVAL  { false } 
   ::= { sshGeneralGroup 1 }

sshCipherList OBJECT-TYPE
      SYNTAX Integer32
      MAX-ACCESS read-write
      STATUS current
      DESCRIPTION
      
      "This object is to configure the cipher-suites list.

      This object takes values as bit mask.  Setting a bit indicates that the 
      corresponding cipher-list will be used for Encryption. 

      The value of each bit position is as given below with bit 0 being the 
      least significant bit:
           BIT 12 - aes256-ctr
           BIT 11 - aes192-ctr
           BIT 10 - aes128-ctr
           BIT  9 - rijndael-cbc@lysator.liu.se
           BIT  8 - aes192-cbc
           BIT  7 - arcfour256
           BIT  6 - arcfour128
           BIT  5 - arcfour
           BIT  4 - cast128-cbc
           BIT  3 - aes256-cbc
           BIT  2 - aes128-cbc
           BIT  1 - not used
           BIT  0 - 3des-cbc
      By default all algorithms are enabled."
          
   DEFVAL  { 8189 }
   ::= { sshGeneralGroup 2}

sshMacList OBJECT-TYPE
      SYNTAX Integer32
      MAX-ACCESS read-write
      STATUS current
      DESCRIPTION

      "This object is to configure the MAC-list.

      This object takes values as bit mask. Setting a bit indicates that the 
      corresponding MAC-list will be used for authentication. 

      The value of each bit position is as given below with bit 0  being the 
      least significant bit: 
            BIT 2 - hmac-sha2
            BIT 1 - hmac-md5
            BIT 0 - hmac-sha1"
            
   DEFVAL  { 5 }
   ::= { sshGeneralGroup 3}


sshTrace     OBJECT-TYPE
         SYNTAX        Integer32
         MAX-ACCESS    read-write
         STATUS        current
         DESCRIPTION
         "Set the trace level for SSH.
            BIT 0 - Initialisation and Shutdown Trace.
            BIT 1 - Management trace.
            BIT 2 - Data path trace.
            BIT 3 - Control Plane trace.
            BIT 4 - Packet Dump.
            BIT 5 - OS Resource trace.
            BIT 6 - All Failure trace (All failures including Packet Validation)
            BIT 7 - Buffer Trace.
            BIT 8 - SSH Server Trace.
            
            Note:BIT 0 - Least significant bit
                 BIT 7 - Most significant bit

            For example,setting the trace level to the value -0001 0101, 
            will enable Init-Shutdown, data path and packet dump trace levels.

            Setting all the bits will enable all the trace levels and 
            resetting them will disable all the trace levels."

         ::= { sshGeneralGroup 4 }

sshStatus  OBJECT-TYPE
   SYNTAX      TruthValue 
   MAX-ACCESS  read-write
   STATUS      current
   DESCRIPTION
      "This object is for enabling or disabling ssh in the system."

   DEFVAL  { true }
   ::= { sshGeneralGroup 5}
sshTransportMaxAllowedBytes        OBJECT-TYPE
        SYNTAX                 Integer32(1..32768)
        MAX-ACCESS        read-write
        STATUS                current
        DESCRIPTION
        "This object is used to configure the maximum number of bytes allowed in an SSH transport connection. The SSH connection will be allowed only if the packet size does not exceed the value configured in this object and dropped otherwise."

   ::= { sshGeneralGroup 6 }

sshSrvBindAddr OBJECT-TYPE
    SYNTAX   OCTET STRING (SIZE (4|16))
    MAX-ACCESS  read-write
    STATUS  current
    DESCRIPTION "This object defines the Ip address on which Ssh Server listens"
    ::=  { sshGeneralGroup 7 }

sshServerBindPortNo OBJECT-TYPE
    SYNTAX   Unsigned32
    MAX-ACCESS  read-write
    STATUS  current
    DESCRIPTION "This object defines the primary port number on which Ssh Server listens"
    DEFVAL    { 22 }
    ::=  { sshGeneralGroup 8 }

END

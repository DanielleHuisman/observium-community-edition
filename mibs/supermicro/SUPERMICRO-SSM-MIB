-- *****************************************************************
-- SUPERMICRO-SSM.mib: Super Micro Enterprise Structure of Management Information
--
-- August 8 2017, Software Dept.
--
-- Copyright (c) 1993-2017 by Super Micro Computer Inc.
-- All rights reserved.
-- 
-- *****************************************************************

SUPERMICRO-SSM-MIB DEFINITIONS ::= BEGIN

IMPORTS
	MODULE-IDENTITY,
	OBJECT-TYPE,
	Integer32
		FROM SNMPv2-SMI
	DisplayString
		FROM SNMPv2-TC
	smSSMInfo
		FROM SUPERMICRO-SMI;
		
smSSMTrapMIB  		OBJECT IDENTIFIER ::= { smSSMInfo 4 }


trapGenericHostStatusNormal TRAP-TYPE
	ENTERPRISE smSSMTrapMIB
	DESCRIPTION "Monitored host has returned to Normal"

	--#TYPE       "Generic Host Event"
	--#SUMMARY    "Monitored host has returned to Normal"
	--#ARGUMENTS  {}
	--#SEVERITY   INFORMATIONAL

	::= 101

trapGenericHostStatusDown TRAP-TYPE
	ENTERPRISE smSSMTrapMIB
	DESCRIPTION "Monitored host is Down"

	--#TYPE       "Generic Host Event"
	--#SUMMARY    "Monitored host is Down"
	--#ARGUMENTS  {}
	--#SEVERITY   CRITICAL

	::= 102
	
trapGenericHostStatusUnreachable TRAP-TYPE
	ENTERPRISE smSSMTrapMIB
	DESCRIPTION "Monitored host is Unreachable"

	--#TYPE       "Generic Host Event"
	--#SUMMARY    "Monitored host is Unreachable"
	--#ARGUMENTS  {}
	--#SEVERITY   CRITICAL

	::= 103


trapGenericServiceStatusNormal TRAP-TYPE
	ENTERPRISE smSSMTrapMIB
	DESCRIPTION "Monitored service has returned to Normal"

	--#TYPE       "Generic Service Event"
	--#SUMMARY    "Monitored service has returned to Normal"
	--#ARGUMENTS  {}
	--#SEVERITY   INFORMATIONAL

	::= 201

trapGenericServiceStatusWarning TRAP-TYPE
	ENTERPRISE smSSMTrapMIB
	DESCRIPTION "Monitored service is Warning"

	--#TYPE       "Generic Service Event"
	--#SUMMARY    "Monitored service is Warning"
	--#ARGUMENTS  {}
	--#SEVERITY   WARNING

	::= 202
	
trapGenericServiceStatusCritical TRAP-TYPE
	ENTERPRISE smSSMTrapMIB
	DESCRIPTION "Monitored service is Critical"

	--#TYPE       "Generic Service Event"
	--#SUMMARY    "Monitored service is Critical"
	--#ARGUMENTS  {}
	--#SEVERITY   CRITICAL

	::= 203
	
trapGenericServiceStatusUnknown TRAP-TYPE
	ENTERPRISE smSSMTrapMIB
	DESCRIPTION "Monitored service is Unknown"

	--#TYPE       "Generic Service Event"
	--#SUMMARY    "Monitored service is Unknown"
	--#ARGUMENTS  {}
	--#SEVERITY   CRITICAL

	::= 204

trapVersionStatusNormal TRAP-TYPE
	ENTERPRISE smSSMTrapMIB
	DESCRIPTION "Agent and its plug-ins version service has returned to Normal"

	--#TYPE       "Agent and its plug-ins version Service Event"
	--#SUMMARY    "Monitored service has returned to Normal"
	--#ARGUMENTS  {}
	--#SEVERITY   INFORMATIONAL

	::= 301

trapVersionStatusWarning TRAP-TYPE
	ENTERPRISE smSSMTrapMIB
	DESCRIPTION "Agent and its plug-ins version service is Warning"

	--#TYPE       "Agent and its plug-ins version Service Event"
	--#SUMMARY    "Monitored service is Warning"
	--#ARGUMENTS  {}
	--#SEVERITY   WARNING

	::= 302
	
trapVersionStatusCritical TRAP-TYPE
	ENTERPRISE smSSMTrapMIB
	DESCRIPTION "Agent and its plug-ins version service is Critical"

	--#TYPE       "Agent and its plug-ins version Service Event"
	--#SUMMARY    "Monitored service is Critical"
	--#ARGUMENTS  {}
	--#SEVERITY   CRITICAL

	::= 303
	
trapVersionStatusUnknown TRAP-TYPE
	ENTERPRISE smSSMTrapMIB
	DESCRIPTION "Agent and its plug-ins version service is Unknown"

	--#TYPE       "Agent and its plug-ins version Service Event"
	--#SUMMARY    "Monitored service is Unknown"
	--#ARGUMENTS  {}
	--#SEVERITY   CRITICAL

	::= 304

trapSysinfoStatusNormal TRAP-TYPE
	ENTERPRISE smSSMTrapMIB
	DESCRIPTION "System Information service has returned to Normal"

	--#TYPE       "System Information Service Event"
	--#SUMMARY    "Monitored service has returned to Normal"
	--#ARGUMENTS  {}
	--#SEVERITY   INFORMATIONAL

	::= 401

trapSysinfoStatusWarning TRAP-TYPE
	ENTERPRISE smSSMTrapMIB
	DESCRIPTION "System Information service is Warning"

	--#TYPE       "System Information Service Event"
	--#SUMMARY    "Monitored service is Warning"
	--#ARGUMENTS  {}
	--#SEVERITY   WARNING

	::= 402
	
trapSysinfoStatusCritical TRAP-TYPE
	ENTERPRISE smSSMTrapMIB
	DESCRIPTION "System Information service is Critical"

	--#TYPE       "System Information Service Event"
	--#SUMMARY    "Monitored service is Critical"
	--#ARGUMENTS  {}
	--#SEVERITY   CRITICAL

	::= 403
	
trapSysinfoStatusUnknown TRAP-TYPE
	ENTERPRISE smSSMTrapMIB
	DESCRIPTION "System Information service is Unknown"

	--#TYPE       "System Information Service Event"
	--#SUMMARY    "Monitored service is Unknown"
	--#ARGUMENTS  {}
	--#SEVERITY   CRITICAL

	::= 404
	
trapBuiltinSensorHealthStatusNormal TRAP-TYPE
	ENTERPRISE smSSMTrapMIB
	DESCRIPTION "Built-in Sensor Health service has returned to Normal"

	--#TYPE       "Built-in Sensor Health Service Event"
	--#SUMMARY    "Monitored service has returned to Normal"
	--#ARGUMENTS  {}
	--#SEVERITY   INFORMATIONAL

	::= 501

trapBuiltinSensorHealthStatusWarning TRAP-TYPE
	ENTERPRISE smSSMTrapMIB
	DESCRIPTION "Built-in Sensor Health service is Warning"

	--#TYPE       "Built-in Sensor Health Service Event"
	--#SUMMARY    "Monitored service is Warning"
	--#ARGUMENTS  {}
	--#SEVERITY   WARNING

	::= 502
	
trapBuiltinSensorHealthStatusCritical TRAP-TYPE
	ENTERPRISE smSSMTrapMIB
	DESCRIPTION "Built-in Sensor Health service is Critical"

	--#TYPE       "Built-in Sensor Health Service Event"
	--#SUMMARY    "Monitored service is Critical"
	--#ARGUMENTS  {}
	--#SEVERITY   CRITICAL

	::= 503
	
trapBuiltinSensorHealthStatusUnknown TRAP-TYPE
	ENTERPRISE smSSMTrapMIB
	DESCRIPTION "Built-in Sensor Health service is Unknown"

	--#TYPE       "Built-in Sensor Health Service Event"
	--#SUMMARY    "Monitored service is Unknown"
	--#ARGUMENTS  {}
	--#SEVERITY   CRITICAL

	::= 504
	
trapExecuteScriptStatusNormal TRAP-TYPE
	ENTERPRISE smSSMTrapMIB
	DESCRIPTION "Execute a script service has returned to Normal"

	--#TYPE       "Execute a script Service Event"
	--#SUMMARY    "Monitored service has returned to Normal"
	--#ARGUMENTS  {}
	--#SEVERITY   INFORMATIONAL

	::= 601

trapExecuteScriptStatusWarning TRAP-TYPE
	ENTERPRISE smSSMTrapMIB
	DESCRIPTION "Execute a script service is Warning"

	--#TYPE       "Execute a script Service Event"
	--#SUMMARY    "Monitored service is Warning"
	--#ARGUMENTS  {}
	--#SEVERITY   WARNING

	::= 602
	
trapExecuteScriptStatusCritical TRAP-TYPE
	ENTERPRISE smSSMTrapMIB
	DESCRIPTION "Execute a script service is Critical"

	--#TYPE       "Execute a script Service Event"
	--#SUMMARY    "Monitored service is Critical"
	--#ARGUMENTS  {}
	--#SEVERITY   CRITICAL

	::= 603
	
trapExecuteScriptStatusUnknown TRAP-TYPE
	ENTERPRISE smSSMTrapMIB
	DESCRIPTION "Execute a script service is Unknown"

	--#TYPE       "Execute a script Service Event"
	--#SUMMARY    "Monitored service is Unknown"
	--#ARGUMENTS  {}
	--#SEVERITY   CRITICAL

	::= 604
	
trapStorageHealthStatusNormal TRAP-TYPE
	ENTERPRISE smSSMTrapMIB
	DESCRIPTION "Storage Health service has returned to Normal"

	--#TYPE       "Storage Health Service Event"
	--#SUMMARY    "Monitored service has returned to Normal"
	--#ARGUMENTS  {}
	--#SEVERITY   INFORMATIONAL

	::= 701

trapStorageHealthStatusWarning TRAP-TYPE
	ENTERPRISE smSSMTrapMIB
	DESCRIPTION "Storage Health service is Warning"

	--#TYPE       "Storage Health Service Event"
	--#SUMMARY    "Monitored service is Warning"
	--#ARGUMENTS  {}
	--#SEVERITY   WARNING

	::= 702
	
trapStorageHealthStatusCritical TRAP-TYPE
	ENTERPRISE smSSMTrapMIB
	DESCRIPTION "Storage Health service is Critical"

	--#TYPE       "Storage Health Service Event"
	--#SUMMARY    "Monitored service is Critical"
	--#ARGUMENTS  {}
	--#SEVERITY   CRITICAL

	::= 703
	
trapStorageHealthStatusUnknown TRAP-TYPE
	ENTERPRISE smSSMTrapMIB
	DESCRIPTION "Storage Health service is Unknown"

	--#TYPE       "Storage Health Service Event"
	--#SUMMARY    "Monitored service is Unknown"
	--#ARGUMENTS  {}
	--#SEVERITY   CRITICAL

	::= 704
	
trapMemoryHealthStatusNormal TRAP-TYPE
	ENTERPRISE smSSMTrapMIB
	DESCRIPTION "Memory Health service has returned to Normal"

	--#TYPE       "Memory Health Service Event"
	--#SUMMARY    "Monitored service has returned to Normal"
	--#ARGUMENTS  {}
	--#SEVERITY   INFORMATIONAL

	::= 801

trapMemoryHealthStatusWarning TRAP-TYPE
	ENTERPRISE smSSMTrapMIB
	DESCRIPTION "Memory Health service is Warning"

	--#TYPE       "Memory Health Service Event"
	--#SUMMARY    "Monitored service is Warning"
	--#ARGUMENTS  {}
	--#SEVERITY   WARNING

	::= 802
	
trapMemoryHealthStatusCritical TRAP-TYPE
	ENTERPRISE smSSMTrapMIB
	DESCRIPTION "Memory Health service is Critical"

	--#TYPE       "Memory Health Service Event"
	--#SUMMARY    "Monitored service is Critical"
	--#ARGUMENTS  {}
	--#SEVERITY   CRITICAL

	::= 803
	
trapMemoryHealthStatusUnknown TRAP-TYPE
	ENTERPRISE smSSMTrapMIB
	DESCRIPTION "Memory Health service is Unknown"

	--#TYPE       "Memory Health Service Event"
	--#SUMMARY    "Monitored service is Unknown"
	--#ARGUMENTS  {}
	--#SEVERITY   CRITICAL

	::= 804

trapHttpStatusNormal TRAP-TYPE
	ENTERPRISE smSSMTrapMIB
	DESCRIPTION "Check HTTP service has returned to Normal"

	--#TYPE       "Check HTTP Service Event"
	--#SUMMARY    "Monitored service has returned to Normal"
	--#ARGUMENTS  {}
	--#SEVERITY   INFORMATIONAL

	::= 901

trapHttpStatusWarning TRAP-TYPE
	ENTERPRISE smSSMTrapMIB
	DESCRIPTION "Check HTTP service is Warning"

	--#TYPE       "Check HTTP Service Event"
	--#SUMMARY    "Monitored service is Warning"
	--#ARGUMENTS  {}
	--#SEVERITY   WARNING

	::= 902
	
trapHttpStatusCritical TRAP-TYPE
	ENTERPRISE smSSMTrapMIB
	DESCRIPTION "Check HTTP service is Critical"

	--#TYPE       "Check HTTP Service Event"
	--#SUMMARY    "Monitored service is Critical"
	--#ARGUMENTS  {}
	--#SEVERITY   CRITICAL

	::= 903
	
trapHttpStatusUnknown TRAP-TYPE
	ENTERPRISE smSSMTrapMIB
	DESCRIPTION "Check HTTP service is Unknown"

	--#TYPE       "Check HTTP Service Event"
	--#SUMMARY    "Monitored service is Unknown"
	--#ARGUMENTS  {}
	--#SEVERITY   CRITICAL

	::= 904
	
trapFtpStatusNormal TRAP-TYPE
	ENTERPRISE smSSMTrapMIB
	DESCRIPTION "Check FTP service has returned to Normal"

	--#TYPE       "Check FTP Service Event"
	--#SUMMARY    "Monitored service has returned to Normal"
	--#ARGUMENTS  {}
	--#SEVERITY   INFORMATIONAL

	::= 1001

trapFtpStatusWarning TRAP-TYPE
	ENTERPRISE smSSMTrapMIB
	DESCRIPTION "Check FTP service is Warning"

	--#TYPE       "Check FTP Service Event"
	--#SUMMARY    "Monitored service is Warning"
	--#ARGUMENTS  {}
	--#SEVERITY   WARNING

	::= 1002
	
trapFtpStatusCritical TRAP-TYPE
	ENTERPRISE smSSMTrapMIB
	DESCRIPTION "Check FTP service is Critical"

	--#TYPE       "Check FTP Service Event"
	--#SUMMARY    "Monitored service is Critical"
	--#ARGUMENTS  {}
	--#SEVERITY   CRITICAL

	::= 1003
	
trapFtpStatusUnknown TRAP-TYPE
	ENTERPRISE smSSMTrapMIB
	DESCRIPTION "Check FTP service is Unknown"

	--#TYPE       "Check FTP Service Event"
	--#SUMMARY    "Monitored service is Unknown"
	--#ARGUMENTS  {}
	--#SEVERITY   CRITICAL

	::= 1004
	
trapSmtpStatusNormal TRAP-TYPE
	ENTERPRISE smSSMTrapMIB
	DESCRIPTION "Check SMTP service has returned to Normal"

	--#TYPE       "Check SMTP Service Event"
	--#SUMMARY    "Monitored service has returned to Normal"
	--#ARGUMENTS  {}
	--#SEVERITY   INFORMATIONAL

	::= 1101

trapSmtpStatusWarning TRAP-TYPE
	ENTERPRISE smSSMTrapMIB
	DESCRIPTION "Check SMTP service is Warning"

	--#TYPE       "Check SMTP Service Event"
	--#SUMMARY    "Monitored service is Warning"
	--#ARGUMENTS  {}
	--#SEVERITY   WARNING

	::= 1102
	
trapSmtpStatusCritical TRAP-TYPE
	ENTERPRISE smSSMTrapMIB
	DESCRIPTION "Check SMTP service is Critical"

	--#TYPE       "Check SMTP Service Event"
	--#SUMMARY    "Monitored service is Critical"
	--#ARGUMENTS  {}
	--#SEVERITY   CRITICAL

	::= 1103
	
trapSmtpStatusUnknown TRAP-TYPE
	ENTERPRISE smSSMTrapMIB
	DESCRIPTION "Check SMTP service is Unknown"

	--#TYPE       "Check SMTP Service Event"
	--#SUMMARY    "Monitored service is Unknown"
	--#ARGUMENTS  {}
	--#SEVERITY   CRITICAL

	::= 1104

trapIpmiSensorHealthStatusNormal TRAP-TYPE
	ENTERPRISE smSSMTrapMIB
	DESCRIPTION "IPMI Sensor Health service has returned to Normal"

	--#TYPE       "IPMI Sensor Health Service Event"
	--#SUMMARY    "Monitored service has returned to Normal"
	--#ARGUMENTS  {}
	--#SEVERITY   INFORMATIONAL

	::= 1201

trapIpmiSensorHealthStatusWarning TRAP-TYPE
	ENTERPRISE smSSMTrapMIB
	DESCRIPTION "IPMI Sensor Health service is Warning"

	--#TYPE       "IPMI Sensor Health Service Event"
	--#SUMMARY    "Monitored service is Warning"
	--#ARGUMENTS  {}
	--#SEVERITY   WARNING

	::= 1202
	
trapIpmiSensorHealthStatusCritical TRAP-TYPE
	ENTERPRISE smSSMTrapMIB
	DESCRIPTION "IPMI Sensor Health service is Critical"

	--#TYPE       "IPMI Sensor Health Service Event"
	--#SUMMARY    "Monitored service is Critical"
	--#ARGUMENTS  {}
	--#SEVERITY   CRITICAL

	::= 1203
	
trapIpmiSensorHealthStatusUnknown TRAP-TYPE
	ENTERPRISE smSSMTrapMIB
	DESCRIPTION "IPMI Sensor Health service is Unknown"

	--#TYPE       "IPMI Sensor Health Service Event"
	--#SUMMARY    "Monitored service is Unknown"
	--#ARGUMENTS  {}
	--#SEVERITY   CRITICAL

	::= 1204
	
trapIpmiPowerConsumptionStatusNormal TRAP-TYPE
	ENTERPRISE smSSMTrapMIB
	DESCRIPTION "IPMI Power Consumption service has returned to Normal"

	--#TYPE       "IPMI Power Consumption Service Event"
	--#SUMMARY    "Monitored service has returned to Normal"
	--#ARGUMENTS  {}
	--#SEVERITY   INFORMATIONAL

	::= 1301

trapIpmiPowerConsumptionStatusWarning TRAP-TYPE
	ENTERPRISE smSSMTrapMIB
	DESCRIPTION "IPMI Power Consumption service is Warning"

	--#TYPE       "IPMI Power Consumption Service Event"
	--#SUMMARY    "Monitored service is Warning"
	--#ARGUMENTS  {}
	--#SEVERITY   WARNING

	::= 1302
	
trapIpmiPowerConsumptionStatusCritical TRAP-TYPE
	ENTERPRISE smSSMTrapMIB
	DESCRIPTION "IPMI Power Consumption service is Critical"

	--#TYPE       "IPMI Power Consumption Service Event"
	--#SUMMARY    "Monitored service is Critical"
	--#ARGUMENTS  {}
	--#SEVERITY   CRITICAL

	::= 1303
	
trapIpmiPowerConsumptionStatusUnknown TRAP-TYPE
	ENTERPRISE smSSMTrapMIB
	DESCRIPTION "IPMI Power Consumption service is Unknown"

	--#TYPE       "IPMI Power Consumption Service Event"
	--#SUMMARY    "Monitored service is Unknown"
	--#ARGUMENTS  {}
	--#SEVERITY   CRITICAL

	::= 1304
	
trapIpmiSysinfoStatusNormal TRAP-TYPE
	ENTERPRISE smSSMTrapMIB
	DESCRIPTION "IPMI System Information service has returned to Normal"

	--#TYPE       "IPMI System Information Service Event"
	--#SUMMARY    "Monitored service has returned to Normal"
	--#ARGUMENTS  {}
	--#SEVERITY   INFORMATIONAL

	::= 1401

trapIpmiSysinfoStatusWarning TRAP-TYPE
	ENTERPRISE smSSMTrapMIB
	DESCRIPTION "IPMI System Information service is Warning"

	--#TYPE       "IPMI System Information Service Event"
	--#SUMMARY    "Monitored service is Warning"
	--#ARGUMENTS  {}
	--#SEVERITY   WARNING

	::= 1402
	
trapIpmiSysinfoStatusCritical TRAP-TYPE
	ENTERPRISE smSSMTrapMIB
	DESCRIPTION "IPMI System Information service is Critical"

	--#TYPE       "IPMI System Information Service Event"
	--#SUMMARY    "Monitored service is Critical"
	--#ARGUMENTS  {}
	--#SEVERITY   CRITICAL

	::= 1403
	
trapIpmiSysinfoStatusUnknown TRAP-TYPE
	ENTERPRISE smSSMTrapMIB
	DESCRIPTION "IPMI System Information service is Unknown"

	--#TYPE       "IPMI System Information Service Event"
	--#SUMMARY    "Monitored service is Unknown"
	--#ARGUMENTS  {}
	--#SEVERITY   CRITICAL

	::= 1404
	
trapSumSupportStatusNormal TRAP-TYPE
	ENTERPRISE smSSMTrapMIB
	DESCRIPTION "Check SUM Support service has returned to Normal"

	--#TYPE       "Check SUM Support Service Event"
	--#SUMMARY    "Monitored service has returned to Normal"
	--#ARGUMENTS  {}
	--#SEVERITY   INFORMATIONAL

	::= 1501

trapSumSupportStatusWarning TRAP-TYPE
	ENTERPRISE smSSMTrapMIB
	DESCRIPTION "Check SUM Support service is Warning"

	--#TYPE       "Check SUM Support Service Event"
	--#SUMMARY    "Monitored service is Warning"
	--#ARGUMENTS  {}
	--#SEVERITY   WARNING

	::= 1502
	
trapSumSupportStatusCritical TRAP-TYPE
	ENTERPRISE smSSMTrapMIB
	DESCRIPTION "Check SUM Support service is Critical"

	--#TYPE       "Check SUM Support Service Event"
	--#SUMMARY    "Monitored service is Critical"
	--#ARGUMENTS  {}
	--#SEVERITY   CRITICAL

	::= 1503
	
trapSumSupportStatusUnknown TRAP-TYPE
	ENTERPRISE smSSMTrapMIB
	DESCRIPTION "Check SUM Support service is Unknown"

	--#TYPE       "Check SUM Support Service Event"
	--#SUMMARY    "Monitored service is Unknown"
	--#ARGUMENTS  {}
	--#SEVERITY   CRITICAL

	::= 1504

trapIpmiSelHealthStatusNormal TRAP-TYPE
	ENTERPRISE smSSMTrapMIB
	DESCRIPTION "IPMI SEL Health service has returned to Normal"

	--#TYPE       "IPMI SEL Health Service Event"
	--#SUMMARY    "Monitored service has returned to Normal"
	--#ARGUMENTS  {}
	--#SEVERITY   INFORMATIONAL

	::= 1601

trapIpmiSelHealthStatusWarning TRAP-TYPE
	ENTERPRISE smSSMTrapMIB
	DESCRIPTION "IPMI SEL Health service is Warning"

	--#TYPE       "IPMI SEL Health Service Event"
	--#SUMMARY    "Monitored service is Warning"
	--#ARGUMENTS  {}
	--#SEVERITY   WARNING

	::= 1602
	
trapIpmiSelHealthStatusCritical TRAP-TYPE
	ENTERPRISE smSSMTrapMIB
	DESCRIPTION "IPMI SEL Health service is Critical"

	--#TYPE       "IPMI SEL Health Service Event"
	--#SUMMARY    "Monitored service is Critical"
	--#ARGUMENTS  {}
	--#SEVERITY   CRITICAL

	::= 1603
	
trapIpmiSelHealthStatusUnknown TRAP-TYPE
	ENTERPRISE smSSMTrapMIB
	DESCRIPTION "IPMI SEL Health service is Unknown"

	--#TYPE       "IPMI SEL Health Service Event"
	--#SUMMARY    "Monitored service is Unknown"
	--#ARGUMENTS  {}
	--#SEVERITY   CRITICAL

	::= 1604
	
END

-- Copyright (C) 2008-2014 Super Micro Computer Inc. All Rights Reserved

-- $Id: fstacsxt.mib,v 1.3 2013/09/20 14:48:24 siva Exp $

-- TACACS-CLIENT-EXT-MIB DEFINITIONS ::= BEGIN

SUPERMICRO-TACACS-EXT-MIB DEFINITIONS ::= BEGIN

IMPORTS
    MODULE-IDENTITY, OBJECT-TYPE,
    Integer32, Unsigned32, enterprises,
    Counter32                        FROM SNMPv2-SMI
    DisplayString, RowStatus         FROM SNMPv2-TC
    InetAddressType, InetAddress     FROM INET-ADDRESS-MIB;

futureTacacsClientExtMIB MODULE-IDENTITY
    LAST-UPDATED "201209050000Z"
    ORGANIZATION "Super Micro Computer Inc."
    CONTACT-INFO "support@Supermicro.com"
	 DESCRIPTION
         "The MIB for ISSAcessControl."
	 REVISION "201209050000Z"
         DESCRIPTION
         "The MIB for ISSAcessControl."
         ::= { enterprises  supermicro-computer-inc(10876) super-switch(101) extended(2) 29 }


futureTacacsClientExtScalarGroup   OBJECT IDENTIFIER 
                                                ::= { futureTacacsClientExtMIB 1 }
futureTacacsClientExtTableGroup   OBJECT IDENTIFIER 
                                                ::= { futureTacacsClientExtMIB 2 }

-- Scalar MIB definitions 
-- ***********************

fsTacClntExtActiveServerAddressType OBJECT-TYPE
   SYNTAX      InetAddressType
   MAX-ACCESS  read-write 
   STATUS      current
   DESCRIPTION
   "The address type of active server.This can be IPv4 or IPv6."
    ::= { futureTacacsClientExtScalarGroup 1 }


fsTacClntExtActiveServer   OBJECT-TYPE
    SYNTAX      InetAddress 
    MAX-ACCESS  read-write
    STATUS      current
    DESCRIPTION
      "Maximum of 5 server's(IPv4 or IPv6) information could be configured 
      for TACACS. This object indicates the active server among 
      those 5 servers. The TACACS+ client interacts with the server 
      having this IP address . Setting this object to zero disables 
      the active server concept."
    ::= { futureTacacsClientExtScalarGroup 2 }


fsTacClntExtTraceLevel   OBJECT-TYPE
    SYNTAX      Unsigned32
    MAX-ACCESS  read-write
    STATUS      current
    DESCRIPTION
      "The debug trace level for TACACS+ client implementation. This is a bit
      mapped data. Each bit of this object reprsents a trace level.
       0x00000001 - Infomation
       0x00000002 - Errors
       0x00000004 - Tx. packet dump
       0x00000008 - Rx. packet dump
       0xffffffff - All of the above
       0x00000000 - No trace"
    ::= { futureTacacsClientExtScalarGroup 3 }

fsTacClntExtRetransmit   OBJECT-TYPE
    SYNTAX      Integer32 (1..100)
    MAX-ACCESS  read-write
    STATUS      current
    DESCRIPTION
      " Number of times the TACACS+ client searches the list of Maximum number of  TACACS+ servers(IPv4 or IPv6)i.e 5 as of now"
    DEFVAL { 2 }
    ::= { futureTacacsClientExtScalarGroup 4 }

-- ----------------------------------
-- Statistics scalar MIB definitions
-- ----------------------------------

fsTacClntExtStatisticsGroup   OBJECT IDENTIFIER 
                                        ::= { futureTacacsClientExtScalarGroup 5 }

fsTacClntExtAuthenStartRequests   OBJECT-TYPE
    SYNTAX      Counter32
    MAX-ACCESS  read-only
    STATUS      current
    DESCRIPTION
      "Number of authentication start requests sent to the server(IPv4 or IPv6)."
    ::= { fsTacClntExtStatisticsGroup 1 }

fsTacClntExtAuthenContinueRequests   OBJECT-TYPE
    SYNTAX      Counter32
    MAX-ACCESS  read-only
    STATUS      current
    DESCRIPTION
      "Number of authentication continue requests sent to the server(IPv4 or IPv6)."
    ::= { fsTacClntExtStatisticsGroup 2 }

fsTacClntExtAuthenEnableRequests   OBJECT-TYPE
    SYNTAX      Counter32
    MAX-ACCESS  read-only
    STATUS      current
    DESCRIPTION
      "Number of authentication enable requests sent to the server(IPv4 or IPv6)."
    ::= { fsTacClntExtStatisticsGroup 3 }

fsTacClntExtAuthenAbortRequests   OBJECT-TYPE
    SYNTAX      Counter32
    MAX-ACCESS  read-only
    STATUS      current
    DESCRIPTION
      "Number of authentication abort requests sent to the server(IPv4 or IPv6)."
    ::= { fsTacClntExtStatisticsGroup 4 }

fsTacClntExtAuthenPassReceived   OBJECT-TYPE
    SYNTAX      Counter32
    MAX-ACCESS  read-only
    STATUS      current
    DESCRIPTION
      "Number of authentication passes received from the server(IPv4 or IPv6)."
    ::= { fsTacClntExtStatisticsGroup 5 }

fsTacClntExtAuthenFailReceived   OBJECT-TYPE
    SYNTAX      Counter32
    MAX-ACCESS  read-only
    STATUS      current
    DESCRIPTION
      "Number of authentication fails received from the server(IPv4 or IPv6)."
    ::= { fsTacClntExtStatisticsGroup 6 }

fsTacClntExtAuthenGetUserReceived   OBJECT-TYPE
    SYNTAX      Counter32
    MAX-ACCESS  read-only
    STATUS      current
    DESCRIPTION
      "Number of authentication get users received from the server(IPv4 or IPv6)."
    ::= { fsTacClntExtStatisticsGroup 7 }

fsTacClntExtAuthenGetPassReceived   OBJECT-TYPE
    SYNTAX      Counter32
    MAX-ACCESS  read-only
    STATUS      current
    DESCRIPTION
      "Number of authentication get passwords received from the server(IPv4 or IPv6)."
    ::= { fsTacClntExtStatisticsGroup 8 }

fsTacClntExtAuthenGetDataReceived   OBJECT-TYPE
    SYNTAX      Counter32
    MAX-ACCESS  read-only
    STATUS      current
    DESCRIPTION
      "Number of authentication get data received from the  server(IPv4 or IPv6)."
    ::= { fsTacClntExtStatisticsGroup 9 }

fsTacClntExtAuthenErrorReceived   OBJECT-TYPE
    SYNTAX      Counter32
    MAX-ACCESS  read-only
    STATUS      current
    DESCRIPTION
      "Number of authentication errors received from the server(IPv4 or IPv6)."
    ::= { fsTacClntExtStatisticsGroup 10 }

fsTacClntExtAuthenFollowReceived   OBJECT-TYPE
    SYNTAX      Counter32
    MAX-ACCESS  read-only
    STATUS      current
    DESCRIPTION
      "Number of authentication follows received from the server(IPv4 or IPv6)."
    ::= { fsTacClntExtStatisticsGroup 11 }

fsTacClntExtAuthenRestartReceived   OBJECT-TYPE
    SYNTAX      Counter32
    MAX-ACCESS  read-only
    STATUS      current
    DESCRIPTION
      "Number of authentication re-starts received from the server(IPv4 or IPv6)."
    ::= { fsTacClntExtStatisticsGroup 12 }

fsTacClntExtAuthenSessionTimouts   OBJECT-TYPE
    SYNTAX      Counter32
    MAX-ACCESS  read-only
    STATUS      current
    DESCRIPTION
      "Number of authentication session time outs"
    ::= { fsTacClntExtStatisticsGroup 13 }

fsTacClntExtAuthorRequests   OBJECT-TYPE
    SYNTAX      Counter32
    MAX-ACCESS  read-only
    STATUS      current
    DESCRIPTION
      "Number of authorization requests sent to the server(IPv4 or IPv6)."
    ::= { fsTacClntExtStatisticsGroup 14 }

fsTacClntExtAuthorPassAddReceived   OBJECT-TYPE
    SYNTAX      Counter32
    MAX-ACCESS  read-only
    STATUS      current
    DESCRIPTION
      "Number of authorization pass adds received from  the server(IPv4 or IPv6)."
    ::= { fsTacClntExtStatisticsGroup 15 }

fsTacClntExtAuthorPassReplReceived   OBJECT-TYPE
    SYNTAX      Counter32
    MAX-ACCESS  read-only
    STATUS      current
    DESCRIPTION
      "Number of authorization pass replaces received from the server(IPv4 or IPv6)."
    ::= { fsTacClntExtStatisticsGroup 16 }

fsTacClntExtAuthorFailReceived   OBJECT-TYPE
    SYNTAX      Counter32
    MAX-ACCESS  read-only
    STATUS      current
    DESCRIPTION
      "Number of authorization fails received from the server(IPv4 or IPv6)."
    ::= { fsTacClntExtStatisticsGroup 17 }

fsTacClntExtAuthorErrorReceived   OBJECT-TYPE
    SYNTAX      Counter32
    MAX-ACCESS  read-only
    STATUS      current
    DESCRIPTION
      "Number of authorization errors received from the server(IPv4 or IPv6)."
    ::= { fsTacClntExtStatisticsGroup 18 }

fsTacClntExtAuthorFollowReceived   OBJECT-TYPE
    SYNTAX      Counter32
    MAX-ACCESS  read-only
    STATUS      current
    DESCRIPTION
      "Number of authorization follow received from the server(IPv4 or IPv6)."
    ::= { fsTacClntExtStatisticsGroup 19 }

fsTacClntExtAuthorSessionTimeouts   OBJECT-TYPE
    SYNTAX      Counter32
    MAX-ACCESS  read-only
    STATUS      current
    DESCRIPTION
      "Number of authorization session time outs"
    ::= { fsTacClntExtStatisticsGroup 20 }

fsTacClntExtAcctStartRequests   OBJECT-TYPE
    SYNTAX      Counter32
    MAX-ACCESS  read-only
    STATUS      current
    DESCRIPTION
      "Number of accounting start requests sent to the server(IPv4 or IPv6)."
    ::= { fsTacClntExtStatisticsGroup 21 }

fsTacClntExtAcctWdRequests   OBJECT-TYPE
    SYNTAX      Counter32
    MAX-ACCESS  read-only
    STATUS      current
    DESCRIPTION
      "Number of accounting watch dog requests sent to the server(IPv4 or IPv6)."
    ::= { fsTacClntExtStatisticsGroup 22 }

fsTacClntExtAcctStopRequests   OBJECT-TYPE
    SYNTAX      Counter32
    MAX-ACCESS  read-only
    STATUS      current
    DESCRIPTION
      "Number of accounting stop requests sent to the server(IPv4 or IPv6)."
    ::= { fsTacClntExtStatisticsGroup 23 }

fsTacClntExtAcctSuccessReceived   OBJECT-TYPE
    SYNTAX      Counter32
    MAX-ACCESS  read-only
    STATUS      current
    DESCRIPTION
      "Number of accounting successes received from the server(IPv4 or IPv6)."
    ::= { fsTacClntExtStatisticsGroup 24 }

fsTacClntExtAcctErrorReceived   OBJECT-TYPE
    SYNTAX      Counter32
    MAX-ACCESS  read-only
    STATUS      current
    DESCRIPTION
      "Number of accounting errors received from the server(IPv4 or IPv6)."
    ::= { fsTacClntExtStatisticsGroup 25 }

fsTacClntExtAcctFollowReceived   OBJECT-TYPE
    SYNTAX      Counter32
    MAX-ACCESS  read-only
    STATUS      current
    DESCRIPTION
      "Number of accounting follows  received from the server(IPv4 or IPv6)."
    ::= { fsTacClntExtStatisticsGroup 26 }

fsTacClntExtAcctSessionTimeouts   OBJECT-TYPE
    SYNTAX      Counter32
    MAX-ACCESS  read-only
    STATUS      current
    DESCRIPTION
      "Number of accounting session time outs."
    ::= { fsTacClntExtStatisticsGroup 27 }

fsTacClntExtMalformedPktsReceived   OBJECT-TYPE
    SYNTAX      Counter32
    MAX-ACCESS  read-only
    STATUS      current
    DESCRIPTION
      "Number of Malformed packets received from the server(IPv4 or IPv6)."
    ::= { fsTacClntExtStatisticsGroup 28 }

fsTacClntExtSocketFailures   OBJECT-TYPE
    SYNTAX      Counter32
    MAX-ACCESS  read-only
    STATUS      current
    DESCRIPTION
      "Number of socket failures occured."
    ::= { fsTacClntExtStatisticsGroup 29 }

fsTacClntExtConnectionFailures   OBJECT-TYPE
    SYNTAX      Counter32
    MAX-ACCESS  read-only
    STATUS      current
    DESCRIPTION
      "Number of connection failures occured."
    ::= { fsTacClntExtStatisticsGroup 30 }

-- Tabular MIB definitions 
-- ***********************

-- ----------------------------------
-- Table 1: TACACS+ Server Table
-- ----------------------------------

fsTacClntExtServerTable   OBJECT-TYPE
    SYNTAX SEQUENCE OF FsTacClntExtServerEntry
    MAX-ACCESS not-accessible
    STATUS     current
    DESCRIPTION
      "The TACACS+ server(IPv4 or IPv6) table of server information entries. The entries have
      server information such as server IP address, secret key, port no and timeout."
   ::= { futureTacacsClientExtTableGroup 1 }

fsTacClntExtServerEntry OBJECT-TYPE
   SYNTAX      FsTacClntExtServerEntry
   MAX-ACCESS  not-accessible
   STATUS      current
   DESCRIPTION
      "The entry has server address type, server IP address, port no. secret key and timeout."
   INDEX {fsTacClntExtServerAddressType, fsTacClntExtServerAddress }
   ::= { fsTacClntExtServerTable 1 }
      
FsTacClntExtServerEntry ::= SEQUENCE {
      fsTacClntExtServerAddressType
         InetAddressType,
      fsTacClntExtServerAddress
         InetAddress, 
      fsTacClntExtServerStatus
         RowStatus,
      fsTacClntExtServerSingleConnect
         INTEGER,
      fsTacClntExtServerPort
         Integer32,
      fsTacClntExtServerTimeout
         Integer32,
      fsTacClntExtServerKey
         DisplayString
      }

fsTacClntExtServerAddressType OBJECT-TYPE
   SYNTAX      InetAddressType
   MAX-ACCESS  not-accessible
   STATUS      current
   DESCRIPTION
   "The type of IP address used.This can be IPv4 or IPv6."
   ::= { fsTacClntExtServerEntry 1 }

fsTacClntExtServerAddress OBJECT-TYPE
    SYNTAX      InetAddress 
    MAX-ACCESS  not-accessible
    STATUS      current
    DESCRIPTION
      "Server IP address"
   ::= { fsTacClntExtServerEntry 2 }

fsTacClntExtServerStatus OBJECT-TYPE
    SYNTAX      RowStatus
    MAX-ACCESS  read-create
    STATUS      current
    DESCRIPTION
      "Row status of the server(IPv4 or IPv6) entry."
   ::= { fsTacClntExtServerEntry 3 }

fsTacClntExtServerSingleConnect   OBJECT-TYPE
    SYNTAX      INTEGER {
                        yes(1), 
                        no(2) 
                        }
    MAX-ACCESS  read-create
    STATUS      current
    DESCRIPTION
      " Multiple sessions are handled over single TCP, when single connect support is enabled.
        When single connect is disabled multiple TCP connections established by server."
    DEFVAL { no }
   ::= { fsTacClntExtServerEntry 4 }

fsTacClntExtServerPort OBJECT-TYPE
    SYNTAX      Integer32 (0..65535)
    MAX-ACCESS  read-create
    STATUS      current
    DESCRIPTION
      "Server port no. for TACACS+ protocol. The default value is 49."
    DEFVAL { 49 }
   ::= { fsTacClntExtServerEntry 5 }

fsTacClntExtServerTimeout OBJECT-TYPE
    SYNTAX      Integer32 (1..255)
    MAX-ACCESS  read-create
    STATUS      current
    DESCRIPTION
      "The time out value within which a response is expected from server(IPv4 or IPv6). The session will be released, 
      if the response is not received within this time out."
    DEFVAL { 5 }
   ::= { fsTacClntExtServerEntry 6 }

fsTacClntExtServerKey OBJECT-TYPE
    SYNTAX      DisplayString
    MAX-ACCESS  read-create
    STATUS      current
    DESCRIPTION
      "Secret key shared between the client and server(IPv4 or IPv6) for encryption and
      decryption"
   ::= { fsTacClntExtServerEntry 7 }

-- ----------------------------------
-- Table 2: TACACS+ Server Group Table
-- ----------------------------------

fsTacClntExtServerGroupMibTable   OBJECT-TYPE
   SYNTAX SEQUENCE OF FsTacClntExtServerGroupMibEntry
   MAX-ACCESS  not-accessible
   STATUS      current
   DESCRIPTION
      "The TACACS+ server group table."
   ::= { futureTacacsClientExtTableGroup 2 }

fsTacClntExtServerGroupMibEntry OBJECT-TYPE
   SYNTAX      FsTacClntExtServerGroupMibEntry
   MAX-ACCESS  not-accessible
   STATUS      current
   DESCRIPTION
      "The TACACS+ server group table entry. The entries are indexed with the
      server group name, server address type, and the server address.
      To create/delete a server group, use the index with server address type 0
      and a 0-length address (0.0).
      Ex: snmpset fsTacClntExtServerGroupMibStatus.'G1'.0.0 4
          snmpset fsTacClntExtServerGroupMibStatus.'G1'.0.0 6
      After a server group is created, servers can be added into it.
      Ex: snmpset fsTacClntExtServerGroupMibStatus.'G1'.1.'1.2.3.4' 4
      "
   INDEX {
      fsTacClntExtServerGroupMibName,
      fsTacClntExtServerGroupServerAddressType,
      fsTacClntExtServerGroupServerAddress
      }
   ::= { fsTacClntExtServerGroupMibTable 1 }

FsTacClntExtServerGroupMibEntry ::= SEQUENCE {
      fsTacClntExtServerGroupMibStatus
         RowStatus,
      fsTacClntExtServerGroupMibName
         DisplayString,
      fsTacClntExtServerGroupServerAddressType
         InetAddressType,
      fsTacClntExtServerGroupServerAddress
         InetAddress
      }

fsTacClntExtServerGroupMibStatus OBJECT-TYPE
    SYNTAX      RowStatus
    MAX-ACCESS  read-create
    STATUS      current
    DESCRIPTION
      "Row status of the server group entry."
   ::= { fsTacClntExtServerGroupMibEntry 1 }

fsTacClntExtServerGroupMibName OBJECT-TYPE
   SYNTAX      DisplayString (SIZE(1..31))
   MAX-ACCESS  not-accessible
   STATUS      current
   DESCRIPTION
   "The name of the server group."
   ::= { fsTacClntExtServerGroupMibEntry 2 }

fsTacClntExtServerGroupServerAddressType OBJECT-TYPE
   SYNTAX      InetAddressType
   MAX-ACCESS  not-accessible
   STATUS      current
   DESCRIPTION
   "The type of IP address used. This can be IPv4 or IPv6."
   ::= { fsTacClntExtServerGroupMibEntry 3 }

fsTacClntExtServerGroupServerAddress OBJECT-TYPE
    SYNTAX      InetAddress
    MAX-ACCESS  not-accessible
    STATUS      current
    DESCRIPTION
      "Server IP address"
   ::= { fsTacClntExtServerGroupMibEntry 4 }

END

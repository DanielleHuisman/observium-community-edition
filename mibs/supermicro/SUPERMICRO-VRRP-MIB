-- Copyright (C) 2008-2014 Super Micro Computer Inc. All Rights Reserved

-- $Id: fsvrrp.mib,v 1.8 2012/09/07 09:52:06 siva Exp $

--    VRRP Proprietary MIB Definition
      
--    This document explains the proprietary MIB implemented
--    for VRRP product.
      
--    This proprietary MIB definition, supplements Rfc 2787 
--    and also provides management of certain proprietary features of
--    VRRP. 
      
--    The proprietary MIB definitions follows:


SUPERMICRO-VRRP-MIB DEFINITIONS ::= BEGIN
    
      IMPORTS
         MODULE-IDENTITY, OBJECT-TYPE, 
         enterprises, Integer32 FROM SNMPv2-SMI
         vrrpOperEntry FROM VRRP-MIB;
    
---   futuresoftware OBJECT IDENTIFIER ::= { enterprises 2076 }
                                                 

      fsvrrp MODULE-IDENTITY
            LAST-UPDATED "201209050000Z"
            ORGANIZATION "Super Micro Computer Inc."
            CONTACT-INFO "support@Supermicro.com"
            DESCRIPTION
               " The proprietary MIB module for VRRP. "
	    REVISION "201209050000Z"	    
            DESCRIPTION
               " The proprietary MIB module for VRRP. "
         ::=  { enterprises supermicro-computer-inc(10876) super-switch(101) basic(1) 153 }
   
-- ------------------------------------------------------------ 
-- groups in the MIB 
-- ------------------------------------------------------------

  fsVrrpSystem                OBJECT IDENTIFIER ::= { fsvrrp 1 }

  fsVrrpStatus OBJECT-TYPE
    SYNTAX INTEGER {
              enabled          (1),
              disabled         (2)
           }
    MAX-ACCESS read-write
    STATUS     current
    DESCRIPTION
        "Indicates whether the VRRP is enabled Globally."
    ::=  { fsVrrpSystem 1 }

  fsVrrpMaxOperEntries OBJECT-TYPE
    SYNTAX Integer32
    MAX-ACCESS read-only
    STATUS     current
    DESCRIPTION
        "Gives the Maximum Number of Oper Table Entries."
    ::=  { fsVrrpSystem 2 }

-- *******************************************************************
--  VRRP Operations Table extension
-- *******************************************************************

 fsVrrpOperTable OBJECT-TYPE
     SYNTAX       SEQUENCE OF FsVrrpOperEntry
     MAX-ACCESS   not-accessible
     STATUS       current
     DESCRIPTION
         "Operations table for a VRRP router which consists of a
          sequence of 'fsVrrpOperEntry' items. This table is a 
          proprietary extension to the standard vrrpOperTable"
     ::= { fsVrrpSystem 3 }

 fsVrrpOperEntry OBJECT-TYPE
     SYNTAX       FsVrrpOperEntry
     MAX-ACCESS   not-accessible
     STATUS       current
     DESCRIPTION
         "An entry in the fsVrrpOperTable contains the additional 
          operational characteristics of a virtual router apart 
          from vrrpOperTable."

     AUGMENTS    { vrrpOperEntry }
     ::= { fsVrrpOperTable 1 }

 FsVrrpOperEntry ::=
     SEQUENCE {
         fsVrrpAdminPriority
             Integer32,
         fsVrrpOperAdvertisementIntervalInMsec
             Integer32,
         fsvrrpOperPingEnable
             TruthValue
 }

 fsVrrpAdminPriority OBJECT-TYPE
     SYNTAX       Integer32 (0..254)
     MAX-ACCESS   read-write
     STATUS       current
     DESCRIPTION
         "This object is same as that of vrrpOperPriority specified 
          in VRRP-MIB. The only difference is, if the router owns the
          associated IP address(es) then vrrpOperPriority will have 
          the value 255 and fsVrrpAdminPriority will have the value 
          configured by the administrator. Write operation requires 
          admin down for this instance and the change will be reflected 
          in the value of vrrpOperPriority also."
     DEFVAL       { 100 }
     ::= { fsVrrpOperEntry 1 }

 fsVrrpOperAdvertisementIntervalInMsec OBJECT-TYPE
     SYNTAX       Integer32 (100..255000)
     UNITS        "milli seconds"
     MAX-ACCESS   read-create
     STATUS       current
     DESCRIPTION
         "The time interval, in milli  seconds, between sending
         advertisement messages. Only the master router sends
         VRRP advertisements."
     DEFVAL       { 1000 }
     ::= { fsVrrpOperEntry 2 }

 fsvrrpOperPingEnable OBJECT-TYPE
    SYNTAX INTEGER {
              enabled          (1),
              disabled         (2)
           }
     MAX-ACCESS   read-create
     STATUS       current
     DESCRIPTION
         "Controls whether VRRP Master to accept ping packets sent to one of the 
          virtual router’s IP addresses."
     DEFVAL       { 2 }
     ::= { fsVrrpOperEntry 3 }
     
   fsVrrpAuthDeprecate OBJECT-TYPE
    SYNTAX INTEGER {
              enabled          (1),
              disabled         (2)
           }
    MAX-ACCESS read-write
    STATUS     current
    DESCRIPTION
        "If this MIB object is set to 'enabled',then authentication can be set
         to Type 0 alone. If it is set to  disabled, then authentication type
         can be set to any one of the values type 0-2. When set to disabled, 
         authentication feature is compatible with RFC 2338" 
    DEFVAL 	{ 1 }
    ::=  { fsVrrpSystem 4 }

    fsVrrpTraceOption OBJECT-TYPE
          SYNTAX      Integer32
          MAX-ACCESS  read-write
          STATUS      current
          DESCRIPTION
             "This object is used to enable trace statements in
              VRRP Module.
              A four byte integer is used for enabling the trace level.
              Each bit in the four byte integer represents a particular
              trace level.
              The mapping between the bit positions & the trace level is
              as follows:

                0x00000000 - No Traces
                0x0000ffff - All Traces
                0x00000001 - Packet Traces
                0x00000002 - Event Traces
                0x00000004 - Init Traces
                0x00000008 - Timers Traces
                0x00000010 - All Failures Traces

              For example if the 0x00000001 and 0x00000002 are set, then the trace
              statement related to Packet and Event related
              messages will be printed."

    DEFVAL { 0 }
    ::= { fsVrrpSystem 5 }


END

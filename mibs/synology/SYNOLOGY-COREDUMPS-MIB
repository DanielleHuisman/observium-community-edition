SYNOLOGY-COREDUMPS-MIB DEFINITIONS ::= BEGIN

IMPORTS
	OBJECT-GROUP, MODULE-COMPLIANCE
		FROM SNMPv2-CONF
	OBJECT-TYPE, Integer32, enterprises, MODULE-IDENTITY
		FROM SNMPv2-SMI;

synologyCoredump MODULE-IDENTITY
	LAST-UPDATED	"201605240000Z"
	ORGANIZATION	"www.synology.com"
	CONTACT-INFO
		 "postal:   Wei-Te Ho
		  email:	weiteho@synology.com"
	DESCRIPTION		"List coredumps in DS"
	REVISION		"201605240000Z"
	DESCRIPTION		"First draft."
	::= { synology 201 }

synology	OBJECT IDENTIFIER
	::= { enterprises 6574 }

coredumpTable OBJECT-TYPE
	SYNTAX		SEQUENCE OF CoredumpEntry
	MAX-ACCESS	not-accessible
	STATUS		current
	DESCRIPTION	"Table of coredumps data."
	::= { synologyCoredump 1 }

coredumpEntry OBJECT-TYPE
	SYNTAX		CoredumpEntry
	MAX-ACCESS	not-accessible
	STATUS		current
	DESCRIPTION "An entry containing coredump information"
	INDEX		{ coredumpInfoIndex }
	::= { coredumpTable 1 }

CoredumpEntry ::= SEQUENCE {
	coredumpInfoIndex	Integer32,
	coredumpFilePath	OCTET STRING,
	coredumpTimestamp	Integer32
}

coredumpInfoIndex OBJECT-TYPE
	SYNTAX		Integer32(0..2147483647)
	MAX-ACCESS	not-accessible
	STATUS		current
	DESCRIPTION	"Coredump info index"
	::= { coredumpEntry 1 }

coredumpFilePath OBJECT-TYPE
	SYNTAX		OCTET STRING
	MAX-ACCESS	read-only
	STATUS		current
	DESCRIPTION	"Coredump file path"
	::= { coredumpEntry 2 }

coredumpTimestamp OBJECT-TYPE
	SYNTAX		Integer32
	MAX-ACCESS	read-only
	STATUS		current
	DESCRIPTION "Coredump time stamp"
	::= { coredumpEntry 3 }

synologyCoredumpConformance	OBJECT IDENTIFIER ::= { synologyCoredump 2 }
synologyCoredumpCompliances	OBJECT IDENTIFIER ::= { synologyCoredumpConformance 1 }
synologyCoredumpGroups			OBJECT IDENTIFIER ::= { synologyCoredumpConformance 2 }

synologyCoredumpCompliance MODULE-COMPLIANCE
	STATUS				current
	DESCRIPTION
						"The compliance statement for coredump information."
	MODULE				-- this module
	MANDATORY-GROUPS	{ synologyCoredumpGroup }
	::= { synologyCoredumpCompliances 1 }

synologyCoredumpGroup OBJECT-GROUP
	OBJECTS {	coredumpFilePath,
				coredumpTimestamp }
	STATUS		current
	DESCRIPTION
				"A collection of objects providing basic information
				of an synology coredump entity."
	::= { synologyCoredumpGroups 1 }

END

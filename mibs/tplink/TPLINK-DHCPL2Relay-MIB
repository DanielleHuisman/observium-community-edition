TPLINK-DHCPL2Relay-MIB DEFINITIONS ::= BEGIN

         IMPORTS
            MODULE-IDENTITY, OBJECT-TYPE
          	  	        FROM SNMPv2-SMI
          	ifIndex
						FROM RFC1213-MIB
            tplinkMgmt
						FROM TPLINK-MIB; 
	    
			tplinkDhcpL2RelayMIB MODULE-IDENTITY
				LAST-UPDATED    "201212171014Z"
				ORGANIZATION    "TPLINK"
				CONTACT-INFO    "www.tplink.com"
				DESCRIPTION	    "Private MIB for DHCP L2 Relay configuration."
				REVISION        "201212171014Z"
				DESCRIPTION
				"Initial version of this MIB module."
			::= { tplinkMgmt 66 }
		
			tplinkDhcpL2RelayMIBObjects		OBJECT IDENTIFIER	::= { tplinkDhcpL2RelayMIB 1 }
			tplinkDhcpL2RelayNotifications		OBJECT IDENTIFIER	::= { tplinkDhcpL2RelayMIB 2 }
                
  			dhcpL2RelayGlobalConfig		OBJECT IDENTIFIER	::= { tplinkDhcpL2RelayMIBObjects 1 }
			dhcpL2RelayOption82Config		OBJECT IDENTIFIER	::= { tplinkDhcpL2RelayMIBObjects 2 }
				
				dhcpL2RelayEnable OBJECT-TYPE
	          		SYNTAX  INTEGER{
	      				disable(0), 						
	      				enable(1)						
	      			}
	            MAX-ACCESS  read-write
	            STATUS  current
	            DESCRIPTION
	                    "0. disable 
	                     1. enable
	                     Enable or disable the DHCP L2 Relay function globally."
	            ::= { dhcpL2RelayGlobalConfig 1 }
      				
				dhcpL2RelayVlanConfigTable OBJECT-TYPE
					SYNTAX  	SEQUENCE OF DhcpL2RelayVlanConfigTable
					MAX-ACCESS  not-accessible
					STATUS  	current
					DESCRIPTION
							"Here you can view and modify the DHCP L2 Relay VLAN config table."
				::= { dhcpL2RelayGlobalConfig 2 }

				dhcpL2RelayVlanConfigEntry OBJECT-TYPE
					SYNTAX  	DhcpL2RelayVlanConfigTable
					MAX-ACCESS  not-accessible
					STATUS  	current
					DESCRIPTION
							"An entry contains of the DHCP L2 Relay function enable status information of a VLAN."
					INDEX   { dhcpL2RelayVlanId }
				::= { dhcpL2RelayVlanConfigTable 1 }

				DhcpL2RelayVlanConfigTable ::=
					SEQUENCE {
						dhcpL2RelayVlanId
								INTEGER(1..4094),
						dhcpL2RelayVlanStatus
								INTEGER
					}

				dhcpL2RelayVlanId OBJECT-TYPE
					SYNTAX 	 	INTEGER(1..4094)
					MAX-ACCESS  read-create
					STATUS  	current
					DESCRIPTION
							"Enter the ID number of VLAN,1-4094."
				::= { dhcpL2RelayVlanConfigEntry 1 }
				
        		dhcpL2RelayVlanStatus OBJECT-TYPE
	          		SYNTAX  INTEGER{
	      				disable(0), 						
	      				enable(1)						
	      			}
	            	MAX-ACCESS  read-create
	            	STATUS  current
	            	DESCRIPTION
	                    "0. disable 
	                     1. enable
	                     Enable or disable DHCP L2 Relay function in specified VLAN. "
	            ::= { dhcpL2RelayVlanConfigEntry 2 }

	           -- the DHCP L2 Relay option 82 config
	         
		       dhcpL2RelayOption82ConfigTable OBJECT-TYPE
		          SYNTAX  SEQUENCE OF DHCPL2RELAYOPTION82CONFIGENTRY
		          MAX-ACCESS  not-accessible
		          STATUS  current
		          DESCRIPTION
		                  "A list of DHCP L2 Relay option 82 config entries.
		                   Here you can configure the port parameters for the DHCP L2 Relay option 82 feature."
		          ::= { dhcpL2RelayOption82Config 1 }
	
		      dhcpL2RelayOption82ConfigEntry OBJECT-TYPE
		          SYNTAX  DHCPL2RELAYOPTION82CONFIGENTRY
		          MAX-ACCESS  not-accessible
		          STATUS  current
		          DESCRIPTION
		                  "An entry contains of the information of DHCP L2 Relay option 82 config."
		          INDEX   {ifIndex}
		          ::= { dhcpL2RelayOption82ConfigTable 1 }
	  
		      DHCPL2RELAYOPTION82CONFIGENTRY ::=
		          SEQUENCE {
									dhcpL2RelayOption82ConfigPort
											OCTET STRING (SIZE (0..255)), 
									dhcpL2RelayOption82ConfigSupportStatus
											INTEGER, 
									dhcpL2RelayOption82ConfigOperationStrategy
											INTEGER,
									dhcpL2RelayOption82ConfigFormat
											INTEGER,
									dhcpL2RelayOption82ConfigCircuitCustomization
											INTEGER,
									dhcpL2RelayOption82ConfigCircuitID
											OCTET STRING (SIZE (0..64)),
									dhcpL2RelayOption82ConfigRemoteCustomization
											INTEGER,
									dhcpL2RelayOption82ConfigRemoteID
											OCTET STRING (SIZE (0..64)),
									dhcpL2RelayOption82ConfigLag
											OCTET STRING (SIZE (1..255))  
		          }
	          
		      dhcpL2RelayOption82ConfigPort OBJECT-TYPE
		          SYNTAX  OCTET STRING (SIZE (0..255))  
		          MAX-ACCESS  read-only
		          STATUS  current
		          DESCRIPTION
		                  "Port number"
		          ::= { dhcpL2RelayOption82ConfigEntry 1 }
	    
		     dhcpL2RelayOption82ConfigSupportStatus OBJECT-TYPE
		          SYNTAX  INTEGER{
		      		disable(0), 						
		      		enable(1)			
		      		}
		          MAX-ACCESS  read-write
		          STATUS  current
		          DESCRIPTION
		                  "0. disable
		                   1. enable
		                   Select Enable/Disable the port to support the Option 82 feature. "       
		          ::= { dhcpL2RelayOption82ConfigEntry 2 }
	       
		      dhcpL2RelayOption82ConfigOperationStrategy OBJECT-TYPE
			        SYNTAX  INTEGER{
		      		keep(0), 						
		      		replace(1),
		      		drop(2)						
		      		}
		            MAX-ACCESS  read-write
		            STATUS  current
		            DESCRIPTION
		                    "Select the operation for the Option 82 filed of the DHCP request packets from the Host.
		                     0. keep: Indicates to keep the Option 82 field of the packets. 
		                     1. replace: Indicates to replace the Option 82 field of the packets with the switch defined one. 
		                     2. drop: Indicates to discard the packets including the Option 82 field."
		            ::= { dhcpL2RelayOption82ConfigEntry 3 }

		      dhcpL2RelayOption82ConfigFormat OBJECT-TYPE
			        SYNTAX  INTEGER{
		      		normal(0), 						
		      		private(1)					
		      		}
		            MAX-ACCESS  read-write
		            STATUS  current
		            DESCRIPTION
		                    "Select the format for the Option 82 sub-option value field.
		                     0. normal: the format of sub-option value field is TLV(type-length-value). 
		                     1. replace: the format of sub-option value field is just value."
		            ::= { dhcpL2RelayOption82ConfigEntry 4 }
					
		      dhcpL2RelayOption82ConfigCircuitCustomization OBJECT-TYPE   
		          SYNTAX  INTEGER{
		      		disable(0), 						
		      		enable(1)						
		      		}
		            MAX-ACCESS  read-write
		            STATUS  current
		            DESCRIPTION
		                    "0. disable 
		                     1. enable
		                     Enable/Disable the switch to define the Option 82 circuit id."
		            ::= { dhcpL2RelayOption82ConfigEntry 5 }
	                      
		      dhcpL2RelayOption82ConfigCircuitID OBJECT-TYPE            
		          SYNTAX  OCTET STRING (SIZE (0..64)) 
		            MAX-ACCESS  read-write
		            STATUS  current
		            DESCRIPTION
		                    "The sub-option Circuit ID for the customized Option 82.(0-64 characters)"
		            ::= { dhcpL2RelayOption82ConfigEntry 6 }
	            
	      dhcpL2RelayOption82ConfigRemoteCustomization OBJECT-TYPE   
	          SYNTAX  INTEGER{
	      		disable(0), 						
	      		enable(1)						
	      		}
	            MAX-ACCESS  read-write
	            STATUS  current
	            DESCRIPTION
	                    "0. disable 
	                     1. enable
	                     Enable/Disable the switch to define the Option 82 remote id. "
	            ::= { dhcpL2RelayOption82ConfigEntry 7 }
	                      
		      dhcpL2RelayOption82ConfigRemoteID OBJECT-TYPE            
		          SYNTAX  OCTET STRING (SIZE (0..64)) 
		            MAX-ACCESS  read-write
		            STATUS  current
		            DESCRIPTION
		                    "The sub-option Remote ID for the customized Option 82.(0-64 characters)"
		            ::= { dhcpL2RelayOption82ConfigEntry 8 }
	 	                      
		      dhcpL2RelayOption82ConfigLag OBJECT-TYPE
		            SYNTAX  OCTET STRING (SIZE (1..255))  
		            MAX-ACCESS  read-only
		            STATUS  current
		            DESCRIPTION
		                    "The LAG to which the port belongs to."
		            ::= { dhcpL2RelayOption82ConfigEntry 9 }
          
END

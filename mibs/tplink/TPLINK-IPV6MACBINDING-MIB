TPLINK-IPV6MACBINDING-MIB DEFINITIONS ::= BEGIN

	 IMPORTS
		TPRowStatus
				FROM TPLINK-TC-MIB 
		tplinkMgmt
				FROM TPLINK-MIB
		OBJECT-TYPE,MODULE-IDENTITY,IpAddress
				FROM SNMPv2-SMI             
		InetAddress
				FROM INET-ADDRESS-MIB;		
				
		tplinkIpv6MacBindingMIB MODULE-IDENTITY
				LAST-UPDATED    "201212171014Z"
				ORGANIZATION    "TPLINK"
				CONTACT-INFO    "www.tplink.com"
				DESCRIPTION	    "Private MIB for IPv6 MAC Binding configuration."
				REVISION        "201212171014Z"
				DESCRIPTION
				"Initial version of this MIB module."
			::= { tplinkMgmt 69 }

            tplinkIpv6MacBindingMIBObjects		OBJECT IDENTIFIER	::= { tplinkIpv6MacBindingMIB 1 }
            tplinkIpv6MacBindingNotifications		OBJECT IDENTIFIER	::= { tplinkIpv6MacBindingMIB 2 }
                                                
            tpIpv6MacBindigConfigure				OBJECT IDENTIFIER ::= {tplinkIpv6MacBindingMIBObjects 1}			
                
            tpIpv6MacBindingTable OBJECT-TYPE
            SYNTAX  SEQUENCE OF TPIPV6MACBINDINGENTRY
            MAX-ACCESS  not-accessible
            STATUS  current
            DESCRIPTION
                "A list of IPv6 MAC Binding entries.
                 Here you can add or delete entries.
                 Here you can only Modify the hostname and protected type of IPv6 MAC Binding entries whitch are already created."
            ::= { tpIpv6MacBindigConfigure 1 }
        
            tpIpv6MacBindingEntry OBJECT-TYPE
            SYNTAX  TPIPV6MACBINDINGENTRY
            MAX-ACCESS  not-accessible
            STATUS  current
            DESCRIPTION
                "An entry contains of the information of IPv6 MAC Binding."
            INDEX   {tpIpv6BindingIp}
            ::= { tpIpv6MacBindingTable 1 }
        
            TPIPV6MACBINDINGENTRY ::=
            SEQUENCE {
                tpIpv6BindingHostName
                    OCTET STRING (SIZE (1..20)),
                tpIpv6BindingIp
                    InetAddress,
                tpIpv6BindingMac
                    OCTET STRING (SIZE (1..17)),
                tpIpv6BindingVlanId
                    INTEGER,
                tpIpv6BindingPort
                    OCTET STRING (SIZE (1..20)),			
                tpIpv6BindingProtectType
                    INTEGER,
                tpIpv6BindingSource
                    INTEGER,
                tpIpv6BindingRowStatus
                    TPRowStatus
            }
            
            tpIpv6BindingHostName OBJECT-TYPE
                SYNTAX OCTET STRING (SIZE (1..20))
                MAX-ACCESS read-write
                STATUS current
                DESCRIPTION
                    "Host Name of the binding entry."
                ::= {tpIpv6MacBindingEntry 1}
        
            tpIpv6BindingIp OBJECT-TYPE
                SYNTAX InetAddress
                MAX-ACCESS read-create
                STATUS current
                DESCRIPTION
                    "IPv6 address of the binding entry."
                ::= {tpIpv6MacBindingEntry 2}
         
            tpIpv6BindingMac OBJECT-TYPE
                SYNTAX OCTET STRING (SIZE (1..17))
                MAX-ACCESS read-create
                STATUS current
                DESCRIPTION
                    "MAC address of the binding entry."
                ::= {tpIpv6MacBindingEntry 3}
        
            tpIpv6BindingVlanId OBJECT-TYPE
                SYNTAX INTEGER
                MAX-ACCESS read-create
                STATUS current
                DESCRIPTION
                    "VLAN ID of the binding entry."
                ::= {tpIpv6MacBindingEntry 4}
        
            tpIpv6BindingPort OBJECT-TYPE
                SYNTAX OCTET STRING (SIZE (1..20))
                MAX-ACCESS read-create
                STATUS current
                DESCRIPTION
                    "Port number of the binding entry."
                ::= {tpIpv6MacBindingEntry 5}
        
            tpIpv6BindingProtectType OBJECT-TYPE
                SYNTAX INTEGER {
                    none(0),
                    nd-detection(1),
                    ipv6-source-guard(2),
                    both(3)
                }
                MAX-ACCESS read-write
                STATUS current
                DESCRIPTION
                    "Protect type of the binding entry.
                    none: Do not apply the entry to any one of network security functions.
                    nd-detection: Apply the entry to ND Detetion function.
                    ipv6-source-guard: Apply the entry to IPv6 Source Guard function. 
                    both: Apply the entry to both ND Detection and IPv6 Source Guard."
                ::= {tpIpv6MacBindingEntry 6}
                
            tpIpv6BindingSource OBJECT-TYPE
                SYNTAX INTEGER{
                    manual(1),
                    dhcp-snooping(2),
                    nd-snooping(3)
                }
                MAX-ACCESS read-only
                STATUS current
                DESCRIPTION
                    "Source of the binding entry.
                    manual: the entry comes from manual binding.
                    dhcp-snooping: the entry comes from DHCPv6 Snooping.
                    nd-snooping: the entry comes from ND Snooping."
                ::= {tpIpv6MacBindingEntry 7}
                        
            tpIpv6BindingRowStatus OBJECT-TYPE
                SYNTAX  TPRowStatus
                MAX-ACCESS  read-write
                STATUS  current
                DESCRIPTION
                    "the following value are states:
                    these values may be read or written
                    active(1),
                    notInService(2),
        
                    the following value is a state:
                    this value may be read, but not written
                    notReady(3),
        
                    the following three values are
                    actions: these values may be written,
                    but are never read
                    createAndGo(4),
                    createAndWait(5),
                    destroy(6)"
                ::= {tpIpv6MacBindingEntry 8}
                
END

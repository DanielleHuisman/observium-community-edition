TPLINK-LOCALPROXYARP-MIB	DEFINITIONS ::= BEGIN	
    IMPORTS
		tplinkMgmt
			FROM TPLINK-MIB			
        OBJECT-TYPE,IpAddress
          	FROM SNMPv2-SMI;
	    
		tplinkLocalProxyArpMIB MODULE-IDENTITY
		LAST-UPDATED    "201212130930Z"
		ORGANIZATION    "TPLINK"
		CONTACT-INFO    "www.tplink.com"
		DESCRIPTION	    "Private MIB for local proxy arp configuration."
		REVISION        "201212130930Z"
		DESCRIPTION
				"Initial version of this MIB module."
		::= { tplinkMgmt 46 }
		
	tplinkLocalProxyArpMIBObjects		OBJECT IDENTIFIER	::= { tplinkLocalProxyArpMIB 1 }
	tplinkLocalProxyArpNotifications		OBJECT IDENTIFIER	::= { tplinkLocalProxyArpMIB 2 }
	
	--**************
	--Set Local Proxy Arp
	--**************
	tpLocalProxyArpConfig	  	OBJECT IDENTIFIER ::= {tplinkLocalProxyArpMIB 1}
	
	tpLocalProxyArpTable OBJECT-TYPE
		SYNTAX  SEQUENCE OF LOCALPROXYARPENTRY
		MAX-ACCESS  not-accessible
		STATUS  current
		DESCRIPTION
			"Local Proxy Arp."
		::= { tpLocalProxyArpConfig 1 }

	tpLocalProxyArpEntry OBJECT-TYPE
		SYNTAX  LOCALPROXYARPENTRY
		MAX-ACCESS  not-accessible
		STATUS  current
		DESCRIPTION
			"An entry contains of the information of port configure."
		INDEX   { tpLocalProxyArpInterface }
		::= { tpLocalProxyArpTable 1 }

	LOCALPROXYARPENTRY ::=
		SEQUENCE {
			tpLocalProxyArpInterface
				OCTET STRING (SIZE (0..50)),
			tpLocalProxyArpIpAddr
				IpAddress,
			tpLocalProxyArpIpMask
				IpAddress,
			tpLocalProxyArpEnable 		
				INTEGER
		}

	tpLocalProxyArpInterface OBJECT-TYPE
		SYNTAX  OCTET STRING (SIZE (0..50))
		MAX-ACCESS  read-only
		STATUS  current
		DESCRIPTION
			"Displays the interface."
		::= { tpLocalProxyArpEntry 1 } 

	tpLocalProxyArpIpAddr OBJECT-TYPE
		SYNTAX  IpAddress  
		MAX-ACCESS  read-only
		STATUS  current
		DESCRIPTION
			"Displays the local proxy arp ip address."
		::= { tpLocalProxyArpEntry 2 }

	tpLocalProxyArpIpMask OBJECT-TYPE
		SYNTAX  IpAddress
		MAX-ACCESS  read-only
		STATUS  current
		DESCRIPTION
			"Displays the local proxy arp ip address mask"
		::= { tpLocalProxyArpEntry 3 }    

	tpLocalProxyArpEnable OBJECT-TYPE
		SYNTAX  INTEGER{
						disable(0), 					--Disable
						enable(1)						--Enable
						}
		MAX-ACCESS  read-write
		STATUS  current
		DESCRIPTION
			"Select Enable/Disable local proxy arp for the interface. 
			0. Disable
			1. Enable"
		::= { tpLocalProxyArpEntry 4 }

END

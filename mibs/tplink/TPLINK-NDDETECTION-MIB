TPLINK-NDDETECTION-MIB DEFINITIONS ::= BEGIN

         IMPORTS
            MODULE-IDENTITY, OBJECT-TYPE, Counter64
          	  	        FROM SNMPv2-SMI
          	ifIndex
						FROM RFC1213-MIB
            tplinkMgmt
						FROM TPLINK-MIB; 
	    
			tplinkNdDetectionMIB MODULE-IDENTITY
				LAST-UPDATED    "201212171014Z"
				ORGANIZATION    "TPLINK"
				CONTACT-INFO    "www.tplink.com"
				DESCRIPTION	    "Private MIB for ND Detection configuration."
				REVISION        "201212171014Z"
				DESCRIPTION
				"Initial version of this MIB module."
			::= { tplinkMgmt 93 }
		
			tplinkNdDetectionMIBObjects		OBJECT IDENTIFIER	::= { tplinkNdDetectionMIB 1 }
			tplinkNdDetectionNotifications		OBJECT IDENTIFIER	::= { tplinkNdDetectionMIB 2 }
  			
  			ndDetectionGlobalConfig		OBJECT IDENTIFIER	::= { tplinkNdDetectionMIBObjects 1 }
			ndDetectionVlanConfig		OBJECT IDENTIFIER	::= { tplinkNdDetectionMIBObjects 2 }
            ndDetectionPortConfig     		OBJECT IDENTIFIER	::= { tplinkNdDetectionMIBObjects 3 }
			ndDetectionStatisticConfig    OBJECT IDENTIFIER ::= {tplinkNdDetectionMIBObjects 4}	
			
				ndDetectionEnable OBJECT-TYPE
	          		SYNTAX  INTEGER{
	      				disable(0), 						
	      				enable(1)						
	      			}
	            MAX-ACCESS  read-write
	            STATUS  current
	            DESCRIPTION
	                    "0. disable 
	                     1. enable
	                     Enable or disable the ND Detection function globally."
	            ::= { ndDetectionGlobalConfig 1 }
				
        -- the ND Detection VLAN config     
				ndDetectionVlanConfigTable OBJECT-TYPE
					SYNTAX  	SEQUENCE OF NdDetectionVlanConfigTable
					MAX-ACCESS  not-accessible
					STATUS  	current
					DESCRIPTION
							"Here you can view and modify the ND Detection VLAN config table."
				::= { ndDetectionVlanConfig 1 }

				ndDetectionVlanConfigEntry OBJECT-TYPE
					SYNTAX  	NdDetectionVlanConfigTable
					MAX-ACCESS  not-accessible
					STATUS  	current
					DESCRIPTION
							"An entry contains of the ND Detection function enable status information of a VLAN."
					INDEX   { ndDetectionVlanId }
				::= { ndDetectionVlanConfigTable 1 }

				NdDetectionVlanConfigTable ::=
					SEQUENCE {
						ndDetectionVlanId
								INTEGER(1..4094),
						ndDetectionVlanStatus
								INTEGER,
						ndDetectionVlanLogStatus
								INTEGER	
					}

				ndDetectionVlanId OBJECT-TYPE
					SYNTAX 	 	INTEGER(1..4094)
					MAX-ACCESS  read-only
					STATUS  	current
					DESCRIPTION
							"Enter the ID number of VLAN,1-4094."
				::= { ndDetectionVlanConfigEntry 1 }
				
        		ndDetectionVlanStatus OBJECT-TYPE
	          		SYNTAX  INTEGER{
	      				disable(0), 						
	      				enable(1)						
	      			}
	            	MAX-ACCESS  read-write
	            	STATUS  current
	            	DESCRIPTION
	                    "0. disable 
	                     1. enable
	                     Enable or disable ND Detection function in specified VLAN. "
	            ::= { ndDetectionVlanConfigEntry 2 }

				ndDetectionVlanLogStatus OBJECT-TYPE
					SYNTAX  INTEGER{
						disable(0), 						
						enable(1)						
					}
					MAX-ACCESS  read-write
					STATUS  current
					DESCRIPTION
						"0. disable 
						 1. enable
						 Enable or disable ND Detection logging function in specified VLAN. "
				::= { ndDetectionVlanConfigEntry 3 }
			
       -- the ND Detection port config
         
       			ndDetectionPortConfigTable OBJECT-TYPE
          			SYNTAX  SEQUENCE OF NdDetectionPortConfigEntry
          			MAX-ACCESS  not-accessible
          			STATUS  current
          			DESCRIPTION
                  		"A list of ND Detection port config entries.
                   		Here you can configure the port parameters for the ND Detection."
          		::= { ndDetectionPortConfig 1 }

      			ndDetectionPortConfigEntry OBJECT-TYPE
          			SYNTAX  NdDetectionPortConfigEntry
          			MAX-ACCESS  not-accessible
          			STATUS  current
          			DESCRIPTION
                  		"An entry contains of the information of ND Detection port config."
          			INDEX   {ifIndex}
          		::= { ndDetectionPortConfigTable 1 }
  
      			NdDetectionPortConfigEntry ::=
          			SEQUENCE {
          					ndDetectionPort
          						    OCTET STRING (SIZE (0..255)),
							ndDetectionPortConfigTrustedPort
									INTEGER, 
							ndDetectionPortConfigPortLag
									OCTET STRING  
          			}
          			
                ndDetectionPort OBJECT-TYPE
					SYNTAX  	OCTET STRING (SIZE (0..255))
					MAX-ACCESS  read-only
					STATUS  	current
					DESCRIPTION
						"Display port number"
				::= { ndDetectionPortConfigEntry 1 }
               
      			ndDetectionPortConfigTrustedPort OBJECT-TYPE
          			SYNTAX  INTEGER{
      					disable(0), 						
      					enable(1)			
      				}
          			MAX-ACCESS  read-write
          			STATUS  current
          			DESCRIPTION
                  		"0. disable
                   		 1. enable
                   		 Select Enable/Disable the port to be a Trusted Port. 
                   		 Only the Trusted Port can forward the Router Advertisement Message and Router Redirect Message from Routers."
          		::= { ndDetectionPortConfigEntry 2 }
       
      			ndDetectionPortConfigPortLag OBJECT-TYPE
            		SYNTAX  OCTET STRING (SIZE (1..255))  
            		MAX-ACCESS  read-only
            		STATUS  current
            		DESCRIPTION
                    	"The LAG to which the port belongs to."
            	::= { ndDetectionPortConfigEntry 3 }

        -- the ND Detection statistic config
		    ndDetectionStatReset OBJECT-TYPE
				  SYNTAX  INTEGER{
					notReset(0), 						
					reset(1)			
					}
					MAX-ACCESS  read-write
					STATUS  current
					DESCRIPTION
							"0. notReset
							 1. reset
							 clear the statistics"
					::= { ndDetectionStatisticConfig 1 }
					
			ndDetectionStatTable OBJECT-TYPE
				SYNTAX  	SEQUENCE OF NDDETECTIONSTATENTRY
				MAX-ACCESS  not-accessible
				STATUS  	current
				DESCRIPTION
						"Here you can view the ND Detection statistics."
			::= { ndDetectionStatisticConfig 2 }

			ndDetectionStatEntry OBJECT-TYPE
				SYNTAX  	NDDETECTIONSTATENTRY
				MAX-ACCESS  not-accessible
				STATUS  	current
				DESCRIPTION
						"An entry contains of the ND Detection packets stastics information of a VLAN."
				INDEX   { ndDetectionStatVlanId }
			::= { ndDetectionStatTable 1 }

			NDDETECTIONSTATENTRY ::=
				SEQUENCE {
					ndDetectionStatVlanId
							INTEGER(1..4094),
					ndDetectionStatForward
							Counter64,
					ndDetectionStatDrop
							Counter64		
				}

			ndDetectionStatVlanId OBJECT-TYPE
				SYNTAX 	 	INTEGER(1..4094)
				MAX-ACCESS  read-only
				STATUS  	current
				DESCRIPTION
						"Enter the ID number of VLAN, 1-4094."
			::= { ndDetectionStatEntry 1 }
			
			ndDetectionStatForward OBJECT-TYPE
				SYNTAX  Counter64
				MAX-ACCESS  read-only
				STATUS  current
				DESCRIPTION
					"Display ND packets number forwarded by the vlan. "
			::= { ndDetectionStatEntry 2 }

			ndDetectionStatDrop OBJECT-TYPE
				SYNTAX  Counter64
				MAX-ACCESS  read-only
				STATUS  current
				DESCRIPTION
					"Display ND packets number drop by the vlan. "
			::= { ndDetectionStatEntry 3 }				
          
END

TPLINK-NDSNOOPING-MIB DEFINITIONS ::= BEGIN

         IMPORTS
            MODULE-IDENTITY, OBJECT-TYPE
          	  	        FROM SNMPv2-SMI
          	ifIndex
						FROM RFC1213-MIB
            tplinkMgmt
						FROM TPLINK-MIB; 
	    
			tplinkNdSnoopingMIB MODULE-IDENTITY
				LAST-UPDATED    "201212171014Z"
				ORGANIZATION    "TPLINK"
				CONTACT-INFO    "www.tplink.com"
				DESCRIPTION	    "Private MIB for ND Snooping configuration."
				REVISION        "201212171014Z"
				DESCRIPTION
				"Initial version of this MIB module."
			::= { tplinkMgmt 92 }
		
			tplinkNdSnoopingMIBObjects		OBJECT IDENTIFIER	::= { tplinkNdSnoopingMIB 1 }
			tplinkNdSnoopingNotifications		OBJECT IDENTIFIER	::= { tplinkNdSnoopingMIB 2 }
  			
  			ndSnoopingGlobalConfig		OBJECT IDENTIFIER	::= { tplinkNdSnoopingMIBObjects 1 }
            ndSnoopingPortConfig     		OBJECT IDENTIFIER	::= { tplinkNdSnoopingMIBObjects 3 }
				
				ndSnoopingEnable OBJECT-TYPE
	          		SYNTAX  INTEGER{
	      				disable(0), 						
	      				enable(1)						
	      			}
	            MAX-ACCESS  read-write
	            STATUS  current
	            DESCRIPTION
	                    "0. disable 
	                     1. enable
	                     Enable or disable the ND Snooping function globally."
	            ::= { ndSnoopingGlobalConfig 1 }
      
				ndSnoopingVlanConfigTable OBJECT-TYPE
					SYNTAX  	SEQUENCE OF NdSnoopingVlanConfigTable
					MAX-ACCESS  not-accessible
					STATUS  	current
					DESCRIPTION
							"Here you can view and modify the ND Snooping VLAN config table."
				::= { ndSnoopingGlobalConfig 2 }

				ndSnoopingVlanConfigEntry OBJECT-TYPE
					SYNTAX  	NdSnoopingVlanConfigTable
					MAX-ACCESS  not-accessible
					STATUS  	current
					DESCRIPTION
							"An entry contains of the ND Snooping function enable status information of a VLAN."
					INDEX   { ndSnoopingVlanId }
				::= { ndSnoopingVlanConfigTable 1 }

				NdSnoopingVlanConfigTable ::=
					SEQUENCE {
						ndSnoopingVlanId
								INTEGER(1..4094),
						ndSnoopingVlanStatus
								INTEGER
					}

				ndSnoopingVlanId OBJECT-TYPE
					SYNTAX 	 	INTEGER(1..4094)
					MAX-ACCESS  read-only
					STATUS  	current
					DESCRIPTION
							"Enter the ID number of VLAN,1-4094."
				::= { ndSnoopingVlanConfigEntry 1 }
				
        		ndSnoopingVlanStatus OBJECT-TYPE
	          		SYNTAX  INTEGER{
	      				disable(0), 						
	      				enable(1)						
	      			}
	            	MAX-ACCESS  read-write
	            	STATUS  current
	            	DESCRIPTION
	                    "0. disable 
	                     1. enable
	                     Enable or disable ND Snooping function in specified VLAN. "
	            ::= { ndSnoopingVlanConfigEntry 2 }	            
       -- the nd Snooping port config
         
       			ndSnoopingPortConfigTable OBJECT-TYPE
          			SYNTAX  SEQUENCE OF NdSnoopingPortConfigEntry
          			MAX-ACCESS  not-accessible
          			STATUS  current
          			DESCRIPTION
                  		"A list of ND Snooping port config entries.
                   		Here you can configure the port parameters for the ND Snooping."
          		::= { ndSnoopingPortConfig 1 }

      			ndSnoopingPortConfigEntry OBJECT-TYPE
          			SYNTAX  NdSnoopingPortConfigEntry
          			MAX-ACCESS  not-accessible
          			STATUS  current
          			DESCRIPTION
                  		"An entry contains of the information of ND Snooping port config."
          			INDEX   {ifIndex}
          		::= { ndSnoopingPortConfigTable 1 }
  
      			NdSnoopingPortConfigEntry ::=
          			SEQUENCE {
          					ndSnoopingPort
          						    OCTET STRING (SIZE (0..255)),
							ndSnoopingPortConfigMaxEntry
									INTEGER(-1..1024), 
							ndSnoopingPortConfigPortLag
									OCTET STRING  
          			}
          			
                ndSnoopingPort OBJECT-TYPE
					SYNTAX  	OCTET STRING (SIZE (0..255))
					MAX-ACCESS  read-only
					STATUS  	current
					DESCRIPTION
						"Display port number"
				::= { ndSnoopingPortConfigEntry 1 }
               
      			ndSnoopingPortConfigMaxEntry OBJECT-TYPE
          			SYNTAX  INTEGER(-1..1024)
          			MAX-ACCESS  read-write
          			STATUS  current
          			DESCRIPTION
                  		"Set the maxinum entry of the interface."
          		::= { ndSnoopingPortConfigEntry 2 }
       
      			ndSnoopingPortConfigPortLag OBJECT-TYPE
            		SYNTAX  OCTET STRING (SIZE (1..255))  
            		MAX-ACCESS  read-only
            		STATUS  current
            		DESCRIPTION
                    	"The LAG to which the port belongs to."
            	::= { ndSnoopingPortConfigEntry 3 }
          
END

TPLINK-PORTMIRROR-MIB DEFINITIONS ::= BEGIN
		IMPORTS
			OBJECT-TYPE,MODULE-IDENTITY
			  	         	FROM SNMPv2-SMI    	  	         	
			tplinkMgmt
							FROM TPLINK-MIB;

   	    tplinkPortMirrorMIB MODULE-IDENTITY  
			LAST-UPDATED    "201212140000Z"
			ORGANIZATION    "TPLINK"
			CONTACT-INFO	"www.tplink.com"
			DESCRIPTION		"The config of the port mirror."
			REVISION        "201212140000Z"
			DESCRIPTION		"Initial version of this MIB module."
			::= { tplinkMgmt 11 } 
	    
		tplinkPortMirrorMIBObjects			OBJECT IDENTIFIER ::= { tplinkPortMirrorMIB 1 }
		tplinkPortMirrorMIBNotifications	OBJECT IDENTIFIER ::= { tplinkPortMirrorMIB 2 }
		
	    tpPortMirrorTable OBJECT-TYPE
			SYNTAX  	SEQUENCE OF TPPORTMIRRORENTRY
			MAX-ACCESS  not-accessible
			STATUS  	current
			DESCRIPTION
				  ""
			::= { tplinkPortMirrorMIBObjects 1 }

	    tpPortMirrorEntry OBJECT-TYPE
			SYNTAX  	TPPORTMIRRORENTRY
			MAX-ACCESS  not-accessible
			STATUS  	current
			DESCRIPTION
				  ""
			INDEX   	{ tpPortMirrorSession }
			::= { tpPortMirrorTable 1 }

	    TPPORTMIRRORENTRY ::=
			SEQUENCE {
				tpPortMirrorSession 		INTEGER,
				tpPortMirrorDestination 	OCTET STRING,
				tpPortMirrorIngressSource 	OCTET STRING,
				tpPortMirrorEgressSource 	OCTET STRING,
				tpPortMirrorBothSource 		OCTET STRING,
				tpPortMirrorSessionState	INTEGER	
			}

        tpPortMirrorSession	OBJECT-TYPE
			SYNTAX		INTEGER    				
			MAX-ACCESS	read-only
			STATUS		current
			DESCRIPTION	
				"This object indicates the session number of the mirror group."

			::= { tpPortMirrorEntry 1 }
            
		tpPortMirrorDestination OBJECT-TYPE
			SYNTAX 		OCTET STRING
			MAX-ACCESS	read-write
			STATUS		current
			DESCRIPTION	
				"	This object indicates a destination port which monitors specified 
				ports on the switch, should be given as 1/0/1.
					Note: The member of LAG cannot be assigned as a destination port."
			::= { tpPortMirrorEntry 2 }
		    
		tpPortMirrorIngressSource OBJECT-TYPE
			SYNTAX 		OCTET STRING
			MAX-ACCESS	read-write
			STATUS		current
			DESCRIPTION	
				"	This object indicates a list of the source ports. Any packets received 
				from these ports will be copyed to the assigned destination port. This 
				should be given as 1/0/1,1/0/2-12.
					Note: The ports in other sessions and destination port can't add to 
				this list."
			::= { tpPortMirrorEntry 3 }
		    
		tpPortMirrorEgressSource OBJECT-TYPE
			SYNTAX 		OCTET STRING
			MAX-ACCESS	read-write
			STATUS		current
			DESCRIPTION	
				"	This object indicates a list of the source ports. Any packets sended 
				out from these ports will be copyed to the assigned destination ports.This 
				should be given as 1/0/1,1/0/2-12.
					Note: The ports in other sessions and destination port can't add to 
				this list."
			::= { tpPortMirrorEntry 4 }
		    
		tpPortMirrorBothSource OBJECT-TYPE
			SYNTAX 		OCTET STRING
			MAX-ACCESS	read-write
			STATUS		current
			DESCRIPTION	
				"	This object indicates a list of the source ports. Any packets received 
				 or sended out from these ports will be copyed to the assigned destination 
				 ports.This should be given as 1/0/1,1/0/2-12.
					Note: The ports in other sessions and destination port can't add to 
				this list."
			::= { tpPortMirrorEntry 5 }
		    
		tpPortMirrorSessionState OBJECT-TYPE
			SYNTAX 		INTEGER
						{
							--the following two values are states,
							--these values may be read, but not written
							negative(1),
							active(2),
							
							--the following value is a state,
							--this value may be read or written
							clear(3)
						}
			MAX-ACCESS	read-write
			STATUS		current
			DESCRIPTION	
				"	This object indicates the state of mirror session.If a session has been 
				assigned both destination port and source ports, then the value of this 
				object changes to active(2). Otherwise the value of this object is to be
				negative(1). When the value of this object is assigned to clear(3), then the 
				configuration of this session will be cleared, and the state changes to 
				negative(1). Be aware of that only clear(3) can be assigned to this object."
			::= { tpPortMirrorEntry 6 }
										          	  	          
END

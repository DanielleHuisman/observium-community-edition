TPLINK-SNMP-MIB DEFINITIONS ::= BEGIN

	IMPORTS
		MODULE-IDENTITY
					FROM SNMPv2-SMI
		tplinkMgmt	          
					FROM TPLINK-MIB; 
          	  	          
          	 
	tplinkSnmpMIB MODULE-IDENTITY
	    LAST-UPDATED    "201212140000Z"
	    ORGANIZATION    "TPLINK"
	    CONTACT-INFO    "www.tplink.com"
	    DESCRIPTION
	             "Private MIB for snmp config."
	    REVISION        "200908190000Z"
	    DESCRIPTION
	            "Initial version of this MIB module."
	    ::= { tplinkMgmt 32 }
	    
	tplinkSnmpMIBObjects		OBJECT IDENTIFIER ::= { tplinkSnmpMIB 1 }
	tplinkSnmpMIBNotifications	OBJECT IDENTIFIER ::= { tplinkSnmpMIB 2 }
  	
END

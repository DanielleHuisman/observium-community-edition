-- - - - - - - - - - - - - - - - - - - - - - - - - - - - - - - - - - - - - - -
--
-- Trend Micro, Inc.
-- Copyright information is in the DESCRIPTION section of the MODULE-IDENTITY.
-- 
-- - - - - - - - - - - - - - - - - - - - - - - - - - - - - - - - - - - - - - -

TPT-ATA-REG-MIB

DEFINITIONS ::= BEGIN

IMPORTS
  MODULE-IDENTITY, 
  OBJECT-IDENTITY
    FROM SNMPv2-SMI

  tpt-reg
    FROM TIPPINGPOINT-REG-MIB
;

tpt-ata-family MODULE-IDENTITY
  LAST-UPDATED "201605251854Z" -- May 25, 2016
  ORGANIZATION "Trend Micro, Inc."
  CONTACT-INFO "www.trendmicro.com"
  DESCRIPTION  
    "Registration sub-tree for TippingPoint Advanced Threat Application (ATA) products.

     Copyright (C) 2016 Trend Micro Incorporated. All Rights Reserved.
     
     Trend Micro makes no warranty of any kind with regard to this material,
     including, but not limited to, the implied warranties of merchantability
     and fitness for a particular purpose. Trend Micro shall not be liable for
     errors contained herein or for incidental or consequential damages in
     connection with the furnishing, performance, or use of this material. This
     document contains proprietary information, which is protected by copyright. No
     part of this document may be photocopied, reproduced, or translated into
     another language without the prior written consent of Trend Micro. The
     information is provided 'as is' without warranty of any kind and is subject to
     change without notice. The only warranties for Trend Micro products and
     services are set forth in the express warranty statements accompanying such
     products and services. Nothing herein should be construed as constituting an
     additional warranty. Trend Micro shall not be liable for technical or editorial
     errors or omissions contained herein. TippingPoint(R), the TippingPoint logo, and
     Digital Vaccine(R) are registered trademarks of Trend Micro. All other company
     and product names may be trademarks of their respective holders. All rights
     reserved. This document contains confidential information, trade secrets or
     both, which are the property of Trend Micro. No part of this documentation may
     be reproduced in any form or by any means or used to make any derivative work
     (such as translation, transformation, or adaptation) without written permission
     from Trend Micro or one of its subsidiaries. All other company and product
     names may be trademarks of their respective holders.
    "
  
  REVISION "201605251854Z" -- May 25, 2016 
  DESCRIPTION "Updated copyright information. Minor MIB syntax fixes."
  
  REVISION "201507301735Z" -- July 30, 2015
  DESCRIPTION "Initial MIB version."
  
::= { tpt-reg 10 }

-- - - - - - - - - - - - - - - - - - - - - - - - - - - - - - - - - - - - - - - 
--
-- ATA Models
--
-- - - - - - - - - - - - - - - - - - - - - - - - - - - - - - - - - - - - - - - 

tpt-model-ata-network OBJECT-IDENTITY
  STATUS         current
  DESCRIPTION    "Registration for TippingPoint ATA Network Appliances."
  ::= { tpt-ata-family 1 }

tpt-model-ata-mail OBJECT-IDENTITY
  STATUS         current
  DESCRIPTION    "Registration for TippingPoint ATA Mail Appliances."
  ::= { tpt-ata-family 2 }

END

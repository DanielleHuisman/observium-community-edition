-- - - - - - - - - - - - - - - - - - - - - - - - - - - - - - - - - - - - - - -
--
-- Trend Micro, Inc.
-- Copyright information is in the DESCRIPTION section of the MODULE-IDENTITY.
-- 
-- - - - - - - - - - - - - - - - - - - - - - - - - - - - - - - - - - - - - - -

TPT-HOST-MIB

DEFINITIONS ::= BEGIN

IMPORTS
  MODULE-IDENTITY, OBJECT-TYPE, 
  Unsigned32
    FROM SNMPv2-SMI

  TEXTUAL-CONVENTION
    FROM SNMPv2-TC

  tpt-tpa-objs
    FROM TPT-TPAMIBS-MIB
  ;

tpt-host-objs MODULE-IDENTITY
  LAST-UPDATED "201605251854Z" -- May 25, 2016
  ORGANIZATION "Trend Micro, Inc."
  CONTACT-INFO "www.trendmicro.com"
  DESCRIPTION
    "Host information for the management port on the device.

     Copyright (C) 2016 Trend Micro Incorporated. All Rights Reserved.
     
     Trend Micro makes no warranty of any kind with regard to this material,
     including, but not limited to, the implied warranties of merchantability
     and fitness for a particular purpose. Trend Micro shall not be liable for
     errors contained herein or for incidental or consequential damages in
     connection with the furnishing, performance, or use of this material. This
     document contains proprietary information, which is protected by copyright. No
     part of this document may be photocopied, reproduced, or translated into
     another language without the prior written consent of Trend Micro. The
     information is provided 'as is' without warranty of any kind and is subject to
     change without notice. The only warranties for Trend Micro products and
     services are set forth in the express warranty statements accompanying such
     products and services. Nothing herein should be construed as constituting an
     additional warranty. Trend Micro shall not be liable for technical or editorial
     errors or omissions contained herein. TippingPoint(R), the TippingPoint logo, and
     Digital Vaccine(R) are registered trademarks of Trend Micro. All other company
     and product names may be trademarks of their respective holders. All rights
     reserved. This document contains confidential information, trade secrets or
     both, which are the property of Trend Micro. No part of this documentation may
     be reproduced in any form or by any means or used to make any derivative work
     (such as translation, transformation, or adaptation) without written permission
     from Trend Micro or one of its subsidiaries. All other company and product
     names may be trademarks of their respective holders.
    "
 
  REVISION "201605251854Z" -- May 25, 2016 
  DESCRIPTION "Updated copyright information. Minor MIB syntax fixes."
     
  ::= { tpt-tpa-objs 12 }

-- - - - - - - - - - - - - - - - - - - - - - - - - - - - - - - - - - - - - - -
--
-- Textual conventions for host MIB objects
--
-- - - - - - - - - - - - - - - - - - - - - - - - - - - - - - - - - - - - - - -

EnabledOrNot ::= TEXTUAL-CONVENTION
  STATUS      current
  DESCRIPTION 
    "An indication of whether a feature is configured as enabled or disabled."
  SYNTAX      INTEGER { disabled(0), enabled(1) }

ActiveOrNot ::= TEXTUAL-CONVENTION
  STATUS      current
  DESCRIPTION 
    "An indication of whether an IP address is active or inactive."
  SYNTAX      INTEGER { inactive(0), active(1) }

IpAddressType ::= TEXTUAL-CONVENTION
  STATUS      current
  DESCRIPTION 
    "The type of an IP address (IPv4, IPv6 user configured, IPv6 link local,
     or IPv6 autoconfig)."
  SYNTAX      INTEGER { iptypeIPv4(1),      iptypeIPv6user(2), 
                        iptypeIPv6local(3), iptypeIPv6auto(4) }

FipsMode ::= TEXTUAL-CONVENTION
  STATUS      current
  DESCRIPTION 
    "The type of FIPS mode."
  SYNTAX      INTEGER { disabled(0), crypto(1), full(2) }

ActiveCert ::= TEXTUAL-CONVENTION
  STATUS      current
  DESCRIPTION 
    "The type of active cert."
  SYNTAX      INTEGER { none(0), temporary(1), authorized(2) }

InitState ::= TEXTUAL-CONVENTION
  STATUS      current
  DESCRIPTION 
    "The state of initialization."
  SYNTAX      INTEGER { in-progress(0), complete(1) }


-- - - - - - - - - - - - - - - - - - - - - - - - - - - - - - - - - - - - - - -
--
-- Table of IP addresses on the device
--
-- - - - - - - - - - - - - - - - - - - - - - - - - - - - - - - - - - - - - - -

hostIpTable OBJECT-TYPE
  SYNTAX      SEQUENCE OF HostIpEntry
  MAX-ACCESS  not-accessible
  STATUS      current
  DESCRIPTION 
    "Table of IP addresses on the device and their attributes."
  ::= { tpt-host-objs 1 }  

hostIpEntry OBJECT-TYPE
  SYNTAX      HostIpEntry
  MAX-ACCESS  not-accessible
  STATUS      current
  DESCRIPTION 
    "An entry in the host IP address table.
     Rows cannot be created or deleted."
  INDEX       { hostIpIndex }
  ::= { hostIpTable 1 }

HostIpEntry ::= SEQUENCE {
  hostIpIndex           Unsigned32,
  hostIpAddress         OCTET STRING (SIZE (0..80)),
  hostIpType            IpAddressType,
  hostIpActive          ActiveOrNot
}

hostIpIndex OBJECT-TYPE
  SYNTAX      Unsigned32
  MAX-ACCESS  not-accessible
  STATUS      current
  DESCRIPTION 
    "Index into the IP address table, starting with 1."
  ::= { hostIpEntry 1 }

hostIpAddress OBJECT-TYPE
  SYNTAX      OCTET STRING (SIZE (0..80))
  MAX-ACCESS  read-only
  STATUS      current
  DESCRIPTION 
    "String representation of an IP address, in CIDR format."
  ::= { hostIpEntry 2 }

hostIpType OBJECT-TYPE
  SYNTAX      IpAddressType
  MAX-ACCESS  read-only
  STATUS      current
  DESCRIPTION
    "Whether this IP address is IPv4 or IPv6 and how it was configured."
  ::= { hostIpEntry 3 }

hostIpActive OBJECT-TYPE
  SYNTAX      ActiveOrNot
  MAX-ACCESS  read-only
  STATUS      current
  DESCRIPTION
    "Whether this IP address is active."
  ::= { hostIpEntry 4 }


-- - - - - - - - - - - - - - - - - - - - - - - - - - - - - - - - - - - - - - -
--
-- Additional host information for the device
--
-- - - - - - - - - - - - - - - - - - - - - - - - - - - - - - - - - - - - - - -

hostIPv4Gateway OBJECT-TYPE
  SYNTAX      OCTET STRING (SIZE (0..80))
  MAX-ACCESS  read-only
  STATUS      current
  DESCRIPTION 
    "The IPv4 default gateway."
  ::= { tpt-host-objs 2 }

hostIPv6Gateway OBJECT-TYPE
  SYNTAX      OCTET STRING (SIZE (0..80))
  MAX-ACCESS  read-only
  STATUS      current
  DESCRIPTION 
    "The IPv6 default gateway."
  ::= { tpt-host-objs 3 }

hostIPv6Enabled OBJECT-TYPE
  SYNTAX      EnabledOrNot
  MAX-ACCESS  read-only
  STATUS      current
  DESCRIPTION 
    "Whether IPv6 is enabled on the device."
  ::= { tpt-host-objs 4 }

hostIPv6AutoConfig OBJECT-TYPE
  SYNTAX      EnabledOrNot
  MAX-ACCESS  read-only
  STATUS      current
  DESCRIPTION 
    "Whether IPv6 autoconfig is enabled on the device."
  ::= { tpt-host-objs 5 }

hostFipsCfgMode OBJECT-TYPE
  SYNTAX      FipsMode
  MAX-ACCESS  read-only
  STATUS      current
  DESCRIPTION 
    "The configured FIPS mode."
  ::= { tpt-host-objs 6 }

hostFipsMode OBJECT-TYPE
  SYNTAX      FipsMode
  MAX-ACCESS  read-only
  STATUS      current
  DESCRIPTION 
    "The currently active FIPS mode."
  ::= { tpt-host-objs 7 }

hostSSLCert OBJECT-TYPE
  SYNTAX      ActiveCert
  MAX-ACCESS  read-only
  STATUS      current
  DESCRIPTION 
    "The currently active SSL cert."
  ::= { tpt-host-objs 8 }

hostInitState OBJECT-TYPE
  SYNTAX      InitState
  MAX-ACCESS  read-only
  STATUS      current
  DESCRIPTION 
    "The current host initialization state."
  ::= { tpt-host-objs 9 }



END

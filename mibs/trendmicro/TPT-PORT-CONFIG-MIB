-- - - - - - - - - - - - - - - - - - - - - - - - - - - - - - - - - - - - - - -
--
-- Trend Micro, Inc.
-- Copyright information is in the DESCRIPTION section of the MODULE-IDENTITY.
-- 
-- - - - - - - - - - - - - - - - - - - - - - - - - - - - - - - - - - - - - - -

TPT-PORT-CONFIG-MIB

DEFINITIONS ::= BEGIN

IMPORTS
  MODULE-IDENTITY, OBJECT-TYPE, 
  Unsigned32
    FROM SNMPv2-SMI

  TEXTUAL-CONVENTION
    FROM SNMPv2-TC

  tpt-tpa-objs
    FROM TPT-TPAMIBS-MIB
  ;

tpt-port-config-objs MODULE-IDENTITY
  LAST-UPDATED "201605251854Z" -- May 25, 2016
  ORGANIZATION "Trend Micro, Inc."
  CONTACT-INFO "www.trendmicro.com"
  DESCRIPTION
    "Configurable items of an interface port on the device.

     Copyright (C) 2016 Trend Micro Incorporated. All Rights Reserved.
     
     Trend Micro makes no warranty of any kind with regard to this material,
     including, but not limited to, the implied warranties of merchantability
     and fitness for a particular purpose. Trend Micro shall not be liable for
     errors contained herein or for incidental or consequential damages in
     connection with the furnishing, performance, or use of this material. This
     document contains proprietary information, which is protected by copyright. No
     part of this document may be photocopied, reproduced, or translated into
     another language without the prior written consent of Trend Micro. The
     information is provided 'as is' without warranty of any kind and is subject to
     change without notice. The only warranties for Trend Micro products and
     services are set forth in the express warranty statements accompanying such
     products and services. Nothing herein should be construed as constituting an
     additional warranty. Trend Micro shall not be liable for technical or editorial
     errors or omissions contained herein. TippingPoint(R), the TippingPoint logo, and
     Digital Vaccine(R) are registered trademarks of Trend Micro. All other company
     and product names may be trademarks of their respective holders. All rights
     reserved. This document contains confidential information, trade secrets or
     both, which are the property of Trend Micro. No part of this documentation may
     be reproduced in any form or by any means or used to make any derivative work
     (such as translation, transformation, or adaptation) without written permission
     from Trend Micro or one of its subsidiaries. All other company and product
     names may be trademarks of their respective holders.
    "
 
  REVISION "201605251854Z" -- May 25, 2016 
  DESCRIPTION "Updated copyright information. Minor MIB syntax fixes."
     
  ::= { tpt-tpa-objs 4 }

-- - - - - - - - - - - - - - - - - - - - - - - - - - - - - - - - - - - - - - -
--
-- Textual conventions for port configuration enumerations
--
-- - - - - - - - - - - - - - - - - - - - - - - - - - - - - - - - - - - - - - -

LineSpeed ::= TEXTUAL-CONVENTION
  STATUS      current
  DESCRIPTION 
    "An indication of configured network line speed."
  SYNTAX      INTEGER { default(0), gigabit(1), 
                        hundred-megabit(2), ten-megabit(3), ten-gigabit(4),
			fourty-gigabit(5)}

DuplexSetting ::= TEXTUAL-CONVENTION
  STATUS      current
  DESCRIPTION 
    "An indication of configured duplex mode."
  SYNTAX      INTEGER { default(0), half(1), full(2) }

AutoNegotiation ::= TEXTUAL-CONVENTION
  STATUS      current
  DESCRIPTION 
    "An indication of configured auto-negotiation mode."
  SYNTAX      INTEGER { default(0), on(1), off(2) }

EnabledOrNot ::= TEXTUAL-CONVENTION
  STATUS      current
  DESCRIPTION 
    "An indication of whether a feature is configured as enabled or disabled."
  SYNTAX      INTEGER { disabled(0), enabled(1) }

FailoverAction ::= TEXTUAL-CONVENTION
  STATUS      current
  DESCRIPTION 
    "An indication of whether a segment should pass traffic on failover."
  SYNTAX      INTEGER { block(0), permit(1) }

LinkDownMode ::= TEXTUAL-CONVENTION
  STATUS      current
  DESCRIPTION 
    "An indication of configured link-down-synchronization mode."
  SYNTAX      INTEGER { hub(0), breaker(1), wire(2) }

-- - - - - - - - - - - - - - - - - - - - - - - - - - - - - - - - - - - - - - -
--
-- Table of port configuration settings on the device
--
-- - - - - - - - - - - - - - - - - - - - - - - - - - - - - - - - - - - - - - -

portConfigTable OBJECT-TYPE
  SYNTAX      SEQUENCE OF PortConfigEntry
  MAX-ACCESS  not-accessible
  STATUS      current
  DESCRIPTION 
    "Table of slots/ports on the device and their configuration settings."
  ::= { tpt-port-config-objs 1 }  

portConfigEntry OBJECT-TYPE
  SYNTAX      PortConfigEntry
  MAX-ACCESS  not-accessible
  STATUS      current
  DESCRIPTION 
    "An entry in the slot/port table.
     Rows cannot be created or deleted."
  INDEX       { portConfigSlot, portConfigPort }
  ::= { portConfigTable 1 }

PortConfigEntry ::= SEQUENCE {
  portConfigSlot        Unsigned32,
  portConfigPort        Unsigned32,
  portConfigLineSpeed   LineSpeed,
  portConfigDuplex      DuplexSetting,
  portConfigAutoNeg     AutoNegotiation,
  portConfigShutdown    EnabledOrNot,
  portConfigLoopback    EnabledOrNot,
  portConfigFailover    FailoverAction,
  portConfigLDSMode     LinkDownMode,
  portConfigLDSTimeout  Unsigned32
}

portConfigSlot OBJECT-TYPE
  SYNTAX      Unsigned32
  MAX-ACCESS  read-only
  STATUS      current
  DESCRIPTION 
    "Slot number for this port."
  ::= { portConfigEntry 1 }

portConfigPort OBJECT-TYPE
  SYNTAX      Unsigned32
  MAX-ACCESS  read-only
  STATUS      current
  DESCRIPTION 
    "Port number for this port."
  ::= { portConfigEntry 2 }

portConfigLineSpeed OBJECT-TYPE
  SYNTAX      LineSpeed
  MAX-ACCESS  read-only
  STATUS      current
  DESCRIPTION
    "The line speed configuration setting of this port."
  ::= { portConfigEntry 3 }

portConfigDuplex OBJECT-TYPE
  SYNTAX      DuplexSetting
  MAX-ACCESS  read-only
  STATUS      current
  DESCRIPTION
    "The duplex configuration setting of this port."
  ::= { portConfigEntry 4 }

portConfigAutoNeg OBJECT-TYPE
  SYNTAX      AutoNegotiation
  MAX-ACCESS  read-only
  STATUS      current
  DESCRIPTION 
    "The auto-negotiation configuration setting of this port."
  ::= { portConfigEntry 5 }

portConfigShutdown OBJECT-TYPE
  SYNTAX      EnabledOrNot
  MAX-ACCESS  read-only
  STATUS      current
  DESCRIPTION 
    "The shutdown configuration setting of this port.  Shutdown enabled means 
     that the port is manually removed from service.  Shutdown disabled means
     that the port is free to come up normally."
  ::= { portConfigEntry 6 }

portConfigLoopback OBJECT-TYPE
  SYNTAX      EnabledOrNot
  MAX-ACCESS  read-only
  STATUS      current
  DESCRIPTION 
    "The loopback (on or off) configuration setting of this port."
  ::= { portConfigEntry 7 }

portConfigFailover OBJECT-TYPE
  SYNTAX      FailoverAction
  MAX-ACCESS  read-only
  STATUS      current
  DESCRIPTION 
    "The failover action (block or permit) configuration setting of this port."
  ::= { portConfigEntry 8 }

portConfigLDSMode OBJECT-TYPE
  SYNTAX      LinkDownMode
  MAX-ACCESS  read-only
  STATUS      current
  DESCRIPTION 
    "The link-down sync mode (hub, breaker, or wire) setting of this port."
  ::= { portConfigEntry 9 }

portConfigLDSTimeout OBJECT-TYPE
  SYNTAX      Unsigned32
  MAX-ACCESS  read-only
  STATUS      current
  DESCRIPTION 
    "The link-down sync timeout configuration setting of this port."
  ::= { portConfigEntry 10 }


END

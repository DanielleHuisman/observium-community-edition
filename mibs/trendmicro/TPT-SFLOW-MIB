-- - - - - - - - - - - - - - - - - - - - - - - - - - - - - - - - - - - - - - -
--
-- Trend Micro, Inc.
-- Copyright information is in the DESCRIPTION section of the MODULE-IDENTITY.
-- 
-- - - - - - - - - - - - - - - - - - - - - - - - - - - - - - - - - - - - - - -

TPT-SFLOW-MIB

DEFINITIONS ::= BEGIN

IMPORTS
  MODULE-IDENTITY, OBJECT-TYPE, Unsigned32
    FROM SNMPv2-SMI

  TEXTUAL-CONVENTION
    FROM SNMPv2-TC

  tpt-tpa-objs
    FROM TPT-TPAMIBS-MIB

  ;

tpt-sflow-objs MODULE-IDENTITY
  LAST-UPDATED "201605251854Z" -- May 25, 2016
  ORGANIZATION "Trend Micro, Inc."
  CONTACT-INFO "www.trendmicro.com"
  DESCRIPTION
    "Global sFlow status and collector address/udp port on the device.


     Copyright (C) 2016 Trend Micro Incorporated. All Rights Reserved.
     
     Trend Micro makes no warranty of any kind with regard to this material,
     including, but not limited to, the implied warranties of merchantability
     and fitness for a particular purpose. Trend Micro shall not be liable for
     errors contained herein or for incidental or consequential damages in
     connection with the furnishing, performance, or use of this material. This
     document contains proprietary information, which is protected by copyright. No
     part of this document may be photocopied, reproduced, or translated into
     another language without the prior written consent of Trend Micro. The
     information is provided 'as is' without warranty of any kind and is subject to
     change without notice. The only warranties for Trend Micro products and
     services are set forth in the express warranty statements accompanying such
     products and services. Nothing herein should be construed as constituting an
     additional warranty. Trend Micro shall not be liable for technical or editorial
     errors or omissions contained herein. TippingPoint(R), the TippingPoint logo, and
     Digital Vaccine(R) are registered trademarks of Trend Micro. All other company
     and product names may be trademarks of their respective holders. All rights
     reserved. This document contains confidential information, trade secrets or
     both, which are the property of Trend Micro. No part of this documentation may
     be reproduced in any form or by any means or used to make any derivative work
     (such as translation, transformation, or adaptation) without written permission
     from Trend Micro or one of its subsidiaries. All other company and product
     names may be trademarks of their respective holders.
    "
  
  REVISION "201605251854Z" -- May 25, 2016 
  DESCRIPTION "Updated copyright information. Minor MIB syntax fixes."
    
  ::= { tpt-tpa-objs 18 }

-- - - - - - - - - - - - - - - - - - - - - - - - - - - - - - - - - - - - - - -
--
-- Textual conventions for slot  MIB objects
--
-- - - - - - - - - - - - - - - - - - - - - - - - - - - - - - - - - - - - - - -

SflowStatus ::= TEXTUAL-CONVENTION
  STATUS      current
  DESCRIPTION 
    "An indication of sFlow enable/disable/applicable status"
  SYNTAX      INTEGER { disable(0), enable(1),  error(2), not-applicable(3) }





-- - - - - - - - - - - - - - - - - - - - - - - - - - - - - - - - - - - - - - -
--
-- sFlow collector address and udp port number
--
-- - - - - - - - - - - - - - - - - - - - - - - - - - - - - - - - - - - - - - -

sFlowCollectorTable OBJECT-TYPE
  SYNTAX      SEQUENCE OF SflowCollectorEntry
  MAX-ACCESS  not-accessible
  STATUS      current
  DESCRIPTION
    "Table of sFlow collectors. It supports up to 2 collectors."
  ::= { tpt-sflow-objs 1 }

sFlowCollectorEntry OBJECT-TYPE
  SYNTAX      SflowCollectorEntry
  MAX-ACCESS  not-accessible
  STATUS      current
  DESCRIPTION
    "A collector address and port in the sFlowCollectorTable.
     Rows cannot be created or deleted.
    "
  INDEX       { collectorIndex }
  ::= { sFlowCollectorTable 1 }

SflowCollectorEntry ::= SEQUENCE {
  collectorIndex         Unsigned32,
  collectorAddr          OCTET STRING (SIZE (0..20)),
  udpPort                Unsigned32,
  collectorAddrV6        OCTET STRING (SIZE (0..60))
}

collectorIndex OBJECT-TYPE
  SYNTAX      Unsigned32
  MAX-ACCESS  not-accessible
  STATUS      current
  DESCRIPTION
    "Index into the sFlow collector table, starting with 1."
  ::= { sFlowCollectorEntry 1 }

collectorAddr  OBJECT-TYPE
  SYNTAX      OCTET STRING (SIZE (0..20))
  MAX-ACCESS  read-only
  STATUS      current
  DESCRIPTION
    "The IPv4 address of the collector. 
     If the address is not set, the value will be an empty string. 
     It is not applicable on platforms (10/110/330). 
     For those platforms, the value will be set to an empty string.
     
    "
  ::= {sFlowCollectorEntry   2 }

udpPort       OBJECT-TYPE
  SYNTAX      Unsigned32
  MAX-ACCESS  read-only
  STATUS      current
  DESCRIPTION
    "The udp port of the collector. 
     It is not applicable on Lowball platforms (10/110/330). 
     For those platforms, the value will be set to 0.
    "
  ::= {sFlowCollectorEntry   3 }

collectorAddrV6 OBJECT-TYPE
  SYNTAX      OCTET STRING (SIZE (0..60))
  MAX-ACCESS  read-only
  STATUS      current
  DESCRIPTION
    "The IPv6 address of the collector.  
     If the address is not set, the value will be an empty string. 
     It is not applicable on Lowball platforms (10/110/330). 
     For those platforms, the value will be set to an empty string
     "
  ::= { sFlowCollectorEntry 4 }


-- - - - - - - - - - - - - - - - - - - - - - - - - - - - - - - - - - - - - - -
--
-- sFlow global enable/disable/applliacble flag
--
-- - - - - - - - - - - - - - - - - - - - - - - - - - - - - - - - - - - - - - -
sFlowStatus OBJECT-TYPE
  SYNTAX      SflowStatus
  MAX-ACCESS  read-only
  STATUS      current
  DESCRIPTION
    "A Device-wide sFlow status."
  ::= { tpt-sflow-objs 2 }




END

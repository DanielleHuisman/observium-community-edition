-- - - - - - - - - - - - - - - - - - - - - - - - - - - - - - - - - - - - - - -
--
-- TippingPoint Technologies, Inc
-- Copyright information is in the DESCRIPTION section of the MODULE-IDENTITY.
--
-- - - - - - - - - - - - - - - - - - - - - - - - - - - - - - - - - - - - - - -

TPT-SMS-TRAP-MIB DEFINITIONS ::= BEGIN

    IMPORTS
        MODULE-IDENTITY, OBJECT-TYPE, NOTIFICATION-TYPE
            FROM SNMPv2-SMI

        OBJECT-GROUP, NOTIFICATION-GROUP
            FROM SNMPv2-CONF

        tpt-reg
            FROM TIPPINGPOINT-REG-MIB

        tpt-sms-notifypayload, tpt-sms-eventsV2, tpt-sms-groups, tpt-smsMIBs
            FROM TPT-SMSMIBS
        ;



    tptSmsTrapsModule MODULE-IDENTITY
        LAST-UPDATED "0508301900Z"
        ORGANIZATION "TippingPoint Technologies, Inc."
        CONTACT-INFO "www.tippingpoint.com"
        DESCRIPTION
        "The following describes the notifications sent to and from an SMS box.

         Copyright 2001-2005 TippingPoint Technologies, Inc.  All rights reserved.
         This document contains confidential and proprietary information to
         TippingPoint Technologies, Inc.  Use of this document is subject to the
         terms and conditions of TippingPoint's Non-Disclosure Agreement."

    ::= { tpt-smsMIBs 4 }


    tptSmsQuarantineRequest NOTIFICATION-TYPE
        OBJECTS   { tptSmsQuarantineNotifyId, tptSmsQuarantineNotifyData }
        STATUS    current
        DESCRIPTION
            "SMS asking an external NMS to quarantine an endstation using the data embedded in the request"
    ::= { tpt-sms-eventsV2 1 }

    tptSmsQuarantineAck NOTIFICATION-TYPE
        OBJECTS   { tptSmsQuarantineNotifyId, tptSmsQuarantineNotifyData }
        STATUS    current
        DESCRIPTION
            "External NMS notifying the SMS that a previously quarantine request was processed."
    ::= { tpt-sms-eventsV2 2 }

    tptSmsQuarantineReleaseRequest NOTIFICATION-TYPE
        OBJECTS   { tptSmsQuarantineNotifyId, tptSmsQuarantineNotifyData }
        STATUS    current
        DESCRIPTION
            "SMS asking an external NMS to unquarantine an endstation using the data embedded in the request"
    ::= { tpt-sms-eventsV2 3 }

    tptSmsQuarantineReleaseAck NOTIFICATION-TYPE
        OBJECTS   { tptSmsQuarantineNotifyId, tptSmsQuarantineNotifyData }
        STATUS    current
        DESCRIPTION
            "External NMS notifying the SMS that a previously unquarantine request was processed."
    ::= { tpt-sms-eventsV2 4 }

    tptSmsQuarantinePolicyNotification NOTIFICATION-TYPE
        OBJECTS   { tptSmsQuarantinePolicyMatchData }
        STATUS    current
        DESCRIPTION
            "SMS sending notification of a policy match"

    ::= { tpt-sms-eventsV2 5 }

    tptSmsUnQuarantineRequest NOTIFICATION-TYPE
        OBJECTS   { tptSmsQuarantineNotifyId, tptSmsQuarantineDeviceIP, tptSmsQuarantineDeviceMAC }
        STATUS    current
        DESCRIPTION
            "Inverse of tptSMSQuarantineCommand - command the SMS to unquarantine an endstation.  You can explicitly specify a quarantined host ID if you know it; otherwise, you may specify the IP only, in which case the SMS will look up the MAC; or the IP+MAC."
    ::= { tpt-sms-eventsV2 6 }

    tptSmsQuarantineCommand NOTIFICATION-TYPE
        OBJECTS   { tptSmsQuarantineDeviceIP, tptSmsQuarantinePolicyName }
        STATUS    current
        DESCRIPTION
            "Inverse of tptSmsUnquarantineRequest Command the SMS to quarantine an endstation.  SMS will look up the MAC."
    ::= { tpt-sms-eventsV2 14 }

-- Lifecycle traps     

    tptSmsBoot NOTIFICATION-TYPE
        STATUS    current
        DESCRIPTION
            "SMS: system has booted"

    ::= { tpt-sms-eventsV2 7 }

    tptSmsReboot NOTIFICATION-TYPE
        STATUS    current
        DESCRIPTION
            "SMS: system is rebooting"

    ::= { tpt-sms-eventsV2 8 }

    tptSmsShuttingDown NOTIFICATION-TYPE
        STATUS    current
        DESCRIPTION
            "SMS: system is shutting down"

    ::= { tpt-sms-eventsV2 9 }

    tptSmsReady NOTIFICATION-TYPE
        STATUS    current
        DESCRIPTION
            "SMS: system is ready"

    ::= { tpt-sms-eventsV2 10 }

    tptSmsAuthenticationError NOTIFICATION-TYPE
        STATUS    current
        DESCRIPTION
            "SMS: authentication error"

    ::= { tpt-sms-eventsV2 11 }

    tptSmsEgpNeighborDownstate NOTIFICATION-TYPE
        STATUS    current
        DESCRIPTION
            "SMS: EGP neighbor to downstate"

    ::= { tpt-sms-eventsV2 12 }

    tptSmsSystemRestart NOTIFICATION-TYPE
        STATUS    current
        DESCRIPTION
            "SMS: server process has restarted"

    ::= { tpt-sms-eventsV2 13 }


    tptSmsRepDvVerifySuccess NOTIFICATION-TYPE
        OBJECTS   { tptSmsRepDvVersion, tptSmsMessage }
        STATUS    current
        DESCRIPTION
            "SMS: Reputation DV downloaded and verified."

    ::= { tpt-sms-eventsV2 15 }

    tptSmsRepDvVerifyFail NOTIFICATION-TYPE
        OBJECTS   { tptSmsRepDvVersion, tptSmsMessage }
        STATUS    current
        DESCRIPTION
            "SMS: Reputation DV downloaded. Verification failed."

    ::= { tpt-sms-eventsV2 16 }

    tptSmsTest NOTIFICATION-TYPE
        OBJECTS   { tptSmsMessage }
        STATUS    current
        DESCRIPTION
            "SMS: Test trap."

    ::= { tpt-sms-eventsV2 17 }

    tptSmsRebootingDevice NOTIFICATION-TYPE
        OBJECTS   { tptSmsMessage }
        STATUS    current
        DESCRIPTION
            "SMS is rebooting a device."

    ::= { tpt-sms-eventsV2 18 }

    tptDeviceNonComm NOTIFICATION-TYPE
        OBJECTS   { tptSmsMessage }
        STATUS    current
        DESCRIPTION
            "SMS has lost communications with a device."

    ::= { tpt-sms-eventsV2 19 }

    tptDeviceBooted NOTIFICATION-TYPE
        OBJECTS   { tptSmsMessage }
        STATUS    current
        DESCRIPTION
            "A device has rebooted."

    ::= { tpt-sms-eventsV2 20 }

-- The following variables are for use in the varbinds of traps only.
-- They cannot be retrieved by the NMS.

    tptSmsQuarantineNotifyId  OBJECT-TYPE
        SYNTAX            INTEGER (0..2147483647)
        MAX-ACCESS        accessible-for-notify
        STATUS            current
        DESCRIPTION
            "A unique incrementing integer assigned for each quarantine event."

    ::= { tpt-sms-notifypayload 1 }

    tptSmsQuarantineNotifyData  OBJECT-TYPE
        SYNTAX            OCTET STRING
        MAX-ACCESS        accessible-for-notify
        STATUS            current
        DESCRIPTION
            "A string consisting of the parameters used to identify the
            device to quarantine. The format is NAME:VALUE with multiple
	    parameters separated by a newline"

    ::= { tpt-sms-notifypayload 2 }

    tptSmsQuarantinePolicyMatchData  OBJECT-TYPE
        SYNTAX            OCTET STRING
        MAX-ACCESS        accessible-for-notify
        STATUS            current
        DESCRIPTION
            "A string consisting of the parameters used to identify the
            matching policy"

    ::= { tpt-sms-notifypayload 3 }

    tptSmsQuarantineNotifyType  OBJECT-TYPE
        SYNTAX            OCTET STRING
        MAX-ACCESS        accessible-for-notify
        STATUS            current
        DESCRIPTION
            "A string consisting of the parameters used to identify the
            matching policy"

    ::= { tpt-sms-notifypayload 4 }

    tptSmsQuarantineDeviceIP  OBJECT-TYPE
        SYNTAX            IpAddress
        MAX-ACCESS        accessible-for-notify
        STATUS            current
        DESCRIPTION
            "An IP address used as a trap parameter."

    ::= { tpt-sms-notifypayload 5 }

    tptSmsQuarantineDeviceMAC  OBJECT-TYPE
        SYNTAX            OCTET STRING
        MAX-ACCESS        accessible-for-notify
        STATUS            current
        DESCRIPTION
            "A MAC address used a a trap parameter"

    ::= { tpt-sms-notifypayload 6 }

    tptSmsQuarantineSwitchPort  OBJECT-TYPE
        SYNTAX            OCTET STRING
        MAX-ACCESS        accessible-for-notify
        STATUS            current
        DESCRIPTION
            "A port number or index used as a trap parameter"

    ::= { tpt-sms-notifypayload 7 }

    tptSmsQuarantineEndpointUser  OBJECT-TYPE
        SYNTAX            OCTET STRING
        MAX-ACCESS        accessible-for-notify
        STATUS            current
        DESCRIPTION
            "A string consisting of the parameters used to identify the
            matching policy"

    ::= { tpt-sms-notifypayload 8 }

    tptSmsQuarantineNotifyActionList  OBJECT-TYPE
        SYNTAX            OCTET STRING
        MAX-ACCESS        accessible-for-notify
        STATUS            current
        DESCRIPTION
            "A string consisting of the parameters used to identify the
            matching policy"

    ::= { tpt-sms-notifypayload 9 }

    tptSmsQuarantineNotifyParamList  OBJECT-TYPE
        SYNTAX            OCTET STRING
        MAX-ACCESS        accessible-for-notify
        STATUS            current
        DESCRIPTION
            "A string consisting of the parameters used to identify the
            matching policy"

    ::= { tpt-sms-notifypayload 10 }

    tptSmsQuarantineNotifyOptionList  OBJECT-TYPE
        SYNTAX            OCTET STRING
        MAX-ACCESS        accessible-for-notify
        STATUS            current
        DESCRIPTION
            "A string consisting of the parameters used to identify the
            matching policy"

    ::= { tpt-sms-notifypayload 11 }

    tptSmsQuarantinePolicyName  OBJECT-TYPE
        SYNTAX            OCTET STRING
        MAX-ACCESS        accessible-for-notify
        STATUS            current
        DESCRIPTION
            "The name of an SMS Quarantine Policy.  If the named policy does not exists on the SMS, a default will be chosen."
    ::= { tpt-sms-notifypayload 12 }

    tptSmsRepDvVersion    OBJECT-TYPE
        SYNTAX            OCTET STRING
        MAX-ACCESS        accessible-for-notify
        STATUS            current
        DESCRIPTION
            "The Rep DV version."
    ::= { tpt-sms-notifypayload 13 }

    tptSmsMessage         OBJECT-TYPE
        SYNTAX            OCTET STRING
        MAX-ACCESS        accessible-for-notify
        STATUS            current
        DESCRIPTION
            "A generic message parameter."
    ::= { tpt-sms-notifypayload 14 }

    -- Quarantine data groups
    
    tptSmsQuarantineDataGroup OBJECT-GROUP
        OBJECTS { tptSmsQuarantineNotifyId, tptSmsQuarantineNotifyData,
            tptSmsQuarantinePolicyMatchData}
        STATUS  current
        DESCRIPTION
            "Payload of SMS quarantine traps consisting of a unique identifier
            and a parseable string"
    ::= { tpt-sms-groups 1 }

    tptSmsQuarantineNotifyGroup NOTIFICATION-GROUP
        NOTIFICATIONS { tptSmsQuarantineRequest, tptSmsQuarantineReleaseRequest,
            tptSmsQuarantinePolicyNotification }
        STATUS  current
        DESCRIPTION
            "SMS quarantine traps sent to an NMS to indicate devices that require
            a quarantine operation"
    ::= { tpt-sms-groups 2 }

    tptSmsQuarantineNotifyAckGroup NOTIFICATION-GROUP
        NOTIFICATIONS { tptSmsQuarantineAck, tptSmsQuarantineReleaseAck }
        STATUS  current
        DESCRIPTION
            "SMS quarantine traps sent to an SMS system to indicate devices
            that have been quarantined"
    ::= { tpt-sms-groups 3 }

    tptSmsQuarantineRequestGroup NOTIFICATION-GROUP
        NOTIFICATIONS { tptSmsQuarantineCommand, tptSmsUnQuarantineRequest }
        STATUS  current
        DESCRIPTION
            "SMS quarantine traps received to indicate devices that require
            a (un)quarantine operation"
    ::= { tpt-sms-groups 4 }

    END

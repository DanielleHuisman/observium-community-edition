UBNT-SUNMAX-MIB DEFINITIONS ::= BEGIN

IMPORTS
  MODULE-IDENTITY, OBJECT-TYPE, Integer32, Counter64, IpAddress
    FROM SNMPv2-SMI
  MODULE-COMPLIANCE, OBJECT-GROUP
    FROM SNMPv2-CONF
  DisplayString, MacAddress
    FROM SNMPv2-TC
  ubntSunMax, ubntSunMaxGroups 
    FROM UBNT-MIB;

sunMaxMIB MODULE-IDENTITY
    LAST-UPDATED "201911290000Z"
    ORGANIZATION "Ubiquiti Networks, Inc."
    CONTACT-INFO "support@ubnt.com"
    DESCRIPTION  "The SunMAx MIB module for Ubiquiti Networks, Inc. entities"
    REVISION "201911290000Z"
    DESCRIPTION "Sunmax MIB"
    ::= { ubntSunMax 1 }

sunMaxCompliances  OBJECT IDENTIFIER ::= {ubntSunMaxGroups 1}
sunMaxGroups       OBJECT IDENTIFIER ::= {ubntSunMaxGroups 2}

sunMaxBatteryStats        OBJECT IDENTIFIER ::= {sunMaxMIB 1}
sunMaxPvPanelStats        OBJECT IDENTIFIER ::= {sunMaxMIB 2}
sunMaxOutPutStats         OBJECT IDENTIFIER ::= {sunMaxMIB 3}
--=== MODULE OBJECTS

--=== SunMax Battery Statistics
sunMaxBatCurrent OBJECT-TYPE
  SYNTAX        Integer32
  MAX-ACCESS    read-only
  STATUS        current
  DESCRIPTION   "Current of battery."
  ::= { sunMaxBatteryStats 1 }

sunMaxBatVoltage OBJECT-TYPE
  SYNTAX        Integer32
  MAX-ACCESS    read-only
  STATUS        current
  DESCRIPTION   "Voltage of battery."
  ::= { sunMaxBatteryStats 2 }

sunMaxBatPower OBJECT-TYPE
  SYNTAX        Integer32
  MAX-ACCESS    read-only
  STATUS        current
  DESCRIPTION   "Power of battery."
  ::= { sunMaxBatteryStats 3 }

sunMaxBatTemp OBJECT-TYPE
  SYNTAX        Integer32
  MAX-ACCESS    read-only
  STATUS        current
  DESCRIPTION   "Temperature of battery."
  ::= { sunMaxBatteryStats 4 }

--=== SunMax Pv Panel Statistics

sunMaxPVCurrent OBJECT-TYPE
  SYNTAX        Integer32
  MAX-ACCESS    read-only
  STATUS        current
  DESCRIPTION   "Current of Pv panel."
  ::= { sunMaxPvPanelStats 1 }

sunMaxPVVoltage OBJECT-TYPE
  SYNTAX        Integer32
  MAX-ACCESS    read-only
  STATUS        current
  DESCRIPTION   "Voltage of Pv panel."
  ::= { sunMaxPvPanelStats 2 }

sunMaxPVPower OBJECT-TYPE
  SYNTAX        Integer32
  MAX-ACCESS    read-only
  STATUS        current
  DESCRIPTION   "Power of Pv panel."
  ::= { sunMaxPvPanelStats 3 }

--=== SunMax Output Statistics

sunMaxOutCurrent OBJECT-TYPE
  SYNTAX        Integer32
  MAX-ACCESS    read-only
  STATUS        current
  DESCRIPTION   "Current of output."
  ::= { sunMaxOutPutStats 1 }

sunMaxOutVoltage OBJECT-TYPE
  SYNTAX        Integer32
  MAX-ACCESS    read-only
  STATUS        current
  DESCRIPTION   "Voltage of output."
  ::= { sunMaxOutPutStats 2 }

sunMaxOutPower OBJECT-TYPE
  SYNTAX        Integer32
  MAX-ACCESS    read-only
  STATUS        current
  DESCRIPTION   "Power of output."
  ::= { sunMaxOutPutStats 3 }

END

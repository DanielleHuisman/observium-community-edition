--- *****************************************************************************
-- Filename:        ut-epon-4000-fault.mib
-- Description:     Contains iSwitch MIB Extension.
-- MIB Version:     1.00
-- 
-- Copyright (C) 2001 by UTStarcom, Inc. All rights reserved.
-- Reproduction of this document is authorized on the condition that
-- the foregoing copyright notice is included.
--
-- NOTE:  The contents of this document are subject to change without notice
-- *****************************************************************************

-- *****************************************************************************
-- Version:        $Id:  $
-- Last Modified:  $DateTime:  $
-- Change List #:  $Change:  $
-- *****************************************************************************

UTEPON4000FAULT-MIB DEFINITIONS ::= BEGIN

    IMPORTS
        MODULE-IDENTITY, 
        NOTIFICATION-TYPE,
        OBJECT-TYPE, IpAddress 		 FROM SNMPv2-SMI
        Counter, TimeTicks               FROM RFC1155-SMI            
        RowStatus, TruthValue            FROM SNMPv2-TC
        ifIndex, DisplayString		 FROM RFC1213-MIB
        MacAddress, BridgeId, Timeout    FROM BRIDGE-MIB
        utsGeponBBS4000            FROM UTS-BBS-COMMON-MIB
    	utsDot3Security8021xRadiusSvrPrimaryOnuAuthIP         FROM UTSECURITY-MIB
		
		alarmModule,
        alarmPort,
        alarmLogicalPort,
    	alarmSeqNo,
    	alarmType,
    	alarmSeverity,
        alarmErrorData,
        alarmErrorDataStr,
        alarmIgmpIIf,
        alarmIgmpGrpAddr,
        alarmIgmpOIf,
		alarmIgmpProxyStatus,
		alarmFanNumber,
		alarmTaskName,
		alarmResourceInt,
		alarmDiagStatus,
		alarmRdsSvrIp,
        alarmPowerSlotStatus,
		alarmPowerSlotNumber,
		alarmRdsSvrIdx,
		alarmBBS4000ModuleType,
		alarmSessionId                  FROM EPONOAMINIT-ALARM-MIB
		
		utAlarmSeqNo,
		utAlarmOccurrenceTime,
		utAlarmSeverity,
		utAlarmProbableCause,
		utAlarmType,
		utAlarmClearType,
		utAlarmResourceType		        FROM UTS-FAULT-MIB;



   utsGeponBBS4000Fault  MODULE-IDENTITY
        LAST-UPDATED "200511211045Z"      -- Wed Nov. 21 10:45:00 2005
        ORGANIZATION "UTSTARcom Inc"
        CONTACT-INFO
            "Postal: UTSTARcom Inc
             Alameda, California 9xxxx
             Tel:    +1 510 555 1212
             E-Mail: mibs@utstar.com "
      DESCRIPTION
         "Contains UT EPON 4000 MIB Extensions."
     ::= { utsGeponBBS4000 3   }   

--
--  BBS 4000 only realted alarms
--

utsBBS4000FaultAlarm OBJECT IDENTIFIER ::= { utsGeponBBS4000Fault 1 }
     
	utsChassisMgmChannelCommOk  NOTIFICATION-TYPE
        OBJECTS { 
            utAlarmSeqNo,
            utAlarmOccurrenceTime,
            utAlarmSeverity,
            utAlarmProbableCause,
            utAlarmType,
            utAlarmClearType,
            utAlarmResourceType,
            alarmSessionId            
        }
    STATUS       current
    DESCRIPTION
        "Serial bus com OK."
    ::= { utsBBS4000FaultAlarm 0 1 }
    
    utsChassisMgmChannelCommAbnormal  NOTIFICATION-TYPE
        OBJECTS { 
            utAlarmSeqNo,
            utAlarmOccurrenceTime,
            utAlarmSeverity,
            utAlarmProbableCause,
            utAlarmType,
            utAlarmClearType,
            utAlarmResourceType,
            alarmSessionId
        }
    STATUS       current
    DESCRIPTION
        "Serial bus com abnormal"
    ::= { utsBBS4000FaultAlarm 0 3 }
    
    utsChassisInvalidCardPlugout  NOTIFICATION-TYPE
        OBJECTS { 
            utAlarmSeqNo,
            utAlarmOccurrenceTime,
            utAlarmSeverity,
            utAlarmProbableCause,
            utAlarmType,
            utAlarmClearType,
            utAlarmResourceType,
            alarmModule,
            alarmSessionId
                        
        }
    STATUS       current
    DESCRIPTION
        "when the invalid card plug out, clear the alarm!"
    ::= { utsBBS4000FaultAlarm 0 4 }
    
    utsChassisInvalidCardInsert  NOTIFICATION-TYPE
        OBJECTS { 
            utAlarmSeqNo,
            utAlarmOccurrenceTime,
            utAlarmSeverity,
            utAlarmProbableCause,
            utAlarmType,
            utAlarmClearType,
            utAlarmResourceType,
            alarmModule,
            alarmSessionId
        }
    STATUS       current
    DESCRIPTION
        "when the card insert and detect the invalid card that system do not recognize."
    ::= { utsBBS4000FaultAlarm 0 6 } 
    
--    utsDownloadMgmImgOK  NOTIFICATION-TYPE
--        OBJECTS { 
--            utAlarmSeqNo,
--            utAlarmOccurrenceTime,
--            utAlarmSeverity,
--            utAlarmProbableCause,
--            utAlarmType,
--            utAlarmClearType,
--            utAlarmResourceType,
--            alarmModule
--                        
--        }
--    STATUS       current
--    DESCRIPTION
--        "when download the image ok, clear the alarm!"
--    ::= { utsBBS4000FaultAlarm 0 8 }
--    
--    utsDownloadMgmImgFail  NOTIFICATION-TYPE
--        OBJECTS { 
--            utAlarmSeqNo,
--            utAlarmOccurrenceTime,
--            utAlarmSeverity,
--            utAlarmProbableCause,
--            utAlarmType,
--            utAlarmClearType,
--            utAlarmResourceType,
--            alarmModule
--        }
--    STATUS       current
--    DESCRIPTION
--        "when downlaod image to the slot fail, raise the alarm"
--  ::= { utsBBS4000FaultAlarm 0 10 } 
    
    utsTemperatureNormal  NOTIFICATION-TYPE
        OBJECTS { 
            utAlarmSeqNo,
            utAlarmOccurrenceTime,
            utAlarmSeverity,
            utAlarmProbableCause,
            utAlarmType,
            utAlarmClearType,
            utAlarmResourceType,
            alarmModule,
            alarmSessionId                        
        }
    STATUS       current
    DESCRIPTION
        "when temperature back to normal, clear the alarm!"
    ::= { utsBBS4000FaultAlarm 0 12 }
    
    utsTemperatureTooHigh  NOTIFICATION-TYPE
        OBJECTS { 
            utAlarmSeqNo,
            utAlarmOccurrenceTime,
            utAlarmSeverity,
            utAlarmProbableCause,
            utAlarmType,
            utAlarmClearType,
            utAlarmResourceType,
            alarmModule,
            alarmSessionId
        }
    STATUS       current
    DESCRIPTION
        "when temperature too high, raise the alarm"
    ::= { utsBBS4000FaultAlarm 0 14 }   
    
    utsFanNormal  NOTIFICATION-TYPE
        OBJECTS { 
            utAlarmSeqNo,
            utAlarmOccurrenceTime,
            utAlarmSeverity,
            utAlarmProbableCause,
            utAlarmType,
            utAlarmClearType,
            utAlarmResourceType,
            alarmFanNumber,
            alarmSessionId                        
        }
    STATUS       current
    DESCRIPTION
        "when fan normal, clear the alarm!"
    ::= { utsBBS4000FaultAlarm 0 16 }
    
    utsFanAbnormal  NOTIFICATION-TYPE
        OBJECTS { 
            utAlarmSeqNo,
            utAlarmOccurrenceTime,
            utAlarmSeverity,
            utAlarmProbableCause,
            utAlarmType,
            utAlarmClearType,
            utAlarmResourceType,
            alarmFanNumber,
            alarmSessionId
        }
    STATUS       current
    DESCRIPTION
        "when fam abnormal, raise the alarm"
    ::= { utsBBS4000FaultAlarm 0 18 }
    
    utsSysPowerNormal  NOTIFICATION-TYPE
        OBJECTS { 
            utAlarmSeqNo,
            utAlarmOccurrenceTime,
            utAlarmSeverity,
            utAlarmProbableCause,
            utAlarmType,
            utAlarmClearType,
            utAlarmResourceType,
            alarmPowerSlotNumber,
            alarmSessionId                        
        }
    STATUS       current
    DESCRIPTION
        "when fan normal, clear the alarm!"
    ::= { utsBBS4000FaultAlarm 0 20 }
    
    utsSysPowerAbnormal  NOTIFICATION-TYPE
        OBJECTS { 
            utAlarmSeqNo,
            utAlarmOccurrenceTime,
            utAlarmSeverity,
            utAlarmProbableCause,
            utAlarmType,
            utAlarmClearType,
            utAlarmResourceType,
            alarmPowerSlotNumber,
            alarmSessionId
        }
    STATUS       current
    DESCRIPTION
        "when fam abnormal, raise the alarm"
    ::= { utsBBS4000FaultAlarm 0 22 }
    
--    utsCardAbnormalRemove  NOTIFICATION-TYPE
--        OBJECTS { 
--            utAlarmSeqNo,
--            utAlarmOccurrenceTime,
--            utAlarmSeverity,
--            utAlarmProbableCause,
--            utAlarmType,
--            utAlarmClearType,
--            utAlarmResourceType,
--            alarmModule,
--            alarmBBS4000ModuleType
--        }
--    STATUS       current
--    DESCRIPTION
--        "Raise when card has been detected not present without hotswap or card failure, need manual clear!"
--  ::= { utsBBS4000FaultAlarm 0 26 }
    
    utsDownloadPonImgOK  NOTIFICATION-TYPE
        OBJECTS { 
            utAlarmSeqNo,
            utAlarmOccurrenceTime,
            utAlarmSeverity,
            utAlarmProbableCause,
            utAlarmType,
            utAlarmClearType,
            utAlarmResourceType,
            alarmModule,
            alarmPort,
            alarmSessionId
                        
        }
    STATUS       current
    DESCRIPTION
        "when download the pon image ok, clear the alarm!"
    ::= { utsBBS4000FaultAlarm 0 28 }
    
    utsDownloadPonImgFail  NOTIFICATION-TYPE
        OBJECTS { 
            utAlarmSeqNo,
            utAlarmOccurrenceTime,
            utAlarmSeverity,
            utAlarmProbableCause,
            utAlarmType,
            utAlarmClearType,
            utAlarmResourceType,
            alarmModule,
            alarmPort,
            alarmSessionId
        }
    STATUS       current
    DESCRIPTION
        "when downlaod image to the pon port fail, raise the alarm"
    ::= { utsBBS4000FaultAlarm 0 30 }
    
    utsOnuUNILinkUp  NOTIFICATION-TYPE
        OBJECTS { 
            utAlarmSeqNo,
            utAlarmOccurrenceTime,
            utAlarmSeverity,
            utAlarmProbableCause,
            utAlarmType,
            utAlarmClearType,
            utAlarmResourceType,
            alarmModule,
            alarmPort,
            alarmLogicalPort,
            alarmMacAddress,
            alarmEponOnuHwType,
            alarmSessionId
                        
        }
    STATUS       current
    DESCRIPTION
        "Clear when PON shutdown or ONU shutdown or ONU link down or UNI link up."
    ::= { utsBBS4000FaultAlarm 0 32 }
    
    utsOnuUNILinkDown  NOTIFICATION-TYPE
        OBJECTS { 
            utAlarmSeqNo,
            utAlarmOccurrenceTime,
            utAlarmSeverity,
            utAlarmProbableCause,
            utAlarmType,
            utAlarmClearType,
            utAlarmResourceType,
            alarmModule,
            alarmPort,
            alarmLogicalPort,
            alarmMacAddress,
            alarmEponOnuHwType,
            alarmSessionId
        }
    STATUS       current
    DESCRIPTION
        "Raise when ONU link up but UNI port link down."
    ::= { utsBBS4000FaultAlarm 0 34 }  
    
    utsBBS4000CardInsertAlarm  NOTIFICATION-TYPE
        OBJECTS { 
            utAlarmSeqNo,
            utAlarmOccurrenceTime,
            utAlarmSeverity,
            utAlarmProbableCause,
            utAlarmType,
            utAlarmClearType,
            utAlarmResourceType,
            alarmModule,
            alarmBBS4000ModuleType,
            alarmSessionId                        
        }
    STATUS       current
    DESCRIPTION
        "Card Insert for bbs 4000!"
    ::= { utsBBS4000FaultAlarm 0 36 }
    
    utsBBS4000CardRemoveAlarm  NOTIFICATION-TYPE
        OBJECTS { 
            utAlarmSeqNo,
            utAlarmOccurrenceTime,
            utAlarmSeverity,
            utAlarmProbableCause,
            utAlarmType,
            utAlarmClearType,
            utAlarmResourceType,
            alarmModule,
            alarmBBS4000ModuleType,
            alarmSessionId
        }
    STATUS       current
    DESCRIPTION
        "Card remove for bbs 4000"
    ::= { utsBBS4000FaultAlarm 0 38 }   

--
--  BBS 4000 only realted event
--

	utsBBS4000CardInsertEvent  NOTIFICATION-TYPE
	        OBJECTS {
	            utEventSeqNo,
	            utEventOccurrenceTime,                     
	            alarmModule,
	            alarmBBS4000ModuleType
	        }
	    STATUS       current
	    DESCRIPTION
	        "BBS 4000 Card Insert Event!"
	    ::= { utsBBS4000FaultAlarm 0 40 }
	    
	utsBBS4000CardRemoveEvent  NOTIFICATION-TYPE
	        OBJECTS {
	            utEventSeqNo,
	            utEventOccurrenceTime,                     
	            alarmModule,
	            alarmBBS4000ModuleType
	        }
	    STATUS       current
	    DESCRIPTION
	        "BBS 4000 card Remove Event!"
	    ::= { utsBBS4000FaultAlarm 0 42 } 
	
	utsCardAbnormalRemoveEvent  NOTIFICATION-TYPE
        	OBJECTS { 
            	utEventSeqNo,
	            utEventOccurrenceTime,                     
	            alarmModule,
	            alarmBBS4000ModuleType
        }
    	STATUS       current
    	DESCRIPTION
        "Send out when card has been detected not present without hotswap or card failure!"
    	::= { utsBBS4000FaultAlarm 0 45 }
      
        
END

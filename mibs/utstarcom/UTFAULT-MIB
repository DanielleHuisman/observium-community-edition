-- *****************************************************************************
-- Filename:        epon-fault.mib
-- Description:     Contains iSwitch MIB Extension.
-- MIB Version:     1.00
-- 
-- Copyright (C) 2001 by UTStarcom, Inc. All rights reserved.
-- Reproduction of this document is authorized on the condition that
-- the foregoing copyright notice is included.
--
-- NOTE:  The contents of this document are subject to change without notice
-- *****************************************************************************

-- *****************************************************************************
-- Version:        $Id:  $
-- Last Modified:  $DateTime:  $
-- Change List #:  $Change:  $
-- *****************************************************************************

UTFAULT-MIB DEFINITIONS ::= BEGIN

    IMPORTS
        MODULE-IDENTITY, 
        NOTIFICATION-TYPE,
        OBJECT-TYPE, IpAddress 		     FROM SNMPv2-SMI
        Counter, TimeTicks               FROM RFC1155-SMI            
        RowStatus, TruthValue            FROM SNMPv2-TC
        ifIndex, DisplayString			 FROM RFC1213-MIB
        MacAddress, BridgeId, Timeout    FROM BRIDGE-MIB
        uts-epon                         FROM UTS-EPON-MIB
    	utsDot3Security8021xRadiusSvrPrimaryOnuAuthIP         FROM UTSECURITY-MIB
    	
        alarmModule,
        alarmPort,
        alarmLogicalPort,
    	alarmSeqNo,
    	alarmType,
    	alarmSeverity,
        alarmErrorData,
        alarmErrorDataStr,
        alarmIgmpIIf,
        alarmIgmpGrpAddr,
        alarmIgmpOIf,
		alarmIgmpProxyStatus,
		alarmFanNumber,
		alarmTaskName,
		alarmResourceInt,
		alarmDiagStatus,
		alarmRdsSvrIp,
        alarmPowerSlotStatus,
		alarmPowerSlotNumber,
		alarmRdsSvrIdx,          
		alarmSessionId,
		alarmOpticalPower,
		alarmOnuEtherPortIndex                  FROM EPONOAMINIT-ALARM-MIB
		
		utAlarmSeqNo,
		utAlarmOccurrenceTime,
		utAlarmSeverity,
		utAlarmProbableCause,
		utAlarmType,
		utAlarmClearType,
		utAlarmResourceType		FROM UTS-FAULT-MIB;
--		utsGeponBBS1000plus                   FROM UTS-BBS-COMMON-MIB;



   utFault  MODULE-IDENTITY
        LAST-UPDATED "9407272253Z"      -- Wed Jul 27 22:53:04 PDT 1994
        ORGANIZATION "UTSTARcom Inc"
        CONTACT-INFO
            "Postal: UTSTARcom Inc
             Alameda, California 9xxxx
             Tel:    +1 510 555 1212
             E-Mail: mibs@utstar.com "
      DESCRIPTION
         "Contains UT EPON MIB Extensions."
     ::= { uts-epon 3   }



utsEponFaultExt     OBJECT IDENTIFIER ::= { utFault 1 }

utsEponFaultExtObjects OBJECT IDENTIFIER ::= { utsEponFaultExt 1 }

utsEponNotifyExtObjects  OBJECT IDENTIFIER ::= { utsEponFaultExt 2 }



--
-- 3. Fault
--


utsFaultTrapObjs OBJECT IDENTIFIER ::= { utsEponFaultExtObjects 1}

utsFaultAlarmObjs OBJECT IDENTIFIER ::= { utsEponFaultExtObjects 2 }

utsFaultThresholdObjs OBJECT IDENTIFIER ::= { utsEponFaultExtObjects 3 }



--
-- TRAP table
--


utsEponTrapTable OBJECT-TYPE
SYNTAX  SEQUENCE OF UtsEponTrapEntry
        MAX-ACCESS  not-accessible
        STATUS  current
        DESCRIPTION
"Table for epon trap configuration."
        ::= { utsFaultTrapObjs 1 }

utsEponTrapEntry OBJECT-TYPE
SYNTAX  UtsEponTrapEntry
       MAX-ACCESS  not-accessible
       STATUS  current
       DESCRIPTION
"An entry in the Trap configuration table."
       INDEX  { utsEponTrapDestIP }
       ::= { utsEponTrapTable 1 }

UtsEponTrapEntry ::=
       SEQUENCE {

                    utsEponTrapDestIP			IpAddress,
                    utsEponTrapUDPPort			INTEGER,
                    utsEponTrapCommunityString		DisplayString,
                    utsEponTrapState			RowStatus

       }


        
utsEponTrapDestIP OBJECT-TYPE
SYNTAX  IpAddress
       MAX-ACCESS  read-create
       STATUS  current
       DESCRIPTION
"Trap destination IP configuration"
        ::= { utsEponTrapEntry 1 }  
        
utsEponTrapUDPPort OBJECT-TYPE
SYNTAX  INTEGER (1..65535)
       MAX-ACCESS  read-create
       STATUS  current
       DESCRIPTION
"SNMP trap udp port configuration, if it different from udp port 162(default)."
        ::= { utsEponTrapEntry 2 } 
        
utsEponTrapCommunityString OBJECT-TYPE
SYNTAX  DisplayString(SIZE(0..32))
       MAX-ACCESS  read-create
       STATUS  current
       DESCRIPTION
"Encryption state."
        ::= { utsEponTrapEntry 3 }                      
        
utsEponTrapState OBJECT-TYPE
SYNTAX  RowStatus
       MAX-ACCESS  read-create
       STATUS  current
       DESCRIPTION
"Encryption direction."
        ::= { utsEponTrapEntry 4 }        




-- ----
-- ---- Alarm table
-- ----


--utsEponAlarmTable OBJECT-TYPE
--SYNTAX  SEQUENCE OF UtsEponAlarmEntry
--        MAX-ACCESS  not-accessible
--        STATUS  current
--        DESCRIPTION
--"Table for epon alarm severity configuration."
--        ::= { utsFaultAlarmObjs 1 }
--
--utsEponAlarmEntry OBJECT-TYPE
--SYNTAX  UtsEponAlarmEntry
--       MAX-ACCESS  not-accessible
--       STATUS  current
--       DESCRIPTION
--"An entry in the Alarm configuration table."
--       INDEX  { utsEponAlarmType }
--       ::= { utsEponAlarmTable 1 }
--
--UtsEponAlarmEntry ::=
--       SEQUENCE {
--                    utsEponAlarmType			INTEGER,
--                    utsEponAlarmSeverity		INTEGER
--       }

        
--utsEponAlarmType OBJECT-TYPE
--SYNTAX  INTEGER {
--         radius-server-access-ok(1),
--         radius-server-not-accessible(2),
--         temperature-normal(3),
--         temperature-too-high(5),
--         fan-normal(6),
--         fan-abnormal(7),
--         cpu-resource-starvation(8),
--         memory-resource-starvation(9),
--         module-inserted(11),
--         module-removed(12),
--         module-diag-status(13),
--         chassis-power-sys-normal(15),
--         chassis-power-sys-abnormal(16),
--         chassis-power-module-event(17),
--         sfp-port-link-up(101),
--         sfp-port-link-down(102),
--         higig-port-link-up(103),
--         higig-port-link-down(104),
--         olt-up(201),
--         olt-down(202),
--         onu-up(301),
--         onu-down(302),
--         oam-802-dot3-link-fault-clear(304),
--         oam-802-dot3-link-fault(303),
--         oam-802-dot3-dying-gasp(305),
--         oam-802-dot3-critical-event-clear(308),
--         oam-802-dot3-critical-event(307),
--	    	igmp-proxy-status-down(402),
--	    	pon-bit-error-rate-alarm-clear(1004),
--	    	pon-bit-error-rate-alarm(1002),
--	    	pon-frame-error-rate-alarm-clear(1007),
--	    	pon-frame-error-rate-alarm(1005)
--}
--       MAX-ACCESS  read-only
--       STATUS  current
--       DESCRIPTION
--"Alarm type of EPON"
--        ::= { utsEponAlarmEntry 1 }  
--        
--utsEponAlarmSeverity OBJECT-TYPE
--SYNTAX  INTEGER {
--            clear(0),
--            warning(1),
--            minor(2),
--            major(3),
--            critical(4), 
--			indeterminate(5),
--            info(6),
--            filter(7)
--}
--       MAX-ACCESS  read-write
--       STATUS  current
--       DESCRIPTION
--"Alarm severity level for the specific alarm type."
--        ::= { utsEponAlarmEntry 2 } 
        



------
------ Alarm Threshold table
------


utsEponAlarmThresholdTable OBJECT-TYPE
SYNTAX  SEQUENCE OF UtsEponAlarmThresholdEntry
        MAX-ACCESS  not-accessible
        STATUS  current
        DESCRIPTION
"Table for epon alarm  threshold value configuration."
        ::= { utsFaultThresholdObjs 1 }

utsEponAlarmThresholdEntry OBJECT-TYPE
SYNTAX  UtsEponAlarmThresholdEntry
       MAX-ACCESS  not-accessible
       STATUS  current
       DESCRIPTION
"An entry in the Alarm configuration table."
       INDEX  { utsEponAlarmThresholdIndex, utsEponAlarmThresholdType }
       ::= { utsEponAlarmThresholdTable 1 }

UtsEponAlarmThresholdEntry ::=
       SEQUENCE {
                    utsEponAlarmThresholdIndex			INTEGER,
                    utsEponAlarmThresholdType			INTEGER,
                    utsEponAlarmThresholdSeverity		INTEGER,
                    utsEponAlarmThresholdCurrent		INTEGER,
                    utsEponAlarmThresholdMinValue		INTEGER,
                    utsEponAlarmThresholdMaxValue		INTEGER
       }

utsEponAlarmThresholdIndex OBJECT-TYPE
SYNTAX  INTEGER 
       MAX-ACCESS  read-only
       STATUS  current
       DESCRIPTION
"Alarm threshold entry index."
        ::= { utsEponAlarmThresholdEntry 1 }
        
utsEponAlarmThresholdType OBJECT-TYPE
SYNTAX  INTEGER {
        llid-mismatch(1001), 
        onu-ber-alarm(1002),
        onu-fer-alarm(1005)
 }
       MAX-ACCESS  read-only
       STATUS  current
       DESCRIPTION
"Alarm type of EPON"
        ::= { utsEponAlarmThresholdEntry 2 }  
        
utsEponAlarmThresholdSeverity OBJECT-TYPE
SYNTAX  INTEGER {
            clear(0),
            warning(1),
            minor(2),
            major(3),
            critical(4), 
			indeterminate(5),
            info(6),
            filter(7)
}
       MAX-ACCESS  read-write
       STATUS  current
       DESCRIPTION
"Alarm severity level for the specific alarm type."
        ::= { utsEponAlarmThresholdEntry 3 } 
        

utsEponAlarmThresholdCurrent OBJECT-TYPE
SYNTAX  INTEGER 
       MAX-ACCESS  read-only
       STATUS  current
       DESCRIPTION
"Current Alarm threshold value for the specific alarm type."
        ::= { utsEponAlarmThresholdEntry 4 } 



utsEponAlarmThresholdMinValue OBJECT-TYPE
SYNTAX  INTEGER 
       MAX-ACCESS  read-write
       STATUS  current
       DESCRIPTION
 "The minimal number of Alarm threshold value for the specific alarm type."
        ::= { utsEponAlarmThresholdEntry 5 } 


utsEponAlarmThresholdMaxValue OBJECT-TYPE
SYNTAX  INTEGER 
       MAX-ACCESS  read-write
       STATUS  current
       DESCRIPTION
"The above Alarm threshold value for the specific alarm type."
        ::= { utsEponAlarmThresholdEntry 6 } 



------
------ OAM alarm threshold
------


utsEponOAMAlarmThresholdTable OBJECT-TYPE
SYNTAX  SEQUENCE OF UtsEponOAMAlarmThresholdEntry
        MAX-ACCESS  not-accessible
        STATUS  current
        DESCRIPTION
"Table for epon alarm  threshold value configuration."
        ::= { utsFaultThresholdObjs 2 }

utsEponOAMAlarmThresholdEntry OBJECT-TYPE
SYNTAX  UtsEponOAMAlarmThresholdEntry
       MAX-ACCESS  not-accessible
       STATUS  current
       DESCRIPTION
"An entry in the oam Alarm threshold configuration table."
       INDEX  { utsEponOAMAlarmThresholdIndex, utsEponOAMAlarmThresholdType }
       ::= { utsEponOAMAlarmThresholdTable 1 }

UtsEponOAMAlarmThresholdEntry ::=
       SEQUENCE {
                    utsEponOAMAlarmThresholdIndex		INTEGER,
                    utsEponOAMAlarmThresholdType		INTEGER,
                    utsEponOAMAlarmThresholdSeverity	INTEGER,
                    utsEponOAMAlarmThresholdCurrent		INTEGER,
                    utsEponOAMAlarmThresholdWindow		INTEGER,
                    utsEponOAMAlarmThresholdValue		INTEGER,
                    utsEponOAMAlarmThresholdTotal		INTEGER,
                    utsEponOAMAlarmEventTotal			INTEGER
       }

utsEponOAMAlarmThresholdIndex OBJECT-TYPE
SYNTAX  INTEGER 
       MAX-ACCESS  read-only
       STATUS  current
       DESCRIPTION
"OAM Alarm threshold entry index."
        ::= { utsEponOAMAlarmThresholdEntry 1 }
        
utsEponOAMAlarmThresholdType OBJECT-TYPE
SYNTAX  INTEGER {
        err-symbol-period-alarm(2001), 
        err-frame-alarm(2002),
        err-frame-period-alarm(2003)
 }
       MAX-ACCESS  read-only
       STATUS  current
       DESCRIPTION
"OAM Alarm type of EPON"
        ::= { utsEponOAMAlarmThresholdEntry 2 }  
        
utsEponOAMAlarmThresholdSeverity OBJECT-TYPE
SYNTAX  INTEGER {
            clear(0),
            warning(1),
            minor(2),
            major(3),
            critical(4), 
				indeterminate(5),
            info(6),
            filter(7)
}
       MAX-ACCESS  read-write
       STATUS  current
       DESCRIPTION
"OAM Alarm severity level for the specific alarm type."
        ::= { utsEponOAMAlarmThresholdEntry 3 } 
        

utsEponOAMAlarmThresholdCurrent OBJECT-TYPE
SYNTAX  INTEGER 
       MAX-ACCESS  read-only
       STATUS  current
       DESCRIPTION
"OAM Current Alarm threshold value for the specific alarm type."
        ::= { utsEponOAMAlarmThresholdEntry 4 } 



utsEponOAMAlarmThresholdWindow OBJECT-TYPE
SYNTAX  INTEGER 
       MAX-ACCESS  read-write
       STATUS  current 
       DESCRIPTION
"OAM Alarm threshold window value for the specific alarm type."
        ::= { utsEponOAMAlarmThresholdEntry 5 } 


utsEponOAMAlarmThresholdValue OBJECT-TYPE
SYNTAX  INTEGER 
       MAX-ACCESS  read-write
       STATUS  current
       DESCRIPTION
"OAM Alarm threshold value for the specific alarm type."
        ::= { utsEponOAMAlarmThresholdEntry 6 } 


utsEponOAMAlarmThresholdTotal OBJECT-TYPE
SYNTAX  INTEGER 
       MAX-ACCESS  read-only
       STATUS  current
       DESCRIPTION
"OAM total Alarm threshold value for the specific alarm type."
        ::= { utsEponOAMAlarmThresholdEntry 7 } 


utsEponOAMAlarmEventTotal OBJECT-TYPE
SYNTAX  INTEGER 
       MAX-ACCESS  read-only
       STATUS  current
       DESCRIPTION
"OAM total Alarm event value for the specific alarm type."
        ::= { utsEponOAMAlarmThresholdEntry 8 } 




------
------    Alarm notify
------


------ utsFaultAlarmNotifyObjs OBJECT IDENTIFIER ::= { utsEponNotifyExtObjects 1 }


--
--  EPON realted alarms
--

utsEponFaultAlarm OBJECT IDENTIFIER ::= { utFault 2 }

    utsEponRadiusServerAccessOk  NOTIFICATION-TYPE
        OBJECTS { 
            utAlarmSeqNo,
            utAlarmOccurrenceTime,
            utAlarmSeverity,
            utAlarmProbableCause,
            utAlarmType,
            utAlarmClearType,
            utAlarmResourceType,
            utsDot3Security8021xRadiusSvrPrimaryOnuAuthIP,
            alarmSessionId
        }
    STATUS       current
    DESCRIPTION
        "Epon Radius server not accessible."
    ::= { utsEponFaultAlarm 0 1 }
    
    utsEponRadiusServerNotAccessible  NOTIFICATION-TYPE
        OBJECTS { 
            utAlarmSeqNo,
            utAlarmOccurrenceTime,
            utAlarmSeverity,
            utAlarmProbableCause,
            utAlarmType,
            utAlarmClearType,
            utAlarmResourceType,
            utsDot3Security8021xRadiusSvrPrimaryOnuAuthIP,
            alarmSessionId
        }
    STATUS       current
    DESCRIPTION
        "Epon Radius server not accessible."
    ::= { utsEponFaultAlarm 0 2 }


    utsEponTemperatureNormal NOTIFICATION-TYPE
        OBJECTS { 
            utAlarmSeqNo,
            utAlarmOccurrenceTime,
            utAlarmSeverity,
            utAlarmProbableCause,
            utAlarmType,
            utAlarmClearType,
            utAlarmResourceType,
            alarmSessionId
        }
    STATUS       current
    DESCRIPTION
        "Epon box temperature back to normal."
    ::= { utsEponFaultAlarm 0 3 }


    utsEponTemperatureTooHigh  NOTIFICATION-TYPE
        OBJECTS { 
            utAlarmSeqNo,
            utAlarmOccurrenceTime,
            utAlarmSeverity,
            utAlarmProbableCause,
            utAlarmType,
            utAlarmClearType,
            utAlarmResourceType,
            alarmSessionId
        }
    STATUS       current
    DESCRIPTION
        "Epon box temperature too low."
    ::= { utsEponFaultAlarm 0 5 }


    utsEponFanNormal  NOTIFICATION-TYPE
        OBJECTS { 
            utAlarmSeqNo,
            utAlarmOccurrenceTime,
            utAlarmSeverity,
            utAlarmProbableCause,
            utAlarmType,
            utAlarmClearType,
            utAlarmResourceType,
				alarmFanNumber,
				alarmSessionId
        }
    STATUS       current
    DESCRIPTION
        "Epon fan start."
    ::= { utsEponFaultAlarm 0 6 }


    utsEponFanAbnormal  NOTIFICATION-TYPE
        OBJECTS { 
            utAlarmSeqNo,
            utAlarmOccurrenceTime,
            utAlarmSeverity,
            utAlarmProbableCause,
            utAlarmType,
            utAlarmClearType,
            utAlarmResourceType,
				alarmFanNumber,
				alarmSessionId
        }
    STATUS       current
    DESCRIPTION
        "Epon fan stop."
    ::= { utsEponFaultAlarm 0 7 }


    utsEponCPUUtil  NOTIFICATION-TYPE
        OBJECTS { 
          utEventSeqNo,
          utEventOccurrenceTime,
	      alarmTaskName,
	      alarmResourceInt
        }
    STATUS       current
    DESCRIPTION
        "Epon cpu resource util."
    ::= { utsEponFaultAlarm 0 8 }

    utsEponMemResource  NOTIFICATION-TYPE
        OBJECTS { 
          utEventSeqNo,
          utEventOccurrenceTime,
	      alarmResourceInt
        }
    STATUS       current
    DESCRIPTION
        "Epon memory resource."
    ::= { utsEponFaultAlarm 0 9 }



    utsEponModuleInsert  NOTIFICATION-TYPE
        OBJECTS { 
            utAlarmSeqNo,
            utAlarmOccurrenceTime,
            utAlarmSeverity,
            utAlarmProbableCause,
            utAlarmType,
            utAlarmClearType,
            utAlarmResourceType,         
            alarmModule,
            alarmSessionId
        }
    STATUS       current
    DESCRIPTION
        "Epon module inserted. "
    ::= { utsEponFaultAlarm 0 11 }


    utsEponModuleRemove  NOTIFICATION-TYPE
        OBJECTS { 
            utAlarmSeqNo,
            utAlarmOccurrenceTime,
            utAlarmSeverity,
            utAlarmProbableCause,
            utAlarmType,
            utAlarmClearType,
            utAlarmResourceType,         
            alarmModule,
            alarmSessionId
        }
    STATUS       current
    DESCRIPTION
        "Epon module removed. "
    ::= { utsEponFaultAlarm 0 12 }


    utsEponModuleDiag  NOTIFICATION-TYPE
        OBJECTS { 
            utEventSeqNo,
            utEventOccurrenceTime,
	    alarmDiagStatus
        }
    STATUS       current
    DESCRIPTION
        "Epon module diag status. "
    ::= { utsEponFaultAlarm 0 13 }

    utsEponModuleSysPwrNormal  NOTIFICATION-TYPE
        OBJECTS { 
            utAlarmSeqNo,
            utAlarmOccurrenceTime,
            utAlarmSeverity,
            utAlarmProbableCause,
            utAlarmType,
            utAlarmClearType,
            utAlarmResourceType,
            alarmSessionId
        }
    STATUS       current
    DESCRIPTION
        "Epon Chassis power supply recover "
    ::= { utsEponFaultAlarm 0 15 }
    
    utsEponModuleSysPwrAbnormal  NOTIFICATION-TYPE
        OBJECTS { 
            utAlarmSeqNo,
            utAlarmOccurrenceTime,
            utAlarmSeverity,
            utAlarmProbableCause,
            utAlarmType,
            utAlarmClearType,
            utAlarmResourceType,
            alarmSessionId
        }
    STATUS       current
    DESCRIPTION
        "Epon Chassis power supply recover "
    ::= { utsEponFaultAlarm 0 16 }

    utsEponModPowerSlotEvent  NOTIFICATION-TYPE
        OBJECTS { 
            utEventSeqNo,
            utEventOccurrenceTime,
            alarmPowerSlotNumber,
            alarmPowerSlotStatus
        }
    STATUS       current
    DESCRIPTION
        "Epon Chassis power supply slot status "
    ::= { utsEponFaultAlarm 0 17 }
    
    utsEponSFPLinkUp  NOTIFICATION-TYPE
        OBJECTS { 
            utAlarmSeqNo,
            utAlarmOccurrenceTime,
            utAlarmSeverity,
            utAlarmProbableCause,
            utAlarmType,
            utAlarmClearType,
            utAlarmResourceType,         
            alarmModule,
            alarmPort,
            alarmSessionId
        }
    STATUS       current
    DESCRIPTION
        "Epon sfp port link up. "
    ::= { utsEponFaultAlarm 0 101 }

    utsEponSFPLinkDown  NOTIFICATION-TYPE
        OBJECTS { 
            utAlarmSeqNo,
            utAlarmOccurrenceTime,
            utAlarmSeverity,
            utAlarmProbableCause,
            utAlarmType,
            utAlarmClearType,
            utAlarmResourceType,         
            alarmModule,
            alarmPort,
            alarmSessionId
        }
    STATUS       current
    DESCRIPTION
        "Epon sfp port link down. "
    ::= { utsEponFaultAlarm 0 102 }

    utsEponHigigLinkUp  NOTIFICATION-TYPE
        OBJECTS { 
            utAlarmSeqNo,
            utAlarmOccurrenceTime,
            utAlarmSeverity,
            utAlarmProbableCause,
            utAlarmType,
            utAlarmClearType,
            utAlarmResourceType,
            alarmSessionId
        }
    STATUS       current
    DESCRIPTION
        "Epon higig port link up. "
    ::= { utsEponFaultAlarm 0 103 }


    utsEponHigigLinkDown  NOTIFICATION-TYPE
        OBJECTS { 
            utAlarmSeqNo,
            utAlarmOccurrenceTime,
            utAlarmSeverity,
            utAlarmProbableCause,
            utAlarmType,
            utAlarmClearType,
            utAlarmResourceType,
            alarmSessionId
        }
    STATUS       current
    DESCRIPTION
        "Epon higig port link down. "
    ::= { utsEponFaultAlarm 0 104 }

    utsEponOltLinkUp  NOTIFICATION-TYPE
        OBJECTS { 
            utAlarmSeqNo,
            utAlarmOccurrenceTime,
            utAlarmSeverity,
            utAlarmProbableCause,
            utAlarmType,
            utAlarmClearType,
            utAlarmResourceType,         
            alarmModule,
            alarmPort,
            alarmSessionId
        }
    STATUS       current
    DESCRIPTION
        "Epon olt port link up. "
    ::= { utsEponFaultAlarm 0 201 }

    utsEponOltLinkDown  NOTIFICATION-TYPE
        OBJECTS { 
            utAlarmSeqNo,
            utAlarmOccurrenceTime,
            utAlarmSeverity,
            utAlarmProbableCause,
            utAlarmType,
            utAlarmClearType,
            utAlarmResourceType,         
            alarmModule,
            alarmPort,
            alarmSessionId
        }
    STATUS       current
    DESCRIPTION
        "Epon olt port link down. "
    ::= { utsEponFaultAlarm 0 202 }

    utsEponOnuLinkUp  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmMacAddress,
            alarmEponOnuHwType,
            alarmSessionId
        }
    STATUS       current
    DESCRIPTION
        "Epon onu port link up. "
    ::= { utsEponFaultAlarm 0 301 }


    utsEponOnuLinkDown  NOTIFICATION-TYPE
        OBJECTS { 
            utAlarmSeqNo,
            utAlarmOccurrenceTime,
            utAlarmSeverity,
            utAlarmProbableCause,
            utAlarmType,
            utAlarmClearType,
            utAlarmResourceType,         
            alarmModule,
            alarmPort,
            alarmLogicalPort,
            alarmMacAddress,
            alarmEponOnuHwType,
            alarmSessionId
        }
    STATUS       current
    DESCRIPTION
        "Epon onu port link down. "
    ::= { utsEponFaultAlarm 0 302 }

    utsEponOnu802Dot3OamLinkFaultClear  NOTIFICATION-TYPE
        OBJECTS { 
            utAlarmSeqNo,
            utAlarmOccurrenceTime,
            utAlarmSeverity,
            utAlarmProbableCause,
            utAlarmType,
            utAlarmClearType,
            utAlarmResourceType,         
            alarmModule,
            alarmPort,
            alarmLogicalPort,
            alarmSessionId
        }
    STATUS       current
    DESCRIPTION
        "Epon 802.3 oam link fault. "
    ::= { utsEponFaultAlarm 0 303 }
    
    utsEponOnu802Dot3OamLinkFault  NOTIFICATION-TYPE
        OBJECTS { 
            utAlarmSeqNo,
            utAlarmOccurrenceTime,
            utAlarmSeverity,
            utAlarmProbableCause,
            utAlarmType,
            utAlarmClearType,
            utAlarmResourceType,         
            alarmModule,
            alarmPort,
            alarmLogicalPort,
            alarmSessionId
        }
    STATUS       current
    DESCRIPTION
        "Epon 802.3 oam link fault. "
    ::= { utsEponFaultAlarm 0 304 }

    utsEponOnuOam802Dot3DyingGasp  NOTIFICATION-TYPE
        OBJECTS {
            utEventSeqNo,
            utEventOccurrenceTime,
            alarmModule,
            alarmPort,
            alarmLogicalPort,
            alarmMacAddress,
            alarmEponOnuHwType
        }
    STATUS       current
    DESCRIPTION
        "Epon 802.3 oam dying gasp. "
    ::= { utsEponFaultAlarm 0 305 }



--    utsEponOnuOam802Dot3CriticalEventClear  NOTIFICATION-TYPE
--        OBJECTS {
--	    utEventSeqNo,
--	    utEventOccurrenceTime,
--            alarmModule,
--            alarmPort,
--            alarmLogicalPort
--        }
--    STATUS       current
--    DESCRIPTION
--        "Epon 802.3 oam critical event. "
--    ::= { utsEponFaultAlarm 0 307 }
    
--    utsEponOnuOam802Dot3CriticalEvent  NOTIFICATION-TYPE
--        OBJECTS {
--	    utEventSeqNo,
--	    utEventOccurrenceTime,
--            alarmModule,
--            alarmPort,
--            alarmLogicalPort
--       }
--    STATUS       current
--    DESCRIPTION
--        "Epon 802.3 oam critical event. "
--    ::= { utsEponFaultAlarm 0 308 }

    utsEponOnuOam802Dot3CriticalAlarmClear  NOTIFICATION-TYPE
        OBJECTS {
	    			utAlarmSeqNo,
            utAlarmOccurrenceTime,
            utAlarmSeverity,
            utAlarmProbableCause,
            utAlarmType,
            utAlarmClearType,
            utAlarmResourceType,
            alarmModule,
            alarmPort,
            alarmLogicalPort,
            alarmSessionId
        }
    STATUS       current
    DESCRIPTION
        "Epon 802.3 oam critical alarm. "
    ::= { utsEponFaultAlarm 0 311 }
    
    
    utsEponOnuOam802Dot3CriticalAlarm  NOTIFICATION-TYPE
        OBJECTS {
	    			utAlarmSeqNo,
            utAlarmOccurrenceTime,
            utAlarmSeverity,
            utAlarmProbableCause,
            utAlarmType,
            utAlarmClearType,
            utAlarmResourceType,
            alarmModule,
            alarmPort,
            alarmLogicalPort,
            alarmSessionId
        }
    STATUS       current
    DESCRIPTION
        "Epon 802.3 oam critical alarm. "
    ::= { utsEponFaultAlarm 0 312 }

    utsEponIgmpProxyStatusDown  NOTIFICATION-TYPE
        OBJECTS {         
	    utEventSeqNo,
	    utEventOccurrenceTime,
            alarmIgmpIIf,
            alarmIgmpGrpAddr,
            alarmIgmpOIf,
            alarmIgmpProxyStatus
        }
    STATUS       current
    DESCRIPTION
        "Epon igmp proxy status down. "
    ::= { utsEponFaultAlarm 0 402 }
    
    utsEponOnuSwitchOfflineClear  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmSessionId
        }
    STATUS       current
    DESCRIPTION
        "Epon ONU switch part off-line alarm clear. "
    ::= { utsEponFaultAlarm 0 1011 }

    utsEponOnuSwitchOffline  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmSessionId
        }
    STATUS       current
    DESCRIPTION
        "Epon ONU swith part off-line alarm. "
    ::= { utsEponFaultAlarm 0 1013 }

-- zhaoxf added Dec 26 2005 
                  
    utsEponOnuBerThresholdEvent  NOTIFICATION-TYPE
        OBJECTS {
            utEventSeqNo,
            utEventOccurrenceTime,                     
            alarmModule,
            alarmPort,
            alarmLogicalPort,            
            alarmPonLinkDirection,
            alarmErrorData            
        }
    STATUS       current
    DESCRIPTION
        "Epon ONU ber up link threshold reach event. "
    ::= { utsEponFaultAlarm 0 1014 }
    
    utsEponOnuFerThresholdEvent  NOTIFICATION-TYPE
        OBJECTS {
            utEventSeqNo,
            utEventOccurrenceTime,                     
            alarmModule,
            alarmPort,
            alarmLogicalPort,
            alarmPonLinkDirection,
            alarmErrorData
        }
    STATUS       current
    DESCRIPTION
        "Epon ONU ber up link threshold reach event. "
    ::= { utsEponFaultAlarm 0 1015 }
    
    utsEponDosAttackClear  NOTIFICATION-TYPE
        OBJECTS {
            utAlarmSeqNo,                                
			utAlarmOccurrenceTime,                       
			utAlarmSeverity,                             
			utAlarmProbableCause,                        
			utAlarmType,                                 
			utAlarmClearType,                            
			utAlarmResourceType,
			utAlarmAttackSource,  
			utAlarmAttackType,
			alarmSessionId
			}
    STATUS       current
    DESCRIPTION
        "Clear Alarm for Dos attack. "
    ::= { utsEponFaultAlarm 0 1016 } 
    
    utsEponDosAttack  NOTIFICATION-TYPE
        OBJECTS {
            utAlarmSeqNo,                                
			utAlarmOccurrenceTime,                       
			utAlarmSeverity,                             
			utAlarmProbableCause,                        
			utAlarmType,                                 
			utAlarmClearType,                            
			utAlarmResourceType,                          
			utAlarmAttackSource,			  
			utAlarmAttackType,
			alarmSessionId
			}
    STATUS       current
    DESCRIPTION
        "Alarm for Dos attack. "     
    ::= { utsEponFaultAlarm 0 1017 }

-- Feb 14, 2006; Obsolete the event type
-- CPU Utility Alarm     

    utsEponCPUUtilOverThresholdClear  NOTIFICATION-TYPE
        OBJECTS { 
            utAlarmSeqNo,
            utAlarmOccurrenceTime,
            utAlarmSeverity,
            utAlarmProbableCause,
            utAlarmType,
            utAlarmClearType,
            utAlarmResourceType, 
            alarmTaskName,
	        alarmResourceInt,
	        alarmSessionId
        }
    STATUS       current
    DESCRIPTION
        "Epon cpu resource util."
    ::= { utsEponFaultAlarm 0 1020 }
        
    utsEponCPUUtilOverThreshold  NOTIFICATION-TYPE
        OBJECTS { 
            utAlarmSeqNo,
            utAlarmOccurrenceTime,
            utAlarmSeverity,
            utAlarmProbableCause,
            utAlarmType,
            utAlarmClearType,
            utAlarmResourceType,             
            alarmTaskName,
	        alarmResourceInt,
	        alarmSessionId
        }
    STATUS       current
    DESCRIPTION
        "Epon cpu resource util."
    ::= { utsEponFaultAlarm 0 1021 }

-- Memory Utility Alarm

    utsEponMemResourceExhaustedClear  NOTIFICATION-TYPE
        OBJECTS { 
            utAlarmSeqNo,
            utAlarmOccurrenceTime,
            utAlarmSeverity,
            utAlarmProbableCause,
            utAlarmType,
            utAlarmClearType,
            utAlarmResourceType, 
	        alarmResourceInt,
	        alarmSessionId
        }
    STATUS       current
    DESCRIPTION
        "Epon memory resource."
    ::= { utsEponFaultAlarm 0 1022 }  

    utsEponMemResourceExhausted  NOTIFICATION-TYPE
        OBJECTS { 
            utAlarmSeqNo,
            utAlarmOccurrenceTime,
            utAlarmSeverity,
            utAlarmProbableCause,
            utAlarmType,
            utAlarmClearType,
            utAlarmResourceType, 
	        alarmResourceInt,
	        alarmSessionId
        }
    STATUS       current
    DESCRIPTION
        "Epon memory resource."
    ::= { utsEponFaultAlarm 0 1023 } 

-- Zhaoxf Added Mar 5,2007
-- CTC EPON spec R1.3 requirments

-- ONU extension OAM discovery procedure error alam

    utsEponOnuExtOamDiscErrorClear  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            utAlarmExtOamErrorType,
            alarmSessionId
        }
    STATUS       current
    DESCRIPTION
        "ONU extension OAM discovery procedure error clear"
    ::= { utsEponFaultAlarm 0 1031 }

    utsEponOnuExtOamDiscError  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            utAlarmExtOamErrorType,
            alarmSessionId
        }
    STATUS       current
    DESCRIPTION
        "ONU extension OAM discovery procedure error"
    ::= { utsEponFaultAlarm 0 1032 }

-- ONU remote OAM response timeout alarm

    utsEponOnuRemoteOamTimeoutClear  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmSessionId
        }
    STATUS       current
    DESCRIPTION
        "ONU remote OAM response timeout alarm clear"
    ::= { utsEponFaultAlarm 0 1033 }

    utsEponOnuRemoteOamTimeout  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmSessionId
        }
    STATUS       current
    DESCRIPTION
        "ONU remote OAM response timeout alarm"
    ::= { utsEponFaultAlarm 0 1034 }

-- ONU invalid registration alarm, CTC spec R1.3 $11.4

    utsEponOnuInvalidRegisterClear  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmMacAddress,
            alarmEponOnuHwType,
            alarmSessionId

        }
    STATUS       current
    DESCRIPTION
        "ONU invalid registeration alarm clear"
    ::= { utsEponFaultAlarm 0 1035 }

    utsEponOnuInvalidRegister  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmMacAddress,
            alarmEponOnuHwType,
            alarmSessionId
        }
    STATUS       current
    DESCRIPTION
        "ONU invalid registeration alarm"
    ::= { utsEponFaultAlarm 0 1036 }

-- ONU encryption key update timeout alarm, CTC spec R1.3 $11.1.2

    utsEponOnuEncryptionKeyUpdateTimeoutClear  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmSessionId
        }
    STATUS       current
    DESCRIPTION
        "ONU encryption key update timeout alarm clear"
    ::= { utsEponFaultAlarm 0 1037 }

    utsEponOnuEncryptionKeyUpdateTimeout  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmSessionId
        }
    STATUS       current
    DESCRIPTION
        "ONU encryption key update timeout alarm"
    ::= { utsEponFaultAlarm 0 1038 }


    utsEponOnuByteErrorRateClear  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmOnuByteErrorWindow,
            alarmOnuByteErrorThresholdMin,
            alarmSessionId
            
        }
    STATUS       current
    DESCRIPTION
        "ONU byte error rate reach threshold alarm clear"
    ::= { utsEponFaultAlarm 0 1039 }

    utsEponOnuByteErrorRate  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmOnuByteErrorWindow,
            alarmOnuByteErrorThresholdMin,
            alarmSessionId
            
        }
    STATUS       current
    DESCRIPTION
        "ONU byte error rate reach threshold alarm"
    ::= { utsEponFaultAlarm 0 1040 }

    utsEponOnuRegisterEvent  NOTIFICATION-TYPE
        OBJECTS {
            utEventSeqNo,
            utEventOccurrenceTime,
            alarmModule,
            alarmPort,
            alarmLogicalPort,
            alarmMacAddress,
            alarmEponOnuHwType
        }
    STATUS       current
    DESCRIPTION
        "Epon ONU registered"
    ::= { utsEponFaultAlarm 0 1041 }

    utsEponOnuDeregisterEvent  NOTIFICATION-TYPE
        OBJECTS {
            utEventSeqNo,
            utEventOccurrenceTime,
            alarmModule,
            alarmPort,
            alarmLogicalPort,
            alarmMacAddress,
            alarmEponOnuHwType
        }
    STATUS       current
    DESCRIPTION
        "Epon ONU deregistered"
    ::= { utsEponFaultAlarm 0 1042 }

    utsEponOltCSMSwitchOver  NOTIFICATION-TYPE
        OBJECTS {
            utEventSeqNo,
            utEventOccurrenceTime,
            alarmModule
        }
    STATUS       current
    DESCRIPTION
        "Epon OLT CSM switch over take place"
    ::= { utsEponFaultAlarm 0 1043 }


    utsEponConfigChangeEvent  NOTIFICATION-TYPE
        OBJECTS {
            utEventSeqNo,
            utEventOccurrenceTime,                     
            utEventConfigChange
        }
    STATUS       current
    DESCRIPTION
        "Epon ONU ber up link threshold reach event. "
    ::= { utsEponFaultAlarm 0 1200 }
    
    utsEponOnuOam802Dot3DyingGaspAlarmClear  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmMacAddress,
            alarmEponOnuHwType,
            alarmSessionId            
        }
    STATUS       current
    DESCRIPTION
        "ONU Dying Gasp Alarm Clear"
    ::= { utsEponFaultAlarm 0 1224 }

    utsEponOnuOam802Dot3DyingGaspAlarm  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmMacAddress,
            alarmEponOnuHwType,
            alarmSessionId        
        }
    STATUS       current
    DESCRIPTION
        "ONU Dying Gasp Alarm"
    ::= { utsEponFaultAlarm 0 1226 }   

   utsEponOnuReceiveSensitivityAlarmClear  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmMacAddress,
            alarmEponOnuHwType,
            alarmOpticalPower,
            alarmSessionId            
        }
    STATUS       current
    DESCRIPTION
        "ONU Reveive Sensitivity Alarm Clear, read the value three times, if these values all good than the 
        system value, then send alarm clear."
    ::= { utsEponFaultAlarm 0 1228 }
    
   utsEponOnuReceiveSensitivityAlarm  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmMacAddress,
            alarmEponOnuHwType,
            alarmOpticalPower,
            alarmSessionId            
        }
    STATUS       current
    DESCRIPTION
        "ONU Reveive Sensitivity Alarm, read the value three times, if these values all bad than the system
        value, then send alarm."
    ::= { utsEponFaultAlarm 0 1230 }
    
  utsEponOnuOverloadOpticalPowerAlarmClear  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmMacAddress,
            alarmEponOnuHwType,
            alarmOpticalPower,
            alarmSessionId            
        }
    STATUS       current
    DESCRIPTION
        "ONU Overload Optical Power Alarm Clear, read the value three times, if these values all good than the system
        value, then send alarm clear."
    ::= { utsEponFaultAlarm 0 1232 }
    
   utsEponOnuOverloadOpticalPowerAlarm  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmMacAddress,
            alarmEponOnuHwType,
            alarmOpticalPower,
            alarmSessionId            
        }
    STATUS       current
    DESCRIPTION
        "ONU Overload Optical Power Alarm, read the value three times, if these values all bad than the system
        value, then send alarm."
    ::= { utsEponFaultAlarm 0 1234 } 
    
--  utsEponLoopbackDetectionEvent  NOTIFICATION-TYPE
--        OBJECTS {
--            utEventSeqNo,
--            utEventOccurrenceTime,
--            alarmModule,
--            alarmPort,
--            alarmLogicalPort,
--            alarmMacAddress,
--            alarmEponOnuHwType
--        }
--    STATUS       current
--    DESCRIPTION
--        "Epon ONU detect the loop."
--    ::= { utsEponFaultAlarm 0 1236 }
    
    
utsEponLoopbackDetectionAlarmClear  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmMacAddress,
            alarmEponOnuHwType,            
            alarmSessionId            
        }
    STATUS       current
    DESCRIPTION
        "ONU Loopback detection Alarm Clear, if not dectect loopback in the continues 3 times, send the 
         alarm clear."
    ::= { utsEponFaultAlarm 0 1238 }
    
   utsEponLoopbackDetectionAlarm  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmMacAddress,
            alarmEponOnuHwType,            
            alarmSessionId            
        }
    STATUS       current
    DESCRIPTION
        "ONU Loopback detection Alarm, if dectect loopback in the continues 3 times, send the 
         alarm."
    ::= { utsEponFaultAlarm 0 1240 }
  
  utsEponOnuEtherPortUp  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmOnuEtherPortIndex,
            alarmSessionId            
        }
    STATUS       current
    DESCRIPTION
        "When the ONU Ether UNI is from down to up, send this trap."
    ::= { utsEponFaultAlarm 0 1250 }
    
   utsEponOnuEtherPortDown  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmOnuEtherPortIndex,
            alarmSessionId            
        }
    STATUS       current
    DESCRIPTION
        "When the ONU Ether UNI is from up to down, send this trap."
    ::= { utsEponFaultAlarm 0 1252 } 
    
   utsEponOltPonProtectionEvent  NOTIFICATION-TYPE
        OBJECTS {
            utEventSeqNo,
            utEventOccurrenceTime,
            alarmModule,
            alarmPort
        }
    STATUS       current
    DESCRIPTION
        "Epon Olt Pon Protecton event, when use in trunk protection, the port is the switch over to port."
    ::= { utsEponFaultAlarm 0 1255 }
    
  
   utsEponOltErroredFrameEvent  NOTIFICATION-TYPE
        OBJECTS {
            utEventSeqNo,
            utEventOccurrenceTime,
            alarmModule,
            alarmPort
        }
    STATUS       current
    DESCRIPTION
        "Epon Olt Pon Errored Frame Event."
    ::= { utsEponFaultAlarm 0 1256 }
    
  utsEponOnuErroredFrameEvent  NOTIFICATION-TYPE
        OBJECTS {
            utEventSeqNo,
            utEventOccurrenceTime,
            alarmModule,
            alarmPort,
            alarmLogicalPort
        }
    STATUS       current
    DESCRIPTION
        "Epon Onu Pon Errored Frame Event."
    ::= { utsEponFaultAlarm 0 1258 }
  
  utsEponOnuRemoteOamTimeoutEvent  NOTIFICATION-TYPE
        OBJECTS {
            utEventSeqNo,
            utEventOccurrenceTime,
            alarmModule,
            alarmPort,
            alarmLogicalPort
        }
    STATUS       current
    DESCRIPTION
        "Epon Onu Remote Oam Timeout Event."
    ::= { utsEponFaultAlarm 0 1260 }

utsEponOnuOpticalTransceiverTempHighAlarmClear  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmOnuOpticalTransceiverTemp,            
            alarmSessionId           
        }
    STATUS       current
    DESCRIPTION
        "The temp high of ONU transceiver alarm clear."
    ::= { utsEponFaultAlarm 0 1262 }
    
   utsEponOnuOpticalTransceiverTempHighAlarm  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmOnuOpticalTransceiverTemp,            
            alarmSessionId            
        }
    STATUS       current
    DESCRIPTION
        "The temp high of ONU transceiver alarm clear."
    ::= { utsEponFaultAlarm 0 1266 }

utsEponOnuOpticalTransceiverTempLowAlarmClear  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmOnuOpticalTransceiverTemp,            
            alarmSessionId           
        }
    STATUS       current
    DESCRIPTION
        "The temp low of ONU transceiver alarm clear."
    ::= { utsEponFaultAlarm 0 1268 }
    
   utsEponOnuOpticalTransceiverTempLowAlarm  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmOnuOpticalTransceiverTemp,            
            alarmSessionId            
        }
    STATUS       current
    DESCRIPTION
        "The temp low of ONU transceiver alarm clear."
    ::= { utsEponFaultAlarm 0 1270 }

utsEponOnuOpticalTransceiverVccHighAlarmClear  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmOnuOpticalTransceiverVcc,            
            alarmSessionId           
        }
    STATUS       current
    DESCRIPTION
        "The vcc high of ONU transceiver alarm clear."
    ::= { utsEponFaultAlarm 0 1272 }
    
   utsEponOnuOpticalTransceiverVccHighAlarm  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmOnuOpticalTransceiverVcc,            
            alarmSessionId            
        }
    STATUS       current
    DESCRIPTION
        "The vcc high of ONU transceiver alarm clear."
    ::= { utsEponFaultAlarm 0 1274 }

utsEponOnuOpticalTransceiverVccLowAlarmClear  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmOnuOpticalTransceiverVcc,            
            alarmSessionId           
        }
    STATUS       current
    DESCRIPTION
        "The vcc low of ONU transceiver alarm clear."
    ::= { utsEponFaultAlarm 0 1276 }
    
   utsEponOnuOpticalTransceiverVccLowAlarm  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmOnuOpticalTransceiverVcc,            
            alarmSessionId            
        }
    STATUS       current
    DESCRIPTION
        "The vcc low of ONU transceiver alarm clear."
    ::= { utsEponFaultAlarm 0 1278 }


utsEponOnuOpticalTransceiverBiasHighAlarmClear  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmOnuOpticalTransceiverBias,            
            alarmSessionId           
        }
    STATUS       current
    DESCRIPTION
        "The bias high of ONU transceiver alarm clear."
    ::= { utsEponFaultAlarm 0 1280 }
    
   utsEponOnuOpticalTransceiverBiasHighAlarm  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmOnuOpticalTransceiverBias,            
            alarmSessionId            
        }
    STATUS       current
    DESCRIPTION
        "The bias high of ONU transceiver alarm clear."
    ::= { utsEponFaultAlarm 0 1282 }

utsEponOnuOpticalTransceiverBiasLowAlarmClear  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmOnuOpticalTransceiverBias,            
            alarmSessionId           
        }
    STATUS       current
    DESCRIPTION
        "The bias low of ONU transceiver alarm clear."
    ::= { utsEponFaultAlarm 0 1284 }
    
   utsEponOnuOpticalTransceiverBiasLowAlarm  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmOnuOpticalTransceiverBias,            
            alarmSessionId            
        }
    STATUS       current
    DESCRIPTION
        "The bias low of ONU transceiver alarm clear."
    ::= { utsEponFaultAlarm 0 1286 }

utsEponOnuOpticalTransceiverTxPowerHighAlarmClear  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmOpticalPower,            
            alarmSessionId           
        }
    STATUS       current
    DESCRIPTION
        "The tx power high of ONU transceiver alarm clear."
    ::= { utsEponFaultAlarm 0 1288 }
    
   utsEponOnuOpticalTransceiverTxPowerHighAlarm  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmOpticalPower,            
            alarmSessionId            
        }
    STATUS       current
    DESCRIPTION
        "The tx power high of ONU transceiver alarm clear."
    ::= { utsEponFaultAlarm 0 1290 }

utsEponOnuOpticalTransceiverTxPowerLowAlarmClear  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmOpticalPower,            
            alarmSessionId           
        }
    STATUS       current
    DESCRIPTION
        "The tx power low of ONU transceiver alarm clear."
    ::= { utsEponFaultAlarm 0 1292 }
    
   utsEponOnuOpticalTransceiverTxPowerLowAlarm  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmOpticalPower,            
            alarmSessionId            
        }
    STATUS       current
    DESCRIPTION
        "The tx power low of ONU transceiver alarm clear."
    ::= { utsEponFaultAlarm 0 1294 }

utsEponOnuOpticalTransceiverRxPowerHighAlarmClear  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmOpticalPower,            
            alarmSessionId           
        }
    STATUS       current
    DESCRIPTION
        "The rx power high of ONU transceiver alarm clear."
    ::= { utsEponFaultAlarm 0 1296 }
    
   utsEponOnuOpticalTransceiverRxPowerHighAlarm  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmOpticalPower,            
            alarmSessionId            
        }
    STATUS       current
    DESCRIPTION
        "The rx power high of ONU transceiver alarm clear."
    ::= { utsEponFaultAlarm 0 1298 }

utsEponOnuOpticalTransceiverRxPowerLowAlarmClear  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmOpticalPower,            
            alarmSessionId           
        }
    STATUS       current
    DESCRIPTION
        "The rx power low of ONU transceiver alarm clear."
    ::= { utsEponFaultAlarm 0 1300 }
    
   utsEponOnuOpticalTransceiverRxPowerLowAlarm  NOTIFICATION-TYPE
        OBJECTS {
            utAlarmSeqNo,
            utAlarmOccurrenceTime,
            utAlarmSeverity,
            utAlarmProbableCause,
            utAlarmType,
            utAlarmClearType,
            utAlarmResourceType,         
            alarmModule,
            alarmPort,
            alarmLogicalPort,
            alarmOpticalPower,            
            alarmSessionId            
        }
    STATUS       current
    DESCRIPTION
        "The rx power low of ONU transceiver alarm clear."
    ::= { utsEponFaultAlarm 0 1302 } 

utsEponUplinkBandwidthBeyondEvent  NOTIFICATION-TYPE
        OBJECTS {
            utEventSeqNo,
            utEventOccurrenceTime,
            alarmModule,
            alarmPort
        }
    STATUS       current
    DESCRIPTION
        "Epon Olt uplink bandwidth beyond the threshold Event."
    ::= { utsEponFaultAlarm 0 1500 }

utsEponOnuUniBandwidthBeyondEvent  NOTIFICATION-TYPE
        OBJECTS {
            utEventSeqNo,
            utEventOccurrenceTime,
            alarmModule,
            alarmPort,
            alarmLogicalPort,
            alarmOnuEtherPortIndex            
        }
    STATUS       current
    DESCRIPTION
        "Epon Onu uni bandwidth beyond Event."
    ::= { utsEponFaultAlarm 0 1502 }
       
    
END

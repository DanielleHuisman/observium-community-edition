UTS-COMMON-TC-MIB DEFINITIONS ::= BEGIN

IMPORTS
	MODULE-IDENTITY, Integer32, Unsigned32
		FROM SNMPv2-SMI
	TEXTUAL-CONVENTION
		FROM SNMPv2-TC
	utModules
		FROM UTS-COMMON-MIB;

utCommonTCModules MODULE-IDENTITY
	LAST-UPDATED "200204280000Z"
	ORGANIZATION 
		"UTStarcom, Inc."
	CONTACT-INFO 
		"Contact: UTStarcom Customer Support Group
		
		          Postal: UTStarcom Shenzhen R&D Center
		                  3/F, Legend Building,
		                  High-tech Industrial Park,
		                  Nanshan Shenzhen, 518057, PRC
		
		             Tel: +86 (755) 6983555
		             Fax: +86 (755) 6983786
		
		             WEB: http://www.utstar.com
		        "
	DESCRIPTION 
		"The root MIB module for UTStarcom UMTS project text convention definitions.
		
		        Copyright (c) 2002 UTStarcom, Inc.
		        All rights reserved.
		
		        Reproduction of this document is authorized on the condition that the 
		        foregoing copyright notice is included.
		
		        This SNMP MIB module (Specification) embodies UTStarcom proprietary 
		        intellectual property.  UTStarcom retains all title and ownership in 
		        the Specification, including any revisions.
		
		        UTStarcom grants all interested parties a non-exclusive license to use 
		        and distribute an unmodified copy of this Specification in connection 
		        with management of UTStarcom products, and without fee, provided this 
		        copyright notice and license appear on all copies.
		
		        This Specification is supplied 'AS IS' and UTStarcom makes no warranty, 
		        either express or implied, as to the use, operation, condition, or 
		        performance of the Specification."

	REVISION "200204280000Z"
	DESCRIPTION 
		"Initial version of the root MIB module UTS-COMMON-MIB."

	REVISION "200312151351Z"
	DESCRIPTION 
		"define ProcedualStatus and UsageState and AdministrativeState according to X.721
		Added ActionCorrelationNo"
::= { utModules 3 }


ActionCorrelationNo ::= TEXTUAL-CONVENTION
	STATUS     current
	DESCRIPTION 
		""
	SYNTAX  OCTET STRING


ActionMode ::= TEXTUAL-CONVENTION
	STATUS     current
	DESCRIPTION 
		""
	SYNTAX  INTEGER {
		sychronization (0),
		asychronization (1)
	}


ActionStatus ::= TEXTUAL-CONVENTION
	STATUS     current
	DESCRIPTION 
		""
	SYNTAX  INTEGER {
		processing (0),
		action-success (1),
		action-failure (2),
		action-partial-failure (3)
	}


AdministrativeState ::= TEXTUAL-CONVENTION
	STATUS     current
	DESCRIPTION 
		"The administration of managed objects operates independently of the
		operability and usage of managed objects and isdescribed by the 
		administrative state attribute, which has three values.
		
		Unlock:
		This event consists of an operation being performed at the managed 
		object boundary to unlock the managed object's corresponding resource. 
		It can occur only if the managed object's administrative state is 
		locked or shutting down. It causes a transition to the unlocked 
		administrative state.
		
		
		Lock:
		This event consists of an operation being performed at the managed 
		object boundary to lock the managed object's corresponding resource. 
		It can occur only if the managed object's administrative state is 
		unlocked or shutting down. It causes a transition to the locked 
		administrative state.
		
		Shut down:
		This event consists of an operation being performed at the managed 
		object boundary to shut down the managed object's corresponding 
		resource. It can occur only if the managed object's administrative 
		state is unlocked. It causes a state transition as follows:
		- if, at the time of the event, the resource has existing users, 
		      the administrative state becomes shutting down;
		- if, at the time of the event, the resource has no users, 
		      the administrative state becomes locked."
	SYNTAX  INTEGER {
		lock (0),
		unlock (1),
		shutdown (2)
	}


AlarmStatus ::= TEXTUAL-CONVENTION
	STATUS     current
	DESCRIPTION 
		"When the value of this attribute is empty set, this implies that none of the status conditions described below are present.
		
		- under repair: The resource is currently being repaired. When under repair value is present, the operational
		state is either disabled or enabled.
		
		- critical: One or more critical alarms indicating a fault have been detected in the resource, and have not
		been cleared. The operational state of the managed object can be disabled or enabled.
		
		- major: One or more major alarms indicating a fault have been detected in the resource, and have not yet
		been cleared. The operational state of the managed object can be disabled or enabled.
		
		- minor: One or more minor alarms indicating a fault have been detected in the resource, and have not yet
		been cleared. The operational state of the managed object can be disabled or enabled.
		
		 - alarm outstanding: One or more alarms have been detected in the resource. The condition may or may not
		be disabling. If the operational state is enabled, additional attributes, particular to the managed object
		class, may indicate the nature and cause of the condition and the services that are affected.
		
		31 ...  6   5   4    3   2   1   0
		bit0:underRepair
		bit1:warning
		bit2:minor
		bit3:major
		bit4:critical
		bit5:alarmOutstanding
		"
	SYNTAX  Unsigned32


AvailableStatus ::= TEXTUAL-CONVENTION
	STATUS     current
	DESCRIPTION 
		"- in test: The resource is undergoing a test procedure. If the 
		administrative state is locked or shutting downthen normal users 
		are precluded from using the resource and the control status 
		attribute has the valuereserved for test. Tests that do not 
		exclude additional users can be present in any operational or
		administrative state but the reserved for test condition should 
		not be present. 
		
		- failed: The resource has an internal fault that prevents it 
		from operating. The operational state is disabled.
		
		- power off: The resource requires power to be applied and is 
		not powered on. For example, a fuse or other protection device 
		is known to have removed power or a low voltage condition has 
		been detected. The operational state is disabled.
		
		- off line: The resource requires a routine operation to be 
		performed to place it online and make it available for use. 
		The operation may be manual or automatic, or both. The 
		operational state is disabled. 
		
		- off duty: The resource has been made inactive by an internal 
		control process in accordance with a predetermined time schedule. 
		Under normal conditions the control process can be expected to 
		reactivate the resource at some scheduled time, and it is 
		therefore considered to be optional. The operational state is
		enabled or disabled.
		
		- dependency: The resource cannot operate because some other 
		resource on which it depends is (i.e. aresource not represented 
		by the same managed object) unavailable. For example, a device 
		is not accessible because its controller is powered off. The 
		operational state is disabled.
		
		- degraded: The service available from the resource is degraded 
		in some respect, such as in speed or operating capacity. 
		Failure of a test or an unacceptable performance measurement 
		has established that some or all services are not functional 
		or are degraded due to the presence of a defect. However, the
		resource remains available for service, either because some 
		services are satisfactory or because degraded service is 
		preferable to no service at all. Object specific attributes 
		may be defined to represent further information indicating, 
		for example, which services are not functional and the nature 
		of the degradation. The operational state is enabled.
		
		- not installed: The resource represented by the managed object 
		is not present, or is incomplete. For example, a plug-in module 
		is missing, a cable is disconnected or a software module is not 
		loaded. The operational state is disabled.
		
		- log full: This indicates a log full condition the semantics 
		of which are defined in CCITT Rec. X.735 | ISO/IEC 10164-6.
		
		31  ...  9   8   7   6   5   4   3    2    1   0
		bit0:inTest
		bit1:failed
		bit2:powerOff
		bit3:offLine
		bit4:offDuty
		bit5:dependency
		bit6:degarded
		bit7:notInstalled
		bit8:logFull
		"
	SYNTAX  Unsigned32


BOOL ::= TEXTUAL-CONVENTION
	STATUS     current
	DESCRIPTION 
		""
	SYNTAX  INTEGER {
		false (0),
		true (1)
	}


BYTE ::= TEXTUAL-CONVENTION
	STATUS     current
	DESCRIPTION 
		"The data type BYTE definition"
	SYNTAX  Integer32 (0..255)


ControlStatus ::= TEXTUAL-CONVENTION
	STATUS     current
	DESCRIPTION 
		"The control status attribute is read-write and set-valued. It can have zero or more of the following values, not all of
		which are applicable to every class of managed object.
		When the value of this attribute is empty set, this implies
		that none of the status conditions described below are present.
		
		- subject to test:
		  The resource is available to normal users, but tests may be conducted on it simultaneously
		  at unpredictable times, which may cause it to exhibit unusual characteristics to users.
		
		- part of services locked:
		  This value indicates whether a manager has administratively restricted a particular
		  part of a service from the user(s) of a resource. The administrative state is unlocked. Examples are
		  incoming service barred, outgoing service barred, write locked by media key, read locked.
		
		- reserved for test:
		  The resource has been made administratively unavailable to normal users because it is
		  undergoing a test procedure. The administrative state is locked.
		
		- suspended:
		  Service has been administratively suspended to the users of the resource. The resource may
		  retain knowledge of current users and/or requests for usage, depending upon the managed object class
		  definition, but does not resume performing services until the suspended condition is revoked. The
		  administrative state in unlocked.
		
		31  ...  4   3   2   1   0
		bit0:subjectToTest
		bit1:pastOfServicesLocked
		bit2:reservedForTest
		bit3:suspended
		"
	SYNTAX  Unsigned32


-- **************************
-- *	TEXT CONVENTION     *
-- **************************

OperationalState ::= TEXTUAL-CONVENTION
	STATUS     current
	DESCRIPTION 
		"The administration of managed objects operates independently of the
		operability and usage of managed objects and isdescribed by the 
		administrative state attribute, which has three values.
		"
	SYNTAX  INTEGER {
		disabled (0),
		enabled (1)
	}


ProceduralStatus ::= TEXTUAL-CONVENTION
	STATUS     current
	DESCRIPTION 
		"31  ...  9   8   7   6   5   4   3    2    1   0 
		
		bit0:
		
		initialized required 
		
		bit1:not initialized  
		
		bit2:initializing 
		
		bit3:reporting 
		
		bit4:terminating
		
		in test,
		
		failed,
		
		power off,
		
		off line,
		
		off duty,
		
		dependency,
		
		degraded,
		
		not installed,
		
		log full"
	SYNTAX  Unsigned32


StandbyStatus ::= TEXTUAL-CONVENTION
	STATUS     current
	DESCRIPTION 
		"The standby status attribute is single-valued and read-only. It shall have one of the following values.
		The value is only
		meaningful when the back-up relationship role exists.
		- hot standby:
		  The resource is not providing service, but is operating in synchronism with another resource
		  that is to be backed-up (e.g., a computer shadowing another computer). A resource with a hot standby
		  status will be immediately able to take over the role of the resource to be backed-up, without the need for
		  initialization activity, and will contain the same information as the resource to be backed up. The hot
		  standby condition is mutually exclusive with the cold standby and providing service conditions.
		- cold standby:
		  The resource is to back-up another resource, but is not synchronized with that resource. A
		  resource with a cold standby status will not be immediately able to take over the role of a resource to be
		  backed up, and will require some initialization activity. The cold standby condition is mutually exclusive
		  with the hot standby and providing service conditions.
		- providing service:
		  The back-up resource is providing service and is backing up another resource. The
		  providing service condition is mutually exclusive with the hot standby and cold standby conditions."
	SYNTAX  INTEGER {
		hot-standby (1),
		cold-standby (2),
		providing-service (3)
	}


UsageState ::= TEXTUAL-CONVENTION
	STATUS     current
	DESCRIPTION 
		"The usage of a resource is described by the usage state attribute, 
		which has three possible values: idle, active and busy."
	SYNTAX  INTEGER {
		idle (0),
		active (1),
		busy (2),
		not-available (3)
	}


WORD ::= TEXTUAL-CONVENTION
	STATUS     current
	DESCRIPTION 
		""
	SYNTAX  Integer32 (0..65535)

END


-- This MIB was created using NuDesign Team's Visual MIBuilder (Ver 4.3).
-- update list
-- 02-11-26  11:20	Modified UsageState "busy" instead of "standby"

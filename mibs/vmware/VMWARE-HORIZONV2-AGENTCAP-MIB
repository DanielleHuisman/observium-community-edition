-- **********************************************************
-- Copyright 2023 VMware, Inc.  All rights reserved.
-- **********************************************************

VMWARE-HORIZONV2-AGENTCAP-MIB DEFINITIONS ::= BEGIN

IMPORTS
    MODULE-IDENTITY
       FROM SNMPv2-SMI
    vmwareAgentCapabilities
       FROM VMWARE-ROOT-MIB
    AGENT-CAPABILITIES
       FROM SNMPv2-CONF;

vmwHorizonv2AgentCapabilityMIB MODULE-IDENTITY
   LAST-UPDATED "202307280000Z"
   ORGANIZATION "VMware, Inc"
   CONTACT-INFO
      "VMware, Inc
      3401 Hillview Ave
      Palo Alto, CA 94304
      Tel: 1-877-486-9273 or 650-427-5000
      Fax: 650-427-5001
      Web: http://kb.vmware.com/kb/1013445
      "
   DESCRIPTION
     "This module defines agent capabilities for deployed
      Horizon v2 agents by release."

  REVISION     "202307280000Z"
   DESCRIPTION
     "Notifications sent by Horizon v2 as updated in 2.0 release"
        ::= { vmwareAgentCapabilities 150 }

vmwHorizonv2Capability OBJECT IDENTIFIER ::= { vmwHorizonv2AgentCapabilityMIB 0 }

vmwHorizonv2Agent2021v200 AGENT-CAPABILITIES
  PRODUCT-RELEASE
     "2.0.0"
  STATUS  current
  DESCRIPTION
     "Release 2.1.0.0 for VMware Horizon v2 supporting
     only SNMPv3 trap PDUs. It describes all the notifications
     sent from the Horizon v2 appliance.
     "
  REFERENCE
     "http://www.vmware.com/products"
     -- REVISION 202307280000Z First Version.
     SUPPORTS VMWARE-HORIZONV2-EVENT-MIB
     INCLUDES {
         vmwHorizonv2NotificationGroup
     }
   ::= { vmwHorizonv2Capability 5 }

END

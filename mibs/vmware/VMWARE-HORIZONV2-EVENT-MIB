-- **********************************************************
-- Copyright 2023 VMware, Inc.  All rights reserved.
-- **********************************************************

VMWARE-HORIZONV2-EVENT-MIB DEFINITIONS ::= BEGIN
IMPORTS
   MODULE-IDENTITY, OBJECT-TYPE, NOTIFICATION-TYPE
        FROM SNMPv2-SMI
   MODULE-COMPLIANCE, OBJECT-GROUP, NOTIFICATION-GROUP
        FROM SNMPv2-CONF
   TEXTUAL-CONVENTION
       FROM SNMPv2-TC
   SnmpAdminString
        FROM SNMP-FRAMEWORK-MIB
   vmwHorizonv2
       FROM VMWARE-ROOT-MIB;
    vmwHorizonv2MIB MODULE-IDENTITY
    LAST-UPDATED "202307280000Z"
    ORGANIZATION "VMware, Inc."
    CONTACT-INFO
        "VMware, Inc.
        3401 Hillview Ave
        Palo Alto, CA 94304
        Tel: 1-877-486-9273 or 650-427-5000
        Fax: 650-427-5001
        Web: https://kb.vmware.com/s/article/1013445
        "
    DESCRIPTION
        "This MIB file contains the definition of the SNMP
        interface of VMware Horizon Edge Gateway.
        Horizon Edge Gateway is an important product which
        enables subscription license for Horizon Edges .
        For more information about Horizon Edge Gateway (Horizon V2), please see
        the latest documentation of Horizon Edge Gateway"
    REVISION     "202307280000Z"
    DESCRIPTION
        "Initial revision"
    ::= { vmwHorizonv2 1 }
vmwHorizonv2Notifications OBJECT IDENTIFIER ::= { vmwHorizonv2 0 }
vmwHorizonv2LicenseEvents OBJECT IDENTIFIER ::= { vmwHorizonv2 5 }
--
-- Object Types
--
vmwHorizonv2LicenseFailureStatus OBJECT-TYPE
   SYNTAX SnmpAdminString
   MAX-ACCESS accessible-for-notify
   STATUS      current
   DESCRIPTION
   "License push status.
   This trap is sent when a license push fails.
   License is pushed every 24 hours
   from Horizon Cloud Control Plane to Horizon on-prem.

   This trap indicates that the license sync failed due to the
   mentioned error code. If you received this event for
   more than one day in a row, please navigate to
   Horizon Admin Console and check for connectivity.

   In case issue doesn't resolve after following troubleshooting
   steps mentioned in KB article, please reach to VMware support.
   "
   ::= { vmwHorizonv2LicenseEvents 1 }
--
-- Notifications Objects
--
vmwHorizonv2LicenseEventTrap NOTIFICATION-TYPE
    OBJECTS {
                vmwHorizonv2LicenseFailureStatus
            }
    STATUS      current
    DESCRIPTION
        "This trap is sent when a license push fails.
        License push occurs every 24 hours from
        Horizon Cloud Control Plane to Horizon on-prem.

        This trap indicates that the license push failed due to the
        mentioned error code. If you received this event for
        more than one day in a row, please navigate to
        Horizon Admin Console and check for connectivity.
        Frequency: This event is sent when the license push fails.
                   After that once every 24 hrs until the issue is resolved
        In case issue doesn't resolve after following troubleshooting
        steps mentioned in KB article, please reach to VMware support
        "
    ::= { vmwHorizonv2Notifications 2 }
-- conformance information
vmwHorizonv2MIBConformance OBJECT IDENTIFIER ::= { vmwHorizonv2MIB 1 }
vmwHorizonv2MIBCompliances OBJECT IDENTIFIER ::= { vmwHorizonv2MIBConformance 1 }
vmwHorizonv2MIBGroups OBJECT IDENTIFIER ::= { vmwHorizonv2MIBConformance 2 }
vmwHorizonv2MIBBasicCompliance MODULE-COMPLIANCE
    STATUS     current
    DESCRIPTION
    "The compliance statement for entities which implement VMWARE-HORIZONV2-EVENT-MIB."
    MODULE -- this module
    MANDATORY-GROUPS { vmwHorizonv2NotificationGroup, vmwHorizonv2ObjectGroup }
    ::= { vmwHorizonv2MIBCompliances 1 }
vmwHorizonv2ObjectGroup OBJECT-GROUP
    OBJECTS {
        vmwHorizonv2LicenseFailureStatus
    }
    STATUS current
    DESCRIPTION
    "These objects provide notification details."
    ::= { vmwHorizonv2MIBGroups 1 }
vmwHorizonv2NotificationGroup NOTIFICATION-GROUP
    NOTIFICATIONS {
        vmwHorizonv2LicenseEventTrap
    }
    STATUS current
    DESCRIPTION
    "Group of objects describing notifications."
    ::= { vmwHorizonv2MIBGroups 2 }
END

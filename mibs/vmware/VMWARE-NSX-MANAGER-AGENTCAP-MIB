-- **********************************************************
-- Copyright 2016-2018 VMware, Inc.  All rights reserved.
-- **********************************************************

VMWARE-NSX-MANAGER-AGENTCAP-MIB DEFINITIONS ::= BEGIN

IMPORTS
    MODULE-IDENTITY
       FROM SNMPv2-SMI
    vmwareAgentCapabilities
       FROM VMWARE-ROOT-MIB
    AGENT-CAPABILITIES
       FROM  SNMPv2-CONF;
vmwNSXAgentCapabilityMIB MODULE-IDENTITY
   LAST-UPDATED "201805310000Z"
   ORGANIZATION "VMware, Inc"
   CONTACT-INFO
      "VMware, Inc
      3401 Hillview Ave
      Palo Alto, CA 94304
      Tel: 1-877-486-9273 or 650-427-5000
      Fax: 650-427-5001
      Web: http://kb.vmware.com/kb/1013445
      "
   DESCRIPTION
     "This module defines agent capabilities for deployed VMware NSX Manager agents by release."
   REVISION     "201805310000Z"
   DESCRIPTION
         "Capabilities for NSX Manager 6.4.x releases."
   REVISION     "201610240001Z"
   DESCRIPTION
         "Capabilities for NSX Manager 6.3.x releases."
   REVISION     "201610240000Z"
   DESCRIPTION
     "Update release version for 2016x to was 6.2.x from 6.5."
   REVISION     "201606020000Z"
   DESCRIPTION
         "Capabilities for NSX Manager releases."
        ::= { vmwareAgentCapabilities 25 }

vmwNSXMCapability OBJECT IDENTIFIER ::= { vmwNSXAgentCapabilityMIB 1 }

vmwNSXManager2018x642 AGENT-CAPABILITIES
  PRODUCT-RELEASE
     "6.4.2"
  STATUS  current
  DESCRIPTION
     "Release 6.4.2 for VMware NSX Manager supporting only SNMPv2c trap PDUs.
     It describes all the notifications sent from the NSX Manager appliance.
     WARNING: This mib module will not be backward compatible with next version.
     "
  REFERENCE
     "http://www.vmware.com/products"
     SUPPORTS VMWARE-NSX-MANAGER-MIB
     INCLUDES {
         vmwNsxManagerNotificationGroup1,
         vmwNsxManagerNotificationGroup2,
         vmwNsxManagerNotificationGroup3,
         vmwNsxManagerNotificationGroup5,
         vmwNsxManagerNotificationGroup7
     }
   ::= { vmwNSXMCapability 11 }

vmwNSXManager2018x637 AGENT-CAPABILITIES
  PRODUCT-RELEASE
     "6.3.7"
  STATUS  current
  DESCRIPTION
     "Release 6.3.7 for VMware NSX Manager supporting only SNMPv2c trap PDUs.
     It describes all the notifications sent from the NSX Manager appliance.
     WARNING: This mib module will not be backward compatible with next version.
     "
  REFERENCE
     "http://www.vmware.com/products"
     SUPPORTS VMWARE-NSX-MANAGER-MIB
     INCLUDES {
         vmwNsxManagerNotificationGroup1,
         vmwNsxManagerNotificationGroup2,
         vmwNsxManagerNotificationGroup3,
         vmwNsxManagerNotificationGroup4,
         vmwNsxManagerNotificationGroup6
     }
   ::= { vmwNSXMCapability 10 }

--
-- Applies to 2018 Release and follow up patch releases
--

vmwNSXManager2018x641 AGENT-CAPABILITIES
  PRODUCT-RELEASE
     "6.4.1"
  STATUS  current
  DESCRIPTION
     "Release 6.4.1 for VMware NSX Manager supporting only SNMPv2c trap PDUs.
     It describes all the notifications sent from the NSX Manager appliance.
     WARNING: This mib module will not be backward compatible with next version.
     "
  REFERENCE
     "http://www.vmware.com/products"
     SUPPORTS VMWARE-NSX-MANAGER-MIB
     INCLUDES {
         vmwNsxManagerNotificationGroup1,
         vmwNsxManagerNotificationGroup2,
         vmwNsxManagerNotificationGroup3,
         vmwNsxManagerNotificationGroup5
     }
   ::= { vmwNSXMCapability 9 }

--
-- Applies to 2018 Release and follow up patch releases
--

vmwNSXManager2018x636 AGENT-CAPABILITIES
  PRODUCT-RELEASE
     "6.3.6"
  STATUS  current
  DESCRIPTION
     "Release 6.3.6 for VMware NSX Manager supporting only SNMPv2c trap PDUs.
     It describes all the notifications sent from the NSX Manager appliance.
     WARNING: This mib module will not be backward compatible with next version.
     "
  REFERENCE
     "http://www.vmware.com/products"
     SUPPORTS VMWARE-NSX-MANAGER-MIB
     INCLUDES {
         vmwNsxManagerNotificationGroup1,
         vmwNsxManagerNotificationGroup2,
         vmwNsxManagerNotificationGroup3,
         vmwNsxManagerNotificationGroup4
     }
   ::= { vmwNSXMCapability 8 }

--
-- Applies to 2017 Release and follow up patch releases
--

vmwNSXManager2017x640 AGENT-CAPABILITIES
  PRODUCT-RELEASE
     "6.4.0"
  STATUS  current
  DESCRIPTION
     "Release 6.4.0 for VMware NSX Manager supporting only SNMPv2c trap PDUs.
     It describes all the notifications sent from the NSX Manager appliance.
     WARNING: This mib module will not be backward compatible with next version.
     "
  REFERENCE
     "http://www.vmware.com/products"
     SUPPORTS VMWARE-NSX-MANAGER-MIB
     INCLUDES {
         vmwNsxManagerNotificationGroup1,
         vmwNsxManagerNotificationGroup2,
         vmwNsxManagerNotificationGroup3
     }
   ::= { vmwNSXMCapability 7 }


vmwNSXManager2017x630 AGENT-CAPABILITIES
  PRODUCT-RELEASE
     "6.3.0"
  STATUS  current
  DESCRIPTION
     "Release 6.3.0 for VMware NSX Manager supporting only SNMPv2c trap PDUs.
     It describes all the notifications sent from the NSX Manager appliance.
     WARNING: This mib module will not be backward compatible with next version.
     "
  REFERENCE
     "http://www.vmware.com/products"
     SUPPORTS VMWARE-NSX-MANAGER-MIB
     INCLUDES {
         vmwNsxManagerNotificationGroup1,
         vmwNsxManagerNotificationGroup2
     }
   ::= { vmwNSXMCapability 6 }

vmwNSXManager2016x AGENT-CAPABILITIES
  PRODUCT-RELEASE
     "6.2.x"
  STATUS  current
  DESCRIPTION
     "Release 6.2.x for VMware NSX Manager supporting only SNMPv2c trap PDUs.
     It describes all the notifications sent from the NSX Manager appliance.
     "
  REFERENCE
     "http://www.vmware.com/products"
     -- REVISION 201606020000Z First Version.
     SUPPORTS VMWARE-NSX-MANAGER-MIB
     INCLUDES {
         vmwNsxManagerNotificationGroup1
     }
   ::= { vmwNSXMCapability 5 }


END

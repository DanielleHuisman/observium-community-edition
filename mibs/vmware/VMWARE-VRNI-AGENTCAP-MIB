-- **********************************************************
-- Copyright 2016-2022 VMware, Inc.  All rights reserved.
-- **********************************************************

VMWARE-VRNI-AGENTCAP-MIB DEFINITIONS ::= BEGIN

IMPORTS
    MODULE-IDENTITY
       FROM SNMPv2-SMI
    vmwareAgentCapabilities
       FROM VMWARE-ROOT-MIB
    AGENT-CAPABILITIES
       FROM SNMPv2-CONF;

vmwVRNIAgentCapabilityMIB MODULE-IDENTITY
   LAST-UPDATED "202209070000Z"
   ORGANIZATION "VMware, Inc"
   CONTACT-INFO
      "VMware, Inc
      3401 Hillview Ave
      Palo Alto, CA 94304
      Tel: 1-877-486-9273 or 650-427-5000
      Fax: 650-427-5001
      Web: http://kb.vmware.com/kb/1013445
      "
   DESCRIPTION
     "This module defines agent capabilities for deployed VRNI agents by release.
     It is compatible with vRNI v3.8 and onwards"

  REVISION     "202209070000Z"
   DESCRIPTION
     "Notifications sent by VRNI as updated in 6.7 and 6.8 release"

  REVISION     "202203300000Z"
   DESCRIPTION
     "Notifications sent by VRNI as updated in 6.5 and 6.6 release"

  REVISION     "202110010000Z"
   DESCRIPTION
     "Notifications sent by VRNI as updated in 6.3 and 6.4 release"

  REVISION     "202105240000Z"
   DESCRIPTION
     "Notifications sent by VRNI as updated in 6.2 release"

  REVISION     "202005200000Z"
   DESCRIPTION
     "Notifications sent by VRNI as updated in 5.1 and 5.2 release"

  REVISION     "201908190000Z"
   DESCRIPTION
     "Notifications sent by VRNI as updated in 5.0 release"

   REVISION     "201906060000Z"
   DESCRIPTION
     "Notifications sent by VRNI as updated in 4.2 release"

   REVISION     "201903220000Z"
   DESCRIPTION
     "Notifications sent by VRNI as updated in 4.1 release"

   REVISION     "201812040000Z"
   DESCRIPTION
     "Notifications sent by VRNI as updated in 4.0 release"

   REVISION     "201809120000Z"
   DESCRIPTION
     "Notifications sent by VRNI as updated in 3.9 release"  

   REVISION     "201710130000Z"
   DESCRIPTION
         "Change vmwVRNIAgentCapabilityMIB root oid to fix duplicate oid."

   REVISION     "201709050000Z"
   DESCRIPTION
         "Notifications send by VRNI as updated in 3.5 release"

   REVISION     "201706010000Z"
   DESCRIPTION
         "Notifications send by VRNI as updated in 3.4 release"

   REVISION     "201703020000Z"
   DESCRIPTION
         "Notifications send by VRNI as updated in 3.3 release"
   REVISION     "201611220001Z"
   DESCRIPTION
         "Describe SNMP agent capabilities for each VRNI appliance release."
        ::= { vmwareAgentCapabilities 125 }

vmwVRNICapability OBJECT IDENTIFIER ::= { vmwVRNIAgentCapabilityMIB 10 }

vmwVRNIAgent2021v660 AGENT-CAPABILITIES
  PRODUCT-RELEASE
    "6.8.0"
  STATUS  current
  DESCRIPTION
    "Release 6.8.0 for VMware VRNI.
    It describes all the notifications sent from this version of VRNI appliance."
  REFERENCE
    "http://www.vmware.com/products"
    -- REVISION 202209070000Z fourteenth Version
    SUPPORTS VMWARE-VRNI-MIB
    INCLUDES { vmwNetworkInsightNotificationInfoGroup3,
               vmwNetworkInsightNotificationGroup1,
               vmwNetworkInsightNotificationGroup2,
               vmwNetworkInsightNotificationGroup3,
               vmwNetworkInsightNotificationGroup4,
               vmwNetworkInsightNotificationGroup5,
               vmwNetworkInsightNotificationGroup6,
               vmwNetworkInsightNotificationGroup7,
               vmwNetworkInsightNotificationGroup8,
               vmwNetworkInsightNotificationGroup9,
               vmwNetworkInsightNotificationGroup10,
               vmwNetworkInsightNotificationGroup11,
               vmwNetworkInsightNotificationGroup12,
               vmwNetworkInsightNotificationGroup13,
               vmwNetworkInsightNotificationGroup14
            }
    ::= { vmwVRNICapability 20 }

vmwVRNIAgent2021v650 AGENT-CAPABILITIES
  PRODUCT-RELEASE
    "6.6.0"
  STATUS  current
  DESCRIPTION
    "Release 6.6.0 for VMware VRNI.
    It describes all the notifications sent from this version of VRNI appliance."
  REFERENCE
    "http://www.vmware.com/products"
    -- REVISION 202203300000Z thirteenth Version
    SUPPORTS VMWARE-VRNI-MIB
    INCLUDES { vmwNetworkInsightNotificationInfoGroup3,
               vmwNetworkInsightNotificationGroup1,
               vmwNetworkInsightNotificationGroup2,
               vmwNetworkInsightNotificationGroup3,
               vmwNetworkInsightNotificationGroup4,
               vmwNetworkInsightNotificationGroup5,
               vmwNetworkInsightNotificationGroup6,
               vmwNetworkInsightNotificationGroup7,
               vmwNetworkInsightNotificationGroup8,
               vmwNetworkInsightNotificationGroup9,
               vmwNetworkInsightNotificationGroup10,
               vmwNetworkInsightNotificationGroup11,
               vmwNetworkInsightNotificationGroup12,
               vmwNetworkInsightNotificationGroup13
            }
    ::= { vmwVRNICapability 19 }

vmwVRNIAgent2021v640 AGENT-CAPABILITIES
  PRODUCT-RELEASE
    "6.4.0"
  STATUS  current
  DESCRIPTION
    "Release 6.4.0 for VMware VRNI.
    It describes all the notifications sent from this version of VRNI appliance."
  REFERENCE
    "http://www.vmware.com/products"
    -- REVISION 202110010000Z twelth Version
    SUPPORTS VMWARE-VRNI-MIB
    INCLUDES { vmwNetworkInsightNotificationInfoGroup3,
               vmwNetworkInsightNotificationGroup1,
               vmwNetworkInsightNotificationGroup2,
               vmwNetworkInsightNotificationGroup3,
               vmwNetworkInsightNotificationGroup4,
               vmwNetworkInsightNotificationGroup5,
               vmwNetworkInsightNotificationGroup6,
               vmwNetworkInsightNotificationGroup7,
               vmwNetworkInsightNotificationGroup8,
               vmwNetworkInsightNotificationGroup9,
               vmwNetworkInsightNotificationGroup10,
               vmwNetworkInsightNotificationGroup11,
               vmwNetworkInsightNotificationGroup12
            }
    ::= { vmwVRNICapability 18 }

vmwVRNIAgent2021v620 AGENT-CAPABILITIES
  PRODUCT-RELEASE
    "6.2.0"
  STATUS  current
  DESCRIPTION
    "Release 6.2.0 for VMware VRNI.
    It describes all the notifications sent from this version of VRNI appliance."
  REFERENCE
    "http://www.vmware.com/products"
    -- REVISION 202105240000Z Eleventh Version
    SUPPORTS VMWARE-VRNI-MIB
    INCLUDES { vmwNetworkInsightNotificationInfoGroup3,
               vmwNetworkInsightNotificationGroup1,
               vmwNetworkInsightNotificationGroup2,
               vmwNetworkInsightNotificationGroup3,
               vmwNetworkInsightNotificationGroup4,
               vmwNetworkInsightNotificationGroup5,
               vmwNetworkInsightNotificationGroup6,
               vmwNetworkInsightNotificationGroup7,
               vmwNetworkInsightNotificationGroup8,
               vmwNetworkInsightNotificationGroup9,
               vmwNetworkInsightNotificationGroup10,
               vmwNetworkInsightNotificationGroup11
            }
    ::= { vmwVRNICapability 17 }

vmwVRNIAgent2020v520 AGENT-CAPABILITIES
  PRODUCT-RELEASE
    "5.2.0"
  STATUS  current
  DESCRIPTION
    "Release 5.2.0 for VMware VRNI.
    It describes all the notifications sent from this version of VRNI appliance."
  REFERENCE
    "http://www.vmware.com/products"
    -- REVISION 202005200000Z Tenth Version
    SUPPORTS VMWARE-VRNI-MIB
    INCLUDES { vmwNetworkInsightNotificationInfoGroup3,
               vmwNetworkInsightNotificationGroup1,
               vmwNetworkInsightNotificationGroup2,
               vmwNetworkInsightNotificationGroup3,
               vmwNetworkInsightNotificationGroup4,
               vmwNetworkInsightNotificationGroup5,
               vmwNetworkInsightNotificationGroup6,
               vmwNetworkInsightNotificationGroup7,
               vmwNetworkInsightNotificationGroup8,
               vmwNetworkInsightNotificationGroup9,
               vmwNetworkInsightNotificationGroup10
            }
    ::= { vmwVRNICapability 16 }

vmwVRNIAgent2019v500 AGENT-CAPABILITIES
  PRODUCT-RELEASE
    "5.0.0"
  STATUS  current
  DESCRIPTION
    "Release 5.0.0 for VMware VRNI.
    It describes all the notifications sent from this version of VRNI appliance."
  REFERENCE
    "http://www.vmware.com/products"
    -- REVISION 201908190000Z Ninth Version
    SUPPORTS VMWARE-VRNI-MIB
    INCLUDES { vmwNetworkInsightNotificationInfoGroup3,
               vmwNetworkInsightNotificationGroup1,
               vmwNetworkInsightNotificationGroup2,
               vmwNetworkInsightNotificationGroup3,
               vmwNetworkInsightNotificationGroup4,
               vmwNetworkInsightNotificationGroup5,
               vmwNetworkInsightNotificationGroup6,
               vmwNetworkInsightNotificationGroup7,
               vmwNetworkInsightNotificationGroup8,
               vmwNetworkInsightNotificationGroup9
            }
    ::= { vmwVRNICapability 15 }

vmwVRNIAgent2019v420 AGENT-CAPABILITIES
  PRODUCT-RELEASE
    "4.2.0"
  STATUS  current
  DESCRIPTION
    "Release 4.2.0 for VMware VRNI.
    It describes all the notifications sent from this version of VRNI appliance."
  REFERENCE
    "http://www.vmware.com/products"
    -- REVISION 201906060000Z Eighth Version
    SUPPORTS VMWARE-VRNI-MIB
    INCLUDES { vmwNetworkInsightNotificationInfoGroup3,
               vmwNetworkInsightNotificationGroup1,
               vmwNetworkInsightNotificationGroup2,
               vmwNetworkInsightNotificationGroup3,
               vmwNetworkInsightNotificationGroup4,
               vmwNetworkInsightNotificationGroup5,
               vmwNetworkInsightNotificationGroup6,
               vmwNetworkInsightNotificationGroup7,
               vmwNetworkInsightNotificationGroup8
            }
    ::= { vmwVRNICapability 14 }

vmwVRNIAgent2019v410 AGENT-CAPABILITIES
  PRODUCT-RELEASE
    "4.1.0"
  STATUS  current
  DESCRIPTION
    "Release 4.1.0 for VMware VRNI.
    It describes all the notifications sent from this version of VRNI appliance."
  REFERENCE
    "http://www.vmware.com/products"
    -- REVISION 201903220000Z Seventh Version
    SUPPORTS VMWARE-VRNI-MIB
    INCLUDES { vmwNetworkInsightNotificationInfoGroup3,
               vmwNetworkInsightNotificationGroup1,
               vmwNetworkInsightNotificationGroup2,
               vmwNetworkInsightNotificationGroup3,
               vmwNetworkInsightNotificationGroup4,
               vmwNetworkInsightNotificationGroup5,
               vmwNetworkInsightNotificationGroup6,
               vmwNetworkInsightNotificationGroup7
            }
    ::= { vmwVRNICapability 13 }

vmwVRNIAgent2018v400 AGENT-CAPABILITIES
  PRODUCT-RELEASE
    "4.0.0"
  STATUS  current
  DESCRIPTION
    "Release 4.0.0 for VMware VRNI.
    It describes all the notifications sent from this version of VRNI appliance."
  REFERENCE
    "http://www.vmware.com/products"
    -- REVISION 201812120000Z Sixth Version
    SUPPORTS VMWARE-VRNI-MIB
    INCLUDES { vmwNetworkInsightNotificationInfoGroup3,
               vmwNetworkInsightNotificationGroup1,
               vmwNetworkInsightNotificationGroup2,
               vmwNetworkInsightNotificationGroup3,
               vmwNetworkInsightNotificationGroup4,
               vmwNetworkInsightNotificationGroup5,
               vmwNetworkInsightNotificationGroup6
            }
    ::= { vmwVRNICapability 12 }

vmwVRNIAgent2018v390 AGENT-CAPABILITIES
  PRODUCT-RELEASE
    "3.9.0"
  STATUS  current
  DESCRIPTION
    "Release 3.9.0 for VMware VRNI.
    It describes all the notifications sent from the VRNI appliance."
  REFERENCE
    "http://www.vmware.com/products"
    -- REVISION 201809120000Z Fifth Version
    SUPPORTS VMWARE-VRNI-MIB
    INCLUDES { vmwNetworkInsightNotificationInfoGroup3,
               vmwNetworkInsightNotificationGroup1,
               vmwNetworkInsightNotificationGroup2,
               vmwNetworkInsightNotificationGroup3,
               vmwNetworkInsightNotificationGroup4,
               vmwNetworkInsightNotificationGroup5
            }
    ::= { vmwVRNICapability 11 }          

vmwVRNIAgent2016v350 AGENT-CAPABILITIES
  PRODUCT-RELEASE
     "3.5.0"
  STATUS  current
  DESCRIPTION
     "Release 3.5.0 for VMware VRNI supporting only SNMPv2c trap PDUs.
     It describes all the notifications sent from the VRNI appliance."
  REFERENCE
     "http://www.vmware.com/products"
     -- REVISION 201709050000Z Fourth Version
     SUPPORTS VMWARE-VRNI-MIB
     INCLUDES {
         vmwNetworkInsightNotificationGroup1,
         vmwNetworkInsightNotificationGroup2,
         vmwNetworkInsightNotificationGroup3,
         vmwNetworkInsightNotificationGroup4,
         vmwNetworkInsightNotificationInfoGroup2
     }
   ::= { vmwVRNICapability 9 }

vmwVRNIAgent2017v340 AGENT-CAPABILITIES
  PRODUCT-RELEASE
     "3.4.0"
  STATUS  current
  DESCRIPTION
     "Release 3.4.0 for VMware VRNI supporting only SNMPv2c trap PDUs.
     It describes all the notifications sent from the VRNI appliance.
     This mib module is backward compatible with next version."
  REFERENCE
     "http://www.vmware.com/products"
     -- REVISION 201706010000Z Third Version
     SUPPORTS VMWARE-VRNI-MIB
     INCLUDES {
         vmwNetworkInsightNotificationGroup1,
         vmwNetworkInsightNotificationGroup2,
         vmwNetworkInsightNotificationGroup3,
         vmwNetworkInsightNotificationInfoGroup2
     }
   ::= { vmwVRNICapability 8 }


vmwVRNIAgent2017v330 AGENT-CAPABILITIES
  PRODUCT-RELEASE
     "3.3.0"
  STATUS  current
  DESCRIPTION
     "Release 3.3.0 for VMware VRNI supporting only SNMPv2c trap PDUs.
     It describes all the notifications sent from the VRNI appliance.
     This mib module is backward compatible with next version. It
     extends 3.2 release events by appending eventName managed object
     to each notification's variable binding and adding a new set of
     notifications."
  REFERENCE
     "http://www.vmware.com/products"
     -- REVISION 201702200000Z Second Version.
     SUPPORTS VMWARE-VRNI-MIB
     INCLUDES {
         vmwNetworkInsightNotificationGroup1,
         vmwNetworkInsightNotificationGroup2,
         vmwNetworkInsightNotificationInfoGroup2
     }
   ::= { vmwVRNICapability 7 }

vmwVRNIAgent2016v320 AGENT-CAPABILITIES
  PRODUCT-RELEASE
     "3.2.0"
  STATUS  current
  DESCRIPTION
     "Release 3.2.0 for VMware VRNI supporting only SNMPv2c trap PDUs.
     It describes all the notifications sent from the VRNI appliance.
     WARNING: This mib module will not be backward compatible with next version.
     "
  REFERENCE
     "http://www.vmware.com/products"
     -- REVISION 201610260000Z First Version.
     SUPPORTS VMWARE-VRNI-MIB
     INCLUDES {
         vmwNetworkInsightMIBGroups
     }
   ::= { vmwVRNICapability 6 }

END

SKYCONTROL-SYSTEM-MIB DEFINITIONS ::= BEGIN

IMPORTS
	NOTIFICATION-TYPE, OBJECT-TYPE, MODULE-IDENTITY, 
	enterprises, Integer32
		FROM SNMPv2-SMI;

skycontrol MODULE-IDENTITY
	LAST-UPDATED "200811010000Z"
	ORGANIZATION 
		"SkyControl s.r.o."
	CONTACT-INFO 
		"support@skycontrol.com"
	DESCRIPTION 
		"SkyControl monitoring units"
::= { enterprises 39052 }

ctlUnit              OBJECT IDENTIFIER ::= { skycontrol 1 }
ctlNotifiers         OBJECT IDENTIFIER ::= { skycontrol 2 }
ctlVirtualDevices    OBJECT IDENTIFIER ::= { skycontrol 3 }
ctlHardwareDevices   OBJECT IDENTIFIER ::= { skycontrol 4 }
ctIInternalSensors   OBJECT IDENTIFIER ::= { skycontrol 5 }
ctlCANSensors        OBJECT IDENTIFIER ::= { skycontrol 6 }
ctlRsSensors         OBJECT IDENTIFIER ::= { skycontrol 7 }

ctlUnitModulesTable  OBJECT-TYPE
	SYNTAX SEQUENCE OF CtlUnitModulesEntry
	MAX-ACCESS not-accessible
	STATUS     current
	DESCRIPTION 
		""
	::= { ctlUnit 1 }

ctlUnitModulesEntry  OBJECT-TYPE
	SYNTAX 	CtlUnitModulesEntry
	MAX-ACCESS not-accessible
	STATUS     current
	DESCRIPTION 
		"Entry of module"
	INDEX { ctlUnitModuleId }
	::= { ctlUnitModulesTable 1 }

CtlUnitModulesEntry ::= SEQUENCE {
	ctlUnitModuleId
		Integer32,
	ctlUnitModulePcode
		Integer32,
	ctlUnitModuleSN
		Integer32,
	ctlUnitModuleClass
		OCTET STRING,
	ctlUnitModuleType
		OCTET STRING,
	ctlUnitModuleName
		OCTET STRING,
	ctlUnitModuleState
		OCTET STRING
}

ctlUnitModuleId  OBJECT-TYPE
	SYNTAX     Integer32
	MAX-ACCESS read-only
	STATUS     current
	DESCRIPTION 
		"Id of module"
	::= { ctlUnitModulesEntry 1 }

ctlUnitModulePcode  OBJECT-TYPE
	SYNTAX     Integer32
	MAX-ACCESS read-only
	STATUS     current
	DESCRIPTION 
		"Product code of module"
	::= { ctlUnitModulesEntry 2 }

ctlUnitModuleSN  OBJECT-TYPE
	SYNTAX     Integer32
	MAX-ACCESS read-only
	STATUS     current
	DESCRIPTION 
		"Serial number of module"
	::= { ctlUnitModulesEntry 3 }

ctlUnitModuleClass  OBJECT-TYPE
	SYNTAX     OCTET STRING
	MAX-ACCESS read-only
	STATUS     current
	DESCRIPTION 
		"Class of module"
	::= { ctlUnitModulesEntry 4 }

ctlUnitModuleType  OBJECT-TYPE
	SYNTAX     OCTET STRING
	MAX-ACCESS read-only
	STATUS     current
	DESCRIPTION 
		"Type of module"
	::= { ctlUnitModulesEntry 5 }

ctlUnitModuleName  OBJECT-TYPE
	SYNTAX     OCTET STRING (SIZE(2..64))
	MAX-ACCESS read-write
	STATUS     current
	DESCRIPTION 
		"Name of module"
	::= { ctlUnitModulesEntry 6 }

ctlUnitModuleState  OBJECT-TYPE
	SYNTAX     OCTET STRING
	MAX-ACCESS read-only
	STATUS     current
	DESCRIPTION 
		"State of module"
	::= { ctlUnitModulesEntry 7 }

ctlUnitGroupsTable  OBJECT-TYPE
	SYNTAX SEQUENCE OF CtlUnitGroupsEntry
	MAX-ACCESS not-accessible
	STATUS     current
	DESCRIPTION 
		""
	::= { ctlUnit 2 }

ctlUnitGroupsEntry  OBJECT-TYPE
	SYNTAX 	CtlUnitGroupsEntry
	MAX-ACCESS not-accessible
	STATUS     current
	DESCRIPTION 
		""
	INDEX { ctlUnitGroupId }
	::= { ctlUnitGroupsTable 1 }

CtlUnitGroupsEntry ::= SEQUENCE {
	ctlUnitGroupId
		Integer32,
	ctlUnitGroupName
		OCTET STRING,
	ctlUnitGroupDesc
		OCTET STRING
}

ctlUnitGroupId  OBJECT-TYPE
	SYNTAX     Integer32
	MAX-ACCESS read-only
	STATUS     current
	DESCRIPTION 
		"Id of group"
	::= { ctlUnitGroupsEntry 1 }

ctlUnitGroupName  OBJECT-TYPE
	SYNTAX     OCTET STRING (SIZE(2..64))
	MAX-ACCESS read-write
	STATUS     current
	DESCRIPTION 
		"Name of group"
	::= { ctlUnitGroupsEntry 2 }

ctlUnitGroupDesc  OBJECT-TYPE
	SYNTAX     OCTET STRING (SIZE(0..256))
	MAX-ACCESS read-write
	STATUS     current
	DESCRIPTION 
		"Description of group"
	::= { ctlUnitGroupsEntry 3 }

ctlUnitElementsTable  OBJECT-TYPE
	SYNTAX SEQUENCE OF CtlUnitElementsEntry
	MAX-ACCESS not-accessible
	STATUS     current
	DESCRIPTION 
		""
	::= { ctlUnit 3 }

ctlUnitElementsEntry  OBJECT-TYPE
	SYNTAX 	CtlUnitElementsEntry
	MAX-ACCESS not-accessible
	STATUS     current
	DESCRIPTION 
		""
	INDEX { ctlUnitElementId }
	::= { ctlUnitElementsTable 1 }

CtlUnitElementsEntry ::= SEQUENCE {
	ctlUnitElementId
		Integer32,
	ctlUnitElementGroup
		Integer32,
	ctlUnitElementModule
		Integer32,
	ctlUnitElementNum
		Integer32,
	ctlUnitElementClass
		OCTET STRING,
	ctlUnitElementType
		OCTET STRING,
	ctlUnitElementName
		OCTET STRING,
	ctlUnitElementState
		OCTET STRING,
	ctlUnitElementValue
		OCTET STRING,
	ctlUnitElementSpec
		Integer32
}

ctlUnitElementId  OBJECT-TYPE
	SYNTAX     Integer32
	MAX-ACCESS read-only
	STATUS     current
	DESCRIPTION 
		"Id of element"
	::= { ctlUnitElementsEntry 1 }

ctlUnitElementGroup  OBJECT-TYPE
	SYNTAX     Integer32
	MAX-ACCESS read-write
	STATUS     current
	DESCRIPTION 
		"Group of element"
	::= { ctlUnitElementsEntry 2 }

ctlUnitElementModule  OBJECT-TYPE
	SYNTAX     Integer32
	MAX-ACCESS read-only
	STATUS     current
	DESCRIPTION 
		"Module of element"
	::= { ctlUnitElementsEntry 3 }

ctlUnitElementNum  OBJECT-TYPE
	SYNTAX     Integer32
	MAX-ACCESS read-only
	STATUS     current
	DESCRIPTION 
		"Number of elemnt's in module"
	::= { ctlUnitElementsEntry 4 }

ctlUnitElementClass  OBJECT-TYPE
	SYNTAX     OCTET STRING
	MAX-ACCESS read-only
	STATUS     current
	DESCRIPTION 
		"Class of element"
	::= { ctlUnitElementsEntry 5 }

ctlUnitElementType  OBJECT-TYPE
	SYNTAX     OCTET STRING
	MAX-ACCESS read-only
	STATUS     current
	DESCRIPTION 
		"Type of element"
	::= { ctlUnitElementsEntry 6 }

ctlUnitElementName  OBJECT-TYPE
	SYNTAX     OCTET STRING (SIZE(2..128))
	MAX-ACCESS read-write
	STATUS     current
	DESCRIPTION 
		"Name of element"
	::= { ctlUnitElementsEntry 7 }

ctlUnitElementState  OBJECT-TYPE
	SYNTAX     OCTET STRING
	MAX-ACCESS read-only
	STATUS     current
	DESCRIPTION 
		"State of element"
	::= { ctlUnitElementsEntry 8 }

ctlUnitElementValue  OBJECT-TYPE
	SYNTAX     OCTET STRING
	MAX-ACCESS read-only
	STATUS     current
	DESCRIPTION 
		"Value of element"
	::= { ctlUnitElementsEntry 9 }

ctlUnitElementSpec  OBJECT-TYPE
	SYNTAX     OCTET STRING
	MAX-ACCESS read-only
	STATUS     current
	DESCRIPTION 
		"Special parameters for element"
	::= { ctlUnitElementsEntry 10 }

ctlUnitLogicsTable  OBJECT-TYPE
	SYNTAX SEQUENCE OF CtlUnitLogicsEntry
	MAX-ACCESS not-accessible
	STATUS     current
	DESCRIPTION 
		""
	::= { ctlUnit 4 }

ctlUnitLogicsEntry  OBJECT-TYPE
	SYNTAX 	CtlUnitLogicsEntry
	MAX-ACCESS not-accessible
	STATUS     current
	DESCRIPTION 
		"Entry of logic"
	INDEX { ctlUnitLogicId }
	::= { ctlUnitLogicsTable 1 }

CtlUnitLogicsEntry ::= SEQUENCE {
	ctlUnitLogicId
		Integer32,
	ctlUnitLogicName
		OCTET STRING,
	ctlUnitLogicDesc
		OCTET STRING,
	ctlUnitLogicDisable
		Integer32,
	ctlUnitLogicRowStatus
		Integer32
}

-- Id of logic's

ctlUnitLogicId  OBJECT-TYPE
	SYNTAX     Integer32
	MAX-ACCESS read-only
	STATUS     current
	DESCRIPTION 
		"Id of logic scheme"
	::= { ctlUnitLogicsEntry 1 }

ctlUnitLogicName  OBJECT-TYPE
	SYNTAX     OCTET STRING (SIZE(2..64))
	MAX-ACCESS read-create
	STATUS     current
	DESCRIPTION 
		"Name of logic scheme"
	::= { ctlUnitLogicsEntry 2 }

ctlUnitLogicDesc  OBJECT-TYPE
	SYNTAX     OCTET STRING (SIZE(2..256))
	MAX-ACCESS read-create
	STATUS     current
	DESCRIPTION 
		"Description of logic scheme"
	::= { ctlUnitLogicsEntry 3 }

ctlUnitLogicDisable  OBJECT-TYPE
	SYNTAX     Integer32
	MAX-ACCESS read-create
	STATUS     current
	DESCRIPTION 
		"Disable of logic's in secs, 0 for enable "
	::= { ctlUnitLogicsEntry 4 }

ctlUnitLogicRowStatus  OBJECT-TYPE
	SYNTAX     Integer32
	MAX-ACCESS read-create
	STATUS     current
	DESCRIPTION 
		""
	::= { ctlUnitLogicsEntry 5 }

ctlUnitTrapNotification  NOTIFICATION-TYPE
	STATUS     current
	DESCRIPTION 
		"Skycontrol EMS trap"
	::= { ctlUnit 5 }

ctlUnitSaveToFlash  OBJECT-TYPE
	SYNTAX     Integer32
	MAX-ACCESS read-write
	STATUS     current
	DESCRIPTION 
		"Save current setting to flash memory"
	::= { ctlUnit 6 }

ctlNotifiersMailersTable  OBJECT-TYPE
	SYNTAX SEQUENCE OF CtlNotifiersMailersEntry
	MAX-ACCESS not-accessible
	STATUS     current
	DESCRIPTION 
		""
	::= { ctlNotifiers 1 }

ctlNotifiersMailersEntry  OBJECT-TYPE
	SYNTAX 	CtlNotifiersMailersEntry
	MAX-ACCESS not-accessible
	STATUS     current
	DESCRIPTION 
		"Entry of email notify"
	INDEX { ctlNotifiersMailerId }
	::= { ctlNotifiersMailersTable 1 }

CtlNotifiersMailersEntry ::= SEQUENCE {
	ctlNotifiersMailerId
		Integer32,
	ctlNotifiersMailerModule
		Integer32,
	ctlNotifiersMailerNum
		Integer32,
	ctlNotifiersMailerGroup
		Integer32,
	ctlNotifiersMailerType
		OCTET STRING,
	ctlNotifiersMailerName
		OCTET STRING,
	ctlNotifiersMailerState
		OCTET STRING,
	ctlNotifiersMailerValue
		OCTET STRING,
	ctlNotifiersMailerServer
		OCTET STRING,
	ctlNotifiersMailerPort
		Integer32,
	ctlNotifiersMailerLogin
		OCTET STRING,
	ctlNotifiersMailerPassword
		Integer32,
	ctlNotifiersMailersTo
		OCTET STRING,
	ctlNotifiersMailersFrom
		OCTET STRING,
	ctlNotifiersMailerMessage
		Integer32
}

ctlNotifiersMailerId  OBJECT-TYPE
	SYNTAX     Integer32
	MAX-ACCESS read-only
	STATUS     current
	DESCRIPTION 
		"Id of mailer"
	::= { ctlNotifiersMailersEntry 1 }

ctlNotifiersMailerModule  OBJECT-TYPE
	SYNTAX     Integer32
	MAX-ACCESS read-only
	STATUS     current
	DESCRIPTION 
		"Module of mailer"
	::= { ctlNotifiersMailersEntry 2 }

ctlNotifiersMailerNum  OBJECT-TYPE
	SYNTAX     Integer32
	MAX-ACCESS read-only
	STATUS     current
	DESCRIPTION 
		"Logical number in module for mailer"
	::= { ctlNotifiersMailersEntry 3 }

ctlNotifiersMailerGroup  OBJECT-TYPE
	SYNTAX     Integer32
	MAX-ACCESS read-write
	STATUS     current
	DESCRIPTION 
		"Group of mailer"
	::= { ctlNotifiersMailersEntry 4 }

ctlNotifiersMailerType  OBJECT-TYPE
	SYNTAX     OCTET STRING
	MAX-ACCESS read-only
	STATUS     current
	DESCRIPTION 
		"Type of element"
	::= { ctlNotifiersMailersEntry 5 }

ctlNotifiersMailerName  OBJECT-TYPE
	SYNTAX     OCTET STRING (SIZE(2..128))
	MAX-ACCESS read-write
	STATUS     current
	DESCRIPTION 
		"Name of mailer"
	::= { ctlNotifiersMailersEntry 6 }

ctlNotifiersMailerState  OBJECT-TYPE
	SYNTAX     OCTET STRING
	MAX-ACCESS read-only
	STATUS     current
	DESCRIPTION 
		"State of mailer"
	::= { ctlNotifiersMailersEntry 7 }

ctlNotifiersMailerValue  OBJECT-TYPE
	SYNTAX     OCTET STRING
	MAX-ACCESS read-write
	STATUS     current
	DESCRIPTION 
		"Value of mailer"
	::= { ctlNotifiersMailersEntry 8 }

ctlNotifiersMailerServer  OBJECT-TYPE
	SYNTAX     OCTET STRING (SIZE(2..256))
	MAX-ACCESS read-write
	STATUS     current
	DESCRIPTION 
		"Mailserver adress"
	::= { ctlNotifiersMailersEntry 9 }

ctlNotifiersMailerPort  OBJECT-TYPE
	SYNTAX     Integer32
	MAX-ACCESS read-write
	STATUS     current
	DESCRIPTION 
		"Port of mailserver"
	::= { ctlNotifiersMailersEntry 10 }

ctlNotifiersMailerLogin  OBJECT-TYPE
	SYNTAX     OCTET STRING (SIZE(2..128))
	MAX-ACCESS read-write
	STATUS     current
	DESCRIPTION 
		"Login on mailserver"
	::= { ctlNotifiersMailersEntry 11 }

ctlNotifiersMailerPassword  OBJECT-TYPE
	SYNTAX     Integer32
	MAX-ACCESS read-write
	STATUS     current
	DESCRIPTION 
		"Password for mailserver"
	::= { ctlNotifiersMailersEntry 12 }

ctlNotifiersMailersTo  OBJECT-TYPE
	SYNTAX     OCTET STRING (SIZE(2..128))
	MAX-ACCESS read-write
	STATUS     current
	DESCRIPTION 
		"To"
	::= { ctlNotifiersMailersEntry 13 }

ctlNotifiersMailersFrom  OBJECT-TYPE
	SYNTAX     OCTET STRING (SIZE(2..512))
	MAX-ACCESS read-write
	STATUS     current
	DESCRIPTION 
		"From"
	::= { ctlNotifiersMailersEntry 14 }

ctlNotifiersMailerMessage  OBJECT-TYPE
	SYNTAX     Integer32
	MAX-ACCESS read-write
	STATUS     current
	DESCRIPTION 
		"Message"
	::= { ctlNotifiersMailersEntry 15 }

ctlNotifiersTrapsTable  OBJECT-TYPE
	SYNTAX SEQUENCE OF CtlNotifiersTrapsEntry
	MAX-ACCESS not-accessible
	STATUS     current
	DESCRIPTION 
		""
	::= { ctlNotifiers 2 }

ctlNotifiersTrapsEntry  OBJECT-TYPE
	SYNTAX 	CtlNotifiersTrapsEntry
	MAX-ACCESS not-accessible
	STATUS     current
	DESCRIPTION 
		"Entry of trap notify"
	INDEX { ctlNotifiersTrapId }
	::= { ctlNotifiersTrapsTable 1 }

CtlNotifiersTrapsEntry ::= SEQUENCE {
	ctlNotifiersTrapId
		Integer32,
	ctlNotifiersTrapModule
		Integer32,
	ctlNotifiersTrapNum
		Integer32,
	ctlNotifiersTrapGroup
		Integer32,
	ctlNotifiersTrapType
		OCTET STRING,
	ctlNotifiersTrapName
		OCTET STRING,
	ctlNotifiersTrapState
		OCTET STRING,
	ctlNotifiersTrapValue
		OCTET STRING,
	ctlNotifiersTrapServer
		OCTET STRING,
	ctlNotifiersTrapPort
		Integer32,
	ctlNotifiersTrapVersion
		OCTET STRING,
	ctlNotifiersTrapCommunity
		OCTET STRING
}

ctlNotifiersTrapId  OBJECT-TYPE
	SYNTAX     Integer32
	MAX-ACCESS read-only
	STATUS     current
	DESCRIPTION 
		"Id of trap"
	::= { ctlNotifiersTrapsEntry 1 }

ctlNotifiersTrapModule  OBJECT-TYPE
	SYNTAX     Integer32
	MAX-ACCESS read-only
	STATUS     current
	DESCRIPTION 
		"Module of trap"
	::= { ctlNotifiersTrapsEntry 2 }

ctlNotifiersTrapNum  OBJECT-TYPE
	SYNTAX     Integer32
	MAX-ACCESS read-only
	STATUS     current
	DESCRIPTION 
		"Logical number in module for trap"
	::= { ctlNotifiersTrapsEntry 3 }

ctlNotifiersTrapGroup  OBJECT-TYPE
	SYNTAX     Integer32
	MAX-ACCESS read-write
	STATUS     current
	DESCRIPTION 
		"Group of trap"
	::= { ctlNotifiersTrapsEntry 4 }

ctlNotifiersTrapType  OBJECT-TYPE
	SYNTAX     OCTET STRING
	MAX-ACCESS read-only
	STATUS     current
	DESCRIPTION 
		"Type of element"
	::= { ctlNotifiersTrapsEntry 5 }

ctlNotifiersTrapName  OBJECT-TYPE
	SYNTAX     OCTET STRING
	MAX-ACCESS read-write
	STATUS     current
	DESCRIPTION 
		"Name of trap"
	::= { ctlNotifiersTrapsEntry 6 }

ctlNotifiersTrapState  OBJECT-TYPE
	SYNTAX     OCTET STRING
	MAX-ACCESS read-only
	STATUS     current
	DESCRIPTION 
		"State of trap"
	::= { ctlNotifiersTrapsEntry 7 }

ctlNotifiersTrapValue  OBJECT-TYPE
	SYNTAX     OCTET STRING
	MAX-ACCESS read-write
	STATUS     current
	DESCRIPTION 
		"Value of trap"
	::= { ctlNotifiersTrapsEntry 8 }

ctlNotifiersTrapServer  OBJECT-TYPE
	SYNTAX     OCTET STRING (SIZE(2..128))
	MAX-ACCESS read-write
	STATUS     current
	DESCRIPTION 
		"Receiver address for trap"
	::= { ctlNotifiersTrapsEntry 9 }

ctlNotifiersTrapPort  OBJECT-TYPE
	SYNTAX     Integer32
	MAX-ACCESS read-write
	STATUS     current
	DESCRIPTION 
		"Port of trap receiver"
	::= { ctlNotifiersTrapsEntry 10 }

ctlNotifiersTrapVersion  OBJECT-TYPE
	SYNTAX     OCTET STRING (SIZE(2..4))
	MAX-ACCESS read-write
	STATUS     current
	DESCRIPTION 
		"Version of trap"
	::= { ctlNotifiersTrapsEntry 11 }

ctlNotifiersTrapCommunity  OBJECT-TYPE
	SYNTAX     OCTET STRING (SIZE(2..32))
	MAX-ACCESS read-write
	STATUS     current
	DESCRIPTION 
		"Password for mailserver"
	::= { ctlNotifiersTrapsEntry 12 }

ctlNotifiersSMSsTable  OBJECT-TYPE
	SYNTAX SEQUENCE OF CtlNotifiersSMSsEntry
	MAX-ACCESS not-accessible
	STATUS     current
	DESCRIPTION 
		""
	::= { ctlNotifiers 3 }

ctlNotifiersSMSsEntry  OBJECT-TYPE
	SYNTAX 	CtlNotifiersSMSsEntry
	MAX-ACCESS not-accessible
	STATUS     current
	DESCRIPTION 
		"Entry of SMS notify"
	INDEX { ctlNotifiersSMSId }
	::= { ctlNotifiersSMSsTable 1 }

CtlNotifiersSMSsEntry ::= SEQUENCE {
	ctlNotifiersSMSId
		Integer32,
	ctlNotifiersSMSModule
		Integer32,
	ctlNotifiersSMSNum
		Integer32,
	ctlNotifiersSMSGroup
		Integer32,
	ctlNotifiersSMSType
		OCTET STRING,
	ctlNotifiersSMSName
		OCTET STRING,
	ctlNotifiersSMSState
		OCTET STRING,
	ctlNotifiersSMSValue
		OCTET STRING,
	ctlNotifiersSMSTo
		OCTET STRING,
	ctlNotifiersSMSMessage
		OCTET STRING
}

ctlNotifiersSMSId  OBJECT-TYPE
	SYNTAX     Integer32
	MAX-ACCESS read-only
	STATUS     current
	DESCRIPTION 
		"Id of SMS"
	::= { ctlNotifiersSMSsEntry 1 }

ctlNotifiersSMSModule  OBJECT-TYPE
	SYNTAX     Integer32
	MAX-ACCESS read-only
	STATUS     current
	DESCRIPTION 
		"Module of SMS"
	::= { ctlNotifiersSMSsEntry 2 }

ctlNotifiersSMSNum  OBJECT-TYPE
	SYNTAX     Integer32
	MAX-ACCESS read-only
	STATUS     current
	DESCRIPTION 
		"Logical number in module for SMS"
	::= { ctlNotifiersSMSsEntry 3 }

-- Group of mailr's

ctlNotifiersSMSGroup  OBJECT-TYPE
	SYNTAX     Integer32
	MAX-ACCESS read-write
	STATUS     current
	DESCRIPTION 
		"Group of SMS"
	::= { ctlNotifiersSMSsEntry 4 }

ctlNotifiersSMSType  OBJECT-TYPE
	SYNTAX     OCTET STRING
	MAX-ACCESS read-only
	STATUS     current
	DESCRIPTION 
		"Type of SMS"
	::= { ctlNotifiersSMSsEntry 5 }

ctlNotifiersSMSName  OBJECT-TYPE
	SYNTAX     OCTET STRING (SIZE(2..128))
	MAX-ACCESS read-write
	STATUS     current
	DESCRIPTION 
		"Name of SMS"
	::= { ctlNotifiersSMSsEntry 6 }

ctlNotifiersSMSState  OBJECT-TYPE
	SYNTAX     OCTET STRING
	MAX-ACCESS read-only
	STATUS     current
	DESCRIPTION 
		"State of SMS"
	::= { ctlNotifiersSMSsEntry 7 }

ctlNotifiersSMSValue  OBJECT-TYPE
	SYNTAX     OCTET STRING
	MAX-ACCESS read-write
	STATUS     current
	DESCRIPTION 
		"Value of SMS"
	::= { ctlNotifiersSMSsEntry 8 }

ctlNotifiersSMSTo  OBJECT-TYPE
	SYNTAX     OCTET STRING (SIZE(3..256))
	MAX-ACCESS read-write
	STATUS     current
	DESCRIPTION 
		"Phone number"
	::= { ctlNotifiersSMSsEntry 9 }

ctlNotifiersSMSMessage  OBJECT-TYPE
	SYNTAX     OCTET STRING (SIZE(2..512))
	MAX-ACCESS read-write
	STATUS     current
	DESCRIPTION 
		"Text of SMS message"
	::= { ctlNotifiersSMSsEntry 10 }

ctlVirtualDevicesTimersTable  OBJECT-TYPE
	SYNTAX SEQUENCE OF CtlVirtualDevicesTimersEntry
	MAX-ACCESS not-accessible
	STATUS     current
	DESCRIPTION 
		""
	::= { ctlVirtualDevices 1 }

ctlVirtualDevicesTimersEntry  OBJECT-TYPE
	SYNTAX 	CtlVirtualDevicesTimersEntry
	MAX-ACCESS not-accessible
	STATUS     current
	DESCRIPTION 
		"Entry of timer"
	INDEX { ctlVirtualDevicesTimerId }
	::= { ctlVirtualDevicesTimersTable 1 }

CtlVirtualDevicesTimersEntry ::= SEQUENCE {
	ctlVirtualDevicesTimerId
		Integer32,
	ctlVirtualDevicesTimerModule
		Integer32,
	ctlVirtualDevicesTimerNum
		Integer32,
	ctlVirtualDevicesTimerGroup
		Integer32,
	ctlVirtualDevicesTimerType
		OCTET STRING,
	ctlVirtualDevicesTimerName
		OCTET STRING,
	ctlVirtualDevicesTimerState
		OCTET STRING,
	ctlVirtualDevicesTimerValue
		OCTET STRING,
	ctlVirtualDevicesTimerBegin
		OCTET STRING,
	ctlVirtualDevicesTimerEnd
		OCTET STRING,
	ctlVirtualDevicesTimerDays
		OCTET STRING,
	ctlVirtualDevicesTimerMode
		OCTET STRING
}

ctlVirtualDevicesTimerId  OBJECT-TYPE
	SYNTAX     Integer32
	MAX-ACCESS read-only
	STATUS     current
	DESCRIPTION 
		"Id of timer"
	::= { ctlVirtualDevicesTimersEntry 1 }

ctlVirtualDevicesTimerModule  OBJECT-TYPE
	SYNTAX     Integer32
	MAX-ACCESS read-only
	STATUS     current
	DESCRIPTION 
		"Module of tiimer"
	::= { ctlVirtualDevicesTimersEntry 2 }

ctlVirtualDevicesTimerNum  OBJECT-TYPE
	SYNTAX     Integer32
	MAX-ACCESS read-only
	STATUS     current
	DESCRIPTION 
		"Logical number in module for timer"
	::= { ctlVirtualDevicesTimersEntry 3 }

ctlVirtualDevicesTimerGroup  OBJECT-TYPE
	SYNTAX     Integer32
	MAX-ACCESS read-write
	STATUS     current
	DESCRIPTION 
		"Group of timer"
	::= { ctlVirtualDevicesTimersEntry 4 }

ctlVirtualDevicesTimerType  OBJECT-TYPE
	SYNTAX     OCTET STRING
	MAX-ACCESS read-only
	STATUS     current
	DESCRIPTION 
		"Type of timer"
	::= { ctlVirtualDevicesTimersEntry 5 }

ctlVirtualDevicesTimerName  OBJECT-TYPE
	SYNTAX     OCTET STRING (SIZE(2..128))
	MAX-ACCESS read-write
	STATUS     current
	DESCRIPTION 
		"Name of timer"
	::= { ctlVirtualDevicesTimersEntry 6 }

ctlVirtualDevicesTimerState  OBJECT-TYPE
	SYNTAX     OCTET STRING
	MAX-ACCESS read-only
	STATUS     current
	DESCRIPTION 
		"State of timer"
	::= { ctlVirtualDevicesTimersEntry 7 }

ctlVirtualDevicesTimerValue  OBJECT-TYPE
	SYNTAX     OCTET STRING
	MAX-ACCESS read-write
	STATUS     current
	DESCRIPTION 
		"Value of timer"
	::= { ctlVirtualDevicesTimersEntry 8 }

ctlVirtualDevicesTimerBegin  OBJECT-TYPE
	SYNTAX     OCTET STRING
	MAX-ACCESS read-write
	STATUS     current
	DESCRIPTION 
		"Begin time for timer (Unix timestamp)"
	::= { ctlVirtualDevicesTimersEntry 9 }

ctlVirtualDevicesTimerEnd  OBJECT-TYPE
	SYNTAX     OCTET STRING
	MAX-ACCESS read-write
	STATUS     current
	DESCRIPTION 
		"End time for timer (Unix timestamp)"
	::= { ctlVirtualDevicesTimersEntry 10 }

ctlVirtualDevicesTimerDays  OBJECT-TYPE
	SYNTAX     OCTET STRING
	MAX-ACCESS read-write
	STATUS     current
	DESCRIPTION 
		"Days for timer"
	::= { ctlVirtualDevicesTimersEntry 11 }

ctlVirtualDevicesTimerMode  OBJECT-TYPE
	SYNTAX     OCTET STRING
	MAX-ACCESS read-write
	STATUS     current
	DESCRIPTION 
		"Mode of timer"
	::= { ctlVirtualDevicesTimersEntry 12 }

ctlVirtualDevicesPingsTable  OBJECT-TYPE
	SYNTAX SEQUENCE OF CtlVirtualDevicesPingsEntry
	MAX-ACCESS not-accessible
	STATUS     current
	DESCRIPTION 
		""
	::= { ctlVirtualDevices 2 }

ctlVirtualDevicesPingsEntry  OBJECT-TYPE
	SYNTAX 	CtlVirtualDevicesPingsEntry
	MAX-ACCESS not-accessible
	STATUS     current
	DESCRIPTION 
		"Entry of ping"
	INDEX { ctlVirtualDevicesPingId }
	::= { ctlVirtualDevicesPingsTable 1 }

CtlVirtualDevicesPingsEntry ::= SEQUENCE {
	ctlVirtualDevicesPingId
		Integer32,
	ctlVirtualDevicesPingModule
		Integer32,
	ctlVirtualDevicesPingNum
		Integer32,
	ctlVirtualDevicesPingGroup
		Integer32,
	ctlVirtualDevicesPingType
		OCTET STRING,
	ctlVirtualDevicesPingName
		OCTET STRING,
	ctlVirtualDevicesPingState
		OCTET STRING,
	ctlVirtualDevicesPingValue
		OCTET STRING,
	ctlVirtualDevicesPingPeriod
		Integer32,
	ctlVirtualDevicesPingRTT
		Integer32,
	ctlVirtualDevicesPingServer
		OCTET STRING,
	ctlVirtualDevicesPingIP
		OCTET STRING,
	ctlVirtualDevicesPingSent
		Integer32,
	ctlVirtualDevicesPingReceived
		Integer32,
	ctlVirtualDevicesPingStatus
		OCTET STRING
}

ctlVirtualDevicesPingId  OBJECT-TYPE
	SYNTAX     Integer32
	MAX-ACCESS read-only
	STATUS     current
	DESCRIPTION 
		"Id of ping"
	::= { ctlVirtualDevicesPingsEntry 1 }

ctlVirtualDevicesPingModule  OBJECT-TYPE
	SYNTAX     Integer32
	MAX-ACCESS read-only
	STATUS     current
	DESCRIPTION 
		"Module of ping"
	::= { ctlVirtualDevicesPingsEntry 2 }

ctlVirtualDevicesPingNum  OBJECT-TYPE
	SYNTAX     Integer32
	MAX-ACCESS read-only
	STATUS     current
	DESCRIPTION 
		"Logical number in module for ping"
	::= { ctlVirtualDevicesPingsEntry 3 }

ctlVirtualDevicesPingGroup  OBJECT-TYPE
	SYNTAX     Integer32
	MAX-ACCESS read-write
	STATUS     current
	DESCRIPTION 
		"Group of ping"
	::= { ctlVirtualDevicesPingsEntry 4 }

ctlVirtualDevicesPingType  OBJECT-TYPE
	SYNTAX     OCTET STRING
	MAX-ACCESS read-only
	STATUS     current
	DESCRIPTION 
		"Type of element"
	::= { ctlVirtualDevicesPingsEntry 5 }

ctlVirtualDevicesPingName  OBJECT-TYPE
	SYNTAX     OCTET STRING (SIZE(2..64))
	MAX-ACCESS read-write
	STATUS     current
	DESCRIPTION 
		"Name of ping"
	::= { ctlVirtualDevicesPingsEntry 6 }

ctlVirtualDevicesPingState  OBJECT-TYPE
	SYNTAX     OCTET STRING
	MAX-ACCESS read-only
	STATUS     current
	DESCRIPTION 
		"State of ping"
	::= { ctlVirtualDevicesPingsEntry 7 }

ctlVirtualDevicesPingValue  OBJECT-TYPE
	SYNTAX     OCTET STRING
	MAX-ACCESS read-write
	STATUS     current
	DESCRIPTION 
		"Value of timer"
	::= { ctlVirtualDevicesPingsEntry 8 }

ctlVirtualDevicesPingPeriod  OBJECT-TYPE
	SYNTAX     Integer32
	MAX-ACCESS read-write
	STATUS     current
	DESCRIPTION 
		"Period for ping"
	::= { ctlVirtualDevicesPingsEntry 9 }

ctlVirtualDevicesPingRTT  OBJECT-TYPE
	SYNTAX     Integer32
	MAX-ACCESS read-write
	STATUS     current
	DESCRIPTION 
		"Round Trip Time of ping"
	::= { ctlVirtualDevicesPingsEntry 10 }

ctlVirtualDevicesPingServer  OBJECT-TYPE
	SYNTAX     OCTET STRING (SIZE(2..256))
	MAX-ACCESS read-write
	STATUS     current
	DESCRIPTION 
		"Server for ping"
	::= { ctlVirtualDevicesPingsEntry 11 }

ctlVirtualDevicesPingIP  OBJECT-TYPE
	SYNTAX     OCTET STRING
	MAX-ACCESS read-only
	STATUS     current
	DESCRIPTION 
		"Resolved IP for ping"
	::= { ctlVirtualDevicesPingsEntry 12 }

ctlVirtualDevicesPingSent  OBJECT-TYPE
	SYNTAX     Integer32
	MAX-ACCESS read-only
	STATUS     current
	DESCRIPTION 
		"Number of sent pings"
	::= { ctlVirtualDevicesPingsEntry 13 }

ctlVirtualDevicesPingReceived  OBJECT-TYPE
	SYNTAX     Integer32
	MAX-ACCESS read-only
	STATUS     current
	DESCRIPTION 
		"Number of received pings"
	::= { ctlVirtualDevicesPingsEntry 14 }

ctlVirtualDevicesPingStatus  OBJECT-TYPE
	SYNTAX     OCTET STRING
	MAX-ACCESS read-only
	STATUS     current
	DESCRIPTION 
		"Status of ping"
	::= { ctlVirtualDevicesPingsEntry 15 }

ctlHardwareDevicesCamerasTable  OBJECT-TYPE
	SYNTAX SEQUENCE OF CtlHardwareDevicesCamerasEntry
	MAX-ACCESS not-accessible
	STATUS     current
	DESCRIPTION 
		""
	::= { ctlHardwareDevices 1 }

ctlHardwareDevicesCamerasEntry  OBJECT-TYPE
	SYNTAX 	CtlHardwareDevicesCamerasEntry
	MAX-ACCESS not-accessible
	STATUS     current
	DESCRIPTION 
		"Entry of camera"
	INDEX { ctlHardwareDevicesCameraId }
	::= { ctlHardwareDevicesCamerasTable 1 }

CtlHardwareDevicesCamerasEntry ::= SEQUENCE {
	ctlHardwareDevicesCameraId
		Integer32,
	ctlHardwareDevicesCameraModule
		Integer32,
	ctlHardwareDevicesCameraNum
		Integer32,
	ctlHardwareDevicesCameraGroup
		Integer32,
	ctlHardwareDevicesCameraType
		OCTET STRING,
	ctlHardwareDevicesCameraName
		OCTET STRING,
	ctlHardwareDevicesCameraState
		OCTET STRING,
	ctlHardwareDevicesCameraValue
		OCTET STRING,
	ctlHardwareDevicesCameraURL
		OCTET STRING,
	ctlHardwareDevicesCameraFPS
		OCTET STRING,
	ctlHardwareDevicesCameraResolution
		OCTET STRING
}

ctlHardwareDevicesCameraId  OBJECT-TYPE
	SYNTAX     Integer32
	MAX-ACCESS read-only
	STATUS     current
	DESCRIPTION 
		"Id of camera"
	::= { ctlHardwareDevicesCamerasEntry 1 }

ctlHardwareDevicesCameraModule  OBJECT-TYPE
	SYNTAX     Integer32
	MAX-ACCESS read-only
	STATUS     current
	DESCRIPTION 
		"Module of camera"
	::= { ctlHardwareDevicesCamerasEntry 2 }

ctlHardwareDevicesCameraNum  OBJECT-TYPE
	SYNTAX     Integer32
	MAX-ACCESS read-only
	STATUS     current
	DESCRIPTION 
		"Logical number in module for camera"
	::= { ctlHardwareDevicesCamerasEntry 3 }

ctlHardwareDevicesCameraGroup  OBJECT-TYPE
	SYNTAX     Integer32
	MAX-ACCESS read-write
	STATUS     current
	DESCRIPTION 
		"Group of camera"
	::= { ctlHardwareDevicesCamerasEntry 4 }

ctlHardwareDevicesCameraType  OBJECT-TYPE
	SYNTAX     OCTET STRING
	MAX-ACCESS read-only
	STATUS     current
	DESCRIPTION 
		"Type of element"
	::= { ctlHardwareDevicesCamerasEntry 5 }

ctlHardwareDevicesCameraName  OBJECT-TYPE
	SYNTAX     OCTET STRING (SIZE(2..64))
	MAX-ACCESS read-write
	STATUS     current
	DESCRIPTION 
		"Name of camera"
	::= { ctlHardwareDevicesCamerasEntry 6 }

ctlHardwareDevicesCameraState  OBJECT-TYPE
	SYNTAX     OCTET STRING
	MAX-ACCESS read-only
	STATUS     current
	DESCRIPTION 
		"State of camera"
	::= { ctlHardwareDevicesCamerasEntry 7 }

ctlHardwareDevicesCameraValue  OBJECT-TYPE
	SYNTAX     OCTET STRING
	MAX-ACCESS read-write
	STATUS     current
	DESCRIPTION 
		"Value of camera"
	::= { ctlHardwareDevicesCamerasEntry 8 }

ctlHardwareDevicesCameraURL  OBJECT-TYPE
	SYNTAX     OCTET STRING (SIZE(2..256))
	MAX-ACCESS read-write
	STATUS     current
	DESCRIPTION 
		"IP camera URL (or device path for USB)"
	::= { ctlHardwareDevicesCamerasEntry 9 }

ctlHardwareDevicesCameraFPS  OBJECT-TYPE
	SYNTAX     OCTET STRING
	MAX-ACCESS read-write
	STATUS     current
	DESCRIPTION 
		"FPS of camera"
	::= { ctlHardwareDevicesCamerasEntry 10 }

ctlHardwareDevicesCameraResolution  OBJECT-TYPE
	SYNTAX     OCTET STRING
	MAX-ACCESS read-write
	STATUS     current
	DESCRIPTION 
		"Resolution of camera"
	::= { ctlHardwareDevicesCamerasEntry 11 }

ctlInternalSensorsDiscretsTable  OBJECT-TYPE
	SYNTAX SEQUENCE OF CtlInternalSensorsDiscretsEntry
	MAX-ACCESS not-accessible
	STATUS     current
	DESCRIPTION 
		""
	::= { ctIInternalSensors 1 }

ctlInternalSensorsDiscretsEntry  OBJECT-TYPE
	SYNTAX 	CtlInternalSensorsDiscretsEntry
	MAX-ACCESS not-accessible
	STATUS     current
	DESCRIPTION 
		"Entry of discret"
	INDEX { ctlInternalSensorsDiscretId }
	::= { ctlInternalSensorsDiscretsTable 1 }

CtlInternalSensorsDiscretsEntry ::= SEQUENCE {
	ctlInternalSensorsDiscretId
		Integer32,
	ctlInternalSensorsDiscretModule
		Integer32,
	ctlInternalSensorsDiscretNum
		Integer32,
	ctlInternalSensorsDiscretGroup
		Integer32,
	ctlInternalSensorsDiscretType
		OCTET STRING,
	ctlInternalSensorsDiscretName
		OCTET STRING,
	ctlInternalSensorsDiscretState
		OCTET STRING,
	ctlInternalSensorsDiscretValue
		Integer32,
	ctlInternalSensorsDiscretReset
		Integer32,
	ctlInternalSensorsDiscretLevel
		Integer32,
	ctlInternalSensorsDiscretReverse
		Integer32,
	ctlInternalSensorsDiscretSpecific
		OCTET STRING
}

ctlInternalSensorsDiscretId  OBJECT-TYPE
	SYNTAX     Integer32
	MAX-ACCESS read-only
	STATUS     current
	DESCRIPTION 
		"Id of sensor"
	::= { ctlInternalSensorsDiscretsEntry 1 }

ctlInternalSensorsDiscretModule  OBJECT-TYPE
	SYNTAX     Integer32
	MAX-ACCESS read-only
	STATUS     current
	DESCRIPTION 
		"Module of sensor"
	::= { ctlInternalSensorsDiscretsEntry 2 }

ctlInternalSensorsDiscretNum  OBJECT-TYPE
	SYNTAX     Integer32
	MAX-ACCESS read-only
	STATUS     current
	DESCRIPTION 
		"Logical number in module for sensor"
	::= { ctlInternalSensorsDiscretsEntry 3 }

ctlInternalSensorsDiscretGroup  OBJECT-TYPE
	SYNTAX     Integer32
	MAX-ACCESS read-write
	STATUS     current
	DESCRIPTION 
		"Group of sensor"
	::= { ctlInternalSensorsDiscretsEntry 4 }

ctlInternalSensorsDiscretType  OBJECT-TYPE
	SYNTAX     OCTET STRING
	MAX-ACCESS read-only
	STATUS     current
	DESCRIPTION 
		"Type of sensor"
	::= { ctlInternalSensorsDiscretsEntry 5 }

ctlInternalSensorsDiscretName  OBJECT-TYPE
	SYNTAX     OCTET STRING (SIZE(2..128))
	MAX-ACCESS read-write
	STATUS     current
	DESCRIPTION 
		"Name of sensor"
	::= { ctlInternalSensorsDiscretsEntry 6 }

ctlInternalSensorsDiscretState  OBJECT-TYPE
	SYNTAX     OCTET STRING
	MAX-ACCESS read-only
	STATUS     current
	DESCRIPTION 
		"State of sensor"
	::= { ctlInternalSensorsDiscretsEntry 7 }

ctlInternalSensorsDiscretValue  OBJECT-TYPE
	SYNTAX     Integer32
	MAX-ACCESS read-write
	STATUS     current
	DESCRIPTION 
		"Value of sensor"
	::= { ctlInternalSensorsDiscretsEntry 8 }

ctlInternalSensorsDiscretReset  OBJECT-TYPE
	SYNTAX     Integer32
	MAX-ACCESS read-write
	STATUS     current
	DESCRIPTION 
		"Reset of sensor"
	::= { ctlInternalSensorsDiscretsEntry 9 }

ctlInternalSensorsDiscretLevel  OBJECT-TYPE
	SYNTAX     Integer32
	MAX-ACCESS read-write
	STATUS     current
	DESCRIPTION 
		"Level of sensor"
	::= { ctlInternalSensorsDiscretsEntry 10 }

ctlInternalSensorsDiscretReverse  OBJECT-TYPE
	SYNTAX     Integer32
	MAX-ACCESS read-write
	STATUS     current
	DESCRIPTION 
		"Reverse of sensor"
	::= { ctlInternalSensorsDiscretsEntry 11 }

ctlInternalSensorsDiscretSpecific  OBJECT-TYPE
	SYNTAX     OCTET STRING
	MAX-ACCESS read-only
	STATUS     current
	DESCRIPTION 
		"Specific parameters for sensor"
	::= { ctlInternalSensorsDiscretsEntry 12 }

ctlInternalSensorsAnalogsTable  OBJECT-TYPE
	SYNTAX SEQUENCE OF CtlInternalSensorsAnalogsEntry
	MAX-ACCESS not-accessible
	STATUS     current
	DESCRIPTION 
		""
	::= { ctIInternalSensors 2 }

ctlInternalSensorsAnalogsEntry  OBJECT-TYPE
	SYNTAX 	CtlInternalSensorsAnalogsEntry
	MAX-ACCESS not-accessible
	STATUS     current
	DESCRIPTION 
		"Entry of analog"
	INDEX { ctlInternalSensorsAnalogId }
	::= { ctlInternalSensorsAnalogsTable 1 }

CtlInternalSensorsAnalogsEntry ::= SEQUENCE {
	ctlInternalSensorsAnalogId
		Integer32,
	ctlInternalSensorsAnalogModule
		Integer32,
	ctlInternalSensorsAnalogNum
		Integer32,
	ctlInternalSensorsAnalogGroup
		Integer32,
	ctlInternalSensorsAnalogType
		OCTET STRING,
	ctlInternalSensorsAnalogName
		OCTET STRING,
	ctlInternalSensorsAnalogState
		OCTET STRING,
	ctlInternalSensorsAnalogValue
		OCTET STRING,
	ctlInternalSensorsAnalogMin
		OCTET STRING,
	ctlInternalSensorsAnalogMax
		OCTET STRING,
	ctlInternalSensorsAnalogLow
		OCTET STRING,
	ctlInternalSensorsAnalogWarning
		OCTET STRING,
	ctlInternalSensorsAnalogHigh
		OCTET STRING,
	ctlInternalSensorsAnalogAt0
		OCTET STRING,
	ctlInternalSensorsAnalogAt75
		OCTET STRING,
	ctlInternalSensorsAnalogExpression
		OCTET STRING,
	ctlInternalSensorsAnalogSpecific
		OCTET STRING
}

ctlInternalSensorsAnalogId  OBJECT-TYPE
	SYNTAX     Integer32
	MAX-ACCESS read-only
	STATUS     current
	DESCRIPTION 
		"Id of sensor"
	::= { ctlInternalSensorsAnalogsEntry 1 }

ctlInternalSensorsAnalogModule  OBJECT-TYPE
	SYNTAX     Integer32
	MAX-ACCESS read-only
	STATUS     current
	DESCRIPTION 
		"Module of sensor"
	::= { ctlInternalSensorsAnalogsEntry 2 }

-- Num in modules for mailer

ctlInternalSensorsAnalogNum  OBJECT-TYPE
	SYNTAX     Integer32
	MAX-ACCESS read-only
	STATUS     current
	DESCRIPTION 
		"Logical number in module for sensor"
	::= { ctlInternalSensorsAnalogsEntry 3 }

ctlInternalSensorsAnalogGroup  OBJECT-TYPE
	SYNTAX     Integer32
	MAX-ACCESS read-write
	STATUS     current
	DESCRIPTION 
		"Group of sensor"
	::= { ctlInternalSensorsAnalogsEntry 4 }

ctlInternalSensorsAnalogType  OBJECT-TYPE
	SYNTAX     OCTET STRING
	MAX-ACCESS read-only
	STATUS     current
	DESCRIPTION 
		"Type of sensor"
	::= { ctlInternalSensorsAnalogsEntry 5 }

ctlInternalSensorsAnalogName  OBJECT-TYPE
	SYNTAX     OCTET STRING (SIZE(2..128))
	MAX-ACCESS read-write
	STATUS     current
	DESCRIPTION 
		"Name of sensor"
	::= { ctlInternalSensorsAnalogsEntry 6 }

ctlInternalSensorsAnalogState  OBJECT-TYPE
	SYNTAX     OCTET STRING
	MAX-ACCESS read-only
	STATUS     current
	DESCRIPTION 
		"State of sensor"
	::= { ctlInternalSensorsAnalogsEntry 7 }

ctlInternalSensorsAnalogValue  OBJECT-TYPE
	SYNTAX     OCTET STRING
	MAX-ACCESS read-write
	STATUS     current
	DESCRIPTION 
		"Value of sensor"
	::= { ctlInternalSensorsAnalogsEntry 8 }

ctlInternalSensorsAnalogMin  OBJECT-TYPE
	SYNTAX     OCTET STRING
	MAX-ACCESS read-only
	STATUS     current
	DESCRIPTION 
		"Minimum of sensor value range"
	::= { ctlInternalSensorsAnalogsEntry 9 }

ctlInternalSensorsAnalogMax  OBJECT-TYPE
	SYNTAX     OCTET STRING
	MAX-ACCESS read-only
	STATUS     current
	DESCRIPTION 
		"Maximum of sensor value range"
	::= { ctlInternalSensorsAnalogsEntry 10 }

ctlInternalSensorsAnalogLow  OBJECT-TYPE
	SYNTAX     OCTET STRING (SIZE(1..16))
	MAX-ACCESS read-write
	STATUS     current
	DESCRIPTION 
		"Low level for sensor value"
	::= { ctlInternalSensorsAnalogsEntry 11 }

ctlInternalSensorsAnalogWarning  OBJECT-TYPE
	SYNTAX     OCTET STRING (SIZE(1..16))
	MAX-ACCESS read-write
	STATUS     current
	DESCRIPTION 
		"Warning level for sensor value"
	::= { ctlInternalSensorsAnalogsEntry 12 }

ctlInternalSensorsAnalogHigh  OBJECT-TYPE
	SYNTAX     OCTET STRING (SIZE(1..16))
	MAX-ACCESS read-write
	STATUS     current
	DESCRIPTION 
		"High level for sensor value"
	::= { ctlInternalSensorsAnalogsEntry 13 }

ctlInternalSensorsAnalogAt0  OBJECT-TYPE
	SYNTAX     OCTET STRING (SIZE(1..16))
	MAX-ACCESS read-write
	STATUS     current
	DESCRIPTION 
		"At0 for sensor value"
	::= { ctlInternalSensorsAnalogsEntry 14 }

ctlInternalSensorsAnalogAt75  OBJECT-TYPE
	SYNTAX     OCTET STRING (SIZE(1..16))
	MAX-ACCESS read-write
	STATUS     current
	DESCRIPTION 
		"At75 for sensor value"
	::= { ctlInternalSensorsAnalogsEntry 15 }

ctlInternalSensorsAnalogExpression  OBJECT-TYPE
	SYNTAX     OCTET STRING (SIZE(1..80))
	MAX-ACCESS read-write
	STATUS     current
	DESCRIPTION 
		"Expression for sensor value"
	::= { ctlInternalSensorsAnalogsEntry 16 }

ctlInternalSensorsAnalogSpecific  OBJECT-TYPE
	SYNTAX     OCTET STRING
	MAX-ACCESS read-only
	STATUS     current
	DESCRIPTION 
		"Specific parameters for sensor"
	::= { ctlInternalSensorsAnalogsEntry 17 }

ctlInternalSensorsOutletsTable  OBJECT-TYPE
	SYNTAX SEQUENCE OF CtlInternalSensorsOutletsEntry
	MAX-ACCESS not-accessible
	STATUS     current
	DESCRIPTION 
		""
	::= { ctIInternalSensors 3 }

ctlInternalSensorsOutletsEntry  OBJECT-TYPE
	SYNTAX 	CtlInternalSensorsOutletsEntry
	MAX-ACCESS not-accessible
	STATUS     current
	DESCRIPTION 
		"Entry of outlet"
	INDEX { ctlInternalSensorsOutletId }
	::= { ctlInternalSensorsOutletsTable 1 }

CtlInternalSensorsOutletsEntry ::= SEQUENCE {
	ctlInternalSensorsOutletId
		Integer32,
	ctlInternalSensorsOutletModule
		Integer32,
	ctlInternalSensorsOutletNum
		Integer32,
	ctlInternalSensorsOutletGroup
		Integer32,
	ctlInternalSensorsOutletType
		OCTET STRING,
	ctlInternalSensorsOutletName
		OCTET STRING,
	ctlInternalSensorsOutletState
		OCTET STRING,
	ctlInternalSensorsOutletValue
		OCTET STRING,
	ctlInternalSensorsOutletInitial
		OCTET STRING,
	ctlInternalSensorsDiscretPulse
		Integer32
}

ctlInternalSensorsOutletId  OBJECT-TYPE
	SYNTAX     Integer32
	MAX-ACCESS read-only
	STATUS     current
	DESCRIPTION 
		"Id of outlet"
	::= { ctlInternalSensorsOutletsEntry 1 }

ctlInternalSensorsOutletModule  OBJECT-TYPE
	SYNTAX     Integer32
	MAX-ACCESS read-only
	STATUS     current
	DESCRIPTION 
		"Module of outlet"
	::= { ctlInternalSensorsOutletsEntry 2 }

ctlInternalSensorsOutletNum  OBJECT-TYPE
	SYNTAX     Integer32
	MAX-ACCESS read-only
	STATUS     current
	DESCRIPTION 
		"Logical number in module for outlet"
	::= { ctlInternalSensorsOutletsEntry 3 }

ctlInternalSensorsOutletGroup  OBJECT-TYPE
	SYNTAX     Integer32
	MAX-ACCESS read-write
	STATUS     current
	DESCRIPTION 
		"Group of outlet"
	::= { ctlInternalSensorsOutletsEntry 4 }

ctlInternalSensorsOutletType  OBJECT-TYPE
	SYNTAX     OCTET STRING
	MAX-ACCESS read-only
	STATUS     current
	DESCRIPTION 
		"Type of outlet"
	::= { ctlInternalSensorsOutletsEntry 5 }

ctlInternalSensorsOutletName  OBJECT-TYPE
	SYNTAX     OCTET STRING (SIZE(2..128))
	MAX-ACCESS read-write
	STATUS     current
	DESCRIPTION 
		"Name of outlet"
	::= { ctlInternalSensorsOutletsEntry 6 }

ctlInternalSensorsOutletState  OBJECT-TYPE
	SYNTAX     OCTET STRING
	MAX-ACCESS read-only
	STATUS     current
	DESCRIPTION 
		"State of outlet"
	::= { ctlInternalSensorsOutletsEntry 7 }

ctlInternalSensorsOutletValue  OBJECT-TYPE
	SYNTAX     OCTET STRING
	MAX-ACCESS read-write
	STATUS     current
	DESCRIPTION 
		"Value of outlet"
	::= { ctlInternalSensorsOutletsEntry 8 }

ctlInternalSensorsOutletInitial  OBJECT-TYPE
	SYNTAX     OCTET STRING
	MAX-ACCESS read-write
	STATUS     current
	DESCRIPTION 
		"Initial state for outlet"
	::= { ctlInternalSensorsOutletsEntry 9 }

ctlInternalSensorsDiscretPulse  OBJECT-TYPE
	SYNTAX     Integer32
	MAX-ACCESS read-write
	STATUS     current
	DESCRIPTION 
		"Pulse duration for outlet"
	::= { ctlInternalSensorsOutletsEntry 10 }

ctlCANSensorsDiscretsTable  OBJECT-TYPE
	SYNTAX SEQUENCE OF CtlCANSensorsDiscretsEntry
	MAX-ACCESS not-accessible
	STATUS     current
	DESCRIPTION 
		""
	::= { ctlCANSensors 1 }

ctlCANSensorsDiscretsEntry  OBJECT-TYPE
	SYNTAX 	CtlCANSensorsDiscretsEntry
	MAX-ACCESS not-accessible
	STATUS     current
	DESCRIPTION 
		"Entry of discret sensor"
	INDEX { ctlCANSensorsDiscretId }
	::= { ctlCANSensorsDiscretsTable 1 }

CtlCANSensorsDiscretsEntry ::= SEQUENCE {
	ctlCANSensorsDiscretId
		Integer32,
	ctlCANSensorsDiscretModule
		Integer32,
	ctlCANSensorsDiscretNum
		Integer32,
	ctlCANSensorsDiscretGroup
		Integer32,
	ctlCANSensorsDiscretType
		OCTET STRING,
	ctlCANSensorsDiscretName
		OCTET STRING,
	ctlCANSensorsDiscretState
		OCTET STRING,
	ctlCANSensorsDiscretValue
		OCTET STRING,
	ctlCANSensorsDiscretReset
		Integer32,
	ctlCANSensorsDiscretLevel
		Integer32,
	ctlCANSensorsDiscretReverse
		Integer32,
	ctlCANSensorsDiscretSpecific
		OCTET STRING
}

ctlCANSensorsDiscretId  OBJECT-TYPE
	SYNTAX     Integer32
	MAX-ACCESS read-only
	STATUS     current
	DESCRIPTION 
		"Id of sensor"
	::= { ctlCANSensorsDiscretsEntry 1 }

ctlCANSensorsDiscretModule  OBJECT-TYPE
	SYNTAX     Integer32
	MAX-ACCESS read-only
	STATUS     current
	DESCRIPTION 
		"Module of sensor"
	::= { ctlCANSensorsDiscretsEntry 2 }

ctlCANSensorsDiscretNum  OBJECT-TYPE
	SYNTAX     Integer32
	MAX-ACCESS read-only
	STATUS     current
	DESCRIPTION 
		"Logical number in module for sensor"
	::= { ctlCANSensorsDiscretsEntry 3 }

ctlCANSensorsDiscretGroup  OBJECT-TYPE
	SYNTAX     Integer32
	MAX-ACCESS read-write
	STATUS     current
	DESCRIPTION 
		"Group of sensor"
	::= { ctlCANSensorsDiscretsEntry 4 }

ctlCANSensorsDiscretType  OBJECT-TYPE
	SYNTAX     OCTET STRING
	MAX-ACCESS read-only
	STATUS     current
	DESCRIPTION 
		"Type of sensor's"
	::= { ctlCANSensorsDiscretsEntry 5 }

ctlCANSensorsDiscretName  OBJECT-TYPE
	SYNTAX     OCTET STRING (SIZE(2..128))
	MAX-ACCESS read-write
	STATUS     current
	DESCRIPTION 
		"Name of sensor"
	::= { ctlCANSensorsDiscretsEntry 6 }

ctlCANSensorsDiscretState  OBJECT-TYPE
	SYNTAX     OCTET STRING
	MAX-ACCESS read-only
	STATUS     current
	DESCRIPTION 
		"State of sensor"
	::= { ctlCANSensorsDiscretsEntry 7 }

ctlCANSensorsDiscretValue  OBJECT-TYPE
	SYNTAX     OCTET STRING
	MAX-ACCESS read-write
	STATUS     current
	DESCRIPTION 
		"Value of sensor"
	::= { ctlCANSensorsDiscretsEntry 8 }

ctlCANSensorsDiscretReset  OBJECT-TYPE
	SYNTAX     Integer32
	MAX-ACCESS read-write
	STATUS     current
	DESCRIPTION 
		"Reset of sensor"
	::= { ctlCANSensorsDiscretsEntry 9 }

ctlCANSensorsDiscretLevel  OBJECT-TYPE
	SYNTAX     Integer32
	MAX-ACCESS read-write
	STATUS     current
	DESCRIPTION 
		"Level of sensor"
	::= { ctlCANSensorsDiscretsEntry 10 }

ctlCANSensorsDiscretReverse  OBJECT-TYPE
	SYNTAX     Integer32
	MAX-ACCESS read-write
	STATUS     current
	DESCRIPTION 
		"Reverse of sensor"
	::= { ctlCANSensorsDiscretsEntry 11 }

ctlCANSensorsDiscretSpecific  OBJECT-TYPE
	SYNTAX     OCTET STRING
	MAX-ACCESS read-only
	STATUS     current
	DESCRIPTION 
		"Specific parameters for sensor"
	::= { ctlCANSensorsDiscretsEntry 12 }

ctlCANSensorsAnalogsTable  OBJECT-TYPE
	SYNTAX SEQUENCE OF CtlCANSensorsAnalogsEntry
	MAX-ACCESS not-accessible
	STATUS     current
	DESCRIPTION 
		""
	::= { ctlCANSensors 2 }

ctlCANSensorsAnalogsEntry  OBJECT-TYPE
	SYNTAX 	CtlCANSensorsAnalogsEntry
	MAX-ACCESS not-accessible
	STATUS     current
	DESCRIPTION 
		"Entry of analog sensor"
	INDEX { ctlCANSensorsAnalogId }
	::= { ctlCANSensorsAnalogsTable 1 }

CtlCANSensorsAnalogsEntry ::= SEQUENCE {
	ctlCANSensorsAnalogId
		Integer32,
	ctlCANSensorsAnalogModule
		Integer32,
	ctlCANSensorsAnalogNum
		Integer32,
	ctlCANSensorsAnalogGroup
		Integer32,
	ctlCANSensorsAnalogType
		OCTET STRING,
	ctlCANSensorsAnalogName
		OCTET STRING,
	ctlCANSensorsAnalogState
		OCTET STRING,
	ctlCANSensorsAnalogValue
		OCTET STRING,
	ctlCANSensorsAnalogMin
		OCTET STRING,
	ctlCANSensorsAnalogMax
		OCTET STRING,
	ctlCANSensorsAnalogLow
		OCTET STRING,
	ctlCANSensorsAnalogWarning
		OCTET STRING,
	ctlCANSensorsAnalogHigh
		OCTET STRING,
	ctlCANSensorsAnalogAt0
		OCTET STRING,
	ctlCANSensorsAnalogAt75
		OCTET STRING,
	ctlCANSensorsAnalogExpression
		OCTET STRING,
	ctlCANSensorsAnalogSpecific
		OCTET STRING
}

ctlCANSensorsAnalogId  OBJECT-TYPE
	SYNTAX     Integer32
	MAX-ACCESS read-only
	STATUS     current
	DESCRIPTION 
		"Id of sensor"
	::= { ctlCANSensorsAnalogsEntry 1 }

ctlCANSensorsAnalogModule  OBJECT-TYPE
	SYNTAX     Integer32
	MAX-ACCESS read-only
	STATUS     current
	DESCRIPTION 
		"Module of sensor"
	::= { ctlCANSensorsAnalogsEntry 2 }

-- Num in modules for mailer

ctlCANSensorsAnalogNum  OBJECT-TYPE
	SYNTAX     Integer32
	MAX-ACCESS read-only
	STATUS     current
	DESCRIPTION 
		"Logical number in module for sensor"
	::= { ctlCANSensorsAnalogsEntry 3 }

ctlCANSensorsAnalogGroup  OBJECT-TYPE
	SYNTAX     Integer32
	MAX-ACCESS read-write
	STATUS     current
	DESCRIPTION 
		"Group of sensor"
	::= { ctlCANSensorsAnalogsEntry 4 }

ctlCANSensorsAnalogType  OBJECT-TYPE
	SYNTAX     OCTET STRING
	MAX-ACCESS read-only
	STATUS     current
	DESCRIPTION 
		"Type of sensor"
	::= { ctlCANSensorsAnalogsEntry 5 }

ctlCANSensorsAnalogName  OBJECT-TYPE
	SYNTAX     OCTET STRING (SIZE(2..128))
	MAX-ACCESS read-write
	STATUS     current
	DESCRIPTION 
		"Name of sensor"
	::= { ctlCANSensorsAnalogsEntry 6 }

ctlCANSensorsAnalogState  OBJECT-TYPE
	SYNTAX     OCTET STRING
	MAX-ACCESS read-only
	STATUS     current
	DESCRIPTION 
		"State of sensor"
	::= { ctlCANSensorsAnalogsEntry 7 }

ctlCANSensorsAnalogValue  OBJECT-TYPE
	SYNTAX     OCTET STRING
	MAX-ACCESS read-write
	STATUS     current
	DESCRIPTION 
		"Value of sensor"
	::= { ctlCANSensorsAnalogsEntry 8 }

ctlCANSensorsAnalogMin  OBJECT-TYPE
	SYNTAX     OCTET STRING
	MAX-ACCESS read-only
	STATUS     current
	DESCRIPTION 
		"Minimum of sensor value range"
	::= { ctlCANSensorsAnalogsEntry 9 }

ctlCANSensorsAnalogMax  OBJECT-TYPE
	SYNTAX     OCTET STRING
	MAX-ACCESS read-only
	STATUS     current
	DESCRIPTION 
		"Maximum of sensor value range"
	::= { ctlCANSensorsAnalogsEntry 10 }

ctlCANSensorsAnalogLow  OBJECT-TYPE
	SYNTAX     OCTET STRING (SIZE(2..16))
	MAX-ACCESS read-write
	STATUS     current
	DESCRIPTION 
		"Low level for sensor value"
	::= { ctlCANSensorsAnalogsEntry 11 }

ctlCANSensorsAnalogWarning  OBJECT-TYPE
	SYNTAX     OCTET STRING (SIZE(2..16))
	MAX-ACCESS read-write
	STATUS     current
	DESCRIPTION 
		"Warning level for sensor value"
	::= { ctlCANSensorsAnalogsEntry 12 }

ctlCANSensorsAnalogHigh  OBJECT-TYPE
	SYNTAX     OCTET STRING (SIZE(2..16))
	MAX-ACCESS read-write
	STATUS     current
	DESCRIPTION 
		"High level for sensor value"
	::= { ctlCANSensorsAnalogsEntry 13 }

ctlCANSensorsAnalogAt0  OBJECT-TYPE
	SYNTAX     OCTET STRING (SIZE(2..16))
	MAX-ACCESS read-write
	STATUS     current
	DESCRIPTION 
		"At0 for sensor value"
	::= { ctlCANSensorsAnalogsEntry 14 }

ctlCANSensorsAnalogAt75  OBJECT-TYPE
	SYNTAX     OCTET STRING (SIZE(2..16))
	MAX-ACCESS read-write
	STATUS     current
	DESCRIPTION 
		"At75 for sensor value"
	::= { ctlCANSensorsAnalogsEntry 15 }

ctlCANSensorsAnalogExpression  OBJECT-TYPE
	SYNTAX     OCTET STRING (SIZE(2..80))
	MAX-ACCESS read-write
	STATUS     current
	DESCRIPTION 
		"Expression for sensor value"
	::= { ctlCANSensorsAnalogsEntry 16 }

ctlCANSensorsAnalogSpecific  OBJECT-TYPE
	SYNTAX     OCTET STRING (SIZE(2..16))
	MAX-ACCESS read-only
	STATUS     current
	DESCRIPTION 
		"Specific parameters for sensor"
	::= { ctlCANSensorsAnalogsEntry 17 }

ctlCANSensorsOutletsTable  OBJECT-TYPE
	SYNTAX SEQUENCE OF CtlCANSensorsOutletsEntry
	MAX-ACCESS not-accessible
	STATUS     current
	DESCRIPTION 
		""
	::= { ctlCANSensors 3 }

ctlCANSensorsOutletsEntry  OBJECT-TYPE
	SYNTAX 	CtlCANSensorsOutletsEntry
	MAX-ACCESS not-accessible
	STATUS     current
	DESCRIPTION 
		"Entry of outlet"
	INDEX { ctlCANSensorsOutletId }
	::= { ctlCANSensorsOutletsTable 1 }

CtlCANSensorsOutletsEntry ::= SEQUENCE {
	ctlCANSensorsOutletId
		Integer32,
	ctlCANSensorsOutletModule
		Integer32,
	ctlCANSensorsOutletNum
		Integer32,
	ctlCANSensorsOutletGroup
		Integer32,
	ctlCANSensorsOutletType
		OCTET STRING,
	ctlCANSensorsOutletName
		OCTET STRING,
	ctlCANSensorsOutletState
		OCTET STRING,
	ctlCANSensorsOutletValue
		OCTET STRING,
	ctlCANSensorsOutletInitial
		OCTET STRING,
	ctlCANSensorsDiscretPulse
		Integer32
}

ctlCANSensorsOutletId  OBJECT-TYPE
	SYNTAX     Integer32
	MAX-ACCESS read-only
	STATUS     current
	DESCRIPTION 
		"Id of outlet"
	::= { ctlCANSensorsOutletsEntry 1 }

ctlCANSensorsOutletModule  OBJECT-TYPE
	SYNTAX     Integer32
	MAX-ACCESS read-only
	STATUS     current
	DESCRIPTION 
		"Module of outlet"
	::= { ctlCANSensorsOutletsEntry 2 }

ctlCANSensorsOutletNum  OBJECT-TYPE
	SYNTAX     Integer32
	MAX-ACCESS read-only
	STATUS     current
	DESCRIPTION 
		"Logical number in module for outlet"
	::= { ctlCANSensorsOutletsEntry 3 }

ctlCANSensorsOutletGroup  OBJECT-TYPE
	SYNTAX     Integer32
	MAX-ACCESS read-write
	STATUS     current
	DESCRIPTION 
		"Group of outlet"
	::= { ctlCANSensorsOutletsEntry 4 }

ctlCANSensorsOutletType  OBJECT-TYPE
	SYNTAX     OCTET STRING
	MAX-ACCESS read-only
	STATUS     current
	DESCRIPTION 
		"Type of outlet"
	::= { ctlCANSensorsOutletsEntry 5 }

ctlCANSensorsOutletName  OBJECT-TYPE
	SYNTAX     OCTET STRING (SIZE(2..128))
	MAX-ACCESS read-write
	STATUS     current
	DESCRIPTION 
		"Name of outlet"
	::= { ctlCANSensorsOutletsEntry 6 }

ctlCANSensorsOutletState  OBJECT-TYPE
	SYNTAX     OCTET STRING
	MAX-ACCESS read-only
	STATUS     current
	DESCRIPTION 
		"State of outlet"
	::= { ctlCANSensorsOutletsEntry 7 }

ctlCANSensorsOutletValue  OBJECT-TYPE
	SYNTAX     OCTET STRING
	MAX-ACCESS read-write
	STATUS     current
	DESCRIPTION 
		"Value of outlet"
	::= { ctlCANSensorsOutletsEntry 8 }

ctlCANSensorsOutletInitial  OBJECT-TYPE
	SYNTAX     OCTET STRING
	MAX-ACCESS read-write
	STATUS     current
	DESCRIPTION 
		"Initial state for outlet"
	::= { ctlCANSensorsOutletsEntry 9 }

ctlCANSensorsDiscretPulse  OBJECT-TYPE
	SYNTAX     Integer32
	MAX-ACCESS read-write
	STATUS     current
	DESCRIPTION 
		"Pulse duration for outlet"
	::= { ctlCANSensorsOutletsEntry 10 }

ctlRsSensorsDiscretsTable  OBJECT-TYPE
	SYNTAX SEQUENCE OF CtlRsSensorsDiscretsEntry
	MAX-ACCESS not-accessible
	STATUS     current
	DESCRIPTION 
		""
	::= { ctlRsSensors 1 }

ctlRsSensorsDiscretsEntry  OBJECT-TYPE
	SYNTAX 	CtlRsSensorsDiscretsEntry
	MAX-ACCESS not-accessible
	STATUS     current
	DESCRIPTION 
		"Entry of discret sensor"
	INDEX { ctlRsSensorsDiscretId }
	::= { ctlRsSensorsDiscretsTable 1 }

CtlRsSensorsDiscretsEntry ::= SEQUENCE {
	ctlRsSensorsDiscretId
		Integer32,
	ctlRsSensorsDiscretModule
		Integer32,
	ctlRsSensorsDiscretNum
		Integer32,
	ctlRsSensorsDiscretGroup
		Integer32,
	ctlRsSensorsDiscretType
		OCTET STRING,
	ctlRsSensorsDiscretName
		OCTET STRING,
	ctlRsSensorsDiscretState
		OCTET STRING,
	ctlRsSensorsDiscretValue
		OCTET STRING,
	ctlRsSensorsDiscretReset
		Integer32,
	ctlRsSensorsDiscretLevel
		Integer32,
	ctlRsSensorsDiscretReverse
		Integer32,
	ctlRsSensorsDiscretSpecific
		OCTET STRING
}

ctlRsSensorsDiscretId  OBJECT-TYPE
	SYNTAX     Integer32
	MAX-ACCESS read-only
	STATUS     current
	DESCRIPTION 
		"Id of sensor"
	::= { ctlRsSensorsDiscretsEntry 1 }

ctlRsSensorsDiscretModule  OBJECT-TYPE
	SYNTAX     Integer32
	MAX-ACCESS read-only
	STATUS     current
	DESCRIPTION 
		"Module of sensor"
	::= { ctlRsSensorsDiscretsEntry 2 }

ctlRsSensorsDiscretNum  OBJECT-TYPE
	SYNTAX     Integer32
	MAX-ACCESS read-only
	STATUS     current
	DESCRIPTION 
		"Logical number in module for sensor"
	::= { ctlRsSensorsDiscretsEntry 3 }

ctlRsSensorsDiscretGroup  OBJECT-TYPE
	SYNTAX     Integer32
	MAX-ACCESS read-write
	STATUS     current
	DESCRIPTION 
		"Group of sensor"
	::= { ctlRsSensorsDiscretsEntry 4 }

ctlRsSensorsDiscretType  OBJECT-TYPE
	SYNTAX     OCTET STRING
	MAX-ACCESS read-only
	STATUS     current
	DESCRIPTION 
		"Type of sensor's"
	::= { ctlRsSensorsDiscretsEntry 5 }

ctlRsSensorsDiscretName  OBJECT-TYPE
	SYNTAX     OCTET STRING (SIZE(2..128))
	MAX-ACCESS read-write
	STATUS     current
	DESCRIPTION 
		"Name of sensor"
	::= { ctlRsSensorsDiscretsEntry 6 }

ctlRsSensorsDiscretState  OBJECT-TYPE
	SYNTAX     OCTET STRING
	MAX-ACCESS read-only
	STATUS     current
	DESCRIPTION 
		"State of sensor"
	::= { ctlRsSensorsDiscretsEntry 7 }

ctlRsSensorsDiscretValue  OBJECT-TYPE
	SYNTAX     OCTET STRING
	MAX-ACCESS read-write
	STATUS     current
	DESCRIPTION 
		"Value of sensor"
	::= { ctlRsSensorsDiscretsEntry 8 }

ctlRsSensorsDiscretReset  OBJECT-TYPE
	SYNTAX     Integer32
	MAX-ACCESS read-write
	STATUS     current
	DESCRIPTION 
		"Reset of sensor"
	::= { ctlRsSensorsDiscretsEntry 9 }

ctlRsSensorsDiscretLevel  OBJECT-TYPE
	SYNTAX     Integer32
	MAX-ACCESS read-write
	STATUS     current
	DESCRIPTION 
		"Level of sensor"
	::= { ctlRsSensorsDiscretsEntry 10 }

ctlRsSensorsDiscretReverse  OBJECT-TYPE
	SYNTAX     Integer32
	MAX-ACCESS read-write
	STATUS     current
	DESCRIPTION 
		"Reverse of sensor"
	::= { ctlRsSensorsDiscretsEntry 11 }

ctlRsSensorsDiscretSpecific  OBJECT-TYPE
	SYNTAX     OCTET STRING
	MAX-ACCESS read-only
	STATUS     current
	DESCRIPTION 
		"Specific parameters for sensor"
	::= { ctlRsSensorsDiscretsEntry 12 }

ctlRsSensorsAnalogsTable  OBJECT-TYPE
	SYNTAX SEQUENCE OF CtlRsSensorsAnalogsEntry
	MAX-ACCESS not-accessible
	STATUS     current
	DESCRIPTION 
		""
	::= { ctlRsSensors 2 }

ctlRsSensorsAnalogsEntry  OBJECT-TYPE
	SYNTAX 	CtlRsSensorsAnalogsEntry
	MAX-ACCESS not-accessible
	STATUS     current
	DESCRIPTION 
		"Entry of analog sensor"
	INDEX { ctlRsSensorsAnalogId }
	::= { ctlRsSensorsAnalogsTable 1 }

CtlRsSensorsAnalogsEntry ::= SEQUENCE {
	ctlRsSensorsAnalogId
		Integer32,
	ctlRsSensorsAnalogModule
		Integer32,
	ctlRsSensorsAnalogNum
		Integer32,
	ctlRsSensorsAnalogGroup
		Integer32,
	ctlRsSensorsAnalogType
		OCTET STRING,
	ctlRsSensorsAnalogName
		OCTET STRING,
	ctlRsSensorsAnalogState
		OCTET STRING,
	ctlRsSensorsAnalogValue
		OCTET STRING,
	ctlRsSensorsAnalogMin
		OCTET STRING,
	ctlRsSensorsAnalogMax
		OCTET STRING,
	ctlRsSensorsAnalogLow
		OCTET STRING,
	ctlRsSensorsAnalogWarning
		OCTET STRING,
	ctlRsSensorsAnalogHigh
		OCTET STRING,
	ctlRsSensorsAnalogAt0
		OCTET STRING,
	ctlRsSensorsAnalogAt75
		OCTET STRING,
	ctlRsSensorsAnalogExpression
		OCTET STRING,
	ctlRsSensorsAnalogSpecific
		OCTET STRING
}

ctlRsSensorsAnalogId  OBJECT-TYPE
	SYNTAX     Integer32
	MAX-ACCESS read-only
	STATUS     current
	DESCRIPTION 
		"Id of sensor"
	::= { ctlRsSensorsAnalogsEntry 1 }

ctlRsSensorsAnalogModule  OBJECT-TYPE
	SYNTAX     Integer32
	MAX-ACCESS read-only
	STATUS     current
	DESCRIPTION 
		"Module of sensor"
	::= { ctlRsSensorsAnalogsEntry 2 }

-- Num in modules for mailer

ctlRsSensorsAnalogNum  OBJECT-TYPE
	SYNTAX     Integer32
	MAX-ACCESS read-only
	STATUS     current
	DESCRIPTION 
		"Logical number in module for sensor"
	::= { ctlRsSensorsAnalogsEntry 3 }

ctlRsSensorsAnalogGroup  OBJECT-TYPE
	SYNTAX     Integer32
	MAX-ACCESS read-write
	STATUS     current
	DESCRIPTION 
		"Group of sensor"
	::= { ctlRsSensorsAnalogsEntry 4 }

ctlRsSensorsAnalogType  OBJECT-TYPE
	SYNTAX     OCTET STRING
	MAX-ACCESS read-only
	STATUS     current
	DESCRIPTION 
		"Type of sensor"
	::= { ctlRsSensorsAnalogsEntry 5 }

ctlRsSensorsAnalogName  OBJECT-TYPE
	SYNTAX     OCTET STRING (SIZE(2..128))
	MAX-ACCESS read-write
	STATUS     current
	DESCRIPTION 
		"Name of sensor"
	::= { ctlRsSensorsAnalogsEntry 6 }

ctlRsSensorsAnalogState  OBJECT-TYPE
	SYNTAX     OCTET STRING
	MAX-ACCESS read-only
	STATUS     current
	DESCRIPTION 
		"State of sensor"
	::= { ctlRsSensorsAnalogsEntry 7 }

ctlRsSensorsAnalogValue  OBJECT-TYPE
	SYNTAX     OCTET STRING
	MAX-ACCESS read-write
	STATUS     current
	DESCRIPTION 
		"Value of sensor"
	::= { ctlRsSensorsAnalogsEntry 8 }

ctlRsSensorsAnalogMin  OBJECT-TYPE
	SYNTAX     OCTET STRING
	MAX-ACCESS read-only
	STATUS     current
	DESCRIPTION 
		"Minimum of sensor value range"
	::= { ctlRsSensorsAnalogsEntry 9 }

ctlRsSensorsAnalogMax  OBJECT-TYPE
	SYNTAX     OCTET STRING
	MAX-ACCESS read-only
	STATUS     current
	DESCRIPTION 
		"Maximum of sensor value range"
	::= { ctlRsSensorsAnalogsEntry 10 }

ctlRsSensorsAnalogLow  OBJECT-TYPE
	SYNTAX     OCTET STRING (SIZE(2..16))
	MAX-ACCESS read-write
	STATUS     current
	DESCRIPTION 
		"Low level for sensor value"
	::= { ctlRsSensorsAnalogsEntry 11 }

ctlRsSensorsAnalogWarning  OBJECT-TYPE
	SYNTAX     OCTET STRING (SIZE(2..16))
	MAX-ACCESS read-write
	STATUS     current
	DESCRIPTION 
		"Warning level for sensor value"
	::= { ctlRsSensorsAnalogsEntry 12 }

ctlRsSensorsAnalogHigh  OBJECT-TYPE
	SYNTAX     OCTET STRING (SIZE(2..16))
	MAX-ACCESS read-write
	STATUS     current
	DESCRIPTION 
		"High level for sensor value"
	::= { ctlRsSensorsAnalogsEntry 13 }

ctlRsSensorsAnalogAt0  OBJECT-TYPE
	SYNTAX     OCTET STRING (SIZE(2..16))
	MAX-ACCESS read-write
	STATUS     current
	DESCRIPTION 
		"At0 for sensor value"
	::= { ctlRsSensorsAnalogsEntry 14 }

ctlRsSensorsAnalogAt75  OBJECT-TYPE
	SYNTAX     OCTET STRING (SIZE(2..16))
	MAX-ACCESS read-write
	STATUS     current
	DESCRIPTION 
		"At75 for sensor value"
	::= { ctlRsSensorsAnalogsEntry 15 }

ctlRsSensorsAnalogExpression  OBJECT-TYPE
	SYNTAX     OCTET STRING (SIZE(2..80))
	MAX-ACCESS read-write
	STATUS     current
	DESCRIPTION 
		"Expression for sensor value"
	::= { ctlRsSensorsAnalogsEntry 16 }

ctlRsSensorsAnalogSpecific  OBJECT-TYPE
	SYNTAX     OCTET STRING (SIZE(2..16))
	MAX-ACCESS read-only
	STATUS     current
	DESCRIPTION 
		"Specific parameters for sensor"
	::= { ctlRsSensorsAnalogsEntry 17 }

ctlRsSensorsOutletsTable  OBJECT-TYPE
	SYNTAX SEQUENCE OF CtlRsSensorsOutletsEntry
	MAX-ACCESS not-accessible
	STATUS     current
	DESCRIPTION 
		""
	::= { ctlRsSensors 3 }

ctlRsSensorsOutletsEntry  OBJECT-TYPE
	SYNTAX 	CtlRsSensorsOutletsEntry
	MAX-ACCESS not-accessible
	STATUS     current
	DESCRIPTION 
		"Entry of outlet"
	INDEX { ctlRsSensorsOutletId }
	::= { ctlRsSensorsOutletsTable 1 }

CtlRsSensorsOutletsEntry ::= SEQUENCE {
	ctlRsSensorsOutletId
		Integer32,
	ctlRsSensorsOutletModule
		Integer32,
	ctlRsSensorsOutletNum
		Integer32,
	ctlRsSensorsOutletGroup
		Integer32,
	ctlRsSensorsOutletType
		OCTET STRING,
	ctlRsSensorsOutletName
		OCTET STRING,
	ctlRsSensorsOutletState
		OCTET STRING,
	ctlRsSensorsOutletValue
		OCTET STRING,
	ctlRsSensorsOutletInitial
		OCTET STRING,
	ctlRsSensorsDiscretPulse
		Integer32
}

ctlRsSensorsOutletId  OBJECT-TYPE
	SYNTAX     Integer32
	MAX-ACCESS read-only
	STATUS     current
	DESCRIPTION 
		"Id of outlet"
	::= { ctlRsSensorsOutletsEntry 1 }

ctlRsSensorsOutletModule  OBJECT-TYPE
	SYNTAX     Integer32
	MAX-ACCESS read-only
	STATUS     current
	DESCRIPTION 
		"Module of outlet"
	::= { ctlRsSensorsOutletsEntry 2 }

ctlRsSensorsOutletNum  OBJECT-TYPE
	SYNTAX     Integer32
	MAX-ACCESS read-only
	STATUS     current
	DESCRIPTION 
		"Logical number in module for outlet"
	::= { ctlRsSensorsOutletsEntry 3 }

ctlRsSensorsOutletGroup  OBJECT-TYPE
	SYNTAX     Integer32
	MAX-ACCESS read-write
	STATUS     current
	DESCRIPTION 
		"Group of outlet"
	::= { ctlRsSensorsOutletsEntry 4 }

ctlRsSensorsOutletType  OBJECT-TYPE
	SYNTAX     OCTET STRING
	MAX-ACCESS read-only
	STATUS     current
	DESCRIPTION 
		"Type of outlet"
	::= { ctlRsSensorsOutletsEntry 5 }

ctlRsSensorsOutletName  OBJECT-TYPE
	SYNTAX     OCTET STRING (SIZE(2..128))
	MAX-ACCESS read-write
	STATUS     current
	DESCRIPTION 
		"Name of outlet"
	::= { ctlRsSensorsOutletsEntry 6 }

ctlRsSensorsOutletState  OBJECT-TYPE
	SYNTAX     OCTET STRING
	MAX-ACCESS read-only
	STATUS     current
	DESCRIPTION 
		"State of outlet"
	::= { ctlRsSensorsOutletsEntry 7 }

ctlRsSensorsOutletValue  OBJECT-TYPE
	SYNTAX     OCTET STRING
	MAX-ACCESS read-write
	STATUS     current
	DESCRIPTION 
		"Value of outlet"
	::= { ctlRsSensorsOutletsEntry 8 }

ctlRsSensorsOutletInitial  OBJECT-TYPE
	SYNTAX     OCTET STRING
	MAX-ACCESS read-write
	STATUS     current
	DESCRIPTION 
		"Initial state for outlet"
	::= { ctlRsSensorsOutletsEntry 9 }

ctlRsSensorsDiscretPulse  OBJECT-TYPE
	SYNTAX     Integer32
	MAX-ACCESS read-write
	STATUS     current
	DESCRIPTION 
		"Pulse duration for outlet"
	::= { ctlRsSensorsOutletsEntry 10 }
END

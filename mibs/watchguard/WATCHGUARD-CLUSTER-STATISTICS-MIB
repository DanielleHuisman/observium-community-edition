WATCHGUARD-CLUSTER-STATISTICS-MIB DEFINITIONS ::= BEGIN

    IMPORTS
        MODULE-IDENTITY, OBJECT-TYPE, 
        OBJECT-IDENTITY, enterprises, 
        IpAddress, TimeTicks       FROM SNMPv2-SMI
        watchguard                 FROM WATCHGUARD-SMI;
        
    wgInfoModule MODULE-IDENTITY
        LAST-UPDATED  "200701251200Z"
        ORGANIZATION  "WatchGuard Technologies, Inc."
        CONTACT-INFO
                   "  WatchGuard Technologies, Inc.

                      505 Fifth Avenue South
                      Suite 500
                      Seattle, WA 98104
                      United States

                      +1.206.613.6600 " 


        DESCRIPTION
            "The MIB module describes various system statistics information
            of WatchGuard system."


        REVISION      "200701251200Z"
        DESCRIPTION
            "Initial revision."
        ::= { watchguard 6 }


    wgClusterStatusMIB OBJECT-IDENTITY
        STATUS      current
        DESCRIPTION
            "This is cluster status information."
    ::= { wgInfoModule 6 }

    wgClusterEnabled OBJECT-TYPE
        SYNTAX      INTEGER {
                        disabled(0),
                        enabled(1)
                    }
        MAX-ACCESS  read-only
        STATUS      current
        DESCRIPTION
            "It is cluster or single box."
        ::= { wgClusterStatusMIB 1 }

    wgFirstMemberId OBJECT-TYPE
        SYNTAX      OCTET STRING (SIZE(0..256))
        MAX-ACCESS  read-only
        STATUS      current
        DESCRIPTION
            "First member id."
        ::= { wgClusterStatusMIB 2 }
            
    wgFirstMemberRole OBJECT-TYPE
        SYNTAX      INTEGER {
                        disabled(0),
                        worker(1),
                        backup(2),
                        master(3),
                        idle(4),
                        standby(5)
                    }
        MAX-ACCESS  read-only
        STATUS      current
        DESCRIPTION
            "First member role."
        ::= { wgClusterStatusMIB 3 }
    
    wgFirstMemberSystemHealth OBJECT-TYPE
        SYNTAX      INTEGER 
        MAX-ACCESS  read-only
        STATUS      current
        DESCRIPTION
            "First member system health value."
        ::= { wgClusterStatusMIB 4 }
    
    wgFirstMemberHardwareHealth OBJECT-TYPE
        SYNTAX      INTEGER 
        MAX-ACCESS  read-only
        STATUS      current
        DESCRIPTION
            "First member hardware health value."
        ::= { wgClusterStatusMIB 5 }
  
    wgFirstMemberMonitorPortHealth OBJECT-TYPE
        SYNTAX      INTEGER 
        MAX-ACCESS  read-only
        STATUS      current
        DESCRIPTION
            "First member monitored ports health value."
        ::= { wgClusterStatusMIB 6 }
  
    wgFirstMemberWeightAvg OBJECT-TYPE
        SYNTAX      INTEGER
        MAX-ACCESS  read-only
        STATUS      current
        DESCRIPTION
            "First member weight avg value."
        ::= { wgClusterStatusMIB 7 }
 
    wgSecondMemberId OBJECT-TYPE
        SYNTAX      OCTET STRING (SIZE(0..256))
        MAX-ACCESS  read-only
        STATUS      current
        DESCRIPTION
            "Second member id."
        ::= { wgClusterStatusMIB 8 }
            
    wgSecondMemberRole OBJECT-TYPE
        SYNTAX      INTEGER {
                        disabled(0),
                        worker(1),
                        backup(2),
                        master(3),
                        idle(4),
                        standby(5)
                    }
        MAX-ACCESS  read-only
        STATUS      current
        DESCRIPTION
            "Second member role."
        ::= { wgClusterStatusMIB 9 }
    
    wgSecondMemberSystemHealth OBJECT-TYPE
        SYNTAX      INTEGER 
        MAX-ACCESS  read-only
        STATUS      current
        DESCRIPTION
            "Second member system health value."
        ::= { wgClusterStatusMIB 10 }
    
    wgSecondMemberHardwareHealth OBJECT-TYPE
        SYNTAX      INTEGER 
        MAX-ACCESS  read-only
        STATUS      current
        DESCRIPTION
            "Second member hardware health value."
        ::= { wgClusterStatusMIB 11 }
  
    wgSecondMemberMonitorPortHealth OBJECT-TYPE
        SYNTAX      INTEGER 
        MAX-ACCESS  read-only
        STATUS      current
        DESCRIPTION
            "Second member monitored ports health value."
        ::= { wgClusterStatusMIB 12 }
  
    wgSecondMemberWeightAvg OBJECT-TYPE
        SYNTAX      INTEGER
        MAX-ACCESS  read-only
        STATUS      current
        DESCRIPTION
            "Second member weight avg value."
        ::= { wgClusterStatusMIB 13 }
END

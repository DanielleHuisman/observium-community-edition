WebGraph-AnalogIn-57641-US-MIB DEFINITIONS ::= BEGIN
----------------------------------------------------------------
-- Revison: 1.29
----------------------------------------------------------------
-- 22.06.2010 	Webio
--		Syntax correction 
----------------------------------------------------------------
-- Revison: 1.28
----------------------------------------------------------------
-- 02.12.2008 	Webio
--		New Graphics java script base parameter 
----------------------------------------------------------------
-- Revison: 1.27
----------------------------------------------------------------
-- 09.11.2006 	Webio
--		DHCP enable 
----------------------------------------------------------------
-- Revison: 1.26
----------------------------------------------------------------
-- 28.06.2006 	New: Community String Trap
--		
----------------------------------------------------------------
-- Revison: 1.25
----------------------------------------------------------------
-- 25.11.2005 	#57641, WebGraph AnalogIn
--		OID correction 
----------------------------------------------------------------
-- Revison: 1.24
----------------------------------------------------------------
-- 26.07.2005 	#57641, WebGraph AnalogIn
--		CRON timer function
----------------------------------------------------------------
-- Revison: 1.23
----------------------------------------------------------------
-- 14.07.2005 	#57641, WebGraph AnalogIn
--		FTP functions
----------------------------------------------------------------
-- Revison: 1.22
----------------------------------------------------------------
-- 17.05.2005 	#57641, WebGraph AnalogIn
--		Trap NMS annotations
----------------------------------------------------------------
-- Revison: 1.21
----------------------------------------------------------------
-- 19.04.2005 	#57605, WebGraph Themometer
--		Mail Authentication
----------------------------------------------------------------
-- Revison: 1.20
----------------------------------------------------------------
-- 05.11.2004 	#57606, WebGraph Thermo-Hygrometer
--		New: Syslog
--		     
----------------------------------------------------------------
-- Revison: 1.19
----------------------------------------------------------------
-- 08.09.2004 	#57606 WebGraph Thermo-Hygrometer
--		New: 
--			wtWebGraphThermHygroAlarmRHMin
--			wtWebGraphThermHygroAlarmRHMax
--			wtWebGraphThermHygroAlarmRHHysteresis
--			wtWebGraphThermHygroPortSensorSelect
--			wtWebGraphThermHygroAlarmDeltaTemp		
--			wtWebGraphThermHygroAlarmAHMin		
--			wtWebGraphThermHygroAlarmAHMax		
----------------------------------------------------------------
-- Revison: 1.18
----------------------------------------------------------------
-- 21.07.2004 	#57601/3/4, Webio Anx
--		New: 
--		     Diagnosis
----------------------------------------------------------------
-- Revison: 1.17
----------------------------------------------------------------
-- 28.06.2004 	#57630/1/2, Webio Digital
--		Neu: Puls Mode
----------------------------------------------------------------
-- Revison: 1.16
----------------------------------------------------------------
-- 16.04.2004 	New: #57632, Webio Digital EA24x24
--
--		#57630/1, Webio Digital EA12x12
--		New:
--			wtWebioEA12x12InputCounterClear
----------------------------------------------------------------
-- Revison: 1.15
----------------------------------------------------------------
-- 27.02.2004 	#57630/1, Webio Digital EA12x12
--		New:
--		Length changed to 32 Bit:
--			wtWebioEA12x12InputValue
--			wtWebioEA12x12OutputValue
--			wtWebioEA12x12LoadControlView
--			wtWebioEA12x12LCShutDownView
--			wtWebioEA12x12SetOutput
--			wtWebioEA12x12AlarmInputTrigger
--			wtWebioEA12x12AlarmOutputTrigger
--			wtWebioEA12x12PortOutputSafetyState
----------------------------------------------------------------
-- Revison: 1.14
----------------------------------------------------------------
-- 16.02.2004 	#57630/1, Webio Digital EA12x12
--		New:
--		Text: Location, Contact
--		SNMP: ColdStart, WarmStart, ComunityString Read/RW
--		Alarm: ColdStart / WarmStart trigger
--
-- 	 	#57601, 1xWebThermometer
--		#57603, 2xWebThermometer		
--		#57604, 8xWebThermometer
--		New:
--		Alarm Hysteresis 
--		Alarm Clear Traps and Mails
----------------------------------------------------------------
-- Revison: 1.13
----------------------------------------------------------------
-- 05.02.2004 	#57601, 1xWebThermometer
--		#57603, 2xWebThermometer		
--		#57604, 8xWebThermometer
--		New:
--		Text: Location, Contact
--		SNMP: ColdStart, WarmStart, ComunityString Read/RW
--		Alarm: ColdStart / WarmStart trigger
----------------------------------------------------------------
-- Revison: 1.12
----------------------------------------------------------------
-- 05.11.2003 	#57601, 1xWebThermometer
--		#57603, 2xWebThermometer		
--		#57604, 8xWebThermometer
--		New features:
--		Mail  : Option CSV attachment
--		Port  : Offset calibration
--		Alarm : TCP Client mode		
----------------------------------------------------------------
-- Revison: 1.11
----------------------------------------------------------------
-- 28.10.2003 	#57630/1, Webio Digital EA12x12
--		New features:
--		Alarm : TCP Client mode		
--		Inputs: Puls filter
----------------------------------------------------------------
-- Revison: 1.10
----------------------------------------------------------------
-- 22.07.2003 	#57630, Webio Digital EA12x12
--		New navigation tree, new binary modes		
--
----------------------------------------------------------------
-- Revison: 1.09
----------------------------------------------------------------
-- 24.03.2003 	Trap Enterprise (Type 1, 2) corrected 
----------------------------------------------------------------
-- Revison: 1.08
----------------------------------------------------------------
-- 04.03.2003 	reconciled the language versions DE/US
----------------------------------------------------------------
-- Revison: 1.07
----------------------------------------------------------------
-- 25.02.2003 	Correction: wtWebioEA12x12LoadControl
----------------------------------------------------------------
-- Revison: 1.06
----------------------------------------------------------------
-- 24.02.2003 	New:
--		#57630, Webio EA12x12, LoadControl Group
--		Correction: Trap variable names
----------------------------------------------------------------
-- Revison: 1.05
----------------------------------------------------------------
-- 21.01.2003 	New:
--		#57630, Webio EA12x12
----------------------------------------------------------------
-- Revison: 1.04
----------------------------------------------------------------
-- 02.01.2003 	New:
--		#57601, 1xWebThermometer
--		#57603, 2xWebThermometer, 8 alarms
----------------------------------------------------------------
-- Revison: 1.03
----------------------------------------------------------------
-- 21.11.2002 	New:
--		#57604, 2xWebThermometer, BOOTP, StartupSite
--		#57603, 8xWebThermometer, BOOTP, StartupSite
----------------------------------------------------------------
-- Revison: 1.02
----------------------------------------------------------------
-- 26.07.2002 	New:
--		#57604, 2xWebThermometer
--		#57603, 8xWebThermometer
-- 		


    IMPORTS

    OBJECT-TYPE                                        FROM RFC-1212
    TRAP-TYPE                                          FROM RFC-1215
    DisplayString, PhysAddress                         FROM RFC1213-MIB
    enterprises, TimeTicks, IpAddress, NetworkAddress  FROM RFC1155-SMI;

 
--    IpAddress ::=
--        [APPLICATION 0]
--            IMPLICIT OCTET STRING (SIZE (4))
--    Counter ::=
--        [APPLICATION 1]
--            IMPLICIT INTEGER (0..4294967295)
--    Gauge ::=
--        [APPLICATION 2]
--            IMPLICIT INTEGER (0..4294967295)
--    TimeTicks ::=
--        [APPLICATION 3]
--            IMPLICIT INTEGER (0..4294967295)


--    DisplayString ::= OCTET STRING
--    PhysAddress   ::= OCTET STRING

--    internet         OBJECT IDENTIFIER ::= { iso org(3) dod(6) 1 }
--    privat           OBJECT IDENTIFIER ::= { internet 4 }
--    enterprises      OBJECT IDENTIFIER ::= { privat 1 }



--  Wiesemann & Theis Com-Server MIB

    wut                				OBJECT IDENTIFIER ::= { enterprises 5040 }
    wtComServer        				OBJECT IDENTIFIER ::= { wut 1 }
    wtWebio            				OBJECT IDENTIFIER ::= { wtComServer 2 }

--  wtWebGraph Tree

    wtWebGraphAnalogIn57641  			OBJECT IDENTIFIER ::= { wtWebio 10 }
    
--  wtWebGraphAnalogIn57641 Tree

    wtWebGraphAnalogIn57641Inventory   		OBJECT IDENTIFIER ::= { wtWebGraphAnalogIn57641 1 }
    wtWebGraphAnalogIn57641SessCntrl 		OBJECT IDENTIFIER ::= { wtWebGraphAnalogIn57641 2 }
    wtWebGraphAnalogIn57641Config    		OBJECT IDENTIFIER ::= { wtWebGraphAnalogIn57641 3 }
    wtWebGraphAnalogIn57641Diag    		OBJECT IDENTIFIER ::= { wtWebGraphAnalogIn57641 4 }
    	
--  wtWebGraphAnalogIn57641Config Tree

    wtWebGraphAnalogIn57641Device    		OBJECT IDENTIFIER ::= { wtWebGraphAnalogIn57641Config 1 }
    wtWebGraphAnalogIn57641Ports     		OBJECT IDENTIFIER ::= { wtWebGraphAnalogIn57641Config 2 }	
    wtWebGraphAnalogIn57641Manufact  		OBJECT IDENTIFIER ::= { wtWebGraphAnalogIn57641Config 3 }	

--  wtWebGraphAnalogIn57641Device Tree

    wtWebGraphAnalogIn57641Text			OBJECT IDENTIFIER ::= { wtWebGraphAnalogIn57641Device 1 }	
    wtWebGraphAnalogIn57641TimeDate 		OBJECT IDENTIFIER ::= { wtWebGraphAnalogIn57641Device 2 }
    wtWebGraphAnalogIn57641Basic		OBJECT IDENTIFIER ::= { wtWebGraphAnalogIn57641Device 3 }	
    wtWebGraphAnalogIn57641Datalogger		OBJECT IDENTIFIER ::= { wtWebGraphAnalogIn57641Device 4 }	
    wtWebGraphAnalogIn57641Alarm		OBJECT IDENTIFIER ::= { wtWebGraphAnalogIn57641Device 5 }
    wtWebGraphAnalogIn57641Graphics 		OBJECT IDENTIFIER ::= { wtWebGraphAnalogIn57641Device 6 }	
    
--  wtWebGraphAnalogIn57641TimeDate Tree

    wtWebGraphAnalogIn57641TimeZone		OBJECT IDENTIFIER ::= { wtWebGraphAnalogIn57641TimeDate 1 }
    wtWebGraphAnalogIn57641TimeServer		OBJECT IDENTIFIER ::= { wtWebGraphAnalogIn57641TimeDate 2 }	
    wtWebGraphAnalogIn57641DeviceClock		OBJECT IDENTIFIER ::= { wtWebGraphAnalogIn57641TimeDate 3 }

--  wtWebGraphAnalogIn57641Basic Tree
    
    wtWebGraphAnalogIn57641Network		OBJECT IDENTIFIER ::= { wtWebGraphAnalogIn57641Basic 1 }
    wtWebGraphAnalogIn57641HTTP			OBJECT IDENTIFIER ::= { wtWebGraphAnalogIn57641Basic 2 }
    wtWebGraphAnalogIn57641Mail			OBJECT IDENTIFIER ::= { wtWebGraphAnalogIn57641Basic 3 }	
    wtWebGraphAnalogIn57641SNMP			OBJECT IDENTIFIER ::= { wtWebGraphAnalogIn57641Basic 4 }
    wtWebGraphAnalogIn57641UDP			OBJECT IDENTIFIER ::= { wtWebGraphAnalogIn57641Basic 5 }
    wtWebGraphAnalogIn57641Syslog		OBJECT IDENTIFIER ::= { wtWebGraphAnalogIn57641Basic 6 }
    wtWebGraphAnalogIn57641FTP			OBJECT IDENTIFIER ::= { wtWebGraphAnalogIn57641Basic 7 }

--  wtWebGraphAnalogIn57641Graphics Tree
    
    wtWebGraphAnalogIn57641GraphicsBase 	OBJECT IDENTIFIER ::= { wtWebGraphAnalogIn57641Graphics 1 }
    wtWebGraphAnalogIn57641GraphicsSelect 	OBJECT IDENTIFIER ::= { wtWebGraphAnalogIn57641Graphics 2 }
    wtWebGraphAnalogIn57641GraphicsScale 	OBJECT IDENTIFIER ::= { wtWebGraphAnalogIn57641Graphics 3 }
       
-- wtWebGraphAnalogIn57641Inventory Group
------------------------

wtWebGraphAnalogIn57641Sensors OBJECT-TYPE
    SYNTAX INTEGER (1..2)
    ACCESS read-only
    STATUS mandatory
    DESCRIPTION
        "Number of sensors"
    ::= { wtWebGraphAnalogIn57641Inventory 1 }

-- Interface Table

wtWebGraphAnalogIn57641SensorTable OBJECT-TYPE
    SYNTAX SEQUENCE OF WtWebGraphAnalogIn57641SensorEntry
    ACCESS not-accessible
    STATUS mandatory
    DESCRIPTION
        "List of sensors."
    ::= { wtWebGraphAnalogIn57641Inventory 2 }

wtWebGraphAnalogIn57641SensorEntry OBJECT-TYPE
    SYNTAX WtWebGraphAnalogIn57641SensorEntry
    ACCESS not-accessible
    STATUS mandatory
    DESCRIPTION
        "List of sensor numbers."
    INDEX  { wtWebGraphAnalogIn57641SensorNo }
    ::= { wtWebGraphAnalogIn57641SensorTable 1 }

WtWebGraphAnalogIn57641SensorEntry ::= SEQUENCE {
    wtWebGraphAnalogIn57641SensorNo INTEGER
}

wtWebGraphAnalogIn57641SensorNo OBJECT-TYPE
    SYNTAX INTEGER (1..2)
    ACCESS read-only
    STATUS mandatory
    DESCRIPTION
        "Sensor number."
    ::= { wtWebGraphAnalogIn57641SensorEntry 1 }


-- wtWebGraphAnalogIn57641Values Table

wtWebGraphAnalogIn57641ValuesTable OBJECT-TYPE
    SYNTAX SEQUENCE OF WtWebGraphAnalogIn57641ValuesEntry
    ACCESS not-accessible
    STATUS mandatory
    DESCRIPTION
        "List of measurement values corresponding to the channel numbers."
    ::= { wtWebGraphAnalogIn57641Inventory 3 }

wtWebGraphAnalogIn57641ValuesEntry OBJECT-TYPE
    SYNTAX WtWebGraphAnalogIn57641ValuesEntry
    ACCESS not-accessible
    STATUS mandatory
    DESCRIPTION
        "Measurement values of the sensors."
    INDEX  { wtWebGraphAnalogIn57641SensorNo }
    ::= { wtWebGraphAnalogIn57641ValuesTable 1 }

WtWebGraphAnalogIn57641ValuesEntry ::= SEQUENCE{
    wtWebGraphAnalogIn57641Values OCTET STRING
}

wtWebGraphAnalogIn57641Values OBJECT-TYPE
    SYNTAX OCTET STRING (SIZE (5))
    ACCESS read-only
    STATUS mandatory
    DESCRIPTION
        "Measurement value of the sensor, ASCII, 7 characters in length."
    ::= { wtWebGraphAnalogIn57641ValuesEntry 1 }

-- wtWebGraphAnalogIn57641BinaryValues Table

wtWebGraphAnalogIn57641BinaryValuesTable OBJECT-TYPE
    SYNTAX SEQUENCE OF WtWebGraphAnalogIn57641BinaryValuesEntry
    ACCESS not-accessible
    STATUS mandatory
    DESCRIPTION
        "List of binary measurement values corresponding to the channel numbers."
    ::= { wtWebGraphAnalogIn57641Inventory 4 }

wtWebGraphAnalogIn57641BinaryValuesEntry OBJECT-TYPE
    SYNTAX WtWebGraphAnalogIn57641BinaryValuesEntry
    ACCESS not-accessible
    STATUS mandatory
    DESCRIPTION
        "Binary measurement values of the sensors."
    INDEX  { wtWebGraphAnalogIn57641SensorNo }
    ::= { wtWebGraphAnalogIn57641BinaryValuesTable 1 }

WtWebGraphAnalogIn57641BinaryValuesEntry ::= SEQUENCE{
    wtWebGraphAnalogIn57641BinaryValues INTEGER
}    

wtWebGraphAnalogIn57641BinaryValues OBJECT-TYPE
    SYNTAX INTEGER
    ACCESS read-only
    STATUS mandatory
    DESCRIPTION
        "Binary measurement value of the sensor in 1/10 degrees Celsius or 1/10 per cent,
        signed number, 0x4FFF6 indicates an 
        invalid measured value."
    ::= { wtWebGraphAnalogIn57641BinaryValuesEntry 1 }

-- wtWebGraphAnalogIn57641SessCntrl Group
--------------------------------

wtWebGraphAnalogIn57641SessCntrlPassword OBJECT-TYPE
    SYNTAX OCTET STRING 
    ACCESS read-write
    STATUS mandatory
    DESCRIPTION
        "Entering this password opens a session which is ended by writing a 1 to 
        wtWebGraphAnalogIn57641SessCntrlLogout. When read this variable provides a string of
        length zero."
    ::= { wtWebGraphAnalogIn57641SessCntrl 1 }

wtWebGraphAnalogIn57641SessCntrlConfigMode OBJECT-TYPE
    SYNTAX INTEGER {
    wtWebGraphAnalogIn57641SessCntrl-NoSession(0),
    wtWebGraphAnalogIn57641SessCntrl-Session(1)
    }
    ACCESS read-only
    STATUS mandatory
    DESCRIPTION
        "When the device is in SNMP configuration mode, the value 1 is
        returned, otherwise 0. If the read value is 0 even though the
        password was written, the device is already in config mode and the
        variables can only be read."
    ::= { wtWebGraphAnalogIn57641SessCntrl 2 }

wtWebGraphAnalogIn57641SessCntrlLogout OBJECT-TYPE
    SYNTAX INTEGER 
    ACCESS read-write
    STATUS mandatory
    DESCRIPTION
        "If the device is in configuration mode and the session was opened by
        this SNMP Manager, writing a 1 to this variable will end the session 
        and all parameters are stored.
        Writing a 2 discards all entries again.
        When read this variable provides the value 0."
    ::= { wtWebGraphAnalogIn57641SessCntrl 3 }

wtWebGraphAnalogIn57641SessCntrlAdminPassword OBJECT-TYPE
    SYNTAX OCTET STRING 
    ACCESS read-write
    STATUS mandatory
    DESCRIPTION
        "This password protects access to the variables with administrator rights.
        It can only be changed by the administrator. If no password was assigned,
        the valid password is public."
    ::= { wtWebGraphAnalogIn57641SessCntrl 4 }

wtWebGraphAnalogIn57641SessCntrlConfigPassword OBJECT-TYPE
    SYNTAX OCTET STRING 
    ACCESS read-write
    STATUS mandatory
    DESCRIPTION
        "This password protects access to the variables with configurator rights. It can
        be changed by the administrator and by the configurator. If no password was assigned, 
        the valid password is public. When read this variable provides a null-pointer."
    ::= { wtWebGraphAnalogIn57641SessCntrl 5 }
    

-- wtWebGraphAnalogIn57641Text Group
------------------------

wtWebGraphAnalogIn57641DeviceName OBJECT-TYPE
    SYNTAX OCTET STRING 
    ACCESS read-write
    STATUS mandatory
    DESCRIPTION
        "Name of the Webio, which is user definable."
    ::= { wtWebGraphAnalogIn57641Text 1 }

wtWebGraphAnalogIn57641DeviceText OBJECT-TYPE
    SYNTAX OCTET STRING 
    ACCESS read-write
    STATUS mandatory
    DESCRIPTION
        "Description of the Webio, which is user definable."
    ::= { wtWebGraphAnalogIn57641Text 2 }

wtWebGraphAnalogIn57641DeviceLocation OBJECT-TYPE
    SYNTAX OCTET STRING 
    ACCESS read-write
    STATUS mandatory
    DESCRIPTION
        "Description of the location of the Webio, which is user definable."
    ::= { wtWebGraphAnalogIn57641Text 3 }

wtWebGraphAnalogIn57641DeviceContact OBJECT-TYPE
    SYNTAX OCTET STRING 
    ACCESS read-write
    STATUS mandatory
    DESCRIPTION
        "Contact address of the system operator of the Webio, which is user definable."
    ::= { wtWebGraphAnalogIn57641Text 4 }

-- wtWebGraphAnalogIn57641TimeZone Group
----------------------------

wtWebGraphAnalogIn57641TzOffsetHrs OBJECT-TYPE
    SYNTAX INTEGER 
    ACCESS read-write
    STATUS mandatory
    DESCRIPTION
        "Offset hours for the time zone (winter time) with respect to UTC."
    ::= { wtWebGraphAnalogIn57641TimeZone 1 }

wtWebGraphAnalogIn57641TzOffsetMin OBJECT-TYPE
    SYNTAX INTEGER 
    ACCESS read-write
    STATUS mandatory
    DESCRIPTION
        "Offset minutes for the time zone (winter time) with respect to UTC."
    ::= { wtWebGraphAnalogIn57641TimeZone 2 }

wtWebGraphAnalogIn57641TzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebGraphAnalogIn57641TimeZone 3 }    
    
wtWebGraphAnalogIn57641StTzOffsetHrs OBJECT-TYPE
    SYNTAX INTEGER 
    ACCESS read-write
    STATUS mandatory
    DESCRIPTION
        "Offset hours of the time zone (summer time) with respect to UTC."
    ::= { wtWebGraphAnalogIn57641TimeZone 4 }

wtWebGraphAnalogIn57641StTzOffsetMin OBJECT-TYPE
    SYNTAX INTEGER 
    ACCESS read-write
    STATUS mandatory
    DESCRIPTION
        "Offset minutes of the time zone (summer time) with respect to UTC."
    ::= { wtWebGraphAnalogIn57641TimeZone 5 }
    
wtWebGraphAnalogIn57641StTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebGraphAnalogIn57641TimeZone 6 }       
    
wtWebGraphAnalogIn57641StTzStartMonth OBJECT-TYPE
    SYNTAX INTEGER {
    	wtWebGraphAnalogIn57641StartMonth-January(1),
    	wtWebGraphAnalogIn57641StartMonth-February(2),
    	wtWebGraphAnalogIn57641StartMonth-March(3),
    	wtWebGraphAnalogIn57641StartMonth-April(4),
    	wtWebGraphAnalogIn57641StartMonth-May(5),
    	wtWebGraphAnalogIn57641StartMonth-June(6),
    	wtWebGraphAnalogIn57641StartMonth-July(7),
    	wtWebGraphAnalogIn57641StartMonth-August(8),
    	wtWebGraphAnalogIn57641StartMonth-September(9),
    	wtWebGraphAnalogIn57641StartMonth-October(10),
    	wtWebGraphAnalogIn57641StartMonth-November(11),
    	wtWebGraphAnalogIn57641StartMonth-December(12)
    	}
    	
    ACCESS read-write
    STATUS mandatory
    DESCRIPTION
        "Month in which the change is made from winter time to summer time."
    ::= { wtWebGraphAnalogIn57641TimeZone 7 }

wtWebGraphAnalogIn57641StTzStartMode OBJECT-TYPE
    SYNTAX INTEGER {
    	wtWebGraphAnalogIn57641StartMode-first(1),
    	wtWebGraphAnalogIn57641StartMode-second(2),
    	wtWebGraphAnalogIn57641StartMode-third(3),
    	wtWebGraphAnalogIn57641StartMode-fourth(4),
    	wtWebGraphAnalogIn57641StartMode-last(5)
    	}
    	
    ACCESS read-write
    STATUS mandatory
    DESCRIPTION
        "Mode of the day of the week for which the change is made from winter time to summer time."
    ::= { wtWebGraphAnalogIn57641TimeZone 8 }

wtWebGraphAnalogIn57641StTzStartWday OBJECT-TYPE
    SYNTAX INTEGER {
    	wtWebGraphAnalogIn57641StartWday-Sunday(1),
    	wtWebGraphAnalogIn57641StartWday-Monday(2),
    	wtWebGraphAnalogIn57641StartWday-Tuesday(3),
    	wtWebGraphAnalogIn57641StartWday-Thursday(4),
    	wtWebGraphAnalogIn57641StartWday-Wednesday(5),
    	wtWebGraphAnalogIn57641StartWday-Friday(6),
    	wtWebGraphAnalogIn57641StartWday-Saturday(7)
    	}
    	
    ACCESS read-write
    STATUS mandatory
    DESCRIPTION
        "Day of the week on which the change is made from winter time to summer time"
    ::= { wtWebGraphAnalogIn57641TimeZone 9 }
    
wtWebGraphAnalogIn57641StTzStartHrs OBJECT-TYPE
    SYNTAX INTEGER 
    ACCESS read-write
    STATUS mandatory
    DESCRIPTION
        "Hour in which the time zone is changed from winter to summer time with
        respect to UTC."
    ::= { wtWebGraphAnalogIn57641TimeZone 10 }

wtWebGraphAnalogIn57641StTzStartMin OBJECT-TYPE
    SYNTAX INTEGER 
    ACCESS read-write
    STATUS mandatory
    DESCRIPTION
        "Minute in which the time zone is changed from winter to summer time with
        respect to UTC."
    ::= { wtWebGraphAnalogIn57641TimeZone 11 }
 
wtWebGraphAnalogIn57641StTzStopMonth OBJECT-TYPE
    SYNTAX INTEGER {
    	wtWebGraphAnalogIn57641StopMonth-January(1),
    	wtWebGraphAnalogIn57641StopMonth-February(2),
    	wtWebGraphAnalogIn57641StopMonth-March(3),
    	wtWebGraphAnalogIn57641StopMonth-April(4),
    	wtWebGraphAnalogIn57641StopMonth-May(5),
    	wtWebGraphAnalogIn57641StopMonth-June(6),
    	wtWebGraphAnalogIn57641StopMonth-July(7),
    	wtWebGraphAnalogIn57641StopMonth-August(8),
    	wtWebGraphAnalogIn57641StopMonth-September(9),
    	wtWebGraphAnalogIn57641StopMonth-October(10),
    	wtWebGraphAnalogIn57641StopMonth-November(11),
    	wtWebGraphAnalogIn57641StopMonth-December(12)
    	}
    ACCESS read-write
    STATUS mandatory
    DESCRIPTION
        "Month in which the change is made from summer time to winter time."
   ::= { wtWebGraphAnalogIn57641TimeZone 12 }

wtWebGraphAnalogIn57641StTzStopMode OBJECT-TYPE
    SYNTAX INTEGER {
    	wtWebGraphAnalogIn57641StopMode-first(1),
    	wtWebGraphAnalogIn57641StopMode-second(2),
    	wtWebGraphAnalogIn57641StopMode-third(3),
    	wtWebGraphAnalogIn57641StopMode-fourth(4),
    	wtWebGraphAnalogIn57641StopMode-last(5)
    	}
    ACCESS read-write
    STATUS mandatory
    DESCRIPTION
        "Mode of the week day on which the change is made from summer time to winter time."
    ::= { wtWebGraphAnalogIn57641TimeZone 13 }

wtWebGraphAnalogIn57641StTzStopWday OBJECT-TYPE
    SYNTAX INTEGER {
    	wtWebGraphAnalogIn57641StopWday-Sunday(1),
    	wtWebGraphAnalogIn57641StopWday-Monday(2),
    	wtWebGraphAnalogIn57641StopWday-Tuesday(3),
    	wtWebGraphAnalogIn57641StopWday-Thursday(4),
    	wtWebGraphAnalogIn57641StopWday-Wednesday(5),
    	wtWebGraphAnalogIn57641StopWday-Friday(6),
    	wtWebGraphAnalogIn57641StopWday-Saturday(7)
    	}
    ACCESS read-write
    STATUS mandatory
    DESCRIPTION
        "Day of the week on which the change is made from summer time to winter time."
    ::= { wtWebGraphAnalogIn57641TimeZone 14 }
    
wtWebGraphAnalogIn57641StTzStopHrs OBJECT-TYPE
    SYNTAX INTEGER 
    ACCESS read-write
    STATUS mandatory
    DESCRIPTION
        "Hour at which the time zone is changed from summer to winter time with
        respect to UTC."
    ::= { wtWebGraphAnalogIn57641TimeZone 15 }

wtWebGraphAnalogIn57641StTzStopMin OBJECT-TYPE
    SYNTAX INTEGER 
    ACCESS read-write
    STATUS mandatory
    DESCRIPTION
        "Minute at which the time zone is changed from summer to winter time with
        respect to UTC."
    ::= { wtWebGraphAnalogIn57641TimeZone 16 }

-- wtWebGraphAnalogIn57641TimeServer Group
----------------------------

wtWebGraphAnalogIn57641TimeServer1 OBJECT-TYPE
    SYNTAX OCTET STRING 
    ACCESS read-write
    STATUS mandatory
    DESCRIPTION
        "IP address or name of the 1st time server in ASCII"
    ::= { wtWebGraphAnalogIn57641TimeServer 1 }

wtWebGraphAnalogIn57641TimeServer2 OBJECT-TYPE
    SYNTAX OCTET STRING 
    ACCESS read-write
    STATUS mandatory
    DESCRIPTION
        "IP address or name of the 2nd time server in ASCII"
    ::= { wtWebGraphAnalogIn57641TimeServer 2 }
    
wtWebGraphAnalogIn57641TsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebGraphAnalogIn57641TimeServer 3 }
    
wtWebGraphAnalogIn57641TsSyncTime OBJECT-TYPE
    SYNTAX INTEGER 
    ACCESS read-write
    STATUS mandatory
    DESCRIPTION
        "Daily synchronisation time with the time server (hour: 0-23)."
    ::= { wtWebGraphAnalogIn57641TimeServer 4 } 
    
-- wtWebGraphAnalogIn57641DeviceClock Group
----------------------------

wtWebGraphAnalogIn57641ClockHrs OBJECT-TYPE
    SYNTAX INTEGER (0..23)
    ACCESS read-write
    STATUS mandatory
    DESCRIPTION
        "Clock hours taking into account the time zone settings."
    ::= { wtWebGraphAnalogIn57641DeviceClock 1 }

wtWebGraphAnalogIn57641ClockMin OBJECT-TYPE
    SYNTAX INTEGER (0..59)
    ACCESS read-write
    STATUS mandatory
    DESCRIPTION
        "Clock minutes taking into account the time zone settings."
    ::= { wtWebGraphAnalogIn57641DeviceClock 2 }

wtWebGraphAnalogIn57641ClockDay OBJECT-TYPE
    SYNTAX INTEGER (1..31)
    ACCESS read-write
    STATUS mandatory
    DESCRIPTION
        "Date: Day of the month, taking into account the time zone settings."
    ::= { wtWebGraphAnalogIn57641DeviceClock 3 }

wtWebGraphAnalogIn57641ClockMonth OBJECT-TYPE
   SYNTAX INTEGER {
    	wtWebGraphAnalogIn57641ClockMonth-January(1),
    	wtWebGraphAnalogIn57641ClockMonth-February(2),
    	wtWebGraphAnalogIn57641ClockMonth-March(3),
    	wtWebGraphAnalogIn57641ClockMonth-April(4),
    	wtWebGraphAnalogIn57641ClockMonth-May(5),
    	wtWebGraphAnalogIn57641ClockMonth-June(6),
    	wtWebGraphAnalogIn57641ClockMonth-July(7),
    	wtWebGraphAnalogIn57641ClockMonth-August(8),
    	wtWebGraphAnalogIn57641ClockMonth-September(9),
    	wtWebGraphAnalogIn57641ClockMonth-October(10),
    	wtWebGraphAnalogIn57641ClockMonth-November(11),
    	wtWebGraphAnalogIn57641ClockMonth-December(12)
    	}
    ACCESS read-write
    STATUS mandatory
    DESCRIPTION
        "Date: Month, taking into account the time zone settings."
    ::= { wtWebGraphAnalogIn57641DeviceClock 4 }

wtWebGraphAnalogIn57641ClockYear OBJECT-TYPE
    SYNTAX INTEGER (0..65535)
    ACCESS read-write
    STATUS mandatory
    DESCRIPTION
        "Date: Year, taking into account the time zone settings."
    ::= { wtWebGraphAnalogIn57641DeviceClock 5 }
    

-- wtWebGraphAnalogIn57641Network Group
------------------------

wtWebGraphAnalogIn57641IpAddress OBJECT-TYPE
    SYNTAX IpAddress
    ACCESS read-write
    STATUS mandatory
    DESCRIPTION
        "IP address of the Webio"
    ::= { wtWebGraphAnalogIn57641Network 1 }

wtWebGraphAnalogIn57641SubnetMask OBJECT-TYPE
    SYNTAX IpAddress
    ACCESS read-write
    STATUS mandatory
    DESCRIPTION
        "Subnet mask of the Webio"
    ::= { wtWebGraphAnalogIn57641Network 2 }

wtWebGraphAnalogIn57641Gateway OBJECT-TYPE
    SYNTAX IpAddress
    ACCESS read-write
    STATUS mandatory
    DESCRIPTION
        "Gateway of the Webio"
    ::= { wtWebGraphAnalogIn57641Network 3 }

wtWebGraphAnalogIn57641DnsServer1 OBJECT-TYPE
    SYNTAX OCTET STRING 
    ACCESS read-write
    STATUS mandatory
    DESCRIPTION
        "IP address of the 1st DNS server in ASCII"
    ::= { wtWebGraphAnalogIn57641Network 4 }

wtWebGraphAnalogIn57641DnsServer2 OBJECT-TYPE
    SYNTAX OCTET STRING 
    ACCESS read-write
    STATUS mandatory
    DESCRIPTION
        "IP address of the 2nd DNS server in ASCII"
    ::= { wtWebGraphAnalogIn57641Network 5 }

wtWebGraphAnalogIn57641AddConfig OBJECT-TYPE
    SYNTAX OCTET STRING 
    ACCESS read-write
    STATUS mandatory
    DESCRIPTION
        "Additional configuration (1=ON):
        Octet 1: unused
        Octet 2: unused
        Octet 3: unused
        Octet 4:
	        Bit 1: DHCP disable
	        Bit 0: BOOTP disable
	        "
    ::= { wtWebGraphAnalogIn57641Network 6 }

--  wtWebGraphAnalogIn57641HTTP Group
--------------------------------

wtWebGraphAnalogIn57641Startup OBJECT-TYPE
    SYNTAX OCTET STRING 
    ACCESS read-write
    STATUS mandatory
    DESCRIPTION
        "Binary coded start page:
        Octet 1: unused
        Octet 2: unused
        Octet 3: unused
        Octet 4:
	        Bit 1: Index.htm
	        Bit 2: Home.htm
	        Bit 3: User.htm
	Only one page may be selected at a time."
    ::= { wtWebGraphAnalogIn57641HTTP 1 }

wtWebGraphAnalogIn57641GetHeaderEnable OBJECT-TYPE
    SYNTAX OCTET STRING 
    ACCESS read-write
    STATUS mandatory
    DESCRIPTION
        "If these bits are set, every answer of a short form GET question will be lead
        by the IP-address and name of the device and/or a HTTP header:
        Octet 1: unused
        Octet 2: unused
        Octet 3: unused
        Octet 4:
        	Bit 1-6: unused
        	Bit 1  : GET HTTP enable
                Bit 0  : GET Header enable"
    ::= { wtWebGraphAnalogIn57641HTTP 2 }  
    
wtWebGraphAnalogIn57641HttpPort OBJECT-TYPE
    SYNTAX INTEGER (1..65535)
    ACCESS read-write
    STATUS mandatory
    DESCRIPTION
        "Definition of the standard HTML port (Default: 80)."
    ::= { wtWebGraphAnalogIn57641HTTP 3 }    


-- wtWebGraphAnalogIn57641Mail Group
--------------------------------

wtWebGraphAnalogIn57641MailAdName OBJECT-TYPE
    SYNTAX OCTET STRING 
    ACCESS read-write
    STATUS mandatory
    DESCRIPTION
        "Device name for mail administration."
    ::= { wtWebGraphAnalogIn57641Mail 1 }
    
wtWebGraphAnalogIn57641MailReply OBJECT-TYPE
    SYNTAX OCTET STRING 
    ACCESS read-write
    STATUS mandatory
    DESCRIPTION
        "Reply address for the mail server."
    ::= { wtWebGraphAnalogIn57641Mail 2 }
    
wtWebGraphAnalogIn57641MailServer OBJECT-TYPE
    SYNTAX OCTET STRING 
    ACCESS read-write
    STATUS mandatory
    DESCRIPTION
        "Name or IP address of the mail server."
    ::= { wtWebGraphAnalogIn57641Mail 3 }
    
wtWebioAn1MailEnable OBJECT-TYPE
    SYNTAX OCTET STRING 
    ACCESS read-write
    STATUS mandatory
    DESCRIPTION
        "Set this bit to enable the sending of mails:
        Octet 1: unused
        Octet 2: unused
        Octet 3: unused
        Octet 4:
        	Bit 1-7: unused
                Bit 0  : Mail enable"
    ::= { wtWebGraphAnalogIn57641Mail 4 }
    
wtWebGraphAnalogIn57641MailAuthentication OBJECT-TYPE
    SYNTAX OCTET STRING (SIZE (4))
    ACCESS read-write
    STATUS mandatory
    DESCRIPTION
        "Selection of the authentication modi:
        The OCTETS are interpreted bit-by-bit, with each bit corresponding to an output. 
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebGraphAnalogIn57641Mail 5 }
    
wtWebGraphAnalogIn57641MailAuthUser OBJECT-TYPE
    SYNTAX OCTET STRING 
    ACCESS read-write
    STATUS mandatory
    DESCRIPTION
        "Name of the user to be authenticated."
    ::= { wtWebGraphAnalogIn57641Mail 6 }    
    
wtWebGraphAnalogIn57641MailAuthPassword OBJECT-TYPE
    SYNTAX OCTET STRING 
    ACCESS read-write
    STATUS mandatory
    DESCRIPTION
        "Authentication password."
    ::= { wtWebGraphAnalogIn57641Mail 7 }    
    
wtWebGraphAnalogIn57641MailPop3Server OBJECT-TYPE
    SYNTAX OCTET STRING 
    ACCESS read-write
    STATUS mandatory
    DESCRIPTION
        "Name or Ip-address of the POP3 Servers."
    ::= { wtWebGraphAnalogIn57641Mail 8 }            

-- wtWebGraphAnalogIn57641SNMP Group
--------------------------------

wtWebGraphAnalogIn57641SnmpCommunityStringRead OBJECT-TYPE
    SYNTAX OCTET STRING
    ACCESS read-write
    STATUS mandatory
    DESCRIPTION
        "Community string read only"
    ::= { wtWebGraphAnalogIn57641SNMP 1 }

wtWebGraphAnalogIn57641SnmpCommunityStringReadWrite OBJECT-TYPE
    SYNTAX OCTET STRING
    ACCESS read-write
    STATUS mandatory
    DESCRIPTION
        "Community string read / write"
    ::= { wtWebGraphAnalogIn57641SNMP 2 }

wtWebGraphAnalogIn57641SystemTrapManagerIP OBJECT-TYPE
    SYNTAX OCTET STRING 
    ACCESS read-write
    STATUS mandatory
    DESCRIPTION
        "Name or IP address of the TCP server which accepts the system trap."
    ::= { wtWebGraphAnalogIn57641SNMP 3 }
    
wtWebGraphAnalogIn57641SystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2-7: unused"
    ::= { wtWebGraphAnalogIn57641SNMP 4 }
    
wtWebGraphAnalogIn57641SnmpEnable OBJECT-TYPE
    SYNTAX OCTET STRING 
    ACCESS read-write
    STATUS mandatory
    DESCRIPTION
        "Set bit 0 to enable SNMP.
        If disabled, the device did not respond to any SNMP requests.
        Bit 1 decided wether the community string of read operations 
        is compared with the system password or not:
        Octet 1: unused
        Octet 2: unused
        Octet 3: unused
        Octet 4:
        	Bit 1-7: unused
        	Bit 0  : SNMP enable"
    ::= { wtWebGraphAnalogIn57641SNMP 5 }
    
wtWebGraphAnalogIn57641SnmpCommunityStringTrap OBJECT-TYPE
    SYNTAX OCTET STRING
    ACCESS read-write
    STATUS mandatory
    DESCRIPTION
        "Community string send within traps."
    ::= { wtWebGraphAnalogIn57641SNMP 6 }    
            
    
-- wtWebGraphAnalogIn57641UDP Group
--------------------------------
    
wtWebGraphAnalogIn57641UdpPort OBJECT-TYPE
    SYNTAX INTEGER (1..65535)
    ACCESS read-write
    STATUS mandatory
    DESCRIPTION
        "Udp port to which the Udp queries ( short form GET requests) can be sent. This
        port number must be unique within the device."
    ::= { wtWebGraphAnalogIn57641UDP 1 }
    
wtWebGraphAnalogIn57641UdpEnable OBJECT-TYPE
    SYNTAX OCTET STRING 
    ACCESS read-write
    STATUS mandatory
    DESCRIPTION
        "Set this bit to enable UDP support:
        Octet 1: unused
        Octet 2: unused
        Octet 3: unused
        Octet 4:
        	Bit 1-7: unused
                Bit 0  : UDP enable"
    ::= { wtWebGraphAnalogIn57641UDP 2 }
    
--  wtWebGraphAnalogIn57641Syslog Group
--------------------------------
    
wtWebGraphAnalogIn57641SyslogServerIP OBJECT-TYPE
    SYNTAX OCTET STRING 
    ACCESS read-write
    STATUS mandatory
    DESCRIPTION
        "Name or IP address of the Syslog server, which accepts the Syslog messgaes."
    ::= { wtWebGraphAnalogIn57641Syslog 1 }
    
wtWebGraphAnalogIn57641SyslogServerPort OBJECT-TYPE
    SYNTAX INTEGER
    ACCESS read-write
    STATUS mandatory
    DESCRIPTION
        "Portnumber of the Syslog servers, default 514."
    ::= { wtWebGraphAnalogIn57641Syslog 2 }

wtWebGraphAnalogIn57641SyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebGraphAnalogIn57641Syslog 3 }    

wtWebGraphAnalogIn57641SyslogEnable OBJECT-TYPE
    SYNTAX OCTET STRING 
    ACCESS read-write
    STATUS mandatory
    DESCRIPTION
        "Set bit 0to enable Syslog:
        Octet 1: unused
        Octet 2: unused
        Octet 3: unused
        Octet 4:
        	Bit 1-7: unused
                Bit 0  : Syslog enable"
    ::= { wtWebGraphAnalogIn57641Syslog 4 }
    
--  wtWebGraphAnalogIn57641FTP Group
--------------------------------

wtWebGraphAnalogIn57641FTPServerIP OBJECT-TYPE
    SYNTAX OCTET STRING 
    ACCESS read-write
    STATUS mandatory
    DESCRIPTION
        "Name or IP address of the FTP server, which accepts the FTP messages."
    ::= { wtWebGraphAnalogIn57641FTP 1 }
    
wtWebGraphAnalogIn57641FTPServerControlPort OBJECT-TYPE
    SYNTAX INTEGER
    ACCESS read-write
    STATUS mandatory
    DESCRIPTION
        "Portnumber of the control port of the FTP server, default 21."
    ::= { wtWebGraphAnalogIn57641FTP 2 }
    
wtWebGraphAnalogIn57641FTPUserName OBJECT-TYPE
    SYNTAX OCTET STRING 
    ACCESS read-write
    STATUS mandatory
    DESCRIPTION
        "FTP Loggin: user name."
    ::= { wtWebGraphAnalogIn57641FTP 3 }
    
wtWebGraphAnalogIn57641FTPPassword OBJECT-TYPE
    SYNTAX OCTET STRING 
    ACCESS read-write
    STATUS mandatory
    DESCRIPTION
        "FTP Loggin: user password."
    ::= { wtWebGraphAnalogIn57641FTP 4 }

wtWebGraphAnalogIn57641FTPAccount OBJECT-TYPE
    SYNTAX OCTET STRING 
    ACCESS read-write
    STATUS mandatory
    DESCRIPTION
        "FTP Loggin: name of account."
    ::= { wtWebGraphAnalogIn57641FTP 5 }

wtWebGraphAnalogIn57641FTPOption OBJECT-TYPE
    SYNTAX OCTET STRING 
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebGraphAnalogIn57641FTP 6 }
    
wtWebGraphAnalogIn57641FTPEnable OBJECT-TYPE
    SYNTAX OCTET STRING 
    ACCESS read-write
    STATUS mandatory
    DESCRIPTION
        "Set Bit 0 to enable FTP:
        Octet 1: unused
        Octet 2: unused
        Octet 3: unused
        Octet 4:
        	Bit 1-7: unused
                Bit 0  : FTP enable"
    ::= { wtWebGraphAnalogIn57641FTP 7 }    
    
-- wtWebGraphAnalogIn57641Datalogger Group
--------------------------------

wtWebGraphAnalogIn57641LoggerTimebase OBJECT-TYPE
    SYNTAX INTEGER {
    wtWebGraphAnalogIn57641Datalogger-1Min(1),
    wtWebGraphAnalogIn57641Datalogger-5Min(2),
    wtWebGraphAnalogIn57641Datalogger-15Min(3),
    wtWebGraphAnalogIn57641Datalogger-60Min(4)
    }
    ACCESS read-write
    STATUS mandatory
    DESCRIPTION
        "Time base of the data logger"
    ::= { wtWebGraphAnalogIn57641Datalogger 1 }

wtWebGraphAnalogIn57641LoggerSensorSel OBJECT-TYPE
    SYNTAX OCTET STRING (SIZE(4))
    ACCESS read-write
    STATUS mandatory
    DESCRIPTION
        "Binary coded trigger conditions:
        Octet 1: unused
        Octet 2: unused
        Octet 3: unused
        Octet 4:
        	Bit 0: Sensor 1
        	Bit 1: Sensor 2
        	Bit 2-7: unused"
    ::= { wtWebGraphAnalogIn57641Datalogger 2 }

wtWebGraphAnalogIn57641DisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0: Sensor 1
        	Bit 1: Sensor 2
        	Bit 2-7: unused"
    ::= { wtWebGraphAnalogIn57641Datalogger 3 }    
    
-- Graph Sensor Color Table

wtWebGraphAnalogIn57641SensorColorTable OBJECT-TYPE
    SYNTAX SEQUENCE OF WtWebGraphAnalogIn57641SensorColorEntry
    ACCESS not-accessible
    STATUS mandatory
    DESCRIPTION
        "List of sensor colors for the praphical presentation."
    ::= { wtWebGraphAnalogIn57641Datalogger 4 }

wtWebGraphAnalogIn57641SensorColorEntry OBJECT-TYPE
    SYNTAX WtWebGraphAnalogIn57641SensorColorEntry
    ACCESS not-accessible
    STATUS mandatory
    DESCRIPTION
        "Index numbers of the sensors."
    INDEX  { wtWebGraphAnalogIn57641SensorNo }
    ::= { wtWebGraphAnalogIn57641SensorColorTable 1 }

WtWebGraphAnalogIn57641SensorColorEntry ::= SEQUENCE {
    wtWebGraphAnalogIn57641SensorColor OCTET STRING
}

wtWebGraphAnalogIn57641SensorColor OBJECT-TYPE
    SYNTAX OCTET STRING (SIZE(3))
    ACCESS read-write
    STATUS mandatory
    DESCRIPTION
        "Color of the sensors at the praphical presention."
    ::= { wtWebGraphAnalogIn57641SensorColorEntry 1 }
    
wtWebGraphAnalogIn57641AutoScaleEnable OBJECT-TYPE
    SYNTAX OCTET STRING 
    ACCESS read-write
    STATUS mandatory
    DESCRIPTION
        "If bit 0 is set, vertical auto scale is enabled:
        Octet 1: unused
        Octet 2: unused
        Octet 3: unused
        Octet 4:
        	Bit 1-7: unused
                Bit 0  : Auto Scale enable"
    ::= { wtWebGraphAnalogIn57641Datalogger 5 }
    
wtWebGraphAnalogIn57641VerticalUpperLimit OBJECT-TYPE
    SYNTAX OCTET STRING 
    ACCESS read-write
    STATUS mandatory
    DESCRIPTION
        "This value defines the maximum temperature shown in the graphical presentation,
        if no auto scaling is selected.
        Temperature in degrees with maximum 2 decimal places."
    ::= { wtWebGraphAnalogIn57641Datalogger 6 }

wtWebGraphAnalogIn57641VerticalLowerLimit OBJECT-TYPE
    SYNTAX OCTET STRING 
    ACCESS read-write
    STATUS mandatory
    DESCRIPTION
        "This value defines the minimum temperature shown in the graphical presentation,
        if no auto scaling is selected.
        Temperature in degrees with maximum 2 decimal places."
    ::= { wtWebGraphAnalogIn57641Datalogger 7 }
    
wtWebGraphAnalogIn57641HorizontalZoom OBJECT-TYPE
    SYNTAX INTEGER {
    wtWebGraphAnalogIn57641Zoom-25min(1),
    wtWebGraphAnalogIn57641Zoom-75min(2),
    wtWebGraphAnalogIn57641Zoom-5hrs(3),
    wtWebGraphAnalogIn57641Zoom-30hrs(4),
    wtWebGraphAnalogIn57641Zoom-5days(5),
    wtWebGraphAnalogIn57641Zoom-25days(6)
    }
    ACCESS read-write
    STATUS mandatory
    DESCRIPTION
        "Defines the default zoom stage, if no auto scaling is selected."
    ::= { wtWebGraphAnalogIn57641Datalogger 8 }    

-- wtWebGraphAnalogIn57641Alarm Group
----------------------------

wtWebGraphAnalogIn57641AlarmCount OBJECT-TYPE
    SYNTAX INTEGER (1..8)
    ACCESS read-only
    STATUS mandatory
    DESCRIPTION
        "Number of independent alarms."
    ::= { wtWebGraphAnalogIn57641Alarm 1 }
    
-- Alarm Interface Table

wtWebGraphAnalogIn57641AlarmIfTable OBJECT-TYPE
    SYNTAX SEQUENCE OF WtWebGraphAnalogIn57641AlarmIfEntry
    ACCESS not-accessible
    STATUS mandatory
    DESCRIPTION
        "List of alarm indices."
    ::= { wtWebGraphAnalogIn57641Alarm 2 }

wtWebGraphAnalogIn57641AlarmIfEntry OBJECT-TYPE
    SYNTAX WtWebGraphAnalogIn57641AlarmIfEntry
    ACCESS not-accessible
    STATUS mandatory
    DESCRIPTION
        "Numbers of the alarms."
    INDEX  { wtWebGraphAnalogIn57641AlarmNo }
    ::= { wtWebGraphAnalogIn57641AlarmIfTable 1 }

WtWebGraphAnalogIn57641AlarmIfEntry ::= SEQUENCE {
    wtWebGraphAnalogIn57641AlarmNo INTEGER
}

wtWebGraphAnalogIn57641AlarmNo OBJECT-TYPE
    SYNTAX INTEGER (1..8)
    ACCESS read-only
    STATUS mandatory
    DESCRIPTION
        "Alarm number."
    ::= { wtWebGraphAnalogIn57641AlarmIfEntry 1 }

-- Alarm Table

wtWebGraphAnalogIn57641AlarmTable OBJECT-TYPE
    SYNTAX SEQUENCE OF WtWebGraphAnalogIn57641AlarmEntry
    ACCESS not-accessible
    STATUS mandatory
    DESCRIPTION
        "List of settings depending on the alarm number."
    ::= { wtWebGraphAnalogIn57641Alarm 3 }

wtWebGraphAnalogIn57641AlarmEntry OBJECT-TYPE
    SYNTAX WtWebGraphAnalogIn57641AlarmEntry
    ACCESS not-accessible
    STATUS mandatory
    DESCRIPTION
        "Alarm parameters of the individual alarms."
    INDEX  { wtWebGraphAnalogIn57641AlarmNo }
    ::= { wtWebGraphAnalogIn57641AlarmTable 1 }

WtWebGraphAnalogIn57641AlarmEntry ::= SEQUENCE {
    wtWebGraphAnalogIn57641AlarmTrigger			OCTET STRING,
    wtWebGraphAnalogIn57641AlarmMin			OCTET STRING,
    wtWebGraphAnalogIn57641AlarmMax			OCTET STRING,
    wtWebGraphAnalogIn57641AlarmHysteresis		OCTET STRING,
    wtWebGraphAnalogIn57641AlarmDelay			OCTET STRING,
    wtWebGraphAnalogIn57641AlarmInterval		OCTET STRING,
    wtWebGraphAnalogIn57641AlarmEnable			OCTET STRING,
    wtWebGraphAnalogIn57641AlarmEMailAddr		OCTET STRING,
    wtWebGraphAnalogIn57641AlarmMailSubject		OCTET STRING,
    wtWebGraphAnalogIn57641AlarmMailText		OCTET STRING,
    wtWebGraphAnalogIn57641AlarmManagerIP		OCTET STRING,
    wtWebGraphAnalogIn57641AlarmTrapText		OCTET STRING,
    wtWebGraphAnalogIn57641AlarmMailOptions		OCTET STRING,
    wtWebGraphAnalogIn57641AlarmTcpIpAddr		OCTET STRING,
    wtWebGraphAnalogIn57641AlarmTcpPort			INTEGER,
    wtWebGraphAnalogIn57641AlarmTcpText			OCTET STRING,
    wtWebGraphAnalogIn57641AlarmClearMailSubject	OCTET STRING,
    wtWebGraphAnalogIn57641AlarmClearMailText		OCTET STRING,
    wtWebGraphAnalogIn57641AlarmClearTrapText		OCTET STRING,
    wtWebGraphAnalogIn57641AlarmClearTcpText		OCTET STRING,
    wtWebGraphAnalogIn57641Alarm2Min			OCTET STRING,
    wtWebGraphAnalogIn57641Alarm2Max			OCTET STRING,
    wtWebGraphAnalogIn57641Alarm2Hysteresis		OCTET STRING,
    wtWebGraphAnalogIn57641AlarmSyslogIpAddr		OCTET STRING,
    wtWebGraphAnalogIn57641AlarmSyslogPort		INTEGER,
    wtWebGraphAnalogIn57641AlarmSyslogText		OCTET STRING,
    wtWebGraphAnalogIn57641AlarmSyslogClearText		OCTET STRING,
    wtWebGraphAnalogIn57641AlarmFtpDataPort		OCTET STRING,
    wtWebGraphAnalogIn57641AlarmFtpFileName		OCTET STRING,
    wtWebGraphAnalogIn57641AlarmFtpText			OCTET STRING,
    wtWebGraphAnalogIn57641AlarmFtpClearText		OCTET STRING,
    wtWebGraphAnalogIn57641AlarmFtpOption		OCTET STRING,
    wtWebGraphAnalogIn57641AlarmTimerCron		OCTET STRING

}

wtWebGraphAnalogIn57641AlarmTrigger OBJECT-TYPE
    SYNTAX OCTET STRING (SIZE(4))
    ACCESS read-write
    STATUS mandatory
    DESCRIPTION
        "Binary coded trigger conditions:
        Octet 1: unused
        Octet 2: unused
        Octet 3:
        	Bit 0: Timer
        	Bit 1: ColdStart
        	Bit 2: WarmStart
        	
        Octet 4:
        	Bit 0: Sensor 1
        	Bit 1: Sensor 2
        	Bit 2-7: unused"
    ::= { wtWebGraphAnalogIn57641AlarmEntry 1 }

wtWebGraphAnalogIn57641AlarmMin OBJECT-TYPE
    SYNTAX OCTET STRING 
    ACCESS read-write
    STATUS mandatory
    DESCRIPTION
        "Minimum temperature in degrees with maximum 2 decimal places."
    ::= { wtWebGraphAnalogIn57641AlarmEntry 2 }

wtWebGraphAnalogIn57641AlarmMax OBJECT-TYPE
    SYNTAX OCTET STRING 
    ACCESS read-write
    STATUS mandatory
    DESCRIPTION
        "Maximum temperature in degrees with maximum 2 decimal places."
    ::= { wtWebGraphAnalogIn57641AlarmEntry 3 }
    
wtWebGraphAnalogIn57641AlarmHysteresis OBJECT-TYPE
    SYNTAX OCTET STRING 
    ACCESS read-write
    STATUS mandatory
    DESCRIPTION
        "Temperature changes of this size clears the alarm state (MAX-hyst, MIN+hyst.)
        , in degrees with maximum 2 decimal places."
    ::= { wtWebGraphAnalogIn57641AlarmEntry 4 }

wtWebGraphAnalogIn57641AlarmDelay OBJECT-TYPE
    SYNTAX OCTET STRING 
    ACCESS read-write
    STATUS mandatory
    DESCRIPTION
        "Alarm will be delayed by setting this time while stable alarm 
        condition occur (time in minutes)."
    ::= { wtWebGraphAnalogIn57641AlarmEntry 5 }
        

wtWebGraphAnalogIn57641AlarmInterval OBJECT-TYPE
    SYNTAX OCTET STRING 
    ACCESS read-write
    STATUS mandatory
    DESCRIPTION
        "Send interval for alarm messages."
    ::= { wtWebGraphAnalogIn57641AlarmEntry 6 }

wtWebGraphAnalogIn57641AlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  TCP Client enable"
    ::= { wtWebGraphAnalogIn57641AlarmEntry 7 }

wtWebGraphAnalogIn57641AlarmEMailAddr OBJECT-TYPE
    SYNTAX OCTET STRING 
    ACCESS read-write
    STATUS mandatory
    DESCRIPTION
        "E-Mail address for sending the alarm mail to."
    ::= { wtWebGraphAnalogIn57641AlarmEntry 8 }

wtWebGraphAnalogIn57641AlarmMailSubject OBJECT-TYPE
    SYNTAX OCTET STRING 
    ACCESS read-write
    STATUS mandatory
    DESCRIPTION
        "Subject line for alarm mail."
    ::= { wtWebGraphAnalogIn57641AlarmEntry 9 }

wtWebGraphAnalogIn57641AlarmMailText OBJECT-TYPE
    SYNTAX OCTET STRING 
    ACCESS read-write
    STATUS mandatory
    DESCRIPTION
        "Alarm mail text: <Tn> provides the current temperature; n = 1..8.
        <Z> provides the current time."
    ::= { wtWebGraphAnalogIn57641AlarmEntry 10 }

wtWebGraphAnalogIn57641AlarmManagerIP OBJECT-TYPE
    SYNTAX OCTET STRING 
    ACCESS read-write
    STATUS mandatory
    DESCRIPTION
        "Name or IP address of the SNMP Manager which accepts the trap."
    ::= { wtWebGraphAnalogIn57641AlarmEntry 11 }

wtWebGraphAnalogIn57641AlarmTrapText OBJECT-TYPE
    SYNTAX OCTET STRING 
    ACCESS read-write
    STATUS mandatory
    DESCRIPTION
        "This text is sent in the trap body."
    ::= { wtWebGraphAnalogIn57641AlarmEntry 12 }
    
wtWebGraphAnalogIn57641AlarmMailOptions OBJECT-TYPE
    SYNTAX OCTET STRING (SIZE(4))
    ACCESS read-write
    STATUS mandatory
    DESCRIPTION
        "Binary coded options:
        Octet 1: unused
        Octet 2: unused
        Octet 3: unused
        Octet 4:
		Bit 0  :	Attach Thermo.csv Enable
		Bit 1  :	CSV-Data_since_last_report
        	Bit 2-7:	unused"
    ::= { wtWebGraphAnalogIn57641AlarmEntry 13 }    
    
wtWebGraphAnalogIn57641AlarmTcpIpAddr OBJECT-TYPE
    SYNTAX OCTET STRING 
    ACCESS read-write
    STATUS mandatory
    DESCRIPTION
        "Name or IP address of the TCP server which accepts the trap."
    ::= { wtWebGraphAnalogIn57641AlarmEntry 14 }    

wtWebGraphAnalogIn57641AlarmTcpPort OBJECT-TYPE
    SYNTAX INTEGER (1..65535) 
    ACCESS read-write
    STATUS mandatory
    DESCRIPTION
        "Port number of the TCP server which accepts the trap."
    ::= { wtWebGraphAnalogIn57641AlarmEntry 15 }    

wtWebGraphAnalogIn57641AlarmTcpText OBJECT-TYPE
    SYNTAX OCTET STRING 
    ACCESS read-write
    STATUS mandatory
    DESCRIPTION
        "This text is sent in the TCP trap body."
    ::= { wtWebGraphAnalogIn57641AlarmEntry 16 }

wtWebGraphAnalogIn57641AlarmClearMailSubject OBJECT-TYPE
    SYNTAX OCTET STRING 
    ACCESS read-write
    STATUS mandatory
    DESCRIPTION
        "Subject line for alarm clear mail."
    ::= { wtWebGraphAnalogIn57641AlarmEntry 17 }

wtWebGraphAnalogIn57641AlarmClearMailText OBJECT-TYPE
    SYNTAX OCTET STRING 
    ACCESS read-write
    STATUS mandatory
    DESCRIPTION
        "Alarm clear mail text: <Tn> provides the current temperature; n = 1..8.
        <Z> provides the current time."
    ::= { wtWebGraphAnalogIn57641AlarmEntry 18 }

wtWebGraphAnalogIn57641AlarmClearTrapText OBJECT-TYPE
    SYNTAX OCTET STRING 
    ACCESS read-write
    STATUS mandatory
    DESCRIPTION
        "This text is sent in the trap body."
    ::= { wtWebGraphAnalogIn57641AlarmEntry 19 }

wtWebGraphAnalogIn57641AlarmClearTcpText OBJECT-TYPE
    SYNTAX OCTET STRING 
    ACCESS read-write
    STATUS mandatory
    DESCRIPTION
        "This text is sent in the TCP trap body."
    ::= { wtWebGraphAnalogIn57641AlarmEntry 20 }
    
wtWebGraphAnalogIn57641Alarm2Min OBJECT-TYPE
    SYNTAX OCTET STRING 
    ACCESS read-write
    STATUS mandatory
    DESCRIPTION
        "Minimum rel. Humidity in percent with maximum 2 decimal places."
    ::= { wtWebGraphAnalogIn57641AlarmEntry 21 }

wtWebGraphAnalogIn57641Alarm2Max OBJECT-TYPE
    SYNTAX OCTET STRING 
    ACCESS read-write
    STATUS mandatory
    DESCRIPTION
        "Maximum rel.Humidity in percent with maximum 2 decimal places."
    ::= { wtWebGraphAnalogIn57641AlarmEntry 22 }

wtWebGraphAnalogIn57641Alarm2Hysteresis OBJECT-TYPE
    SYNTAX OCTET STRING 
    ACCESS read-write
    STATUS mandatory
    DESCRIPTION
        "Hysterese rel. Humidity in percent with maximum 2 decimal places."
    ::= { wtWebGraphAnalogIn57641AlarmEntry 23 }

wtWebGraphAnalogIn57641AlarmSyslogIpAddr OBJECT-TYPE
    SYNTAX IpAddress 
    ACCESS read-write
    STATUS mandatory
    DESCRIPTION
        "IP address of the syslog server to which the Webio device should send syslog messages."
    ::= { wtWebGraphAnalogIn57641AlarmEntry 24 }    

wtWebGraphAnalogIn57641AlarmSyslogPort OBJECT-TYPE
    SYNTAX INTEGER (1..65535) 
    ACCESS read-write
    STATUS mandatory
    DESCRIPTION
        "Port number of the syslog server to which the Webio device should send syslog messages."
    ::= { wtWebGraphAnalogIn57641AlarmEntry 25 }    

wtWebGraphAnalogIn57641AlarmSyslogText OBJECT-TYPE
    SYNTAX OCTET STRING 
    ACCESS read-write
    STATUS mandatory
    DESCRIPTION
        "Every message starts with the priority key, a time stamp and the host ip address, according RFC3164.
        This text appears in the following syslog message body."
    ::= { wtWebGraphAnalogIn57641AlarmEntry 26 }
    
wtWebGraphAnalogIn57641AlarmSyslogClearText OBJECT-TYPE
    SYNTAX OCTET STRING 
    ACCESS read-write
    STATUS mandatory
    DESCRIPTION
        "Every message starts with the priority key, a time stamp and the host ip address, according RFC3164.
        This text appears in the following syslog message body of a alarm clear message."
    ::= { wtWebGraphAnalogIn57641AlarmEntry 27 }
    
wtWebGraphAnalogIn57641AlarmFtpDataPort OBJECT-TYPE
    SYNTAX OCTET STRING 
    ACCESS read-write
    STATUS mandatory
    DESCRIPTION
        "Local data port: 1..65535 or AUTO: the next free port will be assigned."
    ::= { wtWebGraphAnalogIn57641AlarmEntry 28 }
    
wtWebGraphAnalogIn57641AlarmFtpFileName OBJECT-TYPE
    SYNTAX OCTET STRING 
    ACCESS read-write
    STATUS mandatory
    DESCRIPTION
        "Name of the file including path informations."
    ::= { wtWebGraphAnalogIn57641AlarmEntry 29 }
    
wtWebGraphAnalogIn57641AlarmFtpText OBJECT-TYPE
    SYNTAX OCTET STRING 
    ACCESS read-write
    STATUS mandatory
    DESCRIPTION
        "Message text to store on the FTP server."
    ::= { wtWebGraphAnalogIn57641AlarmEntry 30 }

wtWebGraphAnalogIn57641AlarmFtpClearText OBJECT-TYPE
    SYNTAX OCTET STRING 
    ACCESS read-write
    STATUS mandatory
    DESCRIPTION
        "Alarm clear message to store on the FTP server."
    ::= { wtWebGraphAnalogIn57641AlarmEntry 31 }
    
wtWebGraphAnalogIn57641AlarmFtpOption OBJECT-TYPE
    SYNTAX OCTET STRING (SIZE(4))
    ACCESS read-write
    STATUS mandatory
    DESCRIPTION
        "Binary coded options, select only one option at the same time:
        STORE  = replace file
        APPEND = append message at the end of the file
        
        Octet 1: unused
        Octet 2: unused
        Octet 3: unused
        Octet 4:
		Bit 0  :	STORE
		Bit 1  :	APPEND
        	Bit 2-7:	unused"
    ::= { wtWebGraphAnalogIn57641AlarmEntry 32 }      
    
wtWebGraphAnalogIn57641AlarmTimerCron OBJECT-TYPE
    SYNTAX OCTET STRING
    ACCESS read-write
    STATUS mandatory
    DESCRIPTION
        "This entry contains 5 space or tab seperated text fields for time trigger definition.
        Each field must match with the actual time to trigger a message, weekday and day of month
        are interpreted separatley.
        1: Minutes	Range 0-59
        2. Hours	Range 0-23, 0 is midnight
        3: Day of month	Range 1-31
        4: Month	Range 1-12
        5: Weekday	Range 0-6, 0 is sunday
        
        Syntax for every field:
         - an asterix (*) enables every possible setting of a field
         - single numbers seperated by commas
         - a partition within the allowed range (1-5)
         - step size within an partition of the allowed range (0-59/2: every second minute)."
    ::= { wtWebGraphAnalogIn57641AlarmEntry 33 }      

-- wtWebGraphAnalogIn57641GraphicsBase Group
----------------------------

wtWebGraphAnalogIn57641GraphicsBaseEnable OBJECT-TYPE
    SYNTAX OCTET STRING 
    ACCESS read-write
    STATUS mandatory
    DESCRIPTION
        "Defines the viewing options of the graphic:
        Octet 1: unused
        Octet 2: unused
        Octet 3: unused
        Octet 4:
                Bit 0  : Auto scroll enable
                Bit 1  : Show table
                Bit 2  : Show graph
                Bit 3  : Show control buttons
                Bit 4  : Show config menu
                Bit 5-7: unused"
    ::= { wtWebGraphAnalogIn57641GraphicsBase 1 }

wtWebGraphAnalogIn57641GraphicsBaseWidth OBJECT-TYPE
    SYNTAX INTEGER 
    ACCESS read-write
    STATUS mandatory
    DESCRIPTION
        "Defines the width of the graphic in pixels."
    ::= { wtWebGraphAnalogIn57641GraphicsBase 2 }
    
wtWebGraphAnalogIn57641GraphicsBaseHeight OBJECT-TYPE
        SYNTAX INTEGER 
        ACCESS read-write
        STATUS mandatory
        DESCRIPTION
            "Defines the height of the graphic in pixels."
        ::= { wtWebGraphAnalogIn57641GraphicsBase 3 }

wtWebGraphAnalogIn57641GraphicsBaseFrameColor OBJECT-TYPE
    SYNTAX OCTET STRING (SIZE(3))
    ACCESS read-write
    STATUS mandatory
    DESCRIPTION
        "Frame color definition in RGB."
    ::= { wtWebGraphAnalogIn57641GraphicsBase 4 }

wtWebGraphAnalogIn57641GraphicsBaseBackgroundColor OBJECT-TYPE
    SYNTAX OCTET STRING (SIZE(3))
    ACCESS read-write
    STATUS mandatory
    DESCRIPTION
        "Background color definition in RGB."
    ::= { wtWebGraphAnalogIn57641GraphicsBase 5 }
    
wtWebGraphAnalogIn57641GraphicsBasePollingrate OBJECT-TYPE
        SYNTAX INTEGER 
        ACCESS read-write
        STATUS mandatory
        DESCRIPTION
            "Defines the pollingrate in seconds, 
            which defines the refreshing intervall of the graphic."
        ::= { wtWebGraphAnalogIn57641GraphicsBase 6 }
   
-- wtWebGraphAnalogIn57641GraphicsSelect Group
----------------------------

wtWebGraphAnalogIn57641GraphicsSelectDisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0: Sensor 1
        	Bit 1: Sensor 2
        	Bit 2: Sensor 3
        	Bit 3: Sensor 4
        	Bit 4: Sensor 5
        	Bit 5: Sensor 6
        	Bit 6: Sensor 7
        	Bit 7: Sensor 8"
    ::= { wtWebGraphAnalogIn57641GraphicsSelect 1 }   
    
wtWebGraphAnalogIn57641GraphicsSelectDisplayShowExtrem OBJECT-TYPE
    SYNTAX OCTET STRING (SIZE(4))
    ACCESS read-write
    STATUS mandatory
    DESCRIPTION
        "Binary coded sensor selection:
        only selected sensors will be shown with minima and maxima:
        Octet 1: unused
        Octet 2: unused
        Octet 3: unused
        Octet 4:
        	Bit 0: Sensor 1
        	Bit 1: Sensor 2
        	Bit 2: Sensor 3
        	Bit 3: Sensor 4
        	Bit 4: Sensor 5
        	Bit 5: Sensor 6
        	Bit 6: Sensor 7
        	Bit 7: Sensor 8"
     ::= { wtWebGraphAnalogIn57641GraphicsSelect 2 }   

-- Graph Sensor Color Table

wtWebGraphAnalogIn57641SensorColor2Table OBJECT-TYPE
    SYNTAX SEQUENCE OF WtWebGraphAnalogIn57641SensorColor2Entry
    ACCESS not-accessible
    STATUS mandatory
    DESCRIPTION
        "List of sensor colors for the praphical presentation."
    ::= { wtWebGraphAnalogIn57641GraphicsSelect 3 }

wtWebGraphAnalogIn57641SensorColor2Entry OBJECT-TYPE
    SYNTAX WtWebGraphAnalogIn57641SensorColor2Entry
    ACCESS not-accessible
    STATUS mandatory
    DESCRIPTION
        "Numbers of the sensors."
    INDEX  { wtWebGraphAnalogIn57641SensorNo }
    ::= { wtWebGraphAnalogIn57641SensorColor2Table 1 }

WtWebGraphAnalogIn57641SensorColor2Entry ::= SEQUENCE {
    wtWebGraphAnalogIn57641GraphicsSensorColor OCTET STRING,
    wtWebGraphAnalogIn57641GraphicsSelectScale OCTET STRING
}

wtWebGraphAnalogIn57641GraphicsSensorColor OBJECT-TYPE
    SYNTAX OCTET STRING (SIZE(3))
    ACCESS read-write
    STATUS mandatory
    DESCRIPTION
        "Color of the sensors at the praphical presention."
    ::= { wtWebGraphAnalogIn57641SensorColor2Entry 1 }
    
wtWebGraphAnalogIn57641GraphicsSelectScale OBJECT-TYPE
    SYNTAX OCTET STRING 
    ACCESS read-write
    STATUS mandatory
    DESCRIPTION
        "Assignes one of 4 scales to a sensor:
        Octet 1: unused
        Octet 2: unused
        Octet 3: unused
        Octet 4:
                Bit 0  : Use Scale 1
                Bit 1  : Use Scale 2
                Bit 2  : Use Scale 3
                Bit 3  : Use Scale 4
                Bit 4-7: unused"
    ::= { wtWebGraphAnalogIn57641SensorColor2Entry 2 }
   
-- wtWebGraphAnalogIn57641GraphicsScale Group
----------------------------

wtWebGraphAnalogIn57641GraphicsScaleAutoScaleEnable OBJECT-TYPE
    SYNTAX OCTET STRING 
    ACCESS read-write
    STATUS mandatory
    DESCRIPTION
        "Select the Auto Scale Mode:
        Octet 1: unused
        Octet 2: unused
        Octet 3: unused
        Octet 4:
                Bit 0  : Scale 1 Auto scale enable
                Bit 1  : Scale 2 Auto scale enable
                Bit 2  : Scale 3 Auto scale enable
                Bit 3  : Scale 4 Auto scale enable
                Bit 4-7: unused"
    ::= { wtWebGraphAnalogIn57641GraphicsScale 1 }


wtWebGraphAnalogIn57641GraphicsScaleAutoFitEnable OBJECT-TYPE
    SYNTAX OCTET STRING 
    ACCESS read-write
    STATUS mandatory
    DESCRIPTION
        "Select the Auto Fit Mode::
        Octet 1: unused
        Octet 2: unused
        Octet 3: unused
        Octet 4:
                Bit 0  : Scale 1 Auto fit enable
                Bit 1  : Scale 2 Auto fit enable
                Bit 2  : Scale 3 Auto fit enable
                Bit 3  : Scale 4 Auto fit enable
                Bit 4-7: unused"
    ::= { wtWebGraphAnalogIn57641GraphicsScale 2 }

wtWebGraphAnalogIn57641GraphicsScale1Min OBJECT-TYPE
    SYNTAX INTEGER
    ACCESS read-only
    STATUS mandatory
    DESCRIPTION
        "Scale 1: Minimum."
    ::= { wtWebGraphAnalogIn57641GraphicsScale 3 }
   
wtWebGraphAnalogIn57641GraphicsScale2Min OBJECT-TYPE
    SYNTAX INTEGER
    ACCESS read-only
    STATUS mandatory
    DESCRIPTION
        "Scale 2: Minimum."
    ::= { wtWebGraphAnalogIn57641GraphicsScale 4 }

wtWebGraphAnalogIn57641GraphicsScale3Min OBJECT-TYPE
    SYNTAX INTEGER
    ACCESS read-only
    STATUS mandatory
    DESCRIPTION
        "Scale 3: Minimum."
    ::= { wtWebGraphAnalogIn57641GraphicsScale 5 }

wtWebGraphAnalogIn57641GraphicsScale4Min OBJECT-TYPE
    SYNTAX INTEGER
    ACCESS read-only
    STATUS mandatory
    DESCRIPTION
        "Scale 4: Minimum."
    ::= { wtWebGraphAnalogIn57641GraphicsScale 6 }

wtWebGraphAnalogIn57641GraphicsScale1Max OBJECT-TYPE
    SYNTAX INTEGER
    ACCESS read-only
    STATUS mandatory
    DESCRIPTION
        "Scale 1: Maximum."
    ::= { wtWebGraphAnalogIn57641GraphicsScale 7 }

wtWebGraphAnalogIn57641GraphicsScale2Max OBJECT-TYPE
    SYNTAX INTEGER
    ACCESS read-only
    STATUS mandatory
    DESCRIPTION
        "Scale 2: Maximum."
    ::= { wtWebGraphAnalogIn57641GraphicsScale 8 }

wtWebGraphAnalogIn57641GraphicsScale3Max OBJECT-TYPE
    SYNTAX INTEGER
    ACCESS read-only
    STATUS mandatory
    DESCRIPTION
        "Scale 3: Maximum."
    ::= { wtWebGraphAnalogIn57641GraphicsScale 9 }

wtWebGraphAnalogIn57641GraphicsScale4Max OBJECT-TYPE
    SYNTAX INTEGER
    ACCESS read-only
    STATUS mandatory
    DESCRIPTION
        "Scale 4: Maximum."
    ::= { wtWebGraphAnalogIn57641GraphicsScale 10 }

wtWebGraphAnalogIn57641GraphicsScale1Unit OBJECT-TYPE
    SYNTAX OCTET STRING
    ACCESS read-only
    STATUS mandatory
    DESCRIPTION
        "Scale 1: Unit."
    ::= { wtWebGraphAnalogIn57641GraphicsScale 11 }

wtWebGraphAnalogIn57641GraphicsScale2Unit OBJECT-TYPE
    SYNTAX OCTET STRING
    ACCESS read-only
    STATUS mandatory
    DESCRIPTION
        "Scale 2: Unit."
    ::= { wtWebGraphAnalogIn57641GraphicsScale 12 }

wtWebGraphAnalogIn57641GraphicsScale3Unit OBJECT-TYPE
    SYNTAX OCTET STRING
    ACCESS read-only
    STATUS mandatory
    DESCRIPTION
        "Scale 3: Unit."
    ::= { wtWebGraphAnalogIn57641GraphicsScale 13 }

wtWebGraphAnalogIn57641GraphicsScale4Unit OBJECT-TYPE
    SYNTAX OCTET STRING
    ACCESS read-only
    STATUS mandatory
    DESCRIPTION
        "Scale 4: Unit."
    ::= { wtWebGraphAnalogIn57641GraphicsScale 14 }    

    
-- wtWebGraphAnalogIn57641Ports Group
----------------------------

-- Table

wtWebGraphAnalogIn57641PortTable OBJECT-TYPE
    SYNTAX SEQUENCE OF WtWebGraphAnalogIn57641PortEntry
    ACCESS not-accessible
    STATUS mandatory
    DESCRIPTION
        "List of settings depending on the sensor number."
    ::= { wtWebGraphAnalogIn57641Ports 1 }

wtWebGraphAnalogIn57641PortEntry OBJECT-TYPE
    SYNTAX WtWebGraphAnalogIn57641PortEntry
    ACCESS not-accessible
    STATUS mandatory
    DESCRIPTION
        "Sensor parameters for the individual sensors."
    INDEX  { wtWebGraphAnalogIn57641SensorNo }
    ::= { wtWebGraphAnalogIn57641PortTable 1 }

WtWebGraphAnalogIn57641PortEntry ::= SEQUENCE {
    wtWebGraphAnalogIn57641PortName		OCTET STRING,
    wtWebGraphAnalogIn57641PortText		OCTET STRING,
    wtWebGraphAnalogIn57641PortOffset1		OCTET STRING,
    wtWebGraphAnalogIn57641SetPoint1		OCTET STRING,
    wtWebGraphAnalogIn57641PortOffset2		OCTET STRING,
    wtWebGraphAnalogIn57641SetPoint2		OCTET STRING,
    wtWebGraphAnalogIn57641PortComment		OCTET STRING,
    wtWebGraphAnalogIn57641PortSensorSelect	OCTET STRING,
    wtWebGraphAnalogIn57641PortUnit		OCTET STRING,
    wtWebGraphAnalogIn57641PortScale0		OCTET STRING,
    wtWebGraphAnalogIn57641PortScale100		OCTET STRING
}

wtWebGraphAnalogIn57641PortName OBJECT-TYPE
    SYNTAX OCTET STRING 
    ACCESS read-write
    STATUS mandatory
    DESCRIPTION
        "Name of the sensor."
    ::= { wtWebGraphAnalogIn57641PortEntry 1 }

wtWebGraphAnalogIn57641PortText OBJECT-TYPE
    SYNTAX OCTET STRING 
    ACCESS read-write
    STATUS mandatory
    DESCRIPTION
        "Description of the sensor."
    ::= { wtWebGraphAnalogIn57641PortEntry 2 }

wtWebGraphAnalogIn57641PortOffset1 OBJECT-TYPE
    SYNTAX OCTET STRING 
    ACCESS read-write
    STATUS mandatory
    DESCRIPTION
        "Offset calibration: Offset in degrees with maximum 2 decimal places at set point 1."
    ::= { wtWebGraphAnalogIn57641PortEntry 3 }

wtWebGraphAnalogIn57641SetPoint1 OBJECT-TYPE
    SYNTAX OCTET STRING 
    ACCESS read-write
    STATUS mandatory
    DESCRIPTION
        "Offset calibration: set point 1 in degrees with maximum 2 decimal places."
    ::= { wtWebGraphAnalogIn57641PortEntry 4 }

wtWebGraphAnalogIn57641PortOffset2 OBJECT-TYPE
    SYNTAX OCTET STRING 
    ACCESS read-write
    STATUS mandatory
    DESCRIPTION
        "Offset calibration: Offset in degrees with maximum 2 decimal places at set point 2."
    ::= { wtWebGraphAnalogIn57641PortEntry 5 }

wtWebGraphAnalogIn57641SetPoint2 OBJECT-TYPE
    SYNTAX OCTET STRING 
    ACCESS read-write
    STATUS mandatory
    DESCRIPTION
        "Offset calibration: set point 2 in degrees with maximum 2 decimal places."
    ::= { wtWebGraphAnalogIn57641PortEntry 6 }

wtWebGraphAnalogIn57641PortComment OBJECT-TYPE
    SYNTAX OCTET STRING 
    ACCESS read-write
    STATUS mandatory
    DESCRIPTION
        "Offset calibration: informations of date, name of operator, reference devices."
    ::= { wtWebGraphAnalogIn57641PortEntry 7 }   

wtWebGraphAnalogIn57641PortSensorSelect OBJECT-TYPE
    SYNTAX OCTET STRING (SIZE(4))
    ACCESS read-write
    STATUS mandatory
    DESCRIPTION
        "Binary coded options for sensor 1:
        Octet 1: unused
        Octet 2: unused
        Octet 3: unused
        Octet 4:
		Bit 0  :	0-20mA (default)
		Bit 1  :	4-20mA
		Bit 2  :	Disconnect
        	Bit 3-7:	unused
        
        Binary coded options for sensor 2:
	Octet 1: unused
	Octet 2: unused
	Octet 3: unused
	Octet 4:
		Bit 0  :	0-10V (default)
		Bit 1  :	Disconnect
        	Bit 2-7:	unused"
    ::= { wtWebGraphAnalogIn57641PortEntry 8 }    
    
wtWebGraphAnalogIn57641PortUnit OBJECT-TYPE
    SYNTAX OCTET STRING 
    ACCESS read-write
    STATUS mandatory
    DESCRIPTION
        "User scale: displayed unit."
    ::= { wtWebGraphAnalogIn57641PortEntry 9 }   
    
wtWebGraphAnalogIn57641PortScale0 OBJECT-TYPE
    SYNTAX OCTET STRING 
    ACCESS read-write
    STATUS mandatory
    DESCRIPTION
        "User scale: displayed value in 1/1000 at 0% full scale range.
        Range: -999999.999 to 999999.999"
    ::= { wtWebGraphAnalogIn57641PortEntry 10 }   

wtWebGraphAnalogIn57641PortScale100 OBJECT-TYPE
    SYNTAX OCTET STRING 
    ACCESS read-write
    STATUS mandatory
    DESCRIPTION
        "User scale: displayed value in 1/1000 at 100% full scale range.
        Range: -999999.999 to 999999.999"
    ::= { wtWebGraphAnalogIn57641PortEntry 11 }   

-- wtWebGraphAnalogIn57641Manufact Group
----------------------------

wtWebGraphAnalogIn57641MfName OBJECT-TYPE
    SYNTAX OCTET STRING 
    ACCESS read-write
    STATUS mandatory
    DESCRIPTION
        "Manufacturer company name"
    ::= { wtWebGraphAnalogIn57641Manufact 1 }

wtWebGraphAnalogIn57641MfAddr OBJECT-TYPE
    SYNTAX OCTET STRING 
    ACCESS read-write
    STATUS mandatory
    DESCRIPTION
        "Manufacturer address."
    ::= { wtWebGraphAnalogIn57641Manufact 2 }

wtWebGraphAnalogIn57641MfHotline OBJECT-TYPE
    SYNTAX OCTET STRING 
    ACCESS read-write
    STATUS mandatory
    DESCRIPTION
        "Manufacturer hotline."
    ::= { wtWebGraphAnalogIn57641Manufact 3 }

wtWebGraphAnalogIn57641MfInternet OBJECT-TYPE
    SYNTAX OCTET STRING 
    ACCESS read-write
    STATUS mandatory
    DESCRIPTION
        "Manufacturer Internet address."
    ::= { wtWebGraphAnalogIn57641Manufact 4 }

wtWebGraphAnalogIn57641MfDeviceTyp OBJECT-TYPE
    SYNTAX OCTET STRING 
    ACCESS read-write
    STATUS mandatory
    DESCRIPTION
        "Manufacturer device name (model number)."
    ::= { wtWebGraphAnalogIn57641Manufact 5 }

wtWebGraphAnalogIn57641MfOrderNo OBJECT-TYPE
    SYNTAX OCTET STRING 
    ACCESS read-write
    STATUS mandatory
    DESCRIPTION
        "Manufacturer part number."
    ::= { wtWebGraphAnalogIn57641Manufact 6 }

-- wtWebGraphAnalogIn57641Diag Group
----------------------------

wtWebGraphAnalogIn57641DiagErrorCount OBJECT-TYPE
    SYNTAX INTEGER
    ACCESS read-only
    STATUS mandatory
    DESCRIPTION
        "Number of entries in the error memory."
    ::= { wtWebGraphAnalogIn57641Diag 1 }

wtWebGraphAnalogIn57641DiagBinaryError OBJECT-TYPE
    SYNTAX OCTET STRING 
    ACCESS read-only
    STATUS mandatory
    DESCRIPTION
        "Error causes coded bit-by-bit."
    ::= { wtWebGraphAnalogIn57641Diag 2 }

wtWebGraphAnalogIn57641DiagErrorIndex OBJECT-TYPE
    SYNTAX INTEGER
    ACCESS read-write
    STATUS mandatory
    DESCRIPTION
        "The value of this variable is used as an index to read 
        an error massege from wtWebGraphAnalogIn57641DiagErrorMessage.
        Errors are numbered from 1 to wtWebGraphAnalogIn57641DiagErrorCount.
        Writing a valid value into this variable, making the appropriate 
        message readable from wtWebGraphAnalogIn57641DiagErrorMessage."
    ::= { wtWebGraphAnalogIn57641Diag 3 }

wtWebGraphAnalogIn57641DiagErrorMessage OBJECT-TYPE
    SYNTAX OCTET STRING 
    ACCESS read-only
    STATUS mandatory
    DESCRIPTION
        "Using wtWebGraphAnalogIn57641DiagErrorIndex as an index, the appropriate message is available."
    ::= { wtWebGraphAnalogIn57641Diag 4 }
    
wtWebGraphAnalogIn57641DiagErrorClear OBJECT-TYPE
    SYNTAX INTEGER
    ACCESS write-only
    STATUS mandatory
    DESCRIPTION
        "Writing 1 into this variable clears all diagnosis messages."
    ::= { wtWebGraphAnalogIn57641Diag 5 }

-- TRAP DEFINITIONS

-- Diese SNMP-Traps werden gesendet, wenn die Alarmtriggerbedingungen zutreffen 

wtWebGraphAnalogIn57641Alert1 TRAP-TYPE
    ENTERPRISE  wtWebGraphAnalogIn57641
    VARIABLES   { wtWebGraphAnalogIn57641AlarmTrapText }
    DESCRIPTION
        "This SNMP trap is generated when Alarm 1 was triggered,
        SNMP trap enable is set and
        SNMP is enabled."
    -- NMS trap annotation
    --#TYPE "Thermo-Hygrometer Alarm 1"
    --#SUMMARY "Alarm 1: %s"
    --#ARGUMENTS {0}
    --#SEVERITY INFORMATIONAL
    --#TIMEINDEX 99
    --#STATE OPERATIONAL    
    ::= 31

wtWebGraphAnalogIn57641Alert2 TRAP-TYPE
    ENTERPRISE  wtWebGraphAnalogIn57641
    VARIABLES   { wtWebGraphAnalogIn57641AlarmTrapText }
    DESCRIPTION
        "This SNMP trap is generated when Alarm 2 was triggered,
        SNMP trap enable is set and
        SNMP is enabled."
    -- NMS trap annotation
    --#TYPE "Thermo-Hygrometer Alarm 2"
    --#SUMMARY "Alarm 2: %s"
    --#ARGUMENTS {0}
    --#SEVERITY INFORMATIONAL
    --#TIMEINDEX 99
    --#STATE OPERATIONAL    
    ::= 32

wtWebGraphAnalogIn57641Alert3 TRAP-TYPE
    ENTERPRISE  wtWebGraphAnalogIn57641
    VARIABLES   { wtWebGraphAnalogIn57641AlarmTrapText }
    DESCRIPTION
        "This SNMP trap is generated when Alarm 3 was triggered,
        SNMP trap enable is set and
        SNMP is enabled."
    -- NMS trap annotation
    --#TYPE "Thermo-Hygrometer Alarm 3"
    --#SUMMARY "Alarm 3: %s"
    --#ARGUMENTS {0}
    --#SEVERITY INFORMATIONAL
    --#TIMEINDEX 99
    --#STATE OPERATIONAL    
    ::= 33

wtWebGraphAnalogIn57641Alert4 TRAP-TYPE
    ENTERPRISE  wtWebGraphAnalogIn57641
    VARIABLES   { wtWebGraphAnalogIn57641AlarmTrapText }
    DESCRIPTION
        "This SNMP trap is generated when Alarm 4 was triggered,
        SNMP trap enable is set and
        SNMP is enabled."
    -- NMS trap annotation
    --#TYPE "Thermo-Hygrometer Alarm 4"
    --#SUMMARY "Alarm 4: %s"
    --#ARGUMENTS {0}
    --#SEVERITY INFORMATIONAL
    --#TIMEINDEX 99
    --#STATE OPERATIONAL    
    ::= 34

wtWebGraphAnalogIn57641Alert5 TRAP-TYPE
    ENTERPRISE  wtWebGraphAnalogIn57641
    VARIABLES   { wtWebGraphAnalogIn57641AlarmTrapText }
    DESCRIPTION
        "This SNMP trap is generated when Alarm 5 was triggered,
        SNMP trap enable is set and
        SNMP is enabled."
    -- NMS trap annotation
    --#TYPE "Thermo-Hygrometer Alarm 5"
    --#SUMMARY "Alarm 5: %s"
    --#ARGUMENTS {0}
    --#SEVERITY INFORMATIONAL
    --#TIMEINDEX 99
    --#STATE OPERATIONAL    
    ::= 35

wtWebGraphAnalogIn57641Alert6 TRAP-TYPE
    ENTERPRISE  wtWebGraphAnalogIn57641
    VARIABLES   { wtWebGraphAnalogIn57641AlarmTrapText }
    DESCRIPTION
        "This SNMP trap is generated when Alarm 6 was triggered,
        SNMP trap enable is set and
        SNMP is enabled."
    -- NMS trap annotation
    --#TYPE "Thermo-Hygrometer Alarm 6"
    --#SUMMARY "Alarm 6: %s"
    --#ARGUMENTS {0}
    --#SEVERITY INFORMATIONAL
    --#TIMEINDEX 99
    --#STATE OPERATIONAL    
    ::= 36

wtWebGraphAnalogIn57641Alert7 TRAP-TYPE
    ENTERPRISE  wtWebGraphAnalogIn57641
    VARIABLES   { wtWebGraphAnalogIn57641AlarmTrapText }
    DESCRIPTION
        "This SNMP trap is generated when Alarm 7 was triggered,
        SNMP trap enable is set and
        SNMP is enabled."
    -- NMS trap annotation
    --#TYPE "Thermo-Hygrometer Alarm 7"
    --#SUMMARY "Alarm 7: %s"
    --#ARGUMENTS {0}
    --#SEVERITY INFORMATIONAL
    --#TIMEINDEX 99
    --#STATE OPERATIONAL    
    ::= 37

wtWebGraphAnalogIn57641Alert8 TRAP-TYPE
    ENTERPRISE  wtWebGraphAnalogIn57641
    VARIABLES   { wtWebGraphAnalogIn57641AlarmTrapText }
    DESCRIPTION
        "This SNMP trap is generated when Alarm 8 was triggered,
        SNMP trap enable is set and
        SNMP is enabled."
    -- NMS trap annotation
    --#TYPE "Thermo-Hygrometer Alarm 8"
    --#SUMMARY "Alarm 8: %s"
    --#ARGUMENTS {0}
    --#SEVERITY INFORMATIONAL
    --#TIMEINDEX 99
    --#STATE OPERATIONAL    
    ::= 38

    
wtWebGraphAnalogIn57641Alert9 TRAP-TYPE
    ENTERPRISE  wtWebGraphAnalogIn57641
    VARIABLES   { wtWebGraphAnalogIn57641AlarmClearTrapText }
    DESCRIPTION
        "This SNMP trap is generated when Alarm 1 was cleared,
        SNMP trap enable is set and
        SNMP is enabled."
    -- NMS trap annotation
    --#TYPE "Thermo-Hygrometer Release Alarm 1"
    --#SUMMARY "Release Alarm 1: %s"
    --#ARGUMENTS {0}
    --#SEVERITY INFORMATIONAL
    --#TIMEINDEX 99
    --#STATE OPERATIONAL    
    ::= 91

wtWebGraphAnalogIn57641Alert10 TRAP-TYPE
    ENTERPRISE  wtWebGraphAnalogIn57641
    VARIABLES   { wtWebGraphAnalogIn57641AlarmClearTrapText }
    DESCRIPTION
        "This SNMP trap is generated when Alarm 2 was cleared,
        SNMP trap enable is set and
        SNMP is enabled."
    -- NMS trap annotation
    --#TYPE "Thermo-Hygrometer Release Alarm 2"
    --#SUMMARY "Release Alarm 2: %s"
    --#ARGUMENTS {0}
    --#SEVERITY INFORMATIONAL
    --#TIMEINDEX 99
    --#STATE OPERATIONAL    
    ::= 92

wtWebGraphAnalogIn57641Alert11 TRAP-TYPE
    ENTERPRISE  wtWebGraphAnalogIn57641
    VARIABLES   { wtWebGraphAnalogIn57641AlarmClearTrapText }
    DESCRIPTION
        "This SNMP trap is generated when Alarm 3 was cleared,
        SNMP trap enable is set and
        SNMP is enabled."
    -- NMS trap annotation
    --#TYPE "Thermo-Hygrometer Release Alarm 3"
    --#SUMMARY "Release Alarm 3: %s"
    --#ARGUMENTS {0}
    --#SEVERITY INFORMATIONAL
    --#TIMEINDEX 99
    --#STATE OPERATIONAL    
    ::= 93

wtWebGraphAnalogIn57641Alert12 TRAP-TYPE
    ENTERPRISE  wtWebGraphAnalogIn57641
    VARIABLES   { wtWebGraphAnalogIn57641AlarmClearTrapText }
    DESCRIPTION
        "This SNMP trap is generated when Alarm 4 was cleared,
        SNMP trap enable is set and
        SNMP is enabled."
    -- NMS trap annotation
    --#TYPE "Thermo-Hygrometer Release Alarm 4"
    --#SUMMARY "Release Alarm 4: %s"
    --#ARGUMENTS {0}
    --#SEVERITY INFORMATIONAL
    --#TIMEINDEX 99
    --#STATE OPERATIONAL    
    ::= 94

wtWebGraphAnalogIn57641Alert13 TRAP-TYPE
    ENTERPRISE  wtWebGraphAnalogIn57641
    VARIABLES   { wtWebGraphAnalogIn57641AlarmClearTrapText }
    DESCRIPTION
        "This SNMP trap is generated when Alarm 5 was cleared,
        SNMP trap enable is set and
        SNMP is enabled."
    -- NMS trap annotation
    --#TYPE "Thermo-Hygrometer Release Alarm 5"
    --#SUMMARY "Release Alarm 5: %s"
    --#ARGUMENTS {0}
    --#SEVERITY INFORMATIONAL
    --#TIMEINDEX 99
    --#STATE OPERATIONAL    
    ::= 95

wtWebGraphAnalogIn57641Alert14 TRAP-TYPE
    ENTERPRISE  wtWebGraphAnalogIn57641
    VARIABLES   { wtWebGraphAnalogIn57641AlarmClearTrapText }
    DESCRIPTION
        "This SNMP trap is generated when Alarm 6 was cleared,
        SNMP trap enable is set and
        SNMP is enabled."
    -- NMS trap annotation
    --#TYPE "Thermo-Hygrometer Release Alarm 6"
    --#SUMMARY "Release Alarm 6: %s"
    --#ARGUMENTS {0}
    --#SEVERITY INFORMATIONAL
    --#TIMEINDEX 99
    --#STATE OPERATIONAL    
    ::= 96

wtWebGraphAnalogIn57641Alert15 TRAP-TYPE
    ENTERPRISE  wtWebGraphAnalogIn57641
    VARIABLES   { wtWebGraphAnalogIn57641AlarmClearTrapText }
    DESCRIPTION
        "This SNMP trap is generated when Alarm 7 was cleared,
        SNMP trap enable is set and
        SNMP is enabled."
    -- NMS trap annotation
    --#TYPE "Thermo-Hygrometer Release Alarm 7"
    --#SUMMARY "Release Alarm 7: %s"
    --#ARGUMENTS {0}
    --#SEVERITY INFORMATIONAL
    --#TIMEINDEX 99
    --#STATE OPERATIONAL    
    ::= 97

wtWebGraphAnalogIn57641Alert16 TRAP-TYPE
    ENTERPRISE  wtWebGraphAnalogIn57641
    VARIABLES   { wtWebGraphAnalogIn57641AlarmClearTrapText }
    DESCRIPTION
        "This SNMP trap is generated when Alarm 8 was cleared,
        SNMP trap enable is set and
        SNMP is enabled."
    -- NMS trap annotation
    --#TYPE "Thermo-Hygrometer Release Alarm 8"
    --#SUMMARY "Release Alarm 8: %s"
    --#ARGUMENTS {0}
    --#SEVERITY INFORMATIONAL
    --#TIMEINDEX 99
    --#STATE OPERATIONAL    
    ::= 98

wtWebGraphAnalogIn57641AlertDiag TRAP-TYPE
    ENTERPRISE  wtWebGraphAnalogIn57641
    VARIABLES   { 	
    		wtWebGraphAnalogIn57641DiagErrorIndex,
    	  	wtWebGraphAnalogIn57641DiagErrorMessage
    		}
    DESCRIPTION
        "This SNMP trap is generated when a diagnosis/error message was triggered,
        SNMP trap enable is set and
        SNMP is enabled."
    -- NMS trap annotation
    --#TYPE "Thermo-Hygrometer Diagnose Error"
    --#SUMMARY "Diagnose error index: %d, Message: %s."
    --#ARGUMENTS {0,1}
    --#SEVERITY MAJOR
    --#TIMEINDEX 99
    --#STATE DEGRADED    
    ::= 110 
 
END

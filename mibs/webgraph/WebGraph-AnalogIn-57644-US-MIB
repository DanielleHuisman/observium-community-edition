WebGraph-AnalogIn-57644-US-MIB DEFINITIONS ::= BEGIN
----------------------------------------------------------------
-- Revison: 1.29
----------------------------------------------------------------
-- 22.06.2010 	Webio
--		Syntax correction 
----------------------------------------------------------------
-- Revison: 1.28
----------------------------------------------------------------
-- 02.12.2008 	Webio
--		New Graphics java script base parameter 
----------------------------------------------------------------
-- Revison: 1.27
----------------------------------------------------------------
-- 09.11.2006 	Webio
--		DHCP enable 
----------------------------------------------------------------
-- Revison: 1.26
----------------------------------------------------------------
-- 28.06.2006 	New: Community String Trap
--		
----------------------------------------------------------------
-- Revison: 1.25
----------------------------------------------------------------
-- 25.11.2005 	#57644, WebGraph AnalogIn 2x 0..10V
--
----------------------------------------------------------------
-- Revison: 1.24
----------------------------------------------------------------
-- 26.07.2005 	#57644, WebGraph AnalogIn
--		CRON timer function
----------------------------------------------------------------
-- Revison: 1.23
----------------------------------------------------------------
-- 14.07.2005 	#57644, WebGraph AnalogIn
--		FTP functions
----------------------------------------------------------------
-- Revison: 1.22
----------------------------------------------------------------
-- 17.05.2005 	#57644, WebGraph AnalogIn
--		Trap NMS annotations
----------------------------------------------------------------
-- Revison: 1.21
----------------------------------------------------------------
-- 19.04.2005 	#57605, WebGraph Themometer
--		Mail Authentication
----------------------------------------------------------------
-- Revison: 1.20
----------------------------------------------------------------
-- 05.11.2004 	#57606, WebGraph Thermo-Hygrometer
--		New: Syslog
--		     
----------------------------------------------------------------
-- Revison: 1.19
----------------------------------------------------------------
-- 08.09.2004 	#57606 WebGraph Thermo-Hygrometer
--		New: 
--			wtWebGraphThermHygroAlarmRHMin
--			wtWebGraphThermHygroAlarmRHMax
--			wtWebGraphThermHygroAlarmRHHysteresis
--			wtWebGraphThermHygroPortSensorSelect
--			wtWebGraphThermHygroAlarmDeltaTemp		
--			wtWebGraphThermHygroAlarmAHMin		
--			wtWebGraphThermHygroAlarmAHMax		
----------------------------------------------------------------
-- Revison: 1.18
----------------------------------------------------------------
-- 21.07.2004 	#57601/3/4, Webio Anx
--		New: 
--		     Diagnosis
----------------------------------------------------------------
-- Revison: 1.17
----------------------------------------------------------------
-- 28.06.2004 	#57630/1/2, Webio Digital
--		Neu: Puls Mode
----------------------------------------------------------------
-- Revison: 1.16
----------------------------------------------------------------
-- 16.04.2004 	New: #57632, Webio Digital EA24x24
--
--		#57630/1, Webio Digital EA12x12
--		New:
--			wtWebioEA12x12InputCounterClear
----------------------------------------------------------------
-- Revison: 1.15
----------------------------------------------------------------
-- 27.02.2004 	#57630/1, Webio Digital EA12x12
--		New:
--		Length changed to 32 Bit:
--			wtWebioEA12x12InputValue
--			wtWebioEA12x12OutputValue
--			wtWebioEA12x12LoadControlView
--			wtWebioEA12x12LCShutDownView
--			wtWebioEA12x12SetOutput
--			wtWebioEA12x12AlarmInputTrigger
--			wtWebioEA12x12AlarmOutputTrigger
--			wtWebioEA12x12PortOutputSafetyState
----------------------------------------------------------------
-- Revison: 1.14
----------------------------------------------------------------
-- 16.02.2004 	#57630/1, Webio Digital EA12x12
--		New:
--		Text: Location, Contact
--		SNMP: ColdStart, WarmStart, ComunityString Read/RW
--		Alarm: ColdStart / WarmStart trigger
--
-- 	 	#57601, 1xWebThermometer
--		#57603, 2xWebThermometer		
--		#57604, 8xWebThermometer
--		New:
--		Alarm Hysteresis 
--		Alarm Clear Traps and Mails
----------------------------------------------------------------
-- Revison: 1.13
----------------------------------------------------------------
-- 05.02.2004 	#57601, 1xWebThermometer
--		#57603, 2xWebThermometer		
--		#57604, 8xWebThermometer
--		New:
--		Text: Location, Contact
--		SNMP: ColdStart, WarmStart, ComunityString Read/RW
--		Alarm: ColdStart / WarmStart trigger
----------------------------------------------------------------
-- Revison: 1.12
----------------------------------------------------------------
-- 05.11.2003 	#57601, 1xWebThermometer
--		#57603, 2xWebThermometer		
--		#57604, 8xWebThermometer
--		New features:
--		Mail  : Option CSV attachment
--		Port  : Offset calibration
--		Alarm : TCP Client mode		
----------------------------------------------------------------
-- Revison: 1.11
----------------------------------------------------------------
-- 28.10.2003 	#57630/1, Webio Digital EA12x12
--		New features:
--		Alarm : TCP Client mode		
--		Inputs: Puls filter
----------------------------------------------------------------
-- Revison: 1.10
----------------------------------------------------------------
-- 22.07.2003 	#57630, Webio Digital EA12x12
--		New navigation tree, new binary modes		
--
----------------------------------------------------------------
-- Revison: 1.09
----------------------------------------------------------------
-- 24.03.2003 	Trap Enterprise (Type 1, 2) corrected 
----------------------------------------------------------------
-- Revison: 1.08
----------------------------------------------------------------
-- 04.03.2003 	reconciled the language versions DE/US
----------------------------------------------------------------
-- Revison: 1.07
----------------------------------------------------------------
-- 25.02.2003 	Correction: wtWebioEA12x12LoadControl
----------------------------------------------------------------
-- Revison: 1.06
----------------------------------------------------------------
-- 24.02.2003 	New:
--		#57630, Webio EA12x12, LoadControl Group
--		Correction: Trap variable names
----------------------------------------------------------------
-- Revison: 1.05
----------------------------------------------------------------
-- 21.01.2003 	New:
--		#57630, Webio EA12x12
----------------------------------------------------------------
-- Revison: 1.04
----------------------------------------------------------------
-- 02.01.2003 	New:
--		#57601, 1xWebThermometer
--		#57603, 2xWebThermometer, 8 alarms
----------------------------------------------------------------
-- Revison: 1.03
----------------------------------------------------------------
-- 21.11.2002 	New:
--		#57604, 2xWebThermometer, BOOTP, StartupSite
--		#57603, 8xWebThermometer, BOOTP, StartupSite
----------------------------------------------------------------
-- Revison: 1.02
----------------------------------------------------------------
-- 26.07.2002 	New:
--		#57604, 2xWebThermometer
--		#57603, 8xWebThermometer
-- 		


    IMPORTS

    OBJECT-TYPE                                        FROM RFC-1212
    TRAP-TYPE                                          FROM RFC-1215
    DisplayString, PhysAddress                         FROM RFC1213-MIB
    enterprises, TimeTicks, IpAddress, NetworkAddress  FROM RFC1155-SMI;

 
--    IpAddress ::=
--        [APPLICATION 0]
--            IMPLICIT OCTET STRING (SIZE (4))
--    Counter ::=
--        [APPLICATION 1]
--            IMPLICIT INTEGER (0..4294967295)
--    Gauge ::=
--        [APPLICATION 2]
--            IMPLICIT INTEGER (0..4294967295)
--    TimeTicks ::=
--        [APPLICATION 3]
--            IMPLICIT INTEGER (0..4294967295)


--    DisplayString ::= OCTET STRING
--    PhysAddress   ::= OCTET STRING

--    internet         OBJECT IDENTIFIER ::= { iso org(3) dod(6) 1 }
--    privat           OBJECT IDENTIFIER ::= { internet 4 }
--    enterprises      OBJECT IDENTIFIER ::= { privat 1 }



--  Wiesemann & Theis Com-Server MIB

    wut                				OBJECT IDENTIFIER ::= { enterprises 5040 }
    wtComServer        				OBJECT IDENTIFIER ::= { wut 1 }
    wtWebio            				OBJECT IDENTIFIER ::= { wtComServer 2 }

--  wtWebGraph Tree

    wtWebGraphAnalogIn57644  			OBJECT IDENTIFIER ::= { wtWebio 12 }
    
--  wtWebGraphAnalogIn57644 Tree

    wtWebGraphAnalogIn57644Inventory    	OBJECT IDENTIFIER ::= { wtWebGraphAnalogIn57644 1 }
    wtWebGraphAnalogIn57644SessCntrl 		OBJECT IDENTIFIER ::= { wtWebGraphAnalogIn57644 2 }
    wtWebGraphAnalogIn57644Config    		OBJECT IDENTIFIER ::= { wtWebGraphAnalogIn57644 3 }
    wtWebGraphAnalogIn57644Diag    		OBJECT IDENTIFIER ::= { wtWebGraphAnalogIn57644 4 }
    
--  wtWebGraphAnalogIn57644Config Tree

    wtWebGraphAnalogIn57644Device    		OBJECT IDENTIFIER ::= { wtWebGraphAnalogIn57644Config 1 }
    wtWebGraphAnalogIn57644Ports     		OBJECT IDENTIFIER ::= { wtWebGraphAnalogIn57644Config 2 }	
    wtWebGraphAnalogIn57644Manufact  		OBJECT IDENTIFIER ::= { wtWebGraphAnalogIn57644Config 3 }	

--  wtWebGraphAnalogIn57644Device Tree

    wtWebGraphAnalogIn57644Text			OBJECT IDENTIFIER ::= { wtWebGraphAnalogIn57644Device 1 }	
    wtWebGraphAnalogIn57644TimeDate 		OBJECT IDENTIFIER ::= { wtWebGraphAnalogIn57644Device 2 }
    wtWebGraphAnalogIn57644Basic		OBJECT IDENTIFIER ::= { wtWebGraphAnalogIn57644Device 3 }	
    wtWebGraphAnalogIn57644Datalogger		OBJECT IDENTIFIER ::= { wtWebGraphAnalogIn57644Device 4 }	
    wtWebGraphAnalogIn57644Alarm		OBJECT IDENTIFIER ::= { wtWebGraphAnalogIn57644Device 5 }
    wtWebGraphAnalogIn57644Graphics 		OBJECT IDENTIFIER ::= { wtWebGraphAnalogIn57644Device 6 }	
    
--  wtWebGraphAnalogIn57644TimeDate Tree

    wtWebGraphAnalogIn57644TimeZone		OBJECT IDENTIFIER ::= { wtWebGraphAnalogIn57644TimeDate 1 }
    wtWebGraphAnalogIn57644TimeServer		OBJECT IDENTIFIER ::= { wtWebGraphAnalogIn57644TimeDate 2 }	
    wtWebGraphAnalogIn57644DeviceClock		OBJECT IDENTIFIER ::= { wtWebGraphAnalogIn57644TimeDate 3 }

--  wtWebGraphAnalogIn57644Basic Tree
    
    wtWebGraphAnalogIn57644Network		OBJECT IDENTIFIER ::= { wtWebGraphAnalogIn57644Basic 1 }
    wtWebGraphAnalogIn57644HTTP			OBJECT IDENTIFIER ::= { wtWebGraphAnalogIn57644Basic 2 }
    wtWebGraphAnalogIn57644Mail			OBJECT IDENTIFIER ::= { wtWebGraphAnalogIn57644Basic 3 }	
    wtWebGraphAnalogIn57644SNMP			OBJECT IDENTIFIER ::= { wtWebGraphAnalogIn57644Basic 4 }
    wtWebGraphAnalogIn57644UDP			OBJECT IDENTIFIER ::= { wtWebGraphAnalogIn57644Basic 5 }
    wtWebGraphAnalogIn57644Syslog		OBJECT IDENTIFIER ::= { wtWebGraphAnalogIn57644Basic 6 }
    wtWebGraphAnalogIn57644FTP			OBJECT IDENTIFIER ::= { wtWebGraphAnalogIn57644Basic 7 }

--  wtWebGraphAnalogIn57644Graphics Tree
    
    wtWebGraphAnalogIn57644GraphicsBase 	OBJECT IDENTIFIER ::= { wtWebGraphAnalogIn57644Graphics 1 }
    wtWebGraphAnalogIn57644GraphicsSelect 	OBJECT IDENTIFIER ::= { wtWebGraphAnalogIn57644Graphics 2 }
    wtWebGraphAnalogIn57644GraphicsScale 	OBJECT IDENTIFIER ::= { wtWebGraphAnalogIn57644Graphics 3 }
       
-- wtWebGraphAnalogIn57644Inventory Group
------------------------

wtWebGraphAnalogIn57644Sensors OBJECT-TYPE
    SYNTAX INTEGER (1..2)
    ACCESS read-only
    STATUS mandatory
    DESCRIPTION
        "Number of sensors"
    ::= { wtWebGraphAnalogIn57644Inventory 1 }

-- Interface Table

wtWebGraphAnalogIn57644SensorTable OBJECT-TYPE
    SYNTAX SEQUENCE OF WtWebGraphAnalogIn57644SensorEntry
    ACCESS not-accessible
    STATUS mandatory
    DESCRIPTION
        "List of sensors."
    ::= { wtWebGraphAnalogIn57644Inventory 2 }

wtWebGraphAnalogIn57644SensorEntry OBJECT-TYPE
    SYNTAX WtWebGraphAnalogIn57644SensorEntry
    ACCESS not-accessible
    STATUS mandatory
    DESCRIPTION
        "List of sensor numbers."
    INDEX  { wtWebGraphAnalogIn57644SensorNo }
    ::= { wtWebGraphAnalogIn57644SensorTable 1 }

WtWebGraphAnalogIn57644SensorEntry ::= SEQUENCE {
    wtWebGraphAnalogIn57644SensorNo INTEGER
}

wtWebGraphAnalogIn57644SensorNo OBJECT-TYPE
    SYNTAX INTEGER (1..2)
    ACCESS read-only
    STATUS mandatory
    DESCRIPTION
        "Sensor number."
    ::= { wtWebGraphAnalogIn57644SensorEntry 1 }


-- wtWebGraphAnalogIn57644Values Table

wtWebGraphAnalogIn57644ValuesTable OBJECT-TYPE
    SYNTAX SEQUENCE OF WtWebGraphAnalogIn57644ValuesEntry
    ACCESS not-accessible
    STATUS mandatory
    DESCRIPTION
        "List of measurement values corresponding to the channel numbers."
    ::= { wtWebGraphAnalogIn57644Inventory 3 }

wtWebGraphAnalogIn57644ValuesEntry OBJECT-TYPE
    SYNTAX WtWebGraphAnalogIn57644ValuesEntry
    ACCESS not-accessible
    STATUS mandatory
    DESCRIPTION
        "Measurement values of the sensors."
    INDEX  { wtWebGraphAnalogIn57644SensorNo }
    ::= { wtWebGraphAnalogIn57644ValuesTable 1 }

WtWebGraphAnalogIn57644ValuesEntry ::= SEQUENCE{
    wtWebGraphAnalogIn57644Values OCTET STRING
}

wtWebGraphAnalogIn57644Values OBJECT-TYPE
    SYNTAX OCTET STRING (SIZE (5))
    ACCESS read-only
    STATUS mandatory
    DESCRIPTION
        "Measurement value of the sensor, ASCII, 7 characters in length."
    ::= { wtWebGraphAnalogIn57644ValuesEntry 1 }

-- wtWebGraphAnalogIn57644BinaryValues Table

wtWebGraphAnalogIn57644BinaryValuesTable OBJECT-TYPE
    SYNTAX SEQUENCE OF WtWebGraphAnalogIn57644BinaryValuesEntry
    ACCESS not-accessible
    STATUS mandatory
    DESCRIPTION
        "List of binary measurement values corresponding to the channel numbers."
    ::= { wtWebGraphAnalogIn57644Inventory 4 }

wtWebGraphAnalogIn57644BinaryValuesEntry OBJECT-TYPE
    SYNTAX WtWebGraphAnalogIn57644BinaryValuesEntry
    ACCESS not-accessible
    STATUS mandatory
    DESCRIPTION
        "Binary measurement values of the sensors."
    INDEX  { wtWebGraphAnalogIn57644SensorNo }
    ::= { wtWebGraphAnalogIn57644BinaryValuesTable 1 }

WtWebGraphAnalogIn57644BinaryValuesEntry ::= SEQUENCE{
    wtWebGraphAnalogIn57644BinaryValues INTEGER
}    

wtWebGraphAnalogIn57644BinaryValues OBJECT-TYPE
    SYNTAX INTEGER
    ACCESS read-only
    STATUS mandatory
    DESCRIPTION
        "Binary measurement value of the sensor in 1/10 degrees Celsius or 1/10 per cent,
        signed number, 0x4FFF6 indicates an 
        invalid measured value."
    ::= { wtWebGraphAnalogIn57644BinaryValuesEntry 1 }

-- wtWebGraphAnalogIn57644SessCntrl Group
--------------------------------

wtWebGraphAnalogIn57644SessCntrlPassword OBJECT-TYPE
    SYNTAX OCTET STRING 
    ACCESS read-write
    STATUS mandatory
    DESCRIPTION
        "Entering this password opens a session which is ended by writing a 1 to 
        wtWebGraphAnalogIn57644SessCntrlLogout. When read this variable provides a string of
        length zero."
    ::= { wtWebGraphAnalogIn57644SessCntrl 1 }

wtWebGraphAnalogIn57644SessCntrlConfigMode OBJECT-TYPE
    SYNTAX INTEGER {
    wtWebGraphAnalogIn57644SessCntrl-NoSession(0),
    wtWebGraphAnalogIn57644SessCntrl-Session(1)
    }
    ACCESS read-only
    STATUS mandatory
    DESCRIPTION
        "When the device is in SNMP configuration mode, the value 1 is
        returned, otherwise 0. If the read value is 0 even though the
        password was written, the device is already in config mode and the
        variables can only be read."
    ::= { wtWebGraphAnalogIn57644SessCntrl 2 }

wtWebGraphAnalogIn57644SessCntrlLogout OBJECT-TYPE
    SYNTAX INTEGER 
    ACCESS read-write
    STATUS mandatory
    DESCRIPTION
        "If the device is in configuration mode and the session was opened by
        this SNMP Manager, writing a 1 to this variable will end the session 
        and all parameters are stored.
        Writing a 2 discards all entries again.
        When read this variable provides the value 0."
    ::= { wtWebGraphAnalogIn57644SessCntrl 3 }

wtWebGraphAnalogIn57644SessCntrlAdminPassword OBJECT-TYPE
    SYNTAX OCTET STRING 
    ACCESS read-write
    STATUS mandatory
    DESCRIPTION
        "This password protects access to the variables with administrator rights.
        It can only be changed by the administrator. If no password was assigned,
        the valid password is public."
    ::= { wtWebGraphAnalogIn57644SessCntrl 4 }

wtWebGraphAnalogIn57644SessCntrlConfigPassword OBJECT-TYPE
    SYNTAX OCTET STRING 
    ACCESS read-write
    STATUS mandatory
    DESCRIPTION
        "This password protects access to the variables with configurator rights. It can
        be changed by the administrator and by the configurator. If no password was assigned, 
        the valid password is public. When read this variable provides a null-pointer."
    ::= { wtWebGraphAnalogIn57644SessCntrl 5 }
    

-- wtWebGraphAnalogIn57644Text Group
------------------------

wtWebGraphAnalogIn57644DeviceName OBJECT-TYPE
    SYNTAX OCTET STRING 
    ACCESS read-write
    STATUS mandatory
    DESCRIPTION
        "Name of the Webio, which is user definable."
    ::= { wtWebGraphAnalogIn57644Text 1 }

wtWebGraphAnalogIn57644DeviceText OBJECT-TYPE
    SYNTAX OCTET STRING 
    ACCESS read-write
    STATUS mandatory
    DESCRIPTION
        "Description of the Webio, which is user definable."
    ::= { wtWebGraphAnalogIn57644Text 2 }

wtWebGraphAnalogIn57644DeviceLocation OBJECT-TYPE
    SYNTAX OCTET STRING 
    ACCESS read-write
    STATUS mandatory
    DESCRIPTION
        "Description of the location of the Webio, which is user definable."
    ::= { wtWebGraphAnalogIn57644Text 3 }

wtWebGraphAnalogIn57644DeviceContact OBJECT-TYPE
    SYNTAX OCTET STRING 
    ACCESS read-write
    STATUS mandatory
    DESCRIPTION
        "Contact address of the system operator of the Webio, which is user definable."
    ::= { wtWebGraphAnalogIn57644Text 4 }

-- wtWebGraphAnalogIn57644TimeZone Group
----------------------------

wtWebGraphAnalogIn57644TzOffsetHrs OBJECT-TYPE
    SYNTAX INTEGER 
    ACCESS read-write
    STATUS mandatory
    DESCRIPTION
        "Offset hours for the time zone (winter time) with respect to UTC."
    ::= { wtWebGraphAnalogIn57644TimeZone 1 }

wtWebGraphAnalogIn57644TzOffsetMin OBJECT-TYPE
    SYNTAX INTEGER 
    ACCESS read-write
    STATUS mandatory
    DESCRIPTION
        "Offset minutes for the time zone (winter time) with respect to UTC."
    ::= { wtWebGraphAnalogIn57644TimeZone 2 }

wtWebGraphAnalogIn57644TzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebGraphAnalogIn57644TimeZone 3 }    
    
wtWebGraphAnalogIn57644StTzOffsetHrs OBJECT-TYPE
    SYNTAX INTEGER 
    ACCESS read-write
    STATUS mandatory
    DESCRIPTION
        "Offset hours of the time zone (summer time) with respect to UTC."
    ::= { wtWebGraphAnalogIn57644TimeZone 4 }

wtWebGraphAnalogIn57644StTzOffsetMin OBJECT-TYPE
    SYNTAX INTEGER 
    ACCESS read-write
    STATUS mandatory
    DESCRIPTION
        "Offset minutes of the time zone (summer time) with respect to UTC."
    ::= { wtWebGraphAnalogIn57644TimeZone 5 }
    
wtWebGraphAnalogIn57644StTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebGraphAnalogIn57644TimeZone 6 }       
    
wtWebGraphAnalogIn57644StTzStartMonth OBJECT-TYPE
    SYNTAX INTEGER {
    	wtWebGraphAnalogIn57644StartMonth-January(1),
    	wtWebGraphAnalogIn57644StartMonth-February(2),
    	wtWebGraphAnalogIn57644StartMonth-March(3),
    	wtWebGraphAnalogIn57644StartMonth-April(4),
    	wtWebGraphAnalogIn57644StartMonth-May(5),
    	wtWebGraphAnalogIn57644StartMonth-June(6),
    	wtWebGraphAnalogIn57644StartMonth-July(7),
    	wtWebGraphAnalogIn57644StartMonth-August(8),
    	wtWebGraphAnalogIn57644StartMonth-September(9),
    	wtWebGraphAnalogIn57644StartMonth-October(10),
    	wtWebGraphAnalogIn57644StartMonth-November(11),
    	wtWebGraphAnalogIn57644StartMonth-December(12)
    	}
    	
    ACCESS read-write
    STATUS mandatory
    DESCRIPTION
        "Month in which the change is made from winter time to summer time."
    ::= { wtWebGraphAnalogIn57644TimeZone 7 }

wtWebGraphAnalogIn57644StTzStartMode OBJECT-TYPE
    SYNTAX INTEGER {
    	wtWebGraphAnalogIn57644StartMode-first(1),
    	wtWebGraphAnalogIn57644StartMode-second(2),
    	wtWebGraphAnalogIn57644StartMode-third(3),
    	wtWebGraphAnalogIn57644StartMode-fourth(4),
    	wtWebGraphAnalogIn57644StartMode-last(5)
    	}
    	
    ACCESS read-write
    STATUS mandatory
    DESCRIPTION
        "Mode of the day of the week for which the change is made from winter time to summer time."
    ::= { wtWebGraphAnalogIn57644TimeZone 8 }

wtWebGraphAnalogIn57644StTzStartWday OBJECT-TYPE
    SYNTAX INTEGER {
    	wtWebGraphAnalogIn57644StartWday-Sunday(1),
    	wtWebGraphAnalogIn57644StartWday-Monday(2),
    	wtWebGraphAnalogIn57644StartWday-Tuesday(3),
    	wtWebGraphAnalogIn57644StartWday-Thursday(4),
    	wtWebGraphAnalogIn57644StartWday-Wednesday(5),
    	wtWebGraphAnalogIn57644StartWday-Friday(6),
    	wtWebGraphAnalogIn57644StartWday-Saturday(7)
    	}
    	
    ACCESS read-write
    STATUS mandatory
    DESCRIPTION
        "Day of the week on which the change is made from winter time to summer time"
    ::= { wtWebGraphAnalogIn57644TimeZone 9 }
    
wtWebGraphAnalogIn57644StTzStartHrs OBJECT-TYPE
    SYNTAX INTEGER 
    ACCESS read-write
    STATUS mandatory
    DESCRIPTION
        "Hour in which the time zone is changed from winter to summer time with
        respect to UTC."
    ::= { wtWebGraphAnalogIn57644TimeZone 10 }

wtWebGraphAnalogIn57644StTzStartMin OBJECT-TYPE
    SYNTAX INTEGER 
    ACCESS read-write
    STATUS mandatory
    DESCRIPTION
        "Minute in which the time zone is changed from winter to summer time with
        respect to UTC."
    ::= { wtWebGraphAnalogIn57644TimeZone 11 }
 
wtWebGraphAnalogIn57644StTzStopMonth OBJECT-TYPE
    SYNTAX INTEGER {
    	wtWebGraphAnalogIn57644StopMonth-January(1),
    	wtWebGraphAnalogIn57644StopMonth-February(2),
    	wtWebGraphAnalogIn57644StopMonth-March(3),
    	wtWebGraphAnalogIn57644StopMonth-April(4),
    	wtWebGraphAnalogIn57644StopMonth-May(5),
    	wtWebGraphAnalogIn57644StopMonth-June(6),
    	wtWebGraphAnalogIn57644StopMonth-July(7),
    	wtWebGraphAnalogIn57644StopMonth-August(8),
    	wtWebGraphAnalogIn57644StopMonth-September(9),
    	wtWebGraphAnalogIn57644StopMonth-October(10),
    	wtWebGraphAnalogIn57644StopMonth-November(11),
    	wtWebGraphAnalogIn57644StopMonth-December(12)
    	}
    ACCESS read-write
    STATUS mandatory
    DESCRIPTION
        "Month in which the change is made from summer time to winter time."
   ::= { wtWebGraphAnalogIn57644TimeZone 12 }

wtWebGraphAnalogIn57644StTzStopMode OBJECT-TYPE
    SYNTAX INTEGER {
    	wtWebGraphAnalogIn57644StopMode-first(1),
    	wtWebGraphAnalogIn57644StopMode-second(2),
    	wtWebGraphAnalogIn57644StopMode-third(3),
    	wtWebGraphAnalogIn57644StopMode-fourth(4),
    	wtWebGraphAnalogIn57644StopMode-last(5)
    	}
    ACCESS read-write
    STATUS mandatory
    DESCRIPTION
        "Mode of the week day on which the change is made from summer time to winter time."
    ::= { wtWebGraphAnalogIn57644TimeZone 13 }

wtWebGraphAnalogIn57644StTzStopWday OBJECT-TYPE
    SYNTAX INTEGER {
    	wtWebGraphAnalogIn57644StopWday-Sunday(1),
    	wtWebGraphAnalogIn57644StopWday-Monday(2),
    	wtWebGraphAnalogIn57644StopWday-Tuesday(3),
    	wtWebGraphAnalogIn57644StopWday-Thursday(4),
    	wtWebGraphAnalogIn57644StopWday-Wednesday(5),
    	wtWebGraphAnalogIn57644StopWday-Friday(6),
    	wtWebGraphAnalogIn57644StopWday-Saturday(7)
    	}
    ACCESS read-write
    STATUS mandatory
    DESCRIPTION
        "Day of the week on which the change is made from summer time to winter time."
    ::= { wtWebGraphAnalogIn57644TimeZone 14 }
    
wtWebGraphAnalogIn57644StTzStopHrs OBJECT-TYPE
    SYNTAX INTEGER 
    ACCESS read-write
    STATUS mandatory
    DESCRIPTION
        "Hour at which the time zone is changed from summer to winter time with
        respect to UTC."
    ::= { wtWebGraphAnalogIn57644TimeZone 15 }

wtWebGraphAnalogIn57644StTzStopMin OBJECT-TYPE
    SYNTAX INTEGER 
    ACCESS read-write
    STATUS mandatory
    DESCRIPTION
        "Minute at which the time zone is changed from summer to winter time with
        respect to UTC."
    ::= { wtWebGraphAnalogIn57644TimeZone 16 }

-- wtWebGraphAnalogIn57644TimeServer Group
----------------------------

wtWebGraphAnalogIn57644TimeServer1 OBJECT-TYPE
    SYNTAX OCTET STRING 
    ACCESS read-write
    STATUS mandatory
    DESCRIPTION
        "IP address or name of the 1st time server in ASCII"
    ::= { wtWebGraphAnalogIn57644TimeServer 1 }

wtWebGraphAnalogIn57644TimeServer2 OBJECT-TYPE
    SYNTAX OCTET STRING 
    ACCESS read-write
    STATUS mandatory
    DESCRIPTION
        "IP address or name of the 2nd time server in ASCII"
    ::= { wtWebGraphAnalogIn57644TimeServer 2 }
    
wtWebGraphAnalogIn57644TsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebGraphAnalogIn57644TimeServer 3 }
    
wtWebGraphAnalogIn57644TsSyncTime OBJECT-TYPE
    SYNTAX INTEGER 
    ACCESS read-write
    STATUS mandatory
    DESCRIPTION
        "Daily synchronisation time with the time server (hour: 0-23)."
    ::= { wtWebGraphAnalogIn57644TimeServer 4 } 
    
-- wtWebGraphAnalogIn57644DeviceClock Group
----------------------------

wtWebGraphAnalogIn57644ClockHrs OBJECT-TYPE
    SYNTAX INTEGER (0..23)
    ACCESS read-write
    STATUS mandatory
    DESCRIPTION
        "Clock hours taking into account the time zone settings."
    ::= { wtWebGraphAnalogIn57644DeviceClock 1 }

wtWebGraphAnalogIn57644ClockMin OBJECT-TYPE
    SYNTAX INTEGER (0..59)
    ACCESS read-write
    STATUS mandatory
    DESCRIPTION
        "Clock minutes taking into account the time zone settings."
    ::= { wtWebGraphAnalogIn57644DeviceClock 2 }

wtWebGraphAnalogIn57644ClockDay OBJECT-TYPE
    SYNTAX INTEGER (1..31)
    ACCESS read-write
    STATUS mandatory
    DESCRIPTION
        "Date: Day of the month, taking into account the time zone settings."
    ::= { wtWebGraphAnalogIn57644DeviceClock 3 }

wtWebGraphAnalogIn57644ClockMonth OBJECT-TYPE
   SYNTAX INTEGER {
    	wtWebGraphAnalogIn57644ClockMonth-January(1),
    	wtWebGraphAnalogIn57644ClockMonth-February(2),
    	wtWebGraphAnalogIn57644ClockMonth-March(3),
    	wtWebGraphAnalogIn57644ClockMonth-April(4),
    	wtWebGraphAnalogIn57644ClockMonth-May(5),
    	wtWebGraphAnalogIn57644ClockMonth-June(6),
    	wtWebGraphAnalogIn57644ClockMonth-July(7),
    	wtWebGraphAnalogIn57644ClockMonth-August(8),
    	wtWebGraphAnalogIn57644ClockMonth-September(9),
    	wtWebGraphAnalogIn57644ClockMonth-October(10),
    	wtWebGraphAnalogIn57644ClockMonth-November(11),
    	wtWebGraphAnalogIn57644ClockMonth-December(12)
    	}
    ACCESS read-write
    STATUS mandatory
    DESCRIPTION
        "Date: Month, taking into account the time zone settings."
    ::= { wtWebGraphAnalogIn57644DeviceClock 4 }

wtWebGraphAnalogIn57644ClockYear OBJECT-TYPE
    SYNTAX INTEGER (0..65535)
    ACCESS read-write
    STATUS mandatory
    DESCRIPTION
        "Date: Year, taking into account the time zone settings."
    ::= { wtWebGraphAnalogIn57644DeviceClock 5 }
    

-- wtWebGraphAnalogIn57644Network Group
------------------------

wtWebGraphAnalogIn57644IpAddress OBJECT-TYPE
    SYNTAX IpAddress
    ACCESS read-write
    STATUS mandatory
    DESCRIPTION
        "IP address of the Webio"
    ::= { wtWebGraphAnalogIn57644Network 1 }

wtWebGraphAnalogIn57644SubnetMask OBJECT-TYPE
    SYNTAX IpAddress
    ACCESS read-write
    STATUS mandatory
    DESCRIPTION
        "Subnet mask of the Webio"
    ::= { wtWebGraphAnalogIn57644Network 2 }

wtWebGraphAnalogIn57644Gateway OBJECT-TYPE
    SYNTAX IpAddress
    ACCESS read-write
    STATUS mandatory
    DESCRIPTION
        "Gateway of the Webio"
    ::= { wtWebGraphAnalogIn57644Network 3 }

wtWebGraphAnalogIn57644DnsServer1 OBJECT-TYPE
    SYNTAX OCTET STRING 
    ACCESS read-write
    STATUS mandatory
    DESCRIPTION
        "IP address of the 1st DNS server in ASCII"
    ::= { wtWebGraphAnalogIn57644Network 4 }

wtWebGraphAnalogIn57644DnsServer2 OBJECT-TYPE
    SYNTAX OCTET STRING 
    ACCESS read-write
    STATUS mandatory
    DESCRIPTION
        "IP address of the 2nd DNS server in ASCII"
    ::= { wtWebGraphAnalogIn57644Network 5 }

wtWebGraphAnalogIn57644AddConfig OBJECT-TYPE
    SYNTAX OCTET STRING 
    ACCESS read-write
    STATUS mandatory
    DESCRIPTION
        "Additional configuration (1=ON):
        Octet 1: unused
        Octet 2: unused
        Octet 3: unused
        Octet 4:
	        Bit 1: DHCP disable
	        Bit 0: BOOTP disable
	        "
    ::= { wtWebGraphAnalogIn57644Network 6 }

--  wtWebGraphAnalogIn57644HTTP Group
--------------------------------

wtWebGraphAnalogIn57644Startup OBJECT-TYPE
    SYNTAX OCTET STRING 
    ACCESS read-write
    STATUS mandatory
    DESCRIPTION
        "Binary coded start page:
        Octet 1: unused
        Octet 2: unused
        Octet 3: unused
        Octet 4:
	        Bit 1: Index.htm
	        Bit 2: Home.htm
	        Bit 3: User.htm
	Only one page may be selected at a time."
    ::= { wtWebGraphAnalogIn57644HTTP 1 }

wtWebGraphAnalogIn57644GetHeaderEnable OBJECT-TYPE
    SYNTAX OCTET STRING 
    ACCESS read-write
    STATUS mandatory
    DESCRIPTION
        "If these bits are set, every answer of a short form GET question will be lead
        by the IP-address and name of the device and/or a HTTP header:
        Octet 1: unused
        Octet 2: unused
        Octet 3: unused
        Octet 4:
        	Bit 1-6: unused
        	Bit 1  : GET HTTP enable
                Bit 0  : GET Header enable"
    ::= { wtWebGraphAnalogIn57644HTTP 2 }  
    
wtWebGraphAnalogIn57644HttpPort OBJECT-TYPE
    SYNTAX INTEGER (1..65535)
    ACCESS read-write
    STATUS mandatory
    DESCRIPTION
        "Definition of the standard HTML port (Default: 80)."
    ::= { wtWebGraphAnalogIn57644HTTP 3 }    


-- wtWebGraphAnalogIn57644Mail Group
--------------------------------

wtWebGraphAnalogIn57644MailAdName OBJECT-TYPE
    SYNTAX OCTET STRING 
    ACCESS read-write
    STATUS mandatory
    DESCRIPTION
        "Device name for mail administration."
    ::= { wtWebGraphAnalogIn57644Mail 1 }
    
wtWebGraphAnalogIn57644MailReply OBJECT-TYPE
    SYNTAX OCTET STRING 
    ACCESS read-write
    STATUS mandatory
    DESCRIPTION
        "Reply address for the mail server."
    ::= { wtWebGraphAnalogIn57644Mail 2 }
    
wtWebGraphAnalogIn57644MailServer OBJECT-TYPE
    SYNTAX OCTET STRING 
    ACCESS read-write
    STATUS mandatory
    DESCRIPTION
        "Name or IP address of the mail server."
    ::= { wtWebGraphAnalogIn57644Mail 3 }
    
wtWebioAn1MailEnable OBJECT-TYPE
    SYNTAX OCTET STRING 
    ACCESS read-write
    STATUS mandatory
    DESCRIPTION
        "Set this bit to enable the sending of mails:
        Octet 1: unused
        Octet 2: unused
        Octet 3: unused
        Octet 4:
        	Bit 1-7: unused
                Bit 0  : Mail enable"
    ::= { wtWebGraphAnalogIn57644Mail 4 }
    
wtWebGraphAnalogIn57644MailAuthentication OBJECT-TYPE
    SYNTAX OCTET STRING (SIZE (4))
    ACCESS read-write
    STATUS mandatory
    DESCRIPTION
        "Selection of the authentication modi:
        The OCTETS are interpreted bit-by-bit, with each bit corresponding to an output. 
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebGraphAnalogIn57644Mail 5 }
    
wtWebGraphAnalogIn57644MailAuthUser OBJECT-TYPE
    SYNTAX OCTET STRING 
    ACCESS read-write
    STATUS mandatory
    DESCRIPTION
        "Name of the user to be authenticated."
    ::= { wtWebGraphAnalogIn57644Mail 6 }    
    
wtWebGraphAnalogIn57644MailAuthPassword OBJECT-TYPE
    SYNTAX OCTET STRING 
    ACCESS read-write
    STATUS mandatory
    DESCRIPTION
        "Authentication password."
    ::= { wtWebGraphAnalogIn57644Mail 7 }    
    
wtWebGraphAnalogIn57644MailPop3Server OBJECT-TYPE
    SYNTAX OCTET STRING 
    ACCESS read-write
    STATUS mandatory
    DESCRIPTION
        "Name or Ip-address of the POP3 Servers."
    ::= { wtWebGraphAnalogIn57644Mail 8 }            

-- wtWebGraphAnalogIn57644SNMP Group
--------------------------------

wtWebGraphAnalogIn57644SnmpCommunityStringRead OBJECT-TYPE
    SYNTAX OCTET STRING
    ACCESS read-write
    STATUS mandatory
    DESCRIPTION
        "Community string read only"
    ::= { wtWebGraphAnalogIn57644SNMP 1 }

wtWebGraphAnalogIn57644SnmpCommunityStringReadWrite OBJECT-TYPE
    SYNTAX OCTET STRING
    ACCESS read-write
    STATUS mandatory
    DESCRIPTION
        "Community string read / write"
    ::= { wtWebGraphAnalogIn57644SNMP 2 }

wtWebGraphAnalogIn57644SystemTrapManagerIP OBJECT-TYPE
    SYNTAX OCTET STRING 
    ACCESS read-write
    STATUS mandatory
    DESCRIPTION
        "Name or IP address of the TCP server which accepts the system trap."
    ::= { wtWebGraphAnalogIn57644SNMP 3 }
    
wtWebGraphAnalogIn57644SystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2-7: unused"
    ::= { wtWebGraphAnalogIn57644SNMP 4 }
    
wtWebGraphAnalogIn57644SnmpEnable OBJECT-TYPE
    SYNTAX OCTET STRING 
    ACCESS read-write
    STATUS mandatory
    DESCRIPTION
        "Set bit 0 to enable SNMP.
        If disabled, the device did not respond to any SNMP requests.
        Bit 1 decided wether the community string of read operations 
        is compared with the system password or not:
        Octet 1: unused
        Octet 2: unused
        Octet 3: unused
        Octet 4:
        	Bit 1-7: unused
        	Bit 0  : SNMP enable"
    ::= { wtWebGraphAnalogIn57644SNMP 5 }
    
wtWebGraphAnalogIn57644SnmpCommunityStringTrap OBJECT-TYPE
    SYNTAX OCTET STRING
    ACCESS read-write
    STATUS mandatory
    DESCRIPTION
        "Community string send within traps."
    ::= { wtWebGraphAnalogIn57644SNMP 6 }    
            
    
-- wtWebGraphAnalogIn57644UDP Group
--------------------------------
    
wtWebGraphAnalogIn57644UdpPort OBJECT-TYPE
    SYNTAX INTEGER (1..65535)
    ACCESS read-write
    STATUS mandatory
    DESCRIPTION
        "Udp port to which the Udp queries ( short form GET requests) can be sent. This
        port number must be unique within the device."
    ::= { wtWebGraphAnalogIn57644UDP 1 }
    
wtWebGraphAnalogIn57644UdpEnable OBJECT-TYPE
    SYNTAX OCTET STRING 
    ACCESS read-write
    STATUS mandatory
    DESCRIPTION
        "Set this bit to enable UDP support:
        Octet 1: unused
        Octet 2: unused
        Octet 3: unused
        Octet 4:
        	Bit 1-7: unused
                Bit 0  : UDP enable"
    ::= { wtWebGraphAnalogIn57644UDP 2 }
    
--  wtWebGraphAnalogIn57644Syslog Group
--------------------------------
    
wtWebGraphAnalogIn57644SyslogServerIP OBJECT-TYPE
    SYNTAX OCTET STRING 
    ACCESS read-write
    STATUS mandatory
    DESCRIPTION
        "Name or IP address of the Syslog server, which accepts the Syslog messgaes."
    ::= { wtWebGraphAnalogIn57644Syslog 1 }
    
wtWebGraphAnalogIn57644SyslogServerPort OBJECT-TYPE
    SYNTAX INTEGER
    ACCESS read-write
    STATUS mandatory
    DESCRIPTION
        "Portnumber of the Syslog servers, default 514."
    ::= { wtWebGraphAnalogIn57644Syslog 2 }

wtWebGraphAnalogIn57644SyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebGraphAnalogIn57644Syslog 3 }    

wtWebGraphAnalogIn57644SyslogEnable OBJECT-TYPE
    SYNTAX OCTET STRING 
    ACCESS read-write
    STATUS mandatory
    DESCRIPTION
        "Set bit 0to enable Syslog:
        Octet 1: unused
        Octet 2: unused
        Octet 3: unused
        Octet 4:
        	Bit 1-7: unused
                Bit 0  : Syslog enable"
    ::= { wtWebGraphAnalogIn57644Syslog 4 }
    
--  wtWebGraphAnalogIn57644FTP Group
--------------------------------

wtWebGraphAnalogIn57644FTPServerIP OBJECT-TYPE
    SYNTAX OCTET STRING 
    ACCESS read-write
    STATUS mandatory
    DESCRIPTION
        "Name or IP address of the FTP server, which accepts the FTP messages."
    ::= { wtWebGraphAnalogIn57644FTP 1 }
    
wtWebGraphAnalogIn57644FTPServerControlPort OBJECT-TYPE
    SYNTAX INTEGER
    ACCESS read-write
    STATUS mandatory
    DESCRIPTION
        "Portnumber of the control port of the FTP server, default 21."
    ::= { wtWebGraphAnalogIn57644FTP 2 }
    
wtWebGraphAnalogIn57644FTPUserName OBJECT-TYPE
    SYNTAX OCTET STRING 
    ACCESS read-write
    STATUS mandatory
    DESCRIPTION
        "FTP Loggin: user name."
    ::= { wtWebGraphAnalogIn57644FTP 3 }
    
wtWebGraphAnalogIn57644FTPPassword OBJECT-TYPE
    SYNTAX OCTET STRING 
    ACCESS read-write
    STATUS mandatory
    DESCRIPTION
        "FTP Loggin: user password."
    ::= { wtWebGraphAnalogIn57644FTP 4 }

wtWebGraphAnalogIn57644FTPAccount OBJECT-TYPE
    SYNTAX OCTET STRING 
    ACCESS read-write
    STATUS mandatory
    DESCRIPTION
        "FTP Loggin: name of account."
    ::= { wtWebGraphAnalogIn57644FTP 5 }

wtWebGraphAnalogIn57644FTPOption OBJECT-TYPE
    SYNTAX OCTET STRING 
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebGraphAnalogIn57644FTP 6 }
    
wtWebGraphAnalogIn57644FTPEnable OBJECT-TYPE
    SYNTAX OCTET STRING 
    ACCESS read-write
    STATUS mandatory
    DESCRIPTION
        "Set Bit 0 to enable FTP:
        Octet 1: unused
        Octet 2: unused
        Octet 3: unused
        Octet 4:
        	Bit 1-7: unused
                Bit 0  : FTP enable"
    ::= { wtWebGraphAnalogIn57644FTP 7 }    
    
-- wtWebGraphAnalogIn57644Datalogger Group
--------------------------------

wtWebGraphAnalogIn57644LoggerTimebase OBJECT-TYPE
    SYNTAX INTEGER {
    wtWebGraphAnalogIn57644Datalogger-1Min(1),
    wtWebGraphAnalogIn57644Datalogger-5Min(2),
    wtWebGraphAnalogIn57644Datalogger-15Min(3),
    wtWebGraphAnalogIn57644Datalogger-60Min(4)
    }
    ACCESS read-write
    STATUS mandatory
    DESCRIPTION
        "Time base of the data logger"
    ::= { wtWebGraphAnalogIn57644Datalogger 1 }

wtWebGraphAnalogIn57644LoggerSensorSel OBJECT-TYPE
    SYNTAX OCTET STRING (SIZE(4))
    ACCESS read-write
    STATUS mandatory
    DESCRIPTION
        "Binary coded trigger conditions:
        Octet 1: unused
        Octet 2: unused
        Octet 3: unused
        Octet 4:
        	Bit 0: Sensor 1
        	Bit 1: Sensor 2
        	Bit 2-7: unused"
    ::= { wtWebGraphAnalogIn57644Datalogger 2 }

wtWebGraphAnalogIn57644DisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0: Sensor 1
        	Bit 1: Sensor 2
        	Bit 2-7: unused"
    ::= { wtWebGraphAnalogIn57644Datalogger 3 }    
    
-- Graph Sensor Color Table

wtWebGraphAnalogIn57644SensorColorTable OBJECT-TYPE
    SYNTAX SEQUENCE OF WtWebGraphAnalogIn57644SensorColorEntry
    ACCESS not-accessible
    STATUS mandatory
    DESCRIPTION
        "List of sensor colors for the praphical presentation."
    ::= { wtWebGraphAnalogIn57644Datalogger 4 }

wtWebGraphAnalogIn57644SensorColorEntry OBJECT-TYPE
    SYNTAX WtWebGraphAnalogIn57644SensorColorEntry
    ACCESS not-accessible
    STATUS mandatory
    DESCRIPTION
        "Index numbers of the sensors."
    INDEX  { wtWebGraphAnalogIn57644SensorNo }
    ::= { wtWebGraphAnalogIn57644SensorColorTable 1 }

WtWebGraphAnalogIn57644SensorColorEntry ::= SEQUENCE {
    wtWebGraphAnalogIn57644SensorColor OCTET STRING
}

wtWebGraphAnalogIn57644SensorColor OBJECT-TYPE
    SYNTAX OCTET STRING (SIZE(3))
    ACCESS read-write
    STATUS mandatory
    DESCRIPTION
        "Color of the sensors at the praphical presention."
    ::= { wtWebGraphAnalogIn57644SensorColorEntry 1 }
    
wtWebGraphAnalogIn57644AutoScaleEnable OBJECT-TYPE
    SYNTAX OCTET STRING 
    ACCESS read-write
    STATUS mandatory
    DESCRIPTION
        "If bit 0 is set, vertical auto scale is enabled:
        Octet 1: unused
        Octet 2: unused
        Octet 3: unused
        Octet 4:
        	Bit 1-7: unused
                Bit 0  : Auto Scale enable"
    ::= { wtWebGraphAnalogIn57644Datalogger 5 }
    
wtWebGraphAnalogIn57644VerticalUpperLimit OBJECT-TYPE
    SYNTAX OCTET STRING 
    ACCESS read-write
    STATUS mandatory
    DESCRIPTION
        "This value defines the maximum temperature shown in the graphical presentation,
        if no auto scaling is selected.
        Temperature in degrees with maximum 2 decimal places."
    ::= { wtWebGraphAnalogIn57644Datalogger 6 }

wtWebGraphAnalogIn57644VerticalLowerLimit OBJECT-TYPE
    SYNTAX OCTET STRING 
    ACCESS read-write
    STATUS mandatory
    DESCRIPTION
        "This value defines the minimum temperature shown in the graphical presentation,
        if no auto scaling is selected.
        Temperature in degrees with maximum 2 decimal places."
    ::= { wtWebGraphAnalogIn57644Datalogger 7 }
    
wtWebGraphAnalogIn57644HorizontalZoom OBJECT-TYPE
    SYNTAX INTEGER {
    wtWebGraphAnalogIn57644Zoom-25min(1),
    wtWebGraphAnalogIn57644Zoom-75min(2),
    wtWebGraphAnalogIn57644Zoom-5hrs(3),
    wtWebGraphAnalogIn57644Zoom-30hrs(4),
    wtWebGraphAnalogIn57644Zoom-5days(5),
    wtWebGraphAnalogIn57644Zoom-25days(6)
    }
    ACCESS read-write
    STATUS mandatory
    DESCRIPTION
        "Defines the default zoom stage, if no auto scaling is selected."
    ::= { wtWebGraphAnalogIn57644Datalogger 8 }    

-- wtWebGraphAnalogIn57644Alarm Group
----------------------------

wtWebGraphAnalogIn57644AlarmCount OBJECT-TYPE
    SYNTAX INTEGER (1..8)
    ACCESS read-only
    STATUS mandatory
    DESCRIPTION
        "Number of independent alarms."
    ::= { wtWebGraphAnalogIn57644Alarm 1 }
    
-- Alarm Interface Table

wtWebGraphAnalogIn57644AlarmIfTable OBJECT-TYPE
    SYNTAX SEQUENCE OF WtWebGraphAnalogIn57644AlarmIfEntry
    ACCESS not-accessible
    STATUS mandatory
    DESCRIPTION
        "List of alarm indices."
    ::= { wtWebGraphAnalogIn57644Alarm 2 }

wtWebGraphAnalogIn57644AlarmIfEntry OBJECT-TYPE
    SYNTAX WtWebGraphAnalogIn57644AlarmIfEntry
    ACCESS not-accessible
    STATUS mandatory
    DESCRIPTION
        "Numbers of the alarms."
    INDEX  { wtWebGraphAnalogIn57644AlarmNo }
    ::= { wtWebGraphAnalogIn57644AlarmIfTable 1 }

WtWebGraphAnalogIn57644AlarmIfEntry ::= SEQUENCE {
    wtWebGraphAnalogIn57644AlarmNo INTEGER
}

wtWebGraphAnalogIn57644AlarmNo OBJECT-TYPE
    SYNTAX INTEGER (1..8)
    ACCESS read-only
    STATUS mandatory
    DESCRIPTION
        "Alarm number."
    ::= { wtWebGraphAnalogIn57644AlarmIfEntry 1 }

-- Alarm Table

wtWebGraphAnalogIn57644AlarmTable OBJECT-TYPE
    SYNTAX SEQUENCE OF WtWebGraphAnalogIn57644AlarmEntry
    ACCESS not-accessible
    STATUS mandatory
    DESCRIPTION
        "List of settings depending on the alarm number."
    ::= { wtWebGraphAnalogIn57644Alarm 3 }

wtWebGraphAnalogIn57644AlarmEntry OBJECT-TYPE
    SYNTAX WtWebGraphAnalogIn57644AlarmEntry
    ACCESS not-accessible
    STATUS mandatory
    DESCRIPTION
        "Alarm parameters of the individual alarms."
    INDEX  { wtWebGraphAnalogIn57644AlarmNo }
    ::= { wtWebGraphAnalogIn57644AlarmTable 1 }

WtWebGraphAnalogIn57644AlarmEntry ::= SEQUENCE {
    wtWebGraphAnalogIn57644AlarmTrigger			OCTET STRING,
    wtWebGraphAnalogIn57644AlarmMin			OCTET STRING,
    wtWebGraphAnalogIn57644AlarmMax			OCTET STRING,
    wtWebGraphAnalogIn57644AlarmHysteresis		OCTET STRING,
    wtWebGraphAnalogIn57644AlarmDelay			OCTET STRING,
    wtWebGraphAnalogIn57644AlarmInterval		OCTET STRING,
    wtWebGraphAnalogIn57644AlarmEnable			OCTET STRING,
    wtWebGraphAnalogIn57644AlarmEMailAddr		OCTET STRING,
    wtWebGraphAnalogIn57644AlarmMailSubject		OCTET STRING,
    wtWebGraphAnalogIn57644AlarmMailText		OCTET STRING,
    wtWebGraphAnalogIn57644AlarmManagerIP		OCTET STRING,
    wtWebGraphAnalogIn57644AlarmTrapText		OCTET STRING,
    wtWebGraphAnalogIn57644AlarmMailOptions		OCTET STRING,
    wtWebGraphAnalogIn57644AlarmTcpIpAddr		OCTET STRING,
    wtWebGraphAnalogIn57644AlarmTcpPort			INTEGER,
    wtWebGraphAnalogIn57644AlarmTcpText			OCTET STRING,
    wtWebGraphAnalogIn57644AlarmClearMailSubject	OCTET STRING,
    wtWebGraphAnalogIn57644AlarmClearMailText		OCTET STRING,
    wtWebGraphAnalogIn57644AlarmClearTrapText		OCTET STRING,
    wtWebGraphAnalogIn57644AlarmClearTcpText		OCTET STRING,
    wtWebGraphAnalogIn57644Alarm2Min			OCTET STRING,
    wtWebGraphAnalogIn57644Alarm2Max			OCTET STRING,
    wtWebGraphAnalogIn57644Alarm2Hysteresis		OCTET STRING,
    wtWebGraphAnalogIn57644AlarmSyslogIpAddr		OCTET STRING,
    wtWebGraphAnalogIn57644AlarmSyslogPort		INTEGER,
    wtWebGraphAnalogIn57644AlarmSyslogText		OCTET STRING,
    wtWebGraphAnalogIn57644AlarmSyslogClearText		OCTET STRING,
    wtWebGraphAnalogIn57644AlarmFtpDataPort		OCTET STRING,
    wtWebGraphAnalogIn57644AlarmFtpFileName		OCTET STRING,
    wtWebGraphAnalogIn57644AlarmFtpText			OCTET STRING,
    wtWebGraphAnalogIn57644AlarmFtpClearText		OCTET STRING,
    wtWebGraphAnalogIn57644AlarmFtpOption		OCTET STRING,
    wtWebGraphAnalogIn57644AlarmTimerCron		OCTET STRING

}

wtWebGraphAnalogIn57644AlarmTrigger OBJECT-TYPE
    SYNTAX OCTET STRING (SIZE(4))
    ACCESS read-write
    STATUS mandatory
    DESCRIPTION
        "Binary coded trigger conditions:
        Octet 1: unused
        Octet 2: unused
        Octet 3:
        	Bit 0: Timer
        	Bit 1: ColdStart
        	Bit 2: WarmStart
        	
        Octet 4:
        	Bit 0: Sensor 1
        	Bit 1: Sensor 2
        	Bit 2-7: unused"
    ::= { wtWebGraphAnalogIn57644AlarmEntry 1 }

wtWebGraphAnalogIn57644AlarmMin OBJECT-TYPE
    SYNTAX OCTET STRING 
    ACCESS read-write
    STATUS mandatory
    DESCRIPTION
        "Minimum temperature in degrees with maximum 2 decimal places."
    ::= { wtWebGraphAnalogIn57644AlarmEntry 2 }

wtWebGraphAnalogIn57644AlarmMax OBJECT-TYPE
    SYNTAX OCTET STRING 
    ACCESS read-write
    STATUS mandatory
    DESCRIPTION
        "Maximum temperature in degrees with maximum 2 decimal places."
    ::= { wtWebGraphAnalogIn57644AlarmEntry 3 }
    
wtWebGraphAnalogIn57644AlarmHysteresis OBJECT-TYPE
    SYNTAX OCTET STRING 
    ACCESS read-write
    STATUS mandatory
    DESCRIPTION
        "Temperature changes of this size clears the alarm state (MAX-hyst, MIN+hyst.)
        , in degrees with maximum 2 decimal places."
    ::= { wtWebGraphAnalogIn57644AlarmEntry 4 }

wtWebGraphAnalogIn57644AlarmDelay OBJECT-TYPE
    SYNTAX OCTET STRING 
    ACCESS read-write
    STATUS mandatory
    DESCRIPTION
        "Alarm will be delayed by setting this time while stable alarm 
        condition occur (time in minutes)."
    ::= { wtWebGraphAnalogIn57644AlarmEntry 5 }
        

wtWebGraphAnalogIn57644AlarmInterval OBJECT-TYPE
    SYNTAX OCTET STRING 
    ACCESS read-write
    STATUS mandatory
    DESCRIPTION
        "Send interval for alarm messages."
    ::= { wtWebGraphAnalogIn57644AlarmEntry 6 }

wtWebGraphAnalogIn57644AlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  TCP Client enable"
    ::= { wtWebGraphAnalogIn57644AlarmEntry 7 }

wtWebGraphAnalogIn57644AlarmEMailAddr OBJECT-TYPE
    SYNTAX OCTET STRING 
    ACCESS read-write
    STATUS mandatory
    DESCRIPTION
        "E-Mail address for sending the alarm mail to."
    ::= { wtWebGraphAnalogIn57644AlarmEntry 8 }

wtWebGraphAnalogIn57644AlarmMailSubject OBJECT-TYPE
    SYNTAX OCTET STRING 
    ACCESS read-write
    STATUS mandatory
    DESCRIPTION
        "Subject line for alarm mail."
    ::= { wtWebGraphAnalogIn57644AlarmEntry 9 }

wtWebGraphAnalogIn57644AlarmMailText OBJECT-TYPE
    SYNTAX OCTET STRING 
    ACCESS read-write
    STATUS mandatory
    DESCRIPTION
        "Alarm mail text: <Tn> provides the current temperature; n = 1..8.
        <Z> provides the current time."
    ::= { wtWebGraphAnalogIn57644AlarmEntry 10 }

wtWebGraphAnalogIn57644AlarmManagerIP OBJECT-TYPE
    SYNTAX OCTET STRING 
    ACCESS read-write
    STATUS mandatory
    DESCRIPTION
        "Name or IP address of the SNMP Manager which accepts the trap."
    ::= { wtWebGraphAnalogIn57644AlarmEntry 11 }

wtWebGraphAnalogIn57644AlarmTrapText OBJECT-TYPE
    SYNTAX OCTET STRING 
    ACCESS read-write
    STATUS mandatory
    DESCRIPTION
        "This text is sent in the trap body."
    ::= { wtWebGraphAnalogIn57644AlarmEntry 12 }
    
wtWebGraphAnalogIn57644AlarmMailOptions OBJECT-TYPE
    SYNTAX OCTET STRING (SIZE(4))
    ACCESS read-write
    STATUS mandatory
    DESCRIPTION
        "Binary coded options:
        Octet 1: unused
        Octet 2: unused
        Octet 3: unused
        Octet 4:
		Bit 0  :	Attach Thermo.csv Enable
		Bit 1  :	CSV-Data_since_last_report
        	Bit 2-7:	unused"
    ::= { wtWebGraphAnalogIn57644AlarmEntry 13 }    
    
wtWebGraphAnalogIn57644AlarmTcpIpAddr OBJECT-TYPE
    SYNTAX OCTET STRING 
    ACCESS read-write
    STATUS mandatory
    DESCRIPTION
        "Name or IP address of the TCP server which accepts the trap."
    ::= { wtWebGraphAnalogIn57644AlarmEntry 14 }    

wtWebGraphAnalogIn57644AlarmTcpPort OBJECT-TYPE
    SYNTAX INTEGER (1..65535) 
    ACCESS read-write
    STATUS mandatory
    DESCRIPTION
        "Port number of the TCP server which accepts the trap."
    ::= { wtWebGraphAnalogIn57644AlarmEntry 15 }    

wtWebGraphAnalogIn57644AlarmTcpText OBJECT-TYPE
    SYNTAX OCTET STRING 
    ACCESS read-write
    STATUS mandatory
    DESCRIPTION
        "This text is sent in the TCP trap body."
    ::= { wtWebGraphAnalogIn57644AlarmEntry 16 }

wtWebGraphAnalogIn57644AlarmClearMailSubject OBJECT-TYPE
    SYNTAX OCTET STRING 
    ACCESS read-write
    STATUS mandatory
    DESCRIPTION
        "Subject line for alarm clear mail."
    ::= { wtWebGraphAnalogIn57644AlarmEntry 17 }

wtWebGraphAnalogIn57644AlarmClearMailText OBJECT-TYPE
    SYNTAX OCTET STRING 
    ACCESS read-write
    STATUS mandatory
    DESCRIPTION
        "Alarm clear mail text: <Tn> provides the current temperature; n = 1..8.
        <Z> provides the current time."
    ::= { wtWebGraphAnalogIn57644AlarmEntry 18 }

wtWebGraphAnalogIn57644AlarmClearTrapText OBJECT-TYPE
    SYNTAX OCTET STRING 
    ACCESS read-write
    STATUS mandatory
    DESCRIPTION
        "This text is sent in the trap body."
    ::= { wtWebGraphAnalogIn57644AlarmEntry 19 }

wtWebGraphAnalogIn57644AlarmClearTcpText OBJECT-TYPE
    SYNTAX OCTET STRING 
    ACCESS read-write
    STATUS mandatory
    DESCRIPTION
        "This text is sent in the TCP trap body."
    ::= { wtWebGraphAnalogIn57644AlarmEntry 20 }
    
wtWebGraphAnalogIn57644Alarm2Min OBJECT-TYPE
    SYNTAX OCTET STRING 
    ACCESS read-write
    STATUS mandatory
    DESCRIPTION
        "Minimum rel. Humidity in percent with maximum 2 decimal places."
    ::= { wtWebGraphAnalogIn57644AlarmEntry 21 }

wtWebGraphAnalogIn57644Alarm2Max OBJECT-TYPE
    SYNTAX OCTET STRING 
    ACCESS read-write
    STATUS mandatory
    DESCRIPTION
        "Maximum rel.Humidity in percent with maximum 2 decimal places."
    ::= { wtWebGraphAnalogIn57644AlarmEntry 22 }

wtWebGraphAnalogIn57644Alarm2Hysteresis OBJECT-TYPE
    SYNTAX OCTET STRING 
    ACCESS read-write
    STATUS mandatory
    DESCRIPTION
        "Hysterese rel. Humidity in percent with maximum 2 decimal places."
    ::= { wtWebGraphAnalogIn57644AlarmEntry 23 }

wtWebGraphAnalogIn57644AlarmSyslogIpAddr OBJECT-TYPE
    SYNTAX OCTET STRING 
    ACCESS read-write
    STATUS mandatory
    DESCRIPTION
        "IP address of the syslog server to which the Webio device should send syslog messages."
    ::= { wtWebGraphAnalogIn57644AlarmEntry 24 }    

wtWebGraphAnalogIn57644AlarmSyslogPort OBJECT-TYPE
    SYNTAX INTEGER (1..65535) 
    ACCESS read-write
    STATUS mandatory
    DESCRIPTION
        "Port number of the syslog server to which the Webio device should send syslog messages."
    ::= { wtWebGraphAnalogIn57644AlarmEntry 25 }    

wtWebGraphAnalogIn57644AlarmSyslogText OBJECT-TYPE
    SYNTAX OCTET STRING 
    ACCESS read-write
    STATUS mandatory
    DESCRIPTION
        "Every message starts with the priority key, a time stamp and the host ip address, according RFC3164.
        This text appears in the following syslog message body."
    ::= { wtWebGraphAnalogIn57644AlarmEntry 26 }
    
wtWebGraphAnalogIn57644AlarmSyslogClearText OBJECT-TYPE
    SYNTAX OCTET STRING 
    ACCESS read-write
    STATUS mandatory
    DESCRIPTION
        "Every message starts with the priority key, a time stamp and the host ip address, according RFC3164.
        This text appears in the following syslog message body of a alarm clear message."
    ::= { wtWebGraphAnalogIn57644AlarmEntry 27 }
    
wtWebGraphAnalogIn57644AlarmFtpDataPort OBJECT-TYPE
    SYNTAX OCTET STRING 
    ACCESS read-write
    STATUS mandatory
    DESCRIPTION
        "Local data port: 1..65535 or AUTO: the next free port will be assigned."
    ::= { wtWebGraphAnalogIn57644AlarmEntry 28 }
    
wtWebGraphAnalogIn57644AlarmFtpFileName OBJECT-TYPE
    SYNTAX OCTET STRING 
    ACCESS read-write
    STATUS mandatory
    DESCRIPTION
        "Name of the file including path informations."
    ::= { wtWebGraphAnalogIn57644AlarmEntry 29 }
    
wtWebGraphAnalogIn57644AlarmFtpText OBJECT-TYPE
    SYNTAX OCTET STRING 
    ACCESS read-write
    STATUS mandatory
    DESCRIPTION
        "Message text to store on the FTP server."
    ::= { wtWebGraphAnalogIn57644AlarmEntry 30 }

wtWebGraphAnalogIn57644AlarmFtpClearText OBJECT-TYPE
    SYNTAX OCTET STRING 
    ACCESS read-write
    STATUS mandatory
    DESCRIPTION
        "Alarm clear message to store on the FTP server."
    ::= { wtWebGraphAnalogIn57644AlarmEntry 31 }
    
wtWebGraphAnalogIn57644AlarmFtpOption OBJECT-TYPE
    SYNTAX OCTET STRING (SIZE(4))
    ACCESS read-write
    STATUS mandatory
    DESCRIPTION
        "Binary coded options, select only one option at the same time:
        STORE  = replace file
        APPEND = append message at the end of the file
        
        Octet 1: unused
        Octet 2: unused
        Octet 3: unused
        Octet 4:
		Bit 0  :	STORE
		Bit 1  :	APPEND
        	Bit 2-7:	unused"
    ::= { wtWebGraphAnalogIn57644AlarmEntry 32 }      
    
wtWebGraphAnalogIn57644AlarmTimerCron OBJECT-TYPE
    SYNTAX OCTET STRING
    ACCESS read-write
    STATUS mandatory
    DESCRIPTION
        "This entry contains 5 space or tab seperated text fields for time trigger definition.
        Each field must match with the actual time to trigger a message, weekday and day of month
        are interpreted separatley.
        1: Minutes	Range 0-59
        2. Hours	Range 0-23, 0 is midnight
        3: Day of month	Range 1-31
        4: Month	Range 1-12
        5: Weekday	Range 0-6, 0 is sunday
        
        Syntax for every field:
         - an asterix (*) enables every possible setting of a field
         - single numbers seperated by commas
         - a partition within the allowed range (1-5)
         - step size within an partition of the allowed range (0-59/2: every second minute)."
    ::= { wtWebGraphAnalogIn57644AlarmEntry 33 }      
    
-- wtWebGraphAnalogIn57644GraphicsBase Group
----------------------------

wtWebGraphAnalogIn57644GraphicsBaseEnable OBJECT-TYPE
    SYNTAX OCTET STRING 
    ACCESS read-write
    STATUS mandatory
    DESCRIPTION
        "Defines the viewing options of the graphic:
        Octet 1: unused
        Octet 2: unused
        Octet 3: unused
        Octet 4:
                Bit 0  : Auto scroll enable
                Bit 1  : Show table
                Bit 2  : Show graph
                Bit 3  : Show control buttons
                Bit 4  : Show config menu
                Bit 5-7: unused"
    ::= { wtWebGraphAnalogIn57644GraphicsBase 1 }

wtWebGraphAnalogIn57644GraphicsBaseWidth OBJECT-TYPE
    SYNTAX INTEGER 
    ACCESS read-write
    STATUS mandatory
    DESCRIPTION
        "Defines the width of the graphic in pixels."
    ::= { wtWebGraphAnalogIn57644GraphicsBase 2 }
    
wtWebGraphAnalogIn57644GraphicsBaseHeight OBJECT-TYPE
        SYNTAX INTEGER 
        ACCESS read-write
        STATUS mandatory
        DESCRIPTION
            "Defines the height of the graphic in pixels."
        ::= { wtWebGraphAnalogIn57644GraphicsBase 3 }

wtWebGraphAnalogIn57644GraphicsBaseFrameColor OBJECT-TYPE
    SYNTAX OCTET STRING (SIZE(3))
    ACCESS read-write
    STATUS mandatory
    DESCRIPTION
        "Frame color definition in RGB."
    ::= { wtWebGraphAnalogIn57644GraphicsBase 4 }

wtWebGraphAnalogIn57644GraphicsBaseBackgroundColor OBJECT-TYPE
    SYNTAX OCTET STRING (SIZE(3))
    ACCESS read-write
    STATUS mandatory
    DESCRIPTION
        "Background color definition in RGB."
    ::= { wtWebGraphAnalogIn57644GraphicsBase 5 }
    
wtWebGraphAnalogIn57644GraphicsBasePollingrate OBJECT-TYPE
        SYNTAX INTEGER 
        ACCESS read-write
        STATUS mandatory
        DESCRIPTION
            "Defines the pollingrate in seconds, 
            which defines the refreshing intervall of the graphic."
        ::= { wtWebGraphAnalogIn57644GraphicsBase 6 }
   
-- wtWebGraphAnalogIn57644GraphicsSelect Group
----------------------------

wtWebGraphAnalogIn57644GraphicsSelectDisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0: Sensor 1
        	Bit 1: Sensor 2
        	Bit 2: Sensor 3
        	Bit 3: Sensor 4
        	Bit 4: Sensor 5
        	Bit 5: Sensor 6
        	Bit 6: Sensor 7
        	Bit 7: Sensor 8"
    ::= { wtWebGraphAnalogIn57644GraphicsSelect 1 }   
    
wtWebGraphAnalogIn57644GraphicsSelectDisplayShowExtrem OBJECT-TYPE
    SYNTAX OCTET STRING (SIZE(4))
    ACCESS read-write
    STATUS mandatory
    DESCRIPTION
        "Binary coded sensor selection:
        only selected sensors will be shown with minima and maxima:
        Octet 1: unused
        Octet 2: unused
        Octet 3: unused
        Octet 4:
        	Bit 0: Sensor 1
        	Bit 1: Sensor 2
        	Bit 2: Sensor 3
        	Bit 3: Sensor 4
        	Bit 4: Sensor 5
        	Bit 5: Sensor 6
        	Bit 6: Sensor 7
        	Bit 7: Sensor 8"
     ::= { wtWebGraphAnalogIn57644GraphicsSelect 2 }   

-- Graph Sensor Color Table

wtWebGraphAnalogIn57644SensorColor2Table OBJECT-TYPE
    SYNTAX SEQUENCE OF WtWebGraphAnalogIn57644SensorColor2Entry
    ACCESS not-accessible
    STATUS mandatory
    DESCRIPTION
        "List of sensor colors for the praphical presentation."
    ::= { wtWebGraphAnalogIn57644GraphicsSelect 3 }

wtWebGraphAnalogIn57644SensorColor2Entry OBJECT-TYPE
    SYNTAX WtWebGraphAnalogIn57644SensorColor2Entry
    ACCESS not-accessible
    STATUS mandatory
    DESCRIPTION
        "Numbers of the sensors."
    INDEX  { wtWebGraphAnalogIn57644SensorNo }
    ::= { wtWebGraphAnalogIn57644SensorColor2Table 1 }

WtWebGraphAnalogIn57644SensorColor2Entry ::= SEQUENCE {
    wtWebGraphAnalogIn57644GraphicsSensorColor OCTET STRING,
    wtWebGraphAnalogIn57644GraphicsSelectScale OCTET STRING
}

wtWebGraphAnalogIn57644GraphicsSensorColor OBJECT-TYPE
    SYNTAX OCTET STRING (SIZE(3))
    ACCESS read-write
    STATUS mandatory
    DESCRIPTION
        "Color of the sensors at the praphical presention."
    ::= { wtWebGraphAnalogIn57644SensorColor2Entry 1 }
    
wtWebGraphAnalogIn57644GraphicsSelectScale OBJECT-TYPE
    SYNTAX OCTET STRING 
    ACCESS read-write
    STATUS mandatory
    DESCRIPTION
        "Assignes one of 4 scales to a sensor:
        Octet 1: unused
        Octet 2: unused
        Octet 3: unused
        Octet 4:
                Bit 0  : Use Scale 1
                Bit 1  : Use Scale 2
                Bit 2  : Use Scale 3
                Bit 3  : Use Scale 4
                Bit 4-7: unused"
    ::= { wtWebGraphAnalogIn57644SensorColor2Entry 2 }
   
-- wtWebGraphAnalogIn57644GraphicsScale Group
----------------------------

wtWebGraphAnalogIn57644GraphicsScaleAutoScaleEnable OBJECT-TYPE
    SYNTAX OCTET STRING 
    ACCESS read-write
    STATUS mandatory
    DESCRIPTION
        "Select the Auto Scale Mode:
        Octet 1: unused
        Octet 2: unused
        Octet 3: unused
        Octet 4:
                Bit 0  : Scale 1 Auto scale enable
                Bit 1  : Scale 2 Auto scale enable
                Bit 2  : Scale 3 Auto scale enable
                Bit 3  : Scale 4 Auto scale enable
                Bit 4-7: unused"
    ::= { wtWebGraphAnalogIn57644GraphicsScale 1 }


wtWebGraphAnalogIn57644GraphicsScaleAutoFitEnable OBJECT-TYPE
    SYNTAX OCTET STRING 
    ACCESS read-write
    STATUS mandatory
    DESCRIPTION
        "Select the Auto Fit Mode::
        Octet 1: unused
        Octet 2: unused
        Octet 3: unused
        Octet 4:
                Bit 0  : Scale 1 Auto fit enable
                Bit 1  : Scale 2 Auto fit enable
                Bit 2  : Scale 3 Auto fit enable
                Bit 3  : Scale 4 Auto fit enable
                Bit 4-7: unused"
    ::= { wtWebGraphAnalogIn57644GraphicsScale 2 }

wtWebGraphAnalogIn57644GraphicsScale1Min OBJECT-TYPE
    SYNTAX INTEGER
    ACCESS read-only
    STATUS mandatory
    DESCRIPTION
        "Scale 1: Minimum."
    ::= { wtWebGraphAnalogIn57644GraphicsScale 3 }
   
wtWebGraphAnalogIn57644GraphicsScale2Min OBJECT-TYPE
    SYNTAX INTEGER
    ACCESS read-only
    STATUS mandatory
    DESCRIPTION
        "Scale 2: Minimum."
    ::= { wtWebGraphAnalogIn57644GraphicsScale 4 }

wtWebGraphAnalogIn57644GraphicsScale3Min OBJECT-TYPE
    SYNTAX INTEGER
    ACCESS read-only
    STATUS mandatory
    DESCRIPTION
        "Scale 3: Minimum."
    ::= { wtWebGraphAnalogIn57644GraphicsScale 5 }

wtWebGraphAnalogIn57644GraphicsScale4Min OBJECT-TYPE
    SYNTAX INTEGER
    ACCESS read-only
    STATUS mandatory
    DESCRIPTION
        "Scale 4: Minimum."
    ::= { wtWebGraphAnalogIn57644GraphicsScale 6 }

wtWebGraphAnalogIn57644GraphicsScale1Max OBJECT-TYPE
    SYNTAX INTEGER
    ACCESS read-only
    STATUS mandatory
    DESCRIPTION
        "Scale 1: Maximum."
    ::= { wtWebGraphAnalogIn57644GraphicsScale 7 }

wtWebGraphAnalogIn57644GraphicsScale2Max OBJECT-TYPE
    SYNTAX INTEGER
    ACCESS read-only
    STATUS mandatory
    DESCRIPTION
        "Scale 2: Maximum."
    ::= { wtWebGraphAnalogIn57644GraphicsScale 8 }

wtWebGraphAnalogIn57644GraphicsScale3Max OBJECT-TYPE
    SYNTAX INTEGER
    ACCESS read-only
    STATUS mandatory
    DESCRIPTION
        "Scale 3: Maximum."
    ::= { wtWebGraphAnalogIn57644GraphicsScale 9 }

wtWebGraphAnalogIn57644GraphicsScale4Max OBJECT-TYPE
    SYNTAX INTEGER
    ACCESS read-only
    STATUS mandatory
    DESCRIPTION
        "Scale 4: Maximum."
    ::= { wtWebGraphAnalogIn57644GraphicsScale 10 }

wtWebGraphAnalogIn57644GraphicsScale1Unit OBJECT-TYPE
    SYNTAX OCTET STRING
    ACCESS read-only
    STATUS mandatory
    DESCRIPTION
        "Scale 1: Unit."
    ::= { wtWebGraphAnalogIn57644GraphicsScale 11 }

wtWebGraphAnalogIn57644GraphicsScale2Unit OBJECT-TYPE
    SYNTAX OCTET STRING
    ACCESS read-only
    STATUS mandatory
    DESCRIPTION
        "Scale 2: Unit."
    ::= { wtWebGraphAnalogIn57644GraphicsScale 12 }

wtWebGraphAnalogIn57644GraphicsScale3Unit OBJECT-TYPE
    SYNTAX OCTET STRING
    ACCESS read-only
    STATUS mandatory
    DESCRIPTION
        "Scale 3: Unit."
    ::= { wtWebGraphAnalogIn57644GraphicsScale 13 }

wtWebGraphAnalogIn57644GraphicsScale4Unit OBJECT-TYPE
    SYNTAX OCTET STRING
    ACCESS read-only
    STATUS mandatory
    DESCRIPTION
        "Scale 4: Unit."
    ::= { wtWebGraphAnalogIn57644GraphicsScale 14 }    
    
-- wtWebGraphAnalogIn57644Ports Group
----------------------------

-- Table

wtWebGraphAnalogIn57644PortTable OBJECT-TYPE
    SYNTAX SEQUENCE OF WtWebGraphAnalogIn57644PortEntry
    ACCESS not-accessible
    STATUS mandatory
    DESCRIPTION
        "List of settings depending on the sensor number."
    ::= { wtWebGraphAnalogIn57644Ports 1 }

wtWebGraphAnalogIn57644PortEntry OBJECT-TYPE
    SYNTAX WtWebGraphAnalogIn57644PortEntry
    ACCESS not-accessible
    STATUS mandatory
    DESCRIPTION
        "Sensor parameters for the individual sensors."
    INDEX  { wtWebGraphAnalogIn57644SensorNo }
    ::= { wtWebGraphAnalogIn57644PortTable 1 }

WtWebGraphAnalogIn57644PortEntry ::= SEQUENCE {
    wtWebGraphAnalogIn57644PortName		OCTET STRING,
    wtWebGraphAnalogIn57644PortText		OCTET STRING,
    wtWebGraphAnalogIn57644PortOffset1		OCTET STRING,
    wtWebGraphAnalogIn57644SetPoint1		OCTET STRING,
    wtWebGraphAnalogIn57644PortOffset2		OCTET STRING,
    wtWebGraphAnalogIn57644SetPoint2		OCTET STRING,
    wtWebGraphAnalogIn57644PortComment		OCTET STRING,
    wtWebGraphAnalogIn57644PortSensorSelect	OCTET STRING,
    wtWebGraphAnalogIn57644PortUnit		OCTET STRING,
    wtWebGraphAnalogIn57644PortScale0		OCTET STRING,
    wtWebGraphAnalogIn57644PortScale100		OCTET STRING
}

wtWebGraphAnalogIn57644PortName OBJECT-TYPE
    SYNTAX OCTET STRING 
    ACCESS read-write
    STATUS mandatory
    DESCRIPTION
        "Name of the sensor."
    ::= { wtWebGraphAnalogIn57644PortEntry 1 }

wtWebGraphAnalogIn57644PortText OBJECT-TYPE
    SYNTAX OCTET STRING 
    ACCESS read-write
    STATUS mandatory
    DESCRIPTION
        "Description of the sensor."
    ::= { wtWebGraphAnalogIn57644PortEntry 2 }

wtWebGraphAnalogIn57644PortOffset1 OBJECT-TYPE
    SYNTAX OCTET STRING 
    ACCESS read-write
    STATUS mandatory
    DESCRIPTION
        "Offset calibration: Offset in degrees with maximum 2 decimal places at set point 1."
    ::= { wtWebGraphAnalogIn57644PortEntry 3 }

wtWebGraphAnalogIn57644SetPoint1 OBJECT-TYPE
    SYNTAX OCTET STRING 
    ACCESS read-write
    STATUS mandatory
    DESCRIPTION
        "Offset calibration: set point 1 in degrees with maximum 2 decimal places."
    ::= { wtWebGraphAnalogIn57644PortEntry 4 }

wtWebGraphAnalogIn57644PortOffset2 OBJECT-TYPE
    SYNTAX OCTET STRING 
    ACCESS read-write
    STATUS mandatory
    DESCRIPTION
        "Offset calibration: Offset in degrees with maximum 2 decimal places at set point 2."
    ::= { wtWebGraphAnalogIn57644PortEntry 5 }

wtWebGraphAnalogIn57644SetPoint2 OBJECT-TYPE
    SYNTAX OCTET STRING 
    ACCESS read-write
    STATUS mandatory
    DESCRIPTION
        "Offset calibration: set point 2 in degrees with maximum 2 decimal places."
    ::= { wtWebGraphAnalogIn57644PortEntry 6 }

wtWebGraphAnalogIn57644PortComment OBJECT-TYPE
    SYNTAX OCTET STRING 
    ACCESS read-write
    STATUS mandatory
    DESCRIPTION
        "Offset calibration: informations of date, name of operator, reference devices."
    ::= { wtWebGraphAnalogIn57644PortEntry 7 }   

wtWebGraphAnalogIn57644PortSensorSelect OBJECT-TYPE
    SYNTAX OCTET STRING (SIZE(4))
    ACCESS read-write
    STATUS mandatory
    DESCRIPTION
        "Binary coded options for sensor 1:
        Octet 1: unused
        Octet 2: unused
        Octet 3: unused
        Octet 4:
		Bit 0  :	0-10V (default)
		Bit 1  :	Disconnect
        	Bit 2-7:	unused
        
        Binary coded options for sensor 2:
	Octet 1: unused
	Octet 2: unused
	Octet 3: unused
	Octet 4:
		Bit 0  :	0-10V (default)
		Bit 1  :	Disconnect
        	Bit 2-7:	unused"
    ::= { wtWebGraphAnalogIn57644PortEntry 8 }    
    
wtWebGraphAnalogIn57644PortUnit OBJECT-TYPE
    SYNTAX OCTET STRING 
    ACCESS read-write
    STATUS mandatory
    DESCRIPTION
        "User scale: displayed unit."
    ::= { wtWebGraphAnalogIn57644PortEntry 9 }   
    
wtWebGraphAnalogIn57644PortScale0 OBJECT-TYPE
    SYNTAX OCTET STRING 
    ACCESS read-write
    STATUS mandatory
    DESCRIPTION
        "User scale: displayed value in 1/1000 at 0% full scale range.
        Range: -999999.999 to 999999.999"
    ::= { wtWebGraphAnalogIn57644PortEntry 10 }   

wtWebGraphAnalogIn57644PortScale100 OBJECT-TYPE
    SYNTAX OCTET STRING 
    ACCESS read-write
    STATUS mandatory
    DESCRIPTION
        "User scale: displayed value in 1/1000 at 100% full scale range.
        Range: -999999.999 to 999999.999"
    ::= { wtWebGraphAnalogIn57644PortEntry 11 }   

-- wtWebGraphAnalogIn57644Manufact Group
----------------------------

wtWebGraphAnalogIn57644MfName OBJECT-TYPE
    SYNTAX OCTET STRING 
    ACCESS read-write
    STATUS mandatory
    DESCRIPTION
        "Manufacturer company name"
    ::= { wtWebGraphAnalogIn57644Manufact 1 }

wtWebGraphAnalogIn57644MfAddr OBJECT-TYPE
    SYNTAX OCTET STRING 
    ACCESS read-write
    STATUS mandatory
    DESCRIPTION
        "Manufacturer address."
    ::= { wtWebGraphAnalogIn57644Manufact 2 }

wtWebGraphAnalogIn57644MfHotline OBJECT-TYPE
    SYNTAX OCTET STRING 
    ACCESS read-write
    STATUS mandatory
    DESCRIPTION
        "Manufacturer hotline."
    ::= { wtWebGraphAnalogIn57644Manufact 3 }

wtWebGraphAnalogIn57644MfInternet OBJECT-TYPE
    SYNTAX OCTET STRING 
    ACCESS read-write
    STATUS mandatory
    DESCRIPTION
        "Manufacturer Internet address."
    ::= { wtWebGraphAnalogIn57644Manufact 4 }

wtWebGraphAnalogIn57644MfDeviceTyp OBJECT-TYPE
    SYNTAX OCTET STRING 
    ACCESS read-write
    STATUS mandatory
    DESCRIPTION
        "Manufacturer device name (model number)."
    ::= { wtWebGraphAnalogIn57644Manufact 5 }

wtWebGraphAnalogIn57644MfOrderNo OBJECT-TYPE
    SYNTAX OCTET STRING 
    ACCESS read-write
    STATUS mandatory
    DESCRIPTION
        "Manufacturer part number."
    ::= { wtWebGraphAnalogIn57644Manufact 6 }

-- wtWebGraphAnalogIn57644Diag Group
----------------------------

wtWebGraphAnalogIn57644DiagErrorCount OBJECT-TYPE
    SYNTAX INTEGER
    ACCESS read-only
    STATUS mandatory
    DESCRIPTION
        "Number of entries in the error memory."
    ::= { wtWebGraphAnalogIn57644Diag 1 }

wtWebGraphAnalogIn57644DiagBinaryError OBJECT-TYPE
    SYNTAX OCTET STRING 
    ACCESS read-only
    STATUS mandatory
    DESCRIPTION
        "Error causes coded bit-by-bit."
    ::= { wtWebGraphAnalogIn57644Diag 2 }

wtWebGraphAnalogIn57644DiagErrorIndex OBJECT-TYPE
    SYNTAX INTEGER
    ACCESS read-write
    STATUS mandatory
    DESCRIPTION
        "The value of this variable is used as an index to read 
        an error massege from wtWebGraphAnalogIn57644DiagErrorMessage.
        Errors are numbered from 1 to wtWebGraphAnalogIn57644DiagErrorCount.
        Writing a valid value into this variable, making the appropriate 
        message readable from wtWebGraphAnalogIn57644DiagErrorMessage."
    ::= { wtWebGraphAnalogIn57644Diag 3 }

wtWebGraphAnalogIn57644DiagErrorMessage OBJECT-TYPE
    SYNTAX OCTET STRING 
    ACCESS read-only
    STATUS mandatory
    DESCRIPTION
        "Using wtWebGraphAnalogIn57644DiagErrorIndex as an index, the appropriate message is available."
    ::= { wtWebGraphAnalogIn57644Diag 4 }
    
wtWebGraphAnalogIn57644DiagErrorClear OBJECT-TYPE
    SYNTAX INTEGER
    ACCESS write-only
    STATUS mandatory
    DESCRIPTION
        "Writing 1 into this variable clears all diagnosis messages."
    ::= { wtWebGraphAnalogIn57644Diag 5 }

-- TRAP DEFINITIONS

-- Diese SNMP-Traps werden gesendet, wenn die Alarmtriggerbedingungen zutreffen 

wtWebGraphAnalogIn57644Alert1 TRAP-TYPE
    ENTERPRISE  wtWebGraphAnalogIn57644
    VARIABLES   { wtWebGraphAnalogIn57644AlarmTrapText }
    DESCRIPTION
        "This SNMP trap is generated when Alarm 1 was triggered,
        SNMP trap enable is set and
        SNMP is enabled."
    -- NMS trap annotation
    --#TYPE "Thermo-Hygrometer Alarm 1"
    --#SUMMARY "Alarm 1: %s"
    --#ARGUMENTS {0}
    --#SEVERITY INFORMATIONAL
    --#TIMEINDEX 99
    --#STATE OPERATIONAL    
    ::= 31

wtWebGraphAnalogIn57644Alert2 TRAP-TYPE
    ENTERPRISE  wtWebGraphAnalogIn57644
    VARIABLES   { wtWebGraphAnalogIn57644AlarmTrapText }
    DESCRIPTION
        "This SNMP trap is generated when Alarm 2 was triggered,
        SNMP trap enable is set and
        SNMP is enabled."
    -- NMS trap annotation
    --#TYPE "Thermo-Hygrometer Alarm 2"
    --#SUMMARY "Alarm 2: %s"
    --#ARGUMENTS {0}
    --#SEVERITY INFORMATIONAL
    --#TIMEINDEX 99
    --#STATE OPERATIONAL    
    ::= 32

wtWebGraphAnalogIn57644Alert3 TRAP-TYPE
    ENTERPRISE  wtWebGraphAnalogIn57644
    VARIABLES   { wtWebGraphAnalogIn57644AlarmTrapText }
    DESCRIPTION
        "This SNMP trap is generated when Alarm 3 was triggered,
        SNMP trap enable is set and
        SNMP is enabled."
    -- NMS trap annotation
    --#TYPE "Thermo-Hygrometer Alarm 3"
    --#SUMMARY "Alarm 3: %s"
    --#ARGUMENTS {0}
    --#SEVERITY INFORMATIONAL
    --#TIMEINDEX 99
    --#STATE OPERATIONAL    
    ::= 33

wtWebGraphAnalogIn57644Alert4 TRAP-TYPE
    ENTERPRISE  wtWebGraphAnalogIn57644
    VARIABLES   { wtWebGraphAnalogIn57644AlarmTrapText }
    DESCRIPTION
        "This SNMP trap is generated when Alarm 4 was triggered,
        SNMP trap enable is set and
        SNMP is enabled."
    -- NMS trap annotation
    --#TYPE "Thermo-Hygrometer Alarm 4"
    --#SUMMARY "Alarm 4: %s"
    --#ARGUMENTS {0}
    --#SEVERITY INFORMATIONAL
    --#TIMEINDEX 99
    --#STATE OPERATIONAL    
    ::= 34

wtWebGraphAnalogIn57644Alert5 TRAP-TYPE
    ENTERPRISE  wtWebGraphAnalogIn57644
    VARIABLES   { wtWebGraphAnalogIn57644AlarmTrapText }
    DESCRIPTION
        "This SNMP trap is generated when Alarm 5 was triggered,
        SNMP trap enable is set and
        SNMP is enabled."
    -- NMS trap annotation
    --#TYPE "Thermo-Hygrometer Alarm 5"
    --#SUMMARY "Alarm 5: %s"
    --#ARGUMENTS {0}
    --#SEVERITY INFORMATIONAL
    --#TIMEINDEX 99
    --#STATE OPERATIONAL    
    ::= 35

wtWebGraphAnalogIn57644Alert6 TRAP-TYPE
    ENTERPRISE  wtWebGraphAnalogIn57644
    VARIABLES   { wtWebGraphAnalogIn57644AlarmTrapText }
    DESCRIPTION
        "This SNMP trap is generated when Alarm 6 was triggered,
        SNMP trap enable is set and
        SNMP is enabled."
    -- NMS trap annotation
    --#TYPE "Thermo-Hygrometer Alarm 6"
    --#SUMMARY "Alarm 6: %s"
    --#ARGUMENTS {0}
    --#SEVERITY INFORMATIONAL
    --#TIMEINDEX 99
    --#STATE OPERATIONAL    
    ::= 36

wtWebGraphAnalogIn57644Alert7 TRAP-TYPE
    ENTERPRISE  wtWebGraphAnalogIn57644
    VARIABLES   { wtWebGraphAnalogIn57644AlarmTrapText }
    DESCRIPTION
        "This SNMP trap is generated when Alarm 7 was triggered,
        SNMP trap enable is set and
        SNMP is enabled."
    -- NMS trap annotation
    --#TYPE "Thermo-Hygrometer Alarm 7"
    --#SUMMARY "Alarm 7: %s"
    --#ARGUMENTS {0}
    --#SEVERITY INFORMATIONAL
    --#TIMEINDEX 99
    --#STATE OPERATIONAL    
    ::= 37

wtWebGraphAnalogIn57644Alert8 TRAP-TYPE
    ENTERPRISE  wtWebGraphAnalogIn57644
    VARIABLES   { wtWebGraphAnalogIn57644AlarmTrapText }
    DESCRIPTION
        "This SNMP trap is generated when Alarm 8 was triggered,
        SNMP trap enable is set and
        SNMP is enabled."
    -- NMS trap annotation
    --#TYPE "Thermo-Hygrometer Alarm 8"
    --#SUMMARY "Alarm 8: %s"
    --#ARGUMENTS {0}
    --#SEVERITY INFORMATIONAL
    --#TIMEINDEX 99
    --#STATE OPERATIONAL    
    ::= 38

    
wtWebGraphAnalogIn57644Alert9 TRAP-TYPE
    ENTERPRISE  wtWebGraphAnalogIn57644
    VARIABLES   { wtWebGraphAnalogIn57644AlarmClearTrapText }
    DESCRIPTION
        "This SNMP trap is generated when Alarm 1 was cleared,
        SNMP trap enable is set and
        SNMP is enabled."
    -- NMS trap annotation
    --#TYPE "Thermo-Hygrometer Release Alarm 1"
    --#SUMMARY "Release Alarm 1: %s"
    --#ARGUMENTS {0}
    --#SEVERITY INFORMATIONAL
    --#TIMEINDEX 99
    --#STATE OPERATIONAL    
    ::= 91

wtWebGraphAnalogIn57644Alert10 TRAP-TYPE
    ENTERPRISE  wtWebGraphAnalogIn57644
    VARIABLES   { wtWebGraphAnalogIn57644AlarmClearTrapText }
    DESCRIPTION
        "This SNMP trap is generated when Alarm 2 was cleared,
        SNMP trap enable is set and
        SNMP is enabled."
    -- NMS trap annotation
    --#TYPE "Thermo-Hygrometer Release Alarm 2"
    --#SUMMARY "Release Alarm 2: %s"
    --#ARGUMENTS {0}
    --#SEVERITY INFORMATIONAL
    --#TIMEINDEX 99
    --#STATE OPERATIONAL    
    ::= 92

wtWebGraphAnalogIn57644Alert11 TRAP-TYPE
    ENTERPRISE  wtWebGraphAnalogIn57644
    VARIABLES   { wtWebGraphAnalogIn57644AlarmClearTrapText }
    DESCRIPTION
        "This SNMP trap is generated when Alarm 3 was cleared,
        SNMP trap enable is set and
        SNMP is enabled."
    -- NMS trap annotation
    --#TYPE "Thermo-Hygrometer Release Alarm 3"
    --#SUMMARY "Release Alarm 3: %s"
    --#ARGUMENTS {0}
    --#SEVERITY INFORMATIONAL
    --#TIMEINDEX 99
    --#STATE OPERATIONAL    
    ::= 93

wtWebGraphAnalogIn57644Alert12 TRAP-TYPE
    ENTERPRISE  wtWebGraphAnalogIn57644
    VARIABLES   { wtWebGraphAnalogIn57644AlarmClearTrapText }
    DESCRIPTION
        "This SNMP trap is generated when Alarm 4 was cleared,
        SNMP trap enable is set and
        SNMP is enabled."
    -- NMS trap annotation
    --#TYPE "Thermo-Hygrometer Release Alarm 4"
    --#SUMMARY "Release Alarm 4: %s"
    --#ARGUMENTS {0}
    --#SEVERITY INFORMATIONAL
    --#TIMEINDEX 99
    --#STATE OPERATIONAL    
    ::= 94

wtWebGraphAnalogIn57644Alert13 TRAP-TYPE
    ENTERPRISE  wtWebGraphAnalogIn57644
    VARIABLES   { wtWebGraphAnalogIn57644AlarmClearTrapText }
    DESCRIPTION
        "This SNMP trap is generated when Alarm 5 was cleared,
        SNMP trap enable is set and
        SNMP is enabled."
    -- NMS trap annotation
    --#TYPE "Thermo-Hygrometer Release Alarm 5"
    --#SUMMARY "Release Alarm 5: %s"
    --#ARGUMENTS {0}
    --#SEVERITY INFORMATIONAL
    --#TIMEINDEX 99
    --#STATE OPERATIONAL    
    ::= 95

wtWebGraphAnalogIn57644Alert14 TRAP-TYPE
    ENTERPRISE  wtWebGraphAnalogIn57644
    VARIABLES   { wtWebGraphAnalogIn57644AlarmClearTrapText }
    DESCRIPTION
        "This SNMP trap is generated when Alarm 6 was cleared,
        SNMP trap enable is set and
        SNMP is enabled."
    -- NMS trap annotation
    --#TYPE "Thermo-Hygrometer Release Alarm 6"
    --#SUMMARY "Release Alarm 6: %s"
    --#ARGUMENTS {0}
    --#SEVERITY INFORMATIONAL
    --#TIMEINDEX 99
    --#STATE OPERATIONAL    
    ::= 96

wtWebGraphAnalogIn57644Alert15 TRAP-TYPE
    ENTERPRISE  wtWebGraphAnalogIn57644
    VARIABLES   { wtWebGraphAnalogIn57644AlarmClearTrapText }
    DESCRIPTION
        "This SNMP trap is generated when Alarm 7 was cleared,
        SNMP trap enable is set and
        SNMP is enabled."
    -- NMS trap annotation
    --#TYPE "Thermo-Hygrometer Release Alarm 7"
    --#SUMMARY "Release Alarm 7: %s"
    --#ARGUMENTS {0}
    --#SEVERITY INFORMATIONAL
    --#TIMEINDEX 99
    --#STATE OPERATIONAL    
    ::= 97

wtWebGraphAnalogIn57644Alert16 TRAP-TYPE
    ENTERPRISE  wtWebGraphAnalogIn57644
    VARIABLES   { wtWebGraphAnalogIn57644AlarmClearTrapText }
    DESCRIPTION
        "This SNMP trap is generated when Alarm 8 was cleared,
        SNMP trap enable is set and
        SNMP is enabled."
    -- NMS trap annotation
    --#TYPE "Thermo-Hygrometer Release Alarm 8"
    --#SUMMARY "Release Alarm 8: %s"
    --#ARGUMENTS {0}
    --#SEVERITY INFORMATIONAL
    --#TIMEINDEX 99
    --#STATE OPERATIONAL    
    ::= 98

wtWebGraphAnalogIn57644AlertDiag TRAP-TYPE
    ENTERPRISE  wtWebGraphAnalogIn57644
    VARIABLES   { 	
    		wtWebGraphAnalogIn57644DiagErrorIndex,
    	  	wtWebGraphAnalogIn57644DiagErrorMessage
    		}
    DESCRIPTION
        "This SNMP trap is generated when a diagnosis/error message was triggered,
        SNMP trap enable is set and
        SNMP is enabled."
    -- NMS trap annotation
    --#TYPE "Thermo-Hygrometer Diagnose Error"
    --#SUMMARY "Diagnose error index: %d, Message: %s."
    --#ARGUMENTS {0,1}
    --#SEVERITY MAJOR
    --#TIMEINDEX 99
    --#STATE DEGRADED    
    ::= 110 
 
END

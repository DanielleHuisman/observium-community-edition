Webio-ANx-MIB DEFINITIONS ::= BEGIN
----------------------------------------------------------------
-- Revison: 1.20
----------------------------------------------------------------
-- 02.06.2005 	#57601/3/4, WebThermometer
--		Trap NMS annotations
----------------------------------------------------------------
-- Revison: 1.19
----------------------------------------------------------------
-- 18.04.2005 	HTTP-Port adjustable
--		
----------------------------------------------------------------
-- Revison: 1.18
----------------------------------------------------------------
-- 14.07.2004 	Separation into product families
--		
----------------------------------------------------------------
-- Revison: 1.17
----------------------------------------------------------------
-- 28.06.2004 	#57630/1/2, Webio Digital
--		Neu: Puls Mode
----------------------------------------------------------------
-- Revison: 1.16
----------------------------------------------------------------
-- 16.04.2004 	New: #57632, Webio Digital EA24x24
--
--		#57630/1, Webio Digital EA12x12
--		New:
--			wtWebioEA12x12InputCounterClear
----------------------------------------------------------------
-- Revison: 1.15
----------------------------------------------------------------
-- 27.02.2004 	#57630/1, Webio Digital EA12x12
--		New:
--		Length changed to 32 Bit:
--			wtWebioEA12x12InputValue
--			wtWebioEA12x12OutputValue
--			wtWebioEA12x12LoadControlView
--			wtWebioEA12x12LCShutDownView
--			wtWebioEA12x12SetOutput
--			wtWebioEA12x12AlarmInputTrigger
--			wtWebioEA12x12AlarmOutputTrigger
--			wtWebioEA12x12PortOutputSafetyState
----------------------------------------------------------------
-- Revison: 1.14
----------------------------------------------------------------
-- 16.02.2004 	#57630/1, Webio Digital EA12x12
--		New:
--		Text: Location, Contact
--		SNMP: ColdStart, WarmStart, ComunityString Read/RW
--		Alarm: ColdStart / WarmStart trigger
--
-- 	 	#57601, 1xWebThermometer
--		#57603, 2xWebThermometer		
--		#57604, 8xWebThermometer
--		New:
--		Alarm Hysteresis 
--		Alarm Clear Traps and Mails
----------------------------------------------------------------
-- Revison: 1.13
----------------------------------------------------------------
-- 05.02.2004 	#57601, 1xWebThermometer
--		#57603, 2xWebThermometer		
--		#57604, 8xWebThermometer
--		New:
--		Text: Location, Contact
--		SNMP: ColdStart, WarmStart, ComunityString Read/RW
--		Alarm: ColdStart / WarmStart trigger
----------------------------------------------------------------
-- Revison: 1.12
----------------------------------------------------------------
-- 05.11.2003 	#57601, 1xWebThermometer
--		#57603, 2xWebThermometer		
--		#57604, 8xWebThermometer
--		New features:
--		Mail  : Option CSV attachment
--		Port  : Offset calibration
--		Alarm : TCP Client mode		
----------------------------------------------------------------
-- Revison: 1.11
----------------------------------------------------------------
-- 28.10.2003 	#57630/1, Webio Digital EA12x12
--		New features:
--		Alarm : TCP Client mode		
--		Inputs: Puls filter
----------------------------------------------------------------
-- Revison: 1.10
----------------------------------------------------------------
-- 22.07.2003 	#57630, Webio Digital EA12x12
--		New navigation tree, new binary modes		
--
----------------------------------------------------------------
-- Revison: 1.09
----------------------------------------------------------------
-- 24.03.2003 	Trap Enterprise (Type 1, 2) corrected 
----------------------------------------------------------------
-- Revison: 1.08
----------------------------------------------------------------
-- 04.03.2003 	reconciled the language versions DE/US
----------------------------------------------------------------
-- Revison: 1.07
----------------------------------------------------------------
-- 25.02.2003 	Correction: wtWebioEA12x12LoadControl
----------------------------------------------------------------
-- Revison: 1.06
----------------------------------------------------------------
-- 24.02.2003 	New:
--		#57630, Webio EA12x12, LoadControl Group
--		Correction: Trap variable names
----------------------------------------------------------------
-- Revison: 1.05
----------------------------------------------------------------
-- 21.01.2003 	New:
--		#57630, Webio EA12x12
----------------------------------------------------------------
-- Revison: 1.04
----------------------------------------------------------------
-- 02.01.2003 	New:
--		#57601, 1xWebThermometer
--		#57603, 2xWebThermometer, 8 alarms
----------------------------------------------------------------
-- Revison: 1.03
----------------------------------------------------------------
-- 21.11.2002 	New:
--		#57604, 2xWebThermometer, BOOTP, StartupSite
--		#57603, 8xWebThermometer, BOOTP, StartupSite
----------------------------------------------------------------
-- Revison: 1.02
----------------------------------------------------------------
-- 26.07.2002 	New:
--		#57604, 2xWebThermometer
--		#57603, 8xWebThermometer
-- 		

    IMPORTS

    OBJECT-TYPE                                        FROM RFC-1212
    TRAP-TYPE                                          FROM RFC-1215
    DisplayString, PhysAddress                         FROM RFC1213-MIB
    enterprises, TimeTicks, IpAddress, NetworkAddress  FROM RFC1155-SMI;

 
--    IpAddress ::=
--        [APPLICATION 0]
--            IMPLICIT OCTET STRING (SIZE (4))
--    Counter ::=
--        [APPLICATION 1]
--            IMPLICIT INTEGER (0..4294967295)
--    Gauge ::=
--        [APPLICATION 2]
--            IMPLICIT INTEGER (0..4294967295)
--    TimeTicks ::=
--        [APPLICATION 3]
--            IMPLICIT INTEGER (0..4294967295)


--    DisplayString ::= OCTET STRING
--    PhysAddress   ::= OCTET STRING

--    internet         OBJECT IDENTIFIER ::= { iso org(3) dod(6) 1 }
--    privat           OBJECT IDENTIFIER ::= { internet 4 }
--    enterprises      OBJECT IDENTIFIER ::= { privat 1 }



--  Wiesemann & Theis Com-Server MIB

    wut                		OBJECT IDENTIFIER ::= { enterprises 5040 }
    wtComServer        		OBJECT IDENTIFIER ::= { wut 1 }
    wtWebio            		OBJECT IDENTIFIER ::= { wtComServer 2 }


--  wtWebio Tree

    wtWebioAn8         		OBJECT IDENTIFIER ::= { wtWebio 1 }
    wtWebioAn2         		OBJECT IDENTIFIER ::= { wtWebio 2 }
    wtWebioAn1         		OBJECT IDENTIFIER ::= { wtWebio 3 }
    
--  wtWebioAn8 Tree

    wtWebioAn8Temp      	OBJECT IDENTIFIER ::= { wtWebioAn8 1 }
    wtWebioAn8SessCntrl 	OBJECT IDENTIFIER ::= { wtWebioAn8 2 }
    wtWebioAn8Config    	OBJECT IDENTIFIER ::= { wtWebioAn8 3 }
    
--  wtWebioAn8Config Tree

    wtWebioAn8Device    	OBJECT IDENTIFIER ::= { wtWebioAn8Config 1 }
    wtWebioAn8Ports     	OBJECT IDENTIFIER ::= { wtWebioAn8Config 2 }	
    wtWebioAn8Manufact  	OBJECT IDENTIFIER ::= { wtWebioAn8Config 3 }	


--  wtWebioAn8Device Tree

    wtWebioAn8Network		OBJECT IDENTIFIER ::= { wtWebioAn8Device 1 }
    wtWebioAn8Text		OBJECT IDENTIFIER ::= { wtWebioAn8Device 2 }	
    wtWebioAn8TimeDate 		OBJECT IDENTIFIER ::= { wtWebioAn8Device 3 }
    wtWebioAn8MailAdmin		OBJECT IDENTIFIER ::= { wtWebioAn8Device 4 }	
    wtWebioAn8Alarm		OBJECT IDENTIFIER ::= { wtWebioAn8Device 5 }
    wtWebioAn8Datalogger	OBJECT IDENTIFIER ::= { wtWebioAn8Device 6 }	
    wtWebioAn8Protocol		OBJECT IDENTIFIER ::= { wtWebioAn8Device 7 }
    wtWebioAn8Enable		OBJECT IDENTIFIER ::= { wtWebioAn8Device 8 }	
    wtWebioAn8Startup		OBJECT IDENTIFIER ::= { wtWebioAn8Device 9 }
    
--  wtWebioAn8TimeDate Tree

    wtWebioAn8TimeZone		OBJECT IDENTIFIER ::= { wtWebioAn8TimeDate 1 }
    wtWebioAn8TimeServer	OBJECT IDENTIFIER ::= { wtWebioAn8TimeDate 2 }	
    wtWebioAn8DeviceClock	OBJECT IDENTIFIER ::= { wtWebioAn8TimeDate 3 }

--  wtWebioAn8Protocol Group
    wtWebioAn8PrtclUDP		OBJECT IDENTIFIER ::= { wtWebioAn8Protocol 1 }
    wtWebioAn8PrtclSNMP		OBJECT IDENTIFIER ::= { wtWebioAn8Protocol 2 }
    wtWebioAn8PrtclHTTP		OBJECT IDENTIFIER ::= { wtWebioAn8Protocol 3 }


--  wtWebioAn2 Tree

    wtWebioAn2Temp      	OBJECT IDENTIFIER ::= { wtWebioAn2 1 }
    wtWebioAn2SessCntrl 	OBJECT IDENTIFIER ::= { wtWebioAn2 2 }
    wtWebioAn2Config    	OBJECT IDENTIFIER ::= { wtWebioAn2 3 }
    
--  wtWebioAn2Config Tree

    wtWebioAn2Device    	OBJECT IDENTIFIER ::= { wtWebioAn2Config 1 }
    wtWebioAn2Ports     	OBJECT IDENTIFIER ::= { wtWebioAn2Config 2 }	
    wtWebioAn2Manufact  	OBJECT IDENTIFIER ::= { wtWebioAn2Config 3 }	


--  wtWebioAn2Device Tree

    wtWebioAn2Network		OBJECT IDENTIFIER ::= { wtWebioAn2Device 1 }
    wtWebioAn2Text		OBJECT IDENTIFIER ::= { wtWebioAn2Device 2 }	
    wtWebioAn2TimeDate 		OBJECT IDENTIFIER ::= { wtWebioAn2Device 3 }
    wtWebioAn2MailAdmin		OBJECT IDENTIFIER ::= { wtWebioAn2Device 4 }	
    wtWebioAn2Alarm		OBJECT IDENTIFIER ::= { wtWebioAn2Device 5 }
    wtWebioAn2Datalogger	OBJECT IDENTIFIER ::= { wtWebioAn2Device 6 }	
    wtWebioAn2Protocol		OBJECT IDENTIFIER ::= { wtWebioAn2Device 7 }
    wtWebioAn2Enable		OBJECT IDENTIFIER ::= { wtWebioAn2Device 8 }	
    wtWebioAn2Startup		OBJECT IDENTIFIER ::= { wtWebioAn2Device 9 }
    
--  wtWebioAn2TimeDate Tree

    wtWebioAn2TimeZone		OBJECT IDENTIFIER ::= { wtWebioAn2TimeDate 1 }
    wtWebioAn2TimeServer	OBJECT IDENTIFIER ::= { wtWebioAn2TimeDate 2 }	
    wtWebioAn2DeviceClock	OBJECT IDENTIFIER ::= { wtWebioAn2TimeDate 3 }

--  wtWebioAn2Protocol Group
    wtWebioAn2PrtclUDP		OBJECT IDENTIFIER ::= { wtWebioAn2Protocol 1 }
    wtWebioAn2PrtclSNMP		OBJECT IDENTIFIER ::= { wtWebioAn2Protocol 2 }
    wtWebioAn2PrtclHTTP		OBJECT IDENTIFIER ::= { wtWebioAn2Protocol 3 }    

--  wtWebioAn1 Tree

    wtWebioAn1Temp      	OBJECT IDENTIFIER ::= { wtWebioAn1 1 }
    wtWebioAn1SessCntrl 	OBJECT IDENTIFIER ::= { wtWebioAn1 2 }
    wtWebioAn1Config    	OBJECT IDENTIFIER ::= { wtWebioAn1 3 }
    
--  wtWebioAn1Config Tree

    wtWebioAn1Device    	OBJECT IDENTIFIER ::= { wtWebioAn1Config 1 }
    wtWebioAn1Ports     	OBJECT IDENTIFIER ::= { wtWebioAn1Config 2 }	
    wtWebioAn1Manufact  	OBJECT IDENTIFIER ::= { wtWebioAn1Config 3 }	

--  wtWebioAn1Device Tree

    wtWebioAn1Network		OBJECT IDENTIFIER ::= { wtWebioAn1Device 1 }
    wtWebioAn1Text		OBJECT IDENTIFIER ::= { wtWebioAn1Device 2 }	
    wtWebioAn1TimeDate 		OBJECT IDENTIFIER ::= { wtWebioAn1Device 3 }
    wtWebioAn1MailAdmin		OBJECT IDENTIFIER ::= { wtWebioAn1Device 4 }	
    wtWebioAn1Alarm		OBJECT IDENTIFIER ::= { wtWebioAn1Device 5 }
    wtWebioAn1Datalogger	OBJECT IDENTIFIER ::= { wtWebioAn1Device 6 }	
    wtWebioAn1Protocol		OBJECT IDENTIFIER ::= { wtWebioAn1Device 7 }
    wtWebioAn1Enable		OBJECT IDENTIFIER ::= { wtWebioAn1Device 8 }	
    wtWebioAn1Startup		OBJECT IDENTIFIER ::= { wtWebioAn1Device 9 }
    
--  wtWebioAn1TimeDate Tree

    wtWebioAn1TimeZone		OBJECT IDENTIFIER ::= { wtWebioAn1TimeDate 1 }
    wtWebioAn1TimeServer	OBJECT IDENTIFIER ::= { wtWebioAn1TimeDate 2 }	
    wtWebioAn1DeviceClock	OBJECT IDENTIFIER ::= { wtWebioAn1TimeDate 3 }

--  wtWebioAn1Protocol Group
    wtWebioAn1PrtclUDP		OBJECT IDENTIFIER ::= { wtWebioAn1Protocol 1 }
    wtWebioAn1PrtclSNMP		OBJECT IDENTIFIER ::= { wtWebioAn1Protocol 2 }
    wtWebioAn1PrtclHTTP		OBJECT IDENTIFIER ::= { wtWebioAn1Protocol 3 }

--------------------------------------------------------------------------------
--------------------------------------------------------------------------------
--------------------------------------------------------------------------------
-- Webio Area
-- All queries are passed from the ComServer module to the Webio Platform
--------------------------------------------------------------------------------
--------------------------------------------------------------------------------
--------------------------------------------------------------------------------

-- wtWebioAn8Temp Group
------------------------

wtWebioAn8Sensors OBJECT-TYPE
    SYNTAX INTEGER (1..8)
    ACCESS read-only
    STATUS mandatory
    DESCRIPTION
        "Number of temperature sensors"
    ::= { wtWebioAn8Temp 1 }

-- Interface Table

wtWebioAn8SensorTable OBJECT-TYPE
    SYNTAX SEQUENCE OF WtWebioAn8SensorEntry
    ACCESS not-accessible
    STATUS mandatory
    DESCRIPTION
        "List of sensors."
    ::= { wtWebioAn8Temp 2 }

wtWebioAn8SensorEntry OBJECT-TYPE
    SYNTAX WtWebioAn8SensorEntry
    ACCESS not-accessible
    STATUS mandatory
    DESCRIPTION
        "Temperature sensor numbers."
    INDEX  { wtWebioAn8SensorNo }
    ::= { wtWebioAn8SensorTable 1 }

WtWebioAn8SensorEntry ::= SEQUENCE {
    wtWebioAn8SensorNo INTEGER (1..8)
}

wtWebioAn8SensorNo OBJECT-TYPE
    SYNTAX INTEGER (1..8)
    ACCESS read-only
    STATUS mandatory
    DESCRIPTION
        "Temperature sensor number."
    ::= { wtWebioAn8SensorEntry 1 }


-- wtWebioAn8TempValue Table

wtWebioAn8TempValueTable OBJECT-TYPE
    SYNTAX SEQUENCE OF WtWebioAn8TempValueEntry
    ACCESS not-accessible
    STATUS mandatory
    DESCRIPTION
        "List of temperature values corresponding to the channel numbers."
    ::= { wtWebioAn8Temp 3 }

wtWebioAn8TempValueEntry OBJECT-TYPE
    SYNTAX WtWebioAn8TempValueEntry
    ACCESS not-accessible
    STATUS mandatory
    DESCRIPTION
        "Temperatures of the sensors."
    INDEX  { wtWebioAn8SensorNo }
    ::= { wtWebioAn8TempValueTable 1 }

WtWebioAn8TempValueEntry ::= SEQUENCE{
    wtWebioAn8TempValue OCTET STRING (SIZE (5))
}

wtWebioAn8TempValue OBJECT-TYPE
    SYNTAX OCTET STRING (SIZE (5))
    ACCESS read-only
    STATUS mandatory
    DESCRIPTION
        "Temperature value of the sensor, ASCII, 5 characters in length."
    ::= { wtWebioAn8TempValueEntry 1 }

-- wtWebioAn8BinaryTempValue Table

wtWebioAn8BinaryTempValueTable OBJECT-TYPE
    SYNTAX SEQUENCE OF WtWebioAn8BinaryTempValueEntry
    ACCESS not-accessible
    STATUS mandatory
    DESCRIPTION
        "List of binary temperature values corresponding to the channel numbers."
    ::= { wtWebioAn8Temp 4 }

wtWebioAn8BinaryTempValueEntry OBJECT-TYPE
    SYNTAX WtWebioAn8BinaryTempValueEntry
    ACCESS not-accessible
    STATUS mandatory
    DESCRIPTION
        "Binary temperature values of the sensors."
    INDEX  { wtWebioAn8SensorNo }
    ::= { wtWebioAn8BinaryTempValueTable 1 }

WtWebioAn8BinaryTempValueEntry ::= SEQUENCE{
    wtWebioAn8BinaryTempValue INTEGER
}    

wtWebioAn8BinaryTempValue OBJECT-TYPE
    SYNTAX INTEGER
    ACCESS read-only
    STATUS mandatory
    DESCRIPTION
        "Binary temperature value of the sensor in 1/10 degrees Celsius,
        signed number, 0x7FFF indicates an 
        invalid measured value."
    ::= { wtWebioAn8BinaryTempValueEntry 1 }

-- wtWebioAn8SessCntrl Group
--------------------------------

wtWebioAn8SessCntrlPassword OBJECT-TYPE
    SYNTAX OCTET STRING 
    ACCESS read-write
    STATUS mandatory
    DESCRIPTION
        "Entering this password opens a session which is ended by writing a 1 to 
        wtWebioAn8SessCntrlLogout. When read this variable provides a string of
        length zero."
    ::= { wtWebioAn8SessCntrl 1 }

wtWebioAn8SessCntrlConfigMode OBJECT-TYPE
    SYNTAX INTEGER {
    wtWebioAn8SessCntrl-NoSession(0),
    wtWebioAn8SessCntrl-Session(1)
    }
    ACCESS read-only
    STATUS mandatory
    DESCRIPTION
        "When the device is in SNMP configuration mode, the value 1 is returned,
        otherwise 0. If the read value is 0 even though the password was
        written, the device is already in config mode and the variables can only
        be read."
    ::= { wtWebioAn8SessCntrl 2 }

wtWebioAn8SessCntrlLogout OBJECT-TYPE
    SYNTAX INTEGER 
    ACCESS read-write
    STATUS mandatory
    DESCRIPTION
        "If the device is in configuration mode and the session was opened by
        this SNMP Manager, writing a 1 to this variable will end the session and 
        all parameters are stored.
        Writing a 2 discards all entries again.
        When read this variable provides the value 0."
    ::= { wtWebioAn8SessCntrl 3 }

wtWebioAn8SessCntrlAdminPassword OBJECT-TYPE
    SYNTAX OCTET STRING 
    ACCESS read-write
    STATUS mandatory
    DESCRIPTION
        "This password protects access to the variables with administrator rights.
        It can only be changed by the administrator. If no password was assigned,
        the valid password is public."
    ::= { wtWebioAn8SessCntrl 4 }

wtWebioAn8SessCntrlConfigPassword OBJECT-TYPE
    SYNTAX OCTET STRING 
    ACCESS read-write
    STATUS mandatory
    DESCRIPTION
        "This password protects access to the variables with configurator rights. It can
        be changed by the administrator and by the configurator. If no password was assigned, 
        the valid password is public. When read this variable provides a null-pointer."
    ::= { wtWebioAn8SessCntrl 5 }
    

-- wtWebioAn8Network Group
------------------------

wtWebioAn8IpAddress OBJECT-TYPE
    SYNTAX IpAddress
    ACCESS read-write
    STATUS mandatory
    DESCRIPTION
        "IP address of the Webio"
    ::= { wtWebioAn8Network 1 }

wtWebioAn8SubnetMask OBJECT-TYPE
    SYNTAX IpAddress
    ACCESS read-write
    STATUS mandatory
    DESCRIPTION
        "Subnet mask of the Webio"
    ::= { wtWebioAn8Network 2 }

wtWebioAn8Gateway OBJECT-TYPE
    SYNTAX IpAddress
    ACCESS read-write
    STATUS mandatory
    DESCRIPTION
        "Gateway of the Webio"
    ::= { wtWebioAn8Network 3 }

wtWebioAn8DnsServer1 OBJECT-TYPE
    SYNTAX OCTET STRING 
    ACCESS read-write
    STATUS mandatory
    DESCRIPTION
        "IP address of the 1st DNS server in ASCII"
    ::= { wtWebioAn8Network 4 }

wtWebioAn8DnsServer2 OBJECT-TYPE
    SYNTAX OCTET STRING 
    ACCESS read-write
    STATUS mandatory
    DESCRIPTION
        "IP address of the 2nd DNS server in ASCII"
    ::= { wtWebioAn8Network 5 }

wtWebioAn8AddConfig OBJECT-TYPE
    SYNTAX OCTET STRING 
    ACCESS read-write
    STATUS mandatory
    DESCRIPTION
        "Additional configuration (1=ON):
        Octet 1: unused
        Octet 2: unused
        Octet 3: unused
        Octet 4:
	        Bit 0: BOOTP disable
	        "
    ::= { wtWebioAn8Network 6 }

-- wtWebioAn8Text Group
------------------------

wtWebioAn8DeviceName OBJECT-TYPE
    SYNTAX OCTET STRING 
    ACCESS read-write
    STATUS mandatory
    DESCRIPTION
        "Name of the Webio, which is user definable."
    ::= { wtWebioAn8Text 1 }

wtWebioAn8DeviceText OBJECT-TYPE
    SYNTAX OCTET STRING 
    ACCESS read-write
    STATUS mandatory
    DESCRIPTION
        "Description of the Webio, which is user definable."
    ::= { wtWebioAn8Text 2 }

wtWebioAn8DeviceLocation OBJECT-TYPE
    SYNTAX OCTET STRING 
    ACCESS read-write
    STATUS mandatory
    DESCRIPTION
        "Description of the location of the Webio, which is user definable."
    ::= { wtWebioAn8Text 3 }

wtWebioAn8DeviceContact OBJECT-TYPE
    SYNTAX OCTET STRING 
    ACCESS read-write
    STATUS mandatory
    DESCRIPTION
        "Contact address of the system operator of the Webio, which is user definable."
    ::= { wtWebioAn8Text 4 }

-- wtWebioAn8TimeZone Group
----------------------------

wtWebioAn8TzName OBJECT-TYPE
    SYNTAX OCTET STRING 
    ACCESS read-write
    STATUS mandatory
    DESCRIPTION
        "Name of the time zone (winter time)."
    ::= { wtWebioAn8TimeZone 1 }

wtWebioAn8TzOffsetHrs OBJECT-TYPE
    SYNTAX INTEGER 
    ACCESS read-write
    STATUS mandatory
    DESCRIPTION
        "Offset hours for the time zone (winter time) with respect to UTC."
    ::= { wtWebioAn8TimeZone 2 }

wtWebioAn8TzOffsetMin OBJECT-TYPE
    SYNTAX INTEGER 
    ACCESS read-write
    STATUS mandatory
    DESCRIPTION
        "Offset minutes for the time zone (winter time) with respect to UTC."
    ::= { wtWebioAn8TimeZone 3 }

wtWebioAn8StTzName OBJECT-TYPE
    SYNTAX OCTET STRING 
    ACCESS read-write
    STATUS mandatory
    DESCRIPTION
        "Name of the time zone (summer time)."
    ::= { wtWebioAn8TimeZone 4 }

wtWebioAn8StTzOffsetHrs OBJECT-TYPE
    SYNTAX INTEGER 
    ACCESS read-write
    STATUS mandatory
    DESCRIPTION
        "Offset hours of the time zone (summer time) with respect to UTC."
    ::= { wtWebioAn8TimeZone 5 }

wtWebioAn8StTzOffsetMin OBJECT-TYPE
    SYNTAX INTEGER 
    ACCESS read-write
    STATUS mandatory
    DESCRIPTION
        "Offset minutes of the time zone (summer time) with respect to UTC."
    ::= { wtWebioAn8TimeZone 6 }
    
wtWebioAn8StTzStartMonth OBJECT-TYPE
    SYNTAX INTEGER {
    	wtWebioAn8StartMonth-January(1),
    	wtWebioAn8StartMonth-February(2),
    	wtWebioAn8StartMonth-March(3),
    	wtWebioAn8StartMonth-April(4),
    	wtWebioAn8StartMonth-May(5),
    	wtWebioAn8StartMonth-June(6),
    	wtWebioAn8StartMonth-July(7),
    	wtWebioAn8StartMonth-August(8),
    	wtWebioAn8StartMonth-September(9),
    	wtWebioAn8StartMonth-October(10),
    	wtWebioAn8StartMonth-November(11),
    	wtWebioAn8StartMonth-December(12)
    	}
    	
    ACCESS read-write
    STATUS mandatory
    DESCRIPTION
        "Month in which the change is made from winter time to summer time."
    ::= { wtWebioAn8TimeZone 7 }

wtWebioAn8StTzStartMode OBJECT-TYPE
    SYNTAX INTEGER {
    	wtWebioAn8StartMode-first(1),
    	wtWebioAn8StartMode-second(2),
    	wtWebioAn8StartMode-third(3),
    	wtWebioAn8StartMode-fourth(4),
    	wtWebioAn8StartMode-last(5)
    	}
    	
    ACCESS read-write
    STATUS mandatory
    DESCRIPTION
        "Mode of the day of the week for which the change is made from winter time to summer time."
    ::= { wtWebioAn8TimeZone 8 }

wtWebioAn8StTzStartWday OBJECT-TYPE
    SYNTAX INTEGER {
    	wtWebioAn8StartWday-Sunday(1),
    	wtWebioAn8StartWday-Monday(2),
    	wtWebioAn8StartWday-Tuesday(3),
    	wtWebioAn8StartWday-Thursday(4),
    	wtWebioAn8StartWday-Wednesday(5),
    	wtWebioAn8StartWday-Friday(6),
    	wtWebioAn8StartWday-Saturday(7)
    	}
    	
    ACCESS read-write
    STATUS mandatory
    DESCRIPTION
        "Day of the week on which the change is made from winter time to summer time"
    ::= { wtWebioAn8TimeZone 9 }
    
wtWebioAn8StTzStartHrs OBJECT-TYPE
    SYNTAX INTEGER 
    ACCESS read-write
    STATUS mandatory
    DESCRIPTION
        "Hour in which the time zone is changed from winter to summer time with
        respect to UTC."
    ::= { wtWebioAn8TimeZone 10 }

wtWebioAn8StTzStartMin OBJECT-TYPE
    SYNTAX INTEGER 
    ACCESS read-write
    STATUS mandatory
    DESCRIPTION
        "Minute in which the time zone is changed from winter to summer time with
        respect to UTC."
    ::= { wtWebioAn8TimeZone 11 }
 
wtWebioAn8StTzStopMonth OBJECT-TYPE
    SYNTAX INTEGER {
    	wtWebioAn8StopMonth-January(1),
    	wtWebioAn8StopMonth-February(2),
    	wtWebioAn8StopMonth-March(3),
    	wtWebioAn8StopMonth-April(4),
    	wtWebioAn8StopMonth-May(5),
    	wtWebioAn8StopMonth-June(6),
    	wtWebioAn8StopMonth-July(7),
    	wtWebioAn8StopMonth-August(8),
    	wtWebioAn8StopMonth-September(9),
    	wtWebioAn8StopMonth-October(10),
    	wtWebioAn8StopMonth-November(11),
    	wtWebioAn8StopMonth-December(12)
    	}
    ACCESS read-write
    STATUS mandatory
    DESCRIPTION
        "Month in which the change is made from summer time to winter time."
   ::= { wtWebioAn8TimeZone 12 }

wtWebioAn8StTzStopMode OBJECT-TYPE
    SYNTAX INTEGER {
    	wtWebioAn8StopMode-first(1),
    	wtWebioAn8StopMode-second(2),
    	wtWebioAn8StopMode-third(3),
    	wtWebioAn8StopMode-fourth(4),
    	wtWebioAn8StopMode-last(5)
    	}
    ACCESS read-write
    STATUS mandatory
    DESCRIPTION
        "Mode of the week day on which the change is made from summer time to winter time."
    ::= { wtWebioAn8TimeZone 13 }

wtWebioAn8StTzStopWday OBJECT-TYPE
    SYNTAX INTEGER {
    	wtWebioAn8StopWday-Sunday(1),
    	wtWebioAn8StopWday-Monday(2),
    	wtWebioAn8StopWday-Tuesday(3),
    	wtWebioAn8StopWday-Thursday(4),
    	wtWebioAn8StopWday-Wednesday(5),
    	wtWebioAn8StopWday-Friday(6),
    	wtWebioAn8StopWday-Saturday(7)
    	}
    ACCESS read-write
    STATUS mandatory
    DESCRIPTION
        "Day of the week on which the change is made from summer time to winter time."
    ::= { wtWebioAn8TimeZone 14 }
    
wtWebioAn8StTzStopHrs OBJECT-TYPE
    SYNTAX INTEGER 
    ACCESS read-write
    STATUS mandatory
    DESCRIPTION
        "Hour at which the time zone is changed from summer to winter time with
        respect to UTC."
    ::= { wtWebioAn8TimeZone 15 }

wtWebioAn8StTzStopMin OBJECT-TYPE
    SYNTAX INTEGER 
    ACCESS read-write
    STATUS mandatory
    DESCRIPTION
        "Minute at which the time zone is changed from summer to winter time with
        respect to UTC."
    ::= { wtWebioAn8TimeZone 16 }

-- wtWebioAn8TimeServer Group
----------------------------

wtWebioAn8TimeServer1 OBJECT-TYPE
    SYNTAX OCTET STRING 
    ACCESS read-write
    STATUS mandatory
    DESCRIPTION
        "IP address or name of the 1st time server in ASCII"
    ::= { wtWebioAn8TimeServer 1 }

wtWebioAn8TimeServer2 OBJECT-TYPE
    SYNTAX OCTET STRING 
    ACCESS read-write
    STATUS mandatory
    DESCRIPTION
        "IP address or name of the 2nd time server in ASCII"
    ::= { wtWebioAn8TimeServer 2 }
    
-- wtWebioAn8DeviceClock Group
----------------------------

wtWebioAn8ClockHrs OBJECT-TYPE
    SYNTAX INTEGER (0..23)
    ACCESS read-write
    STATUS mandatory
    DESCRIPTION
        "Clock hours taking into account the time zone settings."
    ::= { wtWebioAn8DeviceClock 1 }

wtWebioAn8ClockMin OBJECT-TYPE
    SYNTAX INTEGER (0..59)
    ACCESS read-write
    STATUS mandatory
    DESCRIPTION
        "Clock minutes taking into account the time zone settings."
    ::= { wtWebioAn8DeviceClock 2 }

wtWebioAn8ClockDay OBJECT-TYPE
    SYNTAX INTEGER (1..31)
    ACCESS read-write
    STATUS mandatory
    DESCRIPTION
        "Date: Day of the month, taking into account the time zone settings."
    ::= { wtWebioAn8DeviceClock 3 }

wtWebioAn8ClockMonth OBJECT-TYPE
   SYNTAX INTEGER {
    	wtWebioAn8ClockMonth-January(1),
    	wtWebioAn8ClockMonth-February(2),
    	wtWebioAn8ClockMonth-March(3),
    	wtWebioAn8ClockMonth-April(4),
    	wtWebioAn8ClockMonth-May(5),
    	wtWebioAn8ClockMonth-June(6),
    	wtWebioAn8ClockMonth-July(7),
    	wtWebioAn8ClockMonth-August(8),
    	wtWebioAn8ClockMonth-September(9),
    	wtWebioAn8ClockMonth-October(10),
    	wtWebioAn8ClockMonth-November(11),
    	wtWebioAn8ClockMonth-December(12)
    	}
    ACCESS read-write
    STATUS mandatory
    DESCRIPTION
        "Date: Month, taking into account the time zone settings."
    ::= { wtWebioAn8DeviceClock 4 }

wtWebioAn8ClockYear OBJECT-TYPE
    SYNTAX INTEGER (0..65535)
    ACCESS read-write
    STATUS mandatory
    DESCRIPTION
        "Date: Year, taking into account the time zone settings."
    ::= { wtWebioAn8DeviceClock 5 }
    
-- wtWebioAn8MailAdmin Group
--------------------------------

wtWebioAn8MailAdName OBJECT-TYPE
    SYNTAX OCTET STRING 
    ACCESS read-write
    STATUS mandatory
    DESCRIPTION
        "Device name for mail administration."
    ::= { wtWebioAn8MailAdmin 1 }
    
wtWebioAn8MailReply OBJECT-TYPE
    SYNTAX OCTET STRING 
    ACCESS read-write
    STATUS mandatory
    DESCRIPTION
        "Reply address for the mail server."
    ::= { wtWebioAn8MailAdmin 2 }
    
wtWebioAn8MailServer OBJECT-TYPE
    SYNTAX OCTET STRING 
    ACCESS read-write
    STATUS mandatory
    DESCRIPTION
        "Name or IP address of the mail server."
    ::= { wtWebioAn8MailAdmin 3 }
    

-- wtWebioAn8Alarm Group
----------------------------

wtWebioAn8AlarmCount OBJECT-TYPE
    SYNTAX INTEGER (1..8)
    ACCESS read-only
    STATUS mandatory
    DESCRIPTION
        "Number of independent alarms."
    ::= { wtWebioAn8Alarm 1 }
    
-- Alarm Interface Table

wtWebioAn8AlarmIfTable OBJECT-TYPE
    SYNTAX SEQUENCE OF WtWebioAn8AlarmIfEntry
    ACCESS not-accessible
    STATUS mandatory
    DESCRIPTION
        "List of alarm indices."
    ::= { wtWebioAn8Alarm 2 }

wtWebioAn8AlarmIfEntry OBJECT-TYPE
    SYNTAX WtWebioAn8AlarmIfEntry
    ACCESS not-accessible
    STATUS mandatory
    DESCRIPTION
        "Numbers of the alarms."
    INDEX  { wtWebioAn8AlarmNo }
    ::= { wtWebioAn8AlarmIfTable 1 }

WtWebioAn8AlarmIfEntry ::= SEQUENCE {
    wtWebioAn8AlarmNo INTEGER (1..8)
}

wtWebioAn8AlarmNo OBJECT-TYPE
    SYNTAX INTEGER (1..8)
    ACCESS read-only
    STATUS mandatory
    DESCRIPTION
        "Alarm number."
    ::= { wtWebioAn8AlarmIfEntry 1 }

-- Alarm Table

wtWebioAn8AlarmTable OBJECT-TYPE
    SYNTAX SEQUENCE OF WtWebioAn8AlarmEntry
    ACCESS not-accessible
    STATUS mandatory
    DESCRIPTION
        "List of settings depending on the alarm number."
    ::= { wtWebioAn8Alarm 3 }

wtWebioAn8AlarmEntry OBJECT-TYPE
    SYNTAX WtWebioAn8AlarmEntry
    ACCESS not-accessible
    STATUS mandatory
    DESCRIPTION
        "Alarm parameters of the individual alarms."
    INDEX  { wtWebioAn8AlarmNo }
    ::= { wtWebioAn8AlarmTable 1 }

WtWebioAn8AlarmEntry ::= SEQUENCE {
    wtWebioAn8AlarmTrigger		OCTET STRING,
    wtWebioAn8AlarmMin			OCTET STRING,
    wtWebioAn8AlarmMax			OCTET STRING,
    wtWebioAn8AlarmInterval		OCTET STRING,
    wtWebioAn8AlarmEnable		OCTET STRING,
    wtWebioAn8AlarmEMailAddr		OCTET STRING,
    wtWebioAn8AlarmMailSubject		OCTET STRING,
    wtWebioAn8AlarmMailText		OCTET STRING,
    wtWebioAn8AlarmManagerIP		OCTET STRING,
    wtWebioAn8AlarmTrapText		OCTET STRING,
    wtWebioAn8AlarmMailOptions		OCTET STRING,
    wtWebioAn8AlarmTcpIpAddr		OCTET STRING,
    wtWebioAn8AlarmTcpPort		INTEGER,
    wtWebioAn8AlarmTcpText		OCTET STRING,
    wtWebioAn8AlarmHystersis		OCTET STRING,
    wtWebioAn8AlarmClearMailSubject	OCTET STRING,
    wtWebioAn8AlarmClearMailText	OCTET STRING,
    wtWebioAn8AlarmClearTrapText	OCTET STRING,
    wtWebioAn8AlarmClearTcpText		OCTET STRING
    
}

wtWebioAn8AlarmTrigger OBJECT-TYPE
    SYNTAX OCTET STRING (SIZE(4))
    ACCESS read-write
    STATUS mandatory
    DESCRIPTION
        "Binary coded trigger conditions:
        Octet 1: unused
        Octet 2: unused
        Octet 3:
        	Bit 0: Timer
        	Bit 1: ColdStart
        	Bit 2: WarmStart
        	
        Octet 4:
        	Bit 0: Sensor 1
        	Bit 1: Sensor 2
        	Bit 2: Sensor 3
        	Bit 3: Sensor 4
        	Bit 4: Sensor 5
        	Bit 5: Sensor 6
        	Bit 6: Sensor 7
        	Bit 7: Sensor 8"
    ::= { wtWebioAn8AlarmEntry 1 }

wtWebioAn8AlarmMin OBJECT-TYPE
    SYNTAX OCTET STRING 
    ACCESS read-write
    STATUS mandatory
    DESCRIPTION
        "Minimum temperature in degrees with maximum 2 decimal places."
    ::= { wtWebioAn8AlarmEntry 2 }

wtWebioAn8AlarmMax OBJECT-TYPE
    SYNTAX OCTET STRING 
    ACCESS read-write
    STATUS mandatory
    DESCRIPTION
        "Maximum temperature in degrees with maximum 2 decimal places."
    ::= { wtWebioAn8AlarmEntry 3 }

wtWebioAn8AlarmInterval OBJECT-TYPE
    SYNTAX OCTET STRING 
    ACCESS read-write
    STATUS mandatory
    DESCRIPTION
        "Send interval for alarm messages."
    ::= { wtWebioAn8AlarmEntry 4 }

wtWebioAn8AlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  TCP Client enable"
    ::= { wtWebioAn8AlarmEntry 5 }

wtWebioAn8AlarmEMailAddr OBJECT-TYPE
    SYNTAX OCTET STRING 
    ACCESS read-write
    STATUS mandatory
    DESCRIPTION
        "E-Mail address for sending the alarm mail to."
    ::= { wtWebioAn8AlarmEntry 6 }

wtWebioAn8AlarmMailSubject OBJECT-TYPE
    SYNTAX OCTET STRING 
    ACCESS read-write
    STATUS mandatory
    DESCRIPTION
        "Subject line for alarm mail."
    ::= { wtWebioAn8AlarmEntry 7 }

wtWebioAn8AlarmMailText OBJECT-TYPE
    SYNTAX OCTET STRING 
    ACCESS read-write
    STATUS mandatory
    DESCRIPTION
        "Alarm mail text: <Tn> provides the current temperature; n = 1..8.
        <Z> provides the current time."
    ::= { wtWebioAn8AlarmEntry 8 }

wtWebioAn8AlarmManagerIP OBJECT-TYPE
    SYNTAX OCTET STRING 
    ACCESS read-write
    STATUS mandatory
    DESCRIPTION
        "Name or IP address of the SNMP Manager which accepts the trap."
    ::= { wtWebioAn8AlarmEntry 9 }

wtWebioAn8AlarmTrapText OBJECT-TYPE
    SYNTAX OCTET STRING 
    ACCESS read-write
    STATUS mandatory
    DESCRIPTION
        "This text is sent in the trap body."
    ::= { wtWebioAn8AlarmEntry 10 }
    
wtWebioAn8AlarmMailOptions OBJECT-TYPE
    SYNTAX OCTET STRING (SIZE(4))
    ACCESS read-write
    STATUS mandatory
    DESCRIPTION
        "Binary coded options:
        Octet 1: unused
        Octet 2: unused
        Octet 3: unused
        Octet 4:
		Bit 0  :	Attach Thermo.csv Enable
        	Bit 1-7:	unused"
    ::= { wtWebioAn8AlarmEntry 11 }    
    
wtWebioAn8AlarmTcpIpAddr OBJECT-TYPE
    SYNTAX OCTET STRING 
    ACCESS read-write
    STATUS mandatory
    DESCRIPTION
        "Name or IP address of the TCP server which accepts the trap."
    ::= { wtWebioAn8AlarmEntry 12 }    

wtWebioAn8AlarmTcpPort OBJECT-TYPE
    SYNTAX INTEGER (1..65535) 
    ACCESS read-write
    STATUS mandatory
    DESCRIPTION
        "Port number of the TCP server which accepts the trap."
    ::= { wtWebioAn8AlarmEntry 13 }    

wtWebioAn8AlarmTcpText OBJECT-TYPE
    SYNTAX OCTET STRING 
    ACCESS read-write
    STATUS mandatory
    DESCRIPTION
        "This text is sent in the TCP trap body."
    ::= { wtWebioAn8AlarmEntry 14 }

wtWebioAn8AlarmHysteresis OBJECT-TYPE
    SYNTAX OCTET STRING 
    ACCESS read-write
    STATUS mandatory
    DESCRIPTION
        "Temperature changes of this size clears the alarm state (MAX-hyst, MIN+hyst.)
        , in degrees with maximum 2 decimal places."
    ::= { wtWebioAn8AlarmEntry 15 }
    
wtWebioAn8AlarmClearMailSubject OBJECT-TYPE
    SYNTAX OCTET STRING 
    ACCESS read-write
    STATUS mandatory
    DESCRIPTION
        "Subject line for alarm clear mail."
    ::= { wtWebioAn8AlarmEntry 16 }

wtWebioAn8AlarmClearMailText OBJECT-TYPE
    SYNTAX OCTET STRING 
    ACCESS read-write
    STATUS mandatory
    DESCRIPTION
        "Alarm clear mail text: <Tn> provides the current temperature; n = 1..8.
        <Z> provides the current time."
    ::= { wtWebioAn8AlarmEntry 17 }

wtWebioAn8AlarmClearTrapText OBJECT-TYPE
    SYNTAX OCTET STRING 
    ACCESS read-write
    STATUS mandatory
    DESCRIPTION
        "This text is sent in the trap body."
    ::= { wtWebioAn8AlarmEntry 18 }

wtWebioAn8AlarmClearTcpText OBJECT-TYPE
    SYNTAX OCTET STRING 
    ACCESS read-write
    STATUS mandatory
    DESCRIPTION
        "This text is sent in the TCP trap body."
    ::= { wtWebioAn8AlarmEntry 19 }

-- wtWebioAn8Datalogger Group
--------------------------------

wtWebioAn8LoggerTimebase OBJECT-TYPE
    SYNTAX INTEGER {
    wtWebioAn8Datalogger-1Min(1),
    wtWebioAn8Datalogger-5Min(2),
    wtWebioAn8Datalogger-15Min(3),
    wtWebioAn8Datalogger-60Min(4)
    }
    ACCESS read-write
    STATUS mandatory
    DESCRIPTION
        "Time base of the data logger"
    ::= { wtWebioAn8Datalogger 1 }

wtWebioAn8LoggerSensorSel OBJECT-TYPE
    SYNTAX OCTET STRING (SIZE(4))
    ACCESS read-write
    STATUS mandatory
    DESCRIPTION
        "Binary coded trigger conditions:
        Octet 1: unused
        Octet 2: unused
        Octet 3: unused
        Octet 4:
        	Bit 0: Sensor 1
        	Bit 1: Sensor 2
        	Bit 2: Sensor 3
        	Bit 3: Sensor 4
        	Bit 4: Sensor 5
        	Bit 5: Sensor 6
        	Bit 6: Sensor 7
        	Bit 7: Sensor 8"
    ::= { wtWebioAn8Datalogger 2 }

-- wtWebioAn8Protocol Group
----------------------------

wtWebioAn8PrtclUdpPort OBJECT-TYPE
    SYNTAX INTEGER (1..65535)
    ACCESS read-write
    STATUS mandatory
    DESCRIPTION
        "Udp port to which the Udp queries GET Single can be sent"
    ::= { wtWebioAn8PrtclUDP 1 }

wtWebioAn8PrtclSnmpCommunityStringRead OBJECT-TYPE
    SYNTAX OCTET STRING
    ACCESS read-write
    STATUS mandatory
    DESCRIPTION
        "Community string read only"
    ::= { wtWebioAn8PrtclSNMP 1 }

wtWebioAn8PrtclSnmpCommunityStringReadWrite OBJECT-TYPE
    SYNTAX OCTET STRING
    ACCESS read-write
    STATUS mandatory
    DESCRIPTION
        "Community string read / write"
    ::= { wtWebioAn8PrtclSNMP 2 }

wtWebioAn8SystemTrapManagerIP OBJECT-TYPE
    SYNTAX OCTET STRING 
    ACCESS read-write
    STATUS mandatory
    DESCRIPTION
        "Name or IP address of the TCP server which accepts the system trap."
    ::= { wtWebioAn8PrtclSNMP 3 }
    
wtWebioAn8SystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2-7: unused"
    ::= { wtWebioAn8PrtclSNMP 4 }

wtWebioAn8PrtclHttpPort OBJECT-TYPE
    SYNTAX INTEGER (1..65535)
    ACCESS read-write
    STATUS mandatory
    DESCRIPTION
        "HTTP port to which the HTTP queries GET Single can be sent"
    ::= { wtWebioAn8PrtclHttp 1 }    
    
-- wtWebioAn8Enable Group
----------------------------

wtWebioAn8Enables OBJECT-TYPE
    SYNTAX OCTET STRING (SIZE(4))
    ACCESS read-write
    STATUS mandatory
    DESCRIPTION
        "Binary coded trigger conditions:
        Octet 1: unused
        Octet 2: unused
        Octet 3: unused
        Octet 4:
	        Bit 0: Update enable
	        Bit 1: Mail enable
	        Bit 2: Snmp enable
	        Bit 3: UDP enable
	        Bit 4: Get Singel Header enable
	        Bit 5: Apply Timezone
	        Bit 6: Apply Summertime
	        Bit 7: Apply TimeServer"
    ::= { wtWebioAn8Enable 1 }

-- wtWebioAn8Startup Group
----------------------------

wtWebioAn8StartupSite OBJECT-TYPE
    SYNTAX OCTET STRING (SIZE(4))
    ACCESS read-write
    STATUS mandatory
    DESCRIPTION
        "Binary coded start page:
        Octet 1: unused
        Octet 2: unused
        Octet 3: unused
        Octet 4:
	        Bit 1: Index.htm
	        Bit 2: Home.htm
	        Bit 3: User.htm
	Only one page may be selected at a time."
    ::= { wtWebioAn8Startup 1 }

-- wtWebioAn8Ports Group
----------------------------

-- Table

wtWebioAn8PortTable OBJECT-TYPE
    SYNTAX SEQUENCE OF WtWebioAn8PortEntry
    ACCESS not-accessible
    STATUS mandatory
    DESCRIPTION
        "List of settings depending on the sensor number."
    ::= { wtWebioAn8Ports 1 }

wtWebioAn8PortEntry OBJECT-TYPE
    SYNTAX WtWebioAn8PortEntry
    ACCESS not-accessible
    STATUS mandatory
    DESCRIPTION
        "Sensor parameters for the individual sensors."
    INDEX  { wtWebioAn8SensorNo }
    ::= { wtWebioAn8PortTable 1 }

WtWebioAn8PortEntry ::= SEQUENCE {
    wtWebioAn8PortName		OCTET STRING,
    wtWebioAn8PortText		OCTET STRING,
    wtWebioAn8PortOffset1	OCTET STRING,
    wtWebioAn8PortTemperature1	OCTET STRING,
    wtWebioAn8PortOffset2	OCTET STRING,
    wtWebioAn8PortTemperature2	OCTET STRING,
    wtWebioAn8PortComment	OCTET STRING
    
}

wtWebioAn8PortName OBJECT-TYPE
    SYNTAX OCTET STRING 
    ACCESS read-write
    STATUS mandatory
    DESCRIPTION
        "Name of the sensor."
    ::= { wtWebioAn8PortEntry 1 }

wtWebioAn8PortText OBJECT-TYPE
    SYNTAX OCTET STRING 
    ACCESS read-write
    STATUS mandatory
    DESCRIPTION
        "Description of the sensor."
    ::= { wtWebioAn8PortEntry 2 }
    
wtWebioAn8PortOffset1 OBJECT-TYPE
    SYNTAX OCTET STRING 
    ACCESS read-write
    STATUS mandatory
    DESCRIPTION
        "Offset calibration: Offset in degrees with maximum 2 decimal places at temperature 1."
    ::= { wtWebioAn8PortEntry 3 }

wtWebioAn8PortTemperature1 OBJECT-TYPE
    SYNTAX OCTET STRING 
    ACCESS read-write
    STATUS mandatory
    DESCRIPTION
        "Offset calibration: Reference temperature 1 in degrees with maximum 2 decimal places."
    ::= { wtWebioAn8PortEntry 4 }

wtWebioAn8PortOffset2 OBJECT-TYPE
    SYNTAX OCTET STRING 
    ACCESS read-write
    STATUS mandatory
    DESCRIPTION
        "Offset calibration: Offset in degrees with maximum 2 decimal places at temperature 2."
    ::= { wtWebioAn8PortEntry 5 }

wtWebioAn8PortTemperature2 OBJECT-TYPE
    SYNTAX OCTET STRING 
    ACCESS read-write
    STATUS mandatory
    DESCRIPTION
        "Offset calibration: Reference temperature 1 in degrees with maximum 2 decimal places."
    ::= { wtWebioAn8PortEntry 6 }

wtWebioAn8PortComment OBJECT-TYPE
    SYNTAX OCTET STRING 
    ACCESS read-write
    STATUS mandatory
    DESCRIPTION
        "Offset calibration: informations of date, name of operator, reference devices."
    ::= { wtWebioAn8PortEntry 7 }    

-- wtWebioAn8Manufact Group
----------------------------

wtWebioAn8MfName OBJECT-TYPE
    SYNTAX OCTET STRING 
    ACCESS read-write
    STATUS mandatory
    DESCRIPTION
        "Manufacturer company name"
    ::= { wtWebioAn8Manufact 1 }

wtWebioAn8MfAddr OBJECT-TYPE
    SYNTAX OCTET STRING 
    ACCESS read-write
    STATUS mandatory
    DESCRIPTION
        "Manufacturer address."
    ::= { wtWebioAn8Manufact 2 }

wtWebioAn8MfHotline OBJECT-TYPE
    SYNTAX OCTET STRING 
    ACCESS read-write
    STATUS mandatory
    DESCRIPTION
        "Manufacturer hotline."
    ::= { wtWebioAn8Manufact 3 }

wtWebioAn8MfInternet OBJECT-TYPE
    SYNTAX OCTET STRING 
    ACCESS read-write
    STATUS mandatory
    DESCRIPTION
        "Manufacturer Internet address."
    ::= { wtWebioAn8Manufact 4 }

wtWebioAn8MfDeviceTyp OBJECT-TYPE
    SYNTAX OCTET STRING 
    ACCESS read-write
    STATUS mandatory
    DESCRIPTION
        "Manufacturer device name (model number)."
    ::= { wtWebioAn8Manufact 5 }

wtWebioAn8MfOrderNo OBJECT-TYPE
    SYNTAX OCTET STRING 
    ACCESS read-write
    STATUS mandatory
    DESCRIPTION
        "Manufacturer part number."
    ::= { wtWebioAn8Manufact 6 }



-- TRAP DEFINITIONS

-- These SNMP traps are sent when the alarm trigger conditions apply 

wtWebioAn8Alert1 TRAP-TYPE
    ENTERPRISE  wtWebioAn8
    VARIABLES   { wtWebioAn8AlarmTrapText }
    DESCRIPTION
        "This SNMP trap is generated when Alarm 1 was triggered,
        SNMP trap enable is set and
        SNMP is enabled."
    -- NMS trap annotation
    --#TYPE "WebThermometer Alarm 1"
    --#SUMMARY "Alarm 1: %s"
    --#ARGUMENTS {0}
    --#SEVERITY INFORMATIONAL
    --#TIMEINDEX 99
    --#STATE OPERATIONAL    
    ::= 11

wtWebioAn8Alert2 TRAP-TYPE
    ENTERPRISE  wtWebioAn8
    VARIABLES   { wtWebioAn8AlarmTrapText }
    DESCRIPTION
        "This SNMP trap is generated when Alarm 2 was triggered,
        SNMP trap enable is set and
        SNMP is enabled."
    -- NMS trap annotation
    --#TYPE "WebThermometer Alarm 2"
    --#SUMMARY "Alarm 2: %s"
    --#ARGUMENTS {0}
    --#SEVERITY INFORMATIONAL
    --#TIMEINDEX 99
    --#STATE OPERATIONAL    
    ::= 12

wtWebioAn8Alert3 TRAP-TYPE
    ENTERPRISE  wtWebioAn8
    VARIABLES   { wtWebioAn8AlarmTrapText }
    DESCRIPTION
        "This SNMP trap is generated when Alarm 3 was triggered,
        SNMP trap enable is set and
        SNMP is enabled."
    -- NMS trap annotation
    --#TYPE "WebThermometer Alarm 3"
    --#SUMMARY "Alarm 3: %s"
    --#ARGUMENTS {0}
    --#SEVERITY INFORMATIONAL
    --#TIMEINDEX 99
    --#STATE OPERATIONAL    
    ::= 13

wtWebioAn8Alert4 TRAP-TYPE
    ENTERPRISE  wtWebioAn8
    VARIABLES   { wtWebioAn8AlarmTrapText }
    DESCRIPTION
        "This SNMP trap is generated when Alarm 4 was triggered,
        SNMP trap enable is set and
        SNMP is enabled."
    -- NMS trap annotation
    --#TYPE "WebThermometer Alarm 4"
    --#SUMMARY "Alarm 4: %s"
    --#ARGUMENTS {0}
    --#SEVERITY INFORMATIONAL
    --#TIMEINDEX 99
    --#STATE OPERATIONAL    
    ::= 14

wtWebioAn8Alert5 TRAP-TYPE
    ENTERPRISE  wtWebioAn8
    VARIABLES   { wtWebioAn8AlarmTrapText }
    DESCRIPTION
        "This SNMP trap is generated when Alarm 5 was triggered,
        SNMP trap enable is set and
        SNMP is enabled."
    -- NMS trap annotation
    --#TYPE "WebThermometer Alarm 5"
    --#SUMMARY "Alarm 5: %s"
    --#ARGUMENTS {0}
    --#SEVERITY INFORMATIONAL
    --#TIMEINDEX 99
    --#STATE OPERATIONAL    
    ::= 15

wtWebioAn8Alert6 TRAP-TYPE
    ENTERPRISE  wtWebioAn8
    VARIABLES   { wtWebioAn8AlarmTrapText }
    DESCRIPTION
        "This SNMP trap is generated when Alarm 6 was triggered,
        SNMP trap enable is set and
        SNMP is enabled."
    -- NMS trap annotation
    --#TYPE "WebThermometer Alarm 6"
    --#SUMMARY "Alarm 6: %s"
    --#ARGUMENTS {0}
    --#SEVERITY INFORMATIONAL
    --#TIMEINDEX 99
    --#STATE OPERATIONAL    
    ::= 16

wtWebioAn8Alert7 TRAP-TYPE
    ENTERPRISE  wtWebioAn8
    VARIABLES   { wtWebioAn8AlarmTrapText }
    DESCRIPTION
        "This SNMP trap is generated when Alarm 7 was triggered,
        SNMP trap enable is set and
        SNMP is enabled."
    -- NMS trap annotation
    --#TYPE "WebThermometer Alarm 7"
    --#SUMMARY "Alarm 7: %s"
    --#ARGUMENTS {0}
    --#SEVERITY INFORMATIONAL
    --#TIMEINDEX 99
    --#STATE OPERATIONAL    
    ::= 17

wtWebioAn8Alert8 TRAP-TYPE
    ENTERPRISE  wtWebioAn8
    VARIABLES   { wtWebioAn8AlarmTrapText }
    DESCRIPTION
        "This SNMP trap is generated when Alarm 8 was triggered,
        SNMP trap enable is set and
        SNMP is enabled."
    -- NMS trap annotation
    --#TYPE "WebThermometer Alarm 8"
    --#SUMMARY "Alarm 8: %s"
    --#ARGUMENTS {0}
    --#SEVERITY INFORMATIONAL
    --#TIMEINDEX 99
    --#STATE OPERATIONAL    
    ::= 18

wtWebioAn8Alert9 TRAP-TYPE
    ENTERPRISE  wtWebioAn8
    VARIABLES   { wtWebioAn8AlarmClearTrapText }
    DESCRIPTION
        "This SNMP trap is generated when Alarm 1 was cleared,
        SNMP trap enable is set and
        SNMP is enabled."
    -- NMS trap annotation
    --#TYPE "WebThermometer Release Alarm 1"
    --#SUMMARY "Alarm 1: %s"
    --#ARGUMENTS {0}
    --#SEVERITY INFORMATIONAL
    --#TIMEINDEX 99
    --#STATE OPERATIONAL    
    ::= 71

wtWebioAn8Alert10 TRAP-TYPE
    ENTERPRISE  wtWebioAn8
    VARIABLES   { wtWebioAn8AlarmClearTrapText }
    DESCRIPTION
        "This SNMP trap is generated when Alarm 2 was cleared,
        SNMP trap enable is set and
        SNMP is enabled."
    -- NMS trap annotation
    --#TYPE "WebThermometer Release Alarm 2"
    --#SUMMARY "Alarm 2: %s"
    --#ARGUMENTS {0}
    --#SEVERITY INFORMATIONAL
    --#TIMEINDEX 99
    --#STATE OPERATIONAL    
    ::= 72

wtWebioAn8Alert11 TRAP-TYPE
    ENTERPRISE  wtWebioAn8
    VARIABLES   { wtWebioAn8AlarmClearTrapText }
    DESCRIPTION
        "This SNMP trap is generated when Alarm 3 was cleared,
        SNMP trap enable is set and
        SNMP is enabled."
    -- NMS trap annotation
    --#TYPE "WebThermometer Release Alarm 3"
    --#SUMMARY "Alarm 3: %s"
    --#ARGUMENTS {0}
    --#SEVERITY INFORMATIONAL
    --#TIMEINDEX 99
    --#STATE OPERATIONAL    
    ::= 73

wtWebioAn8Alert12 TRAP-TYPE
    ENTERPRISE  wtWebioAn8
    VARIABLES   { wtWebioAn8AlarmClearTrapText }
    DESCRIPTION
        "This SNMP trap is generated when Alarm 4 was cleared,
        SNMP trap enable is set and
        SNMP is enabled."
    -- NMS trap annotation
    --#TYPE "WebThermometer Release Alarm 4"
    --#SUMMARY "Alarm 4: %s"
    --#ARGUMENTS {0}
    --#SEVERITY INFORMATIONAL
    --#TIMEINDEX 99
    --#STATE OPERATIONAL    
    ::= 74

wtWebioAn8Alert13 TRAP-TYPE
    ENTERPRISE  wtWebioAn8
    VARIABLES   { wtWebioAn8AlarmClearTrapText }
    DESCRIPTION
        "This SNMP trap is generated when Alarm 5 was cleared,
        SNMP trap enable is set and
        SNMP is enabled."
    -- NMS trap annotation
    --#TYPE "WebThermometer Release Alarm 5"
    --#SUMMARY "Alarm 5: %s"
    --#ARGUMENTS {0}
    --#SEVERITY INFORMATIONAL
    --#TIMEINDEX 99
    --#STATE OPERATIONAL    
    ::= 75

wtWebioAn8Alert14 TRAP-TYPE
    ENTERPRISE  wtWebioAn8
    VARIABLES   { wtWebioAn8AlarmClearTrapText }
    DESCRIPTION
        "This SNMP trap is generated when Alarm 6 was cleared,
        SNMP trap enable is set and
        SNMP is enabled."
    -- NMS trap annotation
    --#TYPE "WebThermometer Release Alarm 6"
    --#SUMMARY "Alarm 6: %s"
    --#ARGUMENTS {0}
    --#SEVERITY INFORMATIONAL
    --#TIMEINDEX 99
    --#STATE OPERATIONAL    
    ::= 76

wtWebioAn8Alert15 TRAP-TYPE
    ENTERPRISE  wtWebioAn8
    VARIABLES   { wtWebioAn8AlarmClearTrapText }
    DESCRIPTION
        "This SNMP trap is generated when Alarm 7 was cleared,
        SNMP trap enable is set and
        SNMP is enabled."
    -- NMS trap annotation
    --#TYPE "WebThermometer Release Alarm 7"
    --#SUMMARY "Alarm 7: %s"
    --#ARGUMENTS {0}
    --#SEVERITY INFORMATIONAL
    --#TIMEINDEX 99
    --#STATE OPERATIONAL    
    ::= 77

wtWebioAn8Alert16 TRAP-TYPE
    ENTERPRISE  wtWebioAn8
    VARIABLES   { wtWebioAn8AlarmClearTrapText }
    DESCRIPTION
        "This SNMP trap is generated when Alarm 8 was cleared,
        SNMP trap enable is set and
        SNMP is enabled."
    -- NMS trap annotation
    --#TYPE "WebThermometer Release Alarm 8"
    --#SUMMARY "Alarm 8: %s"
    --#ARGUMENTS {0}
    --#SEVERITY INFORMATIONAL
    --#TIMEINDEX 99
    --#STATE OPERATIONAL    
    ::= 78

--------------------------------------------------------------------------------
--------------------------------------------------------------------------------
--------------------------------------------------------------------------------

-- wtWebioAn2Temp Group
------------------------

wtWebioAn2Sensors OBJECT-TYPE
    SYNTAX INTEGER (1..2)
    ACCESS read-only
    STATUS mandatory
    DESCRIPTION
        "Number of temperature sensors"
    ::= { wtWebioAn2Temp 1 }

-- Interface Table

wtWebioAn2SensorTable OBJECT-TYPE
    SYNTAX SEQUENCE OF WtWebioAn2SensorEntry
    ACCESS not-accessible
    STATUS mandatory
    DESCRIPTION
        "List of Sensors."
    ::= { wtWebioAn2Temp 2 }

wtWebioAn2SensorEntry OBJECT-TYPE
    SYNTAX WtWebioAn2SensorEntry
    ACCESS not-accessible
    STATUS mandatory
    DESCRIPTION
        "Temperature sensor numbers."
    INDEX  { wtWebioAn2SensorNo }
    ::= { wtWebioAn2SensorTable 1 }

WtWebioAn2SensorEntry ::= SEQUENCE {
    wtWebioAn2SensorNo INTEGER (1..2)
}

wtWebioAn2SensorNo OBJECT-TYPE
    SYNTAX INTEGER (1..2)
    ACCESS read-only
    STATUS mandatory
    DESCRIPTION
        "Temperature sensor number."
    ::= { wtWebioAn2SensorEntry 1 }


-- wtWebioAn2TempValue Table

wtWebioAn2TempValueTable OBJECT-TYPE
    SYNTAX SEQUENCE OF WtWebioAn2TempValueEntry
    ACCESS not-accessible
    STATUS mandatory
    DESCRIPTION
        "List of temperature values corresponding to the channel numbers."
    ::= { wtWebioAn2Temp 3 }

wtWebioAn2TempValueEntry OBJECT-TYPE
    SYNTAX WtWebioAn2TempValueEntry
    ACCESS not-accessible
    STATUS mandatory
    DESCRIPTION
        "Temperatures of the sensors."
    INDEX  { wtWebioAn2SensorNo }
    ::= { wtWebioAn2TempValueTable 1 }

WtWebioAn2TempValueEntry ::= SEQUENCE{
    wtWebioAn2TempValue OCTET STRING (SIZE (5))
}

wtWebioAn2TempValue OBJECT-TYPE
    SYNTAX OCTET STRING (SIZE (5))
    ACCESS read-only
    STATUS mandatory
    DESCRIPTION
        "Temperature value of the sensor, ASCII, 5 characters in length."
    ::= { wtWebioAn2TempValueEntry 1 }

-- wtWebioAn2BinaryTempValue Table

wtWebioAn2BinaryTempValueTable OBJECT-TYPE
    SYNTAX SEQUENCE OF WtWebioAn2BinaryTempValueEntry
    ACCESS not-accessible
    STATUS mandatory
    DESCRIPTION
        "List of binary temperature values corresponding to the channel numbers."
    ::= { wtWebioAn2Temp 4 }

wtWebioAn2BinaryTempValueEntry OBJECT-TYPE
    SYNTAX WtWebioAn2BinaryTempValueEntry
    ACCESS not-accessible
    STATUS mandatory
    DESCRIPTION
        "Binary temperature values of the sensors."
    INDEX  { wtWebioAn2SensorNo }
    ::= { wtWebioAn2BinaryTempValueTable 1 }

WtWebioAn2BinaryTempValueEntry ::= SEQUENCE{
    wtWebioAn2BinaryTempValue INTEGER
}    

wtWebioAn2BinaryTempValue OBJECT-TYPE
    SYNTAX INTEGER
    ACCESS read-only
    STATUS mandatory
    DESCRIPTION
        "Binary temperature value of the sensor in 1/10 degrees Celsius,
        signed number, 0x7FFF indicates an 
        invalid measured value."
    ::= { wtWebioAn2BinaryTempValueEntry 1 }
    
-- wtWebioAn2SessCntrl Group
----------------------------

wtWebioAn2SessCntrlPassword OBJECT-TYPE
    SYNTAX OCTET STRING 
    ACCESS read-write
    STATUS mandatory
    DESCRIPTION
        "Entering this password opens a session which is ended by writing a 1 to 
        wtWebioAn2SessCntrlLogout. When read this variable provides a string of
        length zero."
    ::= { wtWebioAn2SessCntrl 1 }

wtWebioAn2SessCntrlConfigMode OBJECT-TYPE
    SYNTAX INTEGER {
    wtWebioAn2SessCntrl-NoSession(0),
    wtWebioAn2SessCntrl-Session(1)
    }
    ACCESS read-only
    STATUS mandatory
    DESCRIPTION
        "When the device is in SNMP configuration mode, the value 1 is
        returned, otherwise 0. If the read value is 0 even though the
        password was written, the device is already in config mode and
        the variables can only be read."
    ::= { wtWebioAn2SessCntrl 2 }

wtWebioAn2SessCntrlLogout OBJECT-TYPE
    SYNTAX INTEGER 
    ACCESS read-write
    STATUS mandatory
    DESCRIPTION
        "If the device is in configuration mode and the session was opened by
        this SNMP Manager, writing a 1 to this variable will end the session 
        and all parameters are stored.
        Writing a 2 discards all entries again.
        When read this variable provides the value 0."
    ::= { wtWebioAn2SessCntrl 3 }

wtWebioAn2SessCntrlAdminPassword OBJECT-TYPE
    SYNTAX OCTET STRING 
    ACCESS read-write
    STATUS mandatory
    DESCRIPTION
        "This password protects access to the variables with administrator rights.
        It can only be changed by the administrator. If no password was assigned,
        the valid password is public."
    ::= { wtWebioAn2SessCntrl 4 }

wtWebioAn2SessCntrlConfigPassword OBJECT-TYPE
    SYNTAX OCTET STRING 
    ACCESS read-write
    STATUS mandatory
    DESCRIPTION
        "This password protects access to the variables with configurator rights. It can
        be changed by the administrator and by the configurator. If no password was assigned, 
        the valid password is public. When read this variable provides a null-pointer."
    ::= { wtWebioAn2SessCntrl 5 }
    

-- wtWebioAn2Network Group
------------------------

wtWebioAn2IpAddress OBJECT-TYPE
    SYNTAX IpAddress
    ACCESS read-write
    STATUS mandatory
    DESCRIPTION
        "IP address of the Webio"
    ::= { wtWebioAn2Network 1 }

wtWebioAn2SubnetMask OBJECT-TYPE
    SYNTAX IpAddress
    ACCESS read-write
    STATUS mandatory
    DESCRIPTION
        "ubnet mask of the Webio"
    ::= { wtWebioAn2Network 2 }

wtWebioAn2Gateway OBJECT-TYPE
    SYNTAX IpAddress
    ACCESS read-write
    STATUS mandatory
    DESCRIPTION
        "Gateway of the Webio"
    ::= { wtWebioAn2Network 3 }

wtWebioAn2DnsServer1 OBJECT-TYPE
    SYNTAX OCTET STRING 
    ACCESS read-write
    STATUS mandatory
    DESCRIPTION
        "IP address of the 1st DNS server in ASCII"
    ::= { wtWebioAn2Network 4 }

wtWebioAn2DnsServer2 OBJECT-TYPE
    SYNTAX OCTET STRING 
    ACCESS read-write
    STATUS mandatory
    DESCRIPTION
        "IP address of the 2nd DNS server in ASCII"
    ::= { wtWebioAn2Network 5 }

wtWebioAn2AddConfig OBJECT-TYPE
    SYNTAX OCTET STRING 
    ACCESS read-write
    STATUS mandatory
    DESCRIPTION
        "Additional configuration (1=ON):
        Octet 1: unused
        Octet 2: unused
        Octet 3: unused
        Octet 4:
	        Bit 0: BOOTP disable
	        "
    ::= { wtWebioAn2Network 6 }

-- wtWebioAn2Text Group
------------------------

wtWebioAn2DeviceName OBJECT-TYPE
    SYNTAX OCTET STRING 
    ACCESS read-write
    STATUS mandatory
    DESCRIPTION
        "Name of the Webio, which is user definable."
    ::= { wtWebioAn2Text 1 }

wtWebioAn2DeviceText OBJECT-TYPE
    SYNTAX OCTET STRING 
    ACCESS read-write
    STATUS mandatory
    DESCRIPTION
        "Description of the Webio, which is user definable."
    ::= { wtWebioAn2Text 2 }

wtWebioAn2DeviceLocation OBJECT-TYPE
    SYNTAX OCTET STRING 
    ACCESS read-write
    STATUS mandatory
    DESCRIPTION
        "Description of the location of the Webio, which is user definable."
    ::= { wtWebioAn2Text 3 }

wtWebioAn2DeviceContact OBJECT-TYPE
    SYNTAX OCTET STRING 
    ACCESS read-write
    STATUS mandatory
    DESCRIPTION
        "Contact address of the system operator of the Webio, which is user definable."
    ::= { wtWebioAn2Text 4 }

-- wtWebioAn2TimeZone Group
----------------------------

wtWebioAn2TzName OBJECT-TYPE
    SYNTAX OCTET STRING 
    ACCESS read-write
    STATUS mandatory
    DESCRIPTION
        "Name of the time zone (winter time)."
    ::= { wtWebioAn2TimeZone 1 }

wtWebioAn2TzOffsetHrs OBJECT-TYPE
    SYNTAX INTEGER 
    ACCESS read-write
    STATUS mandatory
    DESCRIPTION
        "Offset hours for the time zone (winter time) with respect to UTC."
    ::= { wtWebioAn2TimeZone 2 }

wtWebioAn2TzOffsetMin OBJECT-TYPE
    SYNTAX INTEGER 
    ACCESS read-write
    STATUS mandatory
    DESCRIPTION
        "Offset minutes for the time zone (winter time) with respect to UTC."
    ::= { wtWebioAn2TimeZone 3 }

wtWebioAn2StTzName OBJECT-TYPE
    SYNTAX OCTET STRING 
    ACCESS read-write
    STATUS mandatory
    DESCRIPTION
        "Name of the time zone (summer time)."
    ::= { wtWebioAn2TimeZone 4 }

wtWebioAn2StTzOffsetHrs OBJECT-TYPE
    SYNTAX INTEGER 
    ACCESS read-write
    STATUS mandatory
    DESCRIPTION
        "Offset hours of the time zone (summer time) with respect to UTC."
    ::= { wtWebioAn2TimeZone 5 }

wtWebioAn2StTzOffsetMin OBJECT-TYPE
    SYNTAX INTEGER 
    ACCESS read-write
    STATUS mandatory
    DESCRIPTION
        "Offset minutes of the time zone (summer time) with respect to UTC."
    ::= { wtWebioAn2TimeZone 6 }
    
wtWebioAn2StTzStartMonth OBJECT-TYPE
    SYNTAX INTEGER {
    	wtWebioAn2StartMonth-January(1),
    	wtWebioAn2StartMonth-February(2),
    	wtWebioAn2StartMonth-March(3),
    	wtWebioAn2StartMonth-April(4),
    	wtWebioAn2StartMonth-May(5),
    	wtWebioAn2StartMonth-June(6),
    	wtWebioAn2StartMonth-July(7),
    	wtWebioAn2StartMonth-August(8),
    	wtWebioAn2StartMonth-September(9),
    	wtWebioAn2StartMonth-October(10),
    	wtWebioAn2StartMonth-November(11),
    	wtWebioAn2StartMonth-December(12)
    	}
    	
    ACCESS read-write
    STATUS mandatory
    DESCRIPTION
        "Month in which the change is made from winter time to summer time."
    ::= { wtWebioAn2TimeZone 7 }

wtWebioAn2StTzStartMode OBJECT-TYPE
    SYNTAX INTEGER {
    	wtWebioAn2StartMode-first(1),
    	wtWebioAn2StartMode-second(2),
    	wtWebioAn2StartMode-third(3),
    	wtWebioAn2StartMode-fourth(4),
    	wtWebioAn2StartMode-last(5)
    	}
    	
    ACCESS read-write
    STATUS mandatory
    DESCRIPTION
        "Mode of the day of the week for which the change is made from winter time to summer time."
    ::= { wtWebioAn2TimeZone 8 }

wtWebioAn2StTzStartWday OBJECT-TYPE
    SYNTAX INTEGER {
    	wtWebioAn2StartWday-Sunday(1),
    	wtWebioAn2StartWday-Monday(2),
    	wtWebioAn2StartWday-Tuesday(3),
    	wtWebioAn2StartWday-Thursday(4),
    	wtWebioAn2StartWday-Wednesday(5),
    	wtWebioAn2StartWday-Friday(6),
    	wtWebioAn2StartWday-Saturday(7)
    	}
    	
    ACCESS read-write
    STATUS mandatory
    DESCRIPTION
        "Day of the week on which the change is made from winter time to summer time"
    ::= { wtWebioAn2TimeZone 9 }
    
wtWebioAn2StTzStartHrs OBJECT-TYPE
    SYNTAX INTEGER 
    ACCESS read-write
    STATUS mandatory
    DESCRIPTION
        "Hour in which the time zone is changed from winter to summer time with
        respect to UTC."
    ::= { wtWebioAn2TimeZone 10 }

wtWebioAn2StTzStartMin OBJECT-TYPE
    SYNTAX INTEGER 
    ACCESS read-write
    STATUS mandatory
    DESCRIPTION
        "Minute in which the time zone is changed from winter to summer time with
        respect to UTC."
    ::= { wtWebioAn2TimeZone 11 }
 
wtWebioAn2StTzStopMonth OBJECT-TYPE
    SYNTAX INTEGER {
    	wtWebioAn2StopMonth-January(1),
    	wtWebioAn2StopMonth-February(2),
    	wtWebioAn2StopMonth-March(3),
    	wtWebioAn2StopMonth-April(4),
    	wtWebioAn2StopMonth-May(5),
    	wtWebioAn2StopMonth-June(6),
    	wtWebioAn2StopMonth-July(7),
    	wtWebioAn2StopMonth-August(8),
    	wtWebioAn2StopMonth-September(9),
    	wtWebioAn2StopMonth-October(10),
    	wtWebioAn2StopMonth-November(11),
    	wtWebioAn2StopMonth-December(12)
    	}
    ACCESS read-write
    STATUS mandatory
    DESCRIPTION
        "Month in which the change is made from summer time to winter time."
   ::= { wtWebioAn2TimeZone 12 }

wtWebioAn2StTzStopMode OBJECT-TYPE
    SYNTAX INTEGER {
    	wtWebioAn2StopMode-first(1),
    	wtWebioAn2StopMode-second(2),
    	wtWebioAn2StopMode-third(3),
    	wtWebioAn2StopMode-fourth(4),
    	wtWebioAn2StopMode-last(5)
    	}
    ACCESS read-write
    STATUS mandatory
    DESCRIPTION
        "Mode of the week day on which the change is made from summer time to winter time."
    ::= { wtWebioAn2TimeZone 13 }

wtWebioAn2StTzStopWday OBJECT-TYPE
    SYNTAX INTEGER {
    	wtWebioAn2StopWday-Sunday(1),
    	wtWebioAn2StopWday-Monday(2),
    	wtWebioAn2StopWday-Tuesday(3),
    	wtWebioAn2StopWday-Thursday(4),
    	wtWebioAn2StopWday-Wednesday(5),
    	wtWebioAn2StopWday-Friday(6),
    	wtWebioAn2StopWday-Saturday(7)
    	}
    ACCESS read-write
    STATUS mandatory
    DESCRIPTION
        "Day of the week on which the change is made from summer time to winter time."
    ::= { wtWebioAn2TimeZone 14 }
    
wtWebioAn2StTzStopHrs OBJECT-TYPE
    SYNTAX INTEGER 
    ACCESS read-write
    STATUS mandatory
    DESCRIPTION
        "Hour at which the time zone is changed from summer to winter time with
        respect to UTC."
    ::= { wtWebioAn2TimeZone 15 }

wtWebioAn2StTzStopMin OBJECT-TYPE
    SYNTAX INTEGER 
    ACCESS read-write
    STATUS mandatory
    DESCRIPTION
        "Minute at which the time zone is changed from summer to winter time with
        respect to UTC."
    ::= { wtWebioAn2TimeZone 16 }

-- wtWebioAn2TimeServer Group
----------------------------

wtWebioAn2TimeServer1 OBJECT-TYPE
    SYNTAX OCTET STRING 
    ACCESS read-write
    STATUS mandatory
    DESCRIPTION
        "IP address or name of the 1st time server in ASCII"
    ::= { wtWebioAn2TimeServer 1 }

wtWebioAn2TimeServer2 OBJECT-TYPE
    SYNTAX OCTET STRING 
    ACCESS read-write
    STATUS mandatory
    DESCRIPTION
        "IP address or name of the 2nd time server in ASCII"
    ::= { wtWebioAn2TimeServer 2 }
    
-- wtWebioAn2DeviceClock Group
----------------------------

wtWebioAn2ClockHrs OBJECT-TYPE
    SYNTAX INTEGER (0..23)
    ACCESS read-write
    STATUS mandatory
    DESCRIPTION
        "Clock hours taking into account the time zone settings."
    ::= { wtWebioAn2DeviceClock 1 }

wtWebioAn2ClockMin OBJECT-TYPE
    SYNTAX INTEGER (0..59)
    ACCESS read-write
    STATUS mandatory
    DESCRIPTION
        "Clock minutes taking into account the time zone settings."
    ::= { wtWebioAn2DeviceClock 2 }

wtWebioAn2ClockDay OBJECT-TYPE
    SYNTAX INTEGER (1..31)
    ACCESS read-write
    STATUS mandatory
    DESCRIPTION
        "Date: Day of the month, taking into account the time zone settings."
    ::= { wtWebioAn2DeviceClock 3 }

wtWebioAn2ClockMonth OBJECT-TYPE
   SYNTAX INTEGER {
    	wtWebioAn2ClockMonth-January(1),
    	wtWebioAn2ClockMonth-February(2),
    	wtWebioAn2ClockMonth-March(3),
    	wtWebioAn2ClockMonth-April(4),
    	wtWebioAn2ClockMonth-May(5),
    	wtWebioAn2ClockMonth-June(6),
    	wtWebioAn2ClockMonth-July(7),
    	wtWebioAn2ClockMonth-August(8),
    	wtWebioAn2ClockMonth-September(9),
    	wtWebioAn2ClockMonth-October(10),
    	wtWebioAn2ClockMonth-November(11),
    	wtWebioAn2ClockMonth-December(12)
    	}
    ACCESS read-write
    STATUS mandatory
    DESCRIPTION
        "Date: Month, taking into account the time zone settings."
    ::= { wtWebioAn2DeviceClock 4 }

wtWebioAn2ClockYear OBJECT-TYPE
    SYNTAX INTEGER (0..65535)
    ACCESS read-write
    STATUS mandatory
    DESCRIPTION
        "Date: Year, taking into account the time zone settings."
    ::= { wtWebioAn2DeviceClock 5 }
    
-- wtWebioAn2MailAdmin Group
----------------------------

wtWebioAn2MailAdName OBJECT-TYPE
    SYNTAX OCTET STRING 
    ACCESS read-write
    STATUS mandatory
    DESCRIPTION
        "Device name for mail administration."
    ::= { wtWebioAn2MailAdmin 1 }
    
wtWebioAn2MailReply OBJECT-TYPE
    SYNTAX OCTET STRING 
    ACCESS read-write
    STATUS mandatory
    DESCRIPTION
        "Reply address for the mail server."
    ::= { wtWebioAn2MailAdmin 2 }
    
wtWebioAn2MailServer OBJECT-TYPE
    SYNTAX OCTET STRING 
    ACCESS read-write
    STATUS mandatory
    DESCRIPTION
        "Name or IP address of the mail server."
    ::= { wtWebioAn2MailAdmin 3 }
    

-- wtWebioAn2Alarm Group
----------------------------

wtWebioAn2AlarmCount OBJECT-TYPE
    SYNTAX INTEGER (1..8)
    ACCESS read-only
    STATUS mandatory
    DESCRIPTION
        "Number of independent alarms."
    ::= { wtWebioAn2Alarm 1 }
    
-- Alarm Interface Table

wtWebioAn2AlarmIfTable OBJECT-TYPE
    SYNTAX SEQUENCE OF WtWebioAn2AlarmIfEntry
    ACCESS not-accessible
    STATUS mandatory
    DESCRIPTION
        "List of alarm indices."
    ::= { wtWebioAn2Alarm 2 }

wtWebioAn2AlarmIfEntry OBJECT-TYPE
    SYNTAX WtWebioAn2AlarmIfEntry
    ACCESS not-accessible
    STATUS mandatory
    DESCRIPTION
        "Numbers of the alarms."
    INDEX  { wtWebioAn2AlarmNo }
    ::= { wtWebioAn2AlarmIfTable 1 }

WtWebioAn2AlarmIfEntry ::= SEQUENCE {
    wtWebioAn2AlarmNo INTEGER (1..8)
}

wtWebioAn2AlarmNo OBJECT-TYPE
    SYNTAX INTEGER (1..8)
    ACCESS read-only
    STATUS mandatory
    DESCRIPTION
        "Alarm number."
    ::= { wtWebioAn2AlarmIfEntry 1 }

-- Alarm Table

wtWebioAn2AlarmTable OBJECT-TYPE
    SYNTAX SEQUENCE OF WtWebioAn2AlarmEntry
    ACCESS not-accessible
    STATUS mandatory
    DESCRIPTION
        "List of settings depending on the alarm number."
    ::= { wtWebioAn2Alarm 3 }

wtWebioAn2AlarmEntry OBJECT-TYPE
    SYNTAX WtWebioAn2AlarmEntry
    ACCESS not-accessible
    STATUS mandatory
    DESCRIPTION
        "Alarm parameters of the individual alarms."
    INDEX  { wtWebioAn2AlarmNo }
    ::= { wtWebioAn2AlarmTable 1 }

WtWebioAn2AlarmEntry ::= SEQUENCE {
    wtWebioAn2AlarmTrigger		OCTET STRING,
    wtWebioAn2AlarmMin			OCTET STRING,
    wtWebioAn2AlarmMax			OCTET STRING,
    wtWebioAn2AlarmInterval		OCTET STRING,
    wtWebioAn2AlarmEnable		OCTET STRING,
    wtWebioAn2AlarmEMailAddr		OCTET STRING,
    wtWebioAn2AlarmMailSubject		OCTET STRING,
    wtWebioAn2AlarmMailText		OCTET STRING,
    wtWebioAn2AlarmManagerIP		OCTET STRING,
    wtWebioAn2AlarmTrapText		OCTET STRING,
    wtWebioAn2AlarmMailOptions		OCTET STRING,
    wtWebioAn2AlarmTcpIpAddr		OCTET STRING,
    wtWebioAn2AlarmTcpPort		INTEGER,
    wtWebioAn2AlarmTcpText		OCTET STRING,
    wtWebioAn2AlarmHystersis		OCTET STRING,
    wtWebioAn2AlarmClearMailSubject	OCTET STRING,
    wtWebioAn2AlarmClearMailText	OCTET STRING,
    wtWebioAn2AlarmClearTrapText	OCTET STRING,
    wtWebioAn2AlarmClearTcpText		OCTET STRING
    
}

wtWebioAn2AlarmTrigger OBJECT-TYPE
    SYNTAX OCTET STRING (SIZE(4))
    ACCESS read-write
    STATUS mandatory
    DESCRIPTION
        "Binary coded trigger conditions:
        Octet 1: unused
        Octet 2: unused
        Octet 3: unused
        Octet 4:
	        Bit 0: Sensor 1
	        Bit 1: Sensor 2
	        Bit 2: Timer
        	Bit 1: ColdStart
        	Bit 2: WarmStart"
    ::= { wtWebioAn2AlarmEntry 1 }

wtWebioAn2AlarmMin OBJECT-TYPE
    SYNTAX OCTET STRING 
    ACCESS read-write
    STATUS mandatory
    DESCRIPTION
        "Minimum temperature in degrees with maximum 2 decimal places."
    ::= { wtWebioAn2AlarmEntry 2 }

wtWebioAn2AlarmMax OBJECT-TYPE
    SYNTAX OCTET STRING 
    ACCESS read-write
    STATUS mandatory
    DESCRIPTION
        "Maximum temperature in degrees with maximum 2 decimal places."
    ::= { wtWebioAn2AlarmEntry 3 }

wtWebioAn2AlarmInterval OBJECT-TYPE
    SYNTAX OCTET STRING 
    ACCESS read-write
    STATUS mandatory
    DESCRIPTION
        "Send interval for alarm messages."
    ::= { wtWebioAn2AlarmEntry 4 }

wtWebioAn2AlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  TCP Client enable"
    ::= { wtWebioAn2AlarmEntry 5 }

wtWebioAn2AlarmEMailAddr OBJECT-TYPE
    SYNTAX OCTET STRING 
    ACCESS read-write
    STATUS mandatory
    DESCRIPTION
        "E-Mail address for sending the alarm mail to."
    ::= { wtWebioAn2AlarmEntry 6 }

wtWebioAn2AlarmMailSubject OBJECT-TYPE
    SYNTAX OCTET STRING 
    ACCESS read-write
    STATUS mandatory
    DESCRIPTION
        "Subject line for alarm mail."
    ::= { wtWebioAn2AlarmEntry 7 }

wtWebioAn2AlarmMailText OBJECT-TYPE
    SYNTAX OCTET STRING 
    ACCESS read-write
    STATUS mandatory
    DESCRIPTION
        "Alarm mail text: <Tn> provides the current temperature; n = 1..2.
        <Z> provides the current time."
    ::= { wtWebioAn2AlarmEntry 8 }

wtWebioAn2AlarmManagerIP OBJECT-TYPE
    SYNTAX OCTET STRING 
    ACCESS read-write
    STATUS mandatory
    DESCRIPTION
        "Name or IP address of the SNMP Manager which accepts the trap."
    ::= { wtWebioAn2AlarmEntry 9 }

wtWebioAn2AlarmTrapText OBJECT-TYPE
    SYNTAX OCTET STRING 
    ACCESS read-write
    STATUS mandatory
    DESCRIPTION
        "This text is sent in the trap body."
    ::= { wtWebioAn2AlarmEntry 10 }
    
wtWebioAn2AlarmMailOptions OBJECT-TYPE
    SYNTAX OCTET STRING (SIZE(4))
    ACCESS read-write
    STATUS mandatory
    DESCRIPTION
        "Binary coded options:
        Octet 1: unused
        Octet 2: unused
        Octet 3: unused
        Octet 4:
		Bit 0  :	Attach Thermo.csv Enable
        	Bit 1-7:	unused"
    ::= { wtWebioAn2AlarmEntry 11 }   
    
wtWebioAn2AlarmTcpIpAddr OBJECT-TYPE
    SYNTAX OCTET STRING 
    ACCESS read-write
    STATUS mandatory
    DESCRIPTION
        "Name or IP address of the TCP server which accepts the trap."
    ::= { wtWebioAn2AlarmEntry 12 }    

wtWebioAn2AlarmTcpPort OBJECT-TYPE
    SYNTAX INTEGER (1..65535) 
    ACCESS read-write
    STATUS mandatory
    DESCRIPTION
        "Port number of the TCP server which accepts the trap."
    ::= { wtWebioAn2AlarmEntry 13 }    

wtWebioAn2AlarmTcpText OBJECT-TYPE
    SYNTAX OCTET STRING 
    ACCESS read-write
    STATUS mandatory
    DESCRIPTION
        "This text is sent in the TCP trap body."
    ::= { wtWebioAn2AlarmEntry 14 }

wtWebioAn2AlarmHysteresis OBJECT-TYPE
    SYNTAX OCTET STRING 
    ACCESS read-write
    STATUS mandatory
    DESCRIPTION
        "Temperature changes of this size clears the alarm state (MAX-hyst, MIN+hyst.)
        , in degrees with maximum 2 decimal places."
    ::= { wtWebioAn2AlarmEntry 15 }
    
wtWebioAn2AlarmClearMailSubject OBJECT-TYPE
    SYNTAX OCTET STRING 
    ACCESS read-write
    STATUS mandatory
    DESCRIPTION
        "Subject line for alarm clear mail."
    ::= { wtWebioAn2AlarmEntry 16 }

wtWebioAn2AlarmClearMailText OBJECT-TYPE
    SYNTAX OCTET STRING 
    ACCESS read-write
    STATUS mandatory
    DESCRIPTION
        "Alarm clear mail text: <Tn> provides the current temperature; n = 1..8.
        <Z> provides the current time."
    ::= { wtWebioAn2AlarmEntry 17 }

wtWebioAn2AlarmClearTrapText OBJECT-TYPE
    SYNTAX OCTET STRING 
    ACCESS read-write
    STATUS mandatory
    DESCRIPTION
        "This text is sent in the trap body."
    ::= { wtWebioAn2AlarmEntry 18 }

wtWebioAn2AlarmClearTcpText OBJECT-TYPE
    SYNTAX OCTET STRING 
    ACCESS read-write
    STATUS mandatory
    DESCRIPTION
        "This text is sent in the TCP trap body."
    ::= { wtWebioAn2AlarmEntry 19 }

    

-- wtWebioAn2Datalogger Group
--------------------------------

wtWebioAn2LoggerTimebase OBJECT-TYPE
    SYNTAX INTEGER {
    wtWebioAn2Datalogger-1Min(1),
    wtWebioAn2Datalogger-5Min(2),
    wtWebioAn2Datalogger-15Min(3),
    wtWebioAn2Datalogger-60Min(4)
    }
    ACCESS read-write
    STATUS mandatory
    DESCRIPTION
        "Time base of the data logger"
    ::= { wtWebioAn2Datalogger 1 }

wtWebioAn2LoggerSensorSel OBJECT-TYPE
    SYNTAX OCTET STRING (SIZE(4))
    ACCESS read-write
    STATUS mandatory
    DESCRIPTION
        "Binary coded trigger conditions:
        Octet 1: unused
        Octet 2: unused
        Octet 3: unused
        Octet 4:
		Bit 0: Sensor 1
        	Bit 1: Sensor 2"
    ::= { wtWebioAn2Datalogger 2 }

-- wtWebioAn2Protocol Group
----------------------------

wtWebioAn2PrtclUdpPort OBJECT-TYPE
    SYNTAX INTEGER (1..65535)
    ACCESS read-write
    STATUS mandatory
    DESCRIPTION
        "Udp port to which the Udp queries GET Single can be sent"
    ::= { wtWebioAn2PrtclUDP 1 }

wtWebioAn2PrtclSnmpCommunityStringRead OBJECT-TYPE
    SYNTAX OCTET STRING
    ACCESS read-write
    STATUS mandatory
    DESCRIPTION
        "Community string read only"
    ::= { wtWebioAn2PrtclSNMP 1 }

wtWebioAn2PrtclSnmpCommunityStringReadWrite OBJECT-TYPE
    SYNTAX OCTET STRING
    ACCESS read-write
    STATUS mandatory
    DESCRIPTION
        "Community string read / write"
    ::= { wtWebioAn2PrtclSNMP 2 }

wtWebioAn2SystemTrapManagerIP OBJECT-TYPE
    SYNTAX OCTET STRING 
    ACCESS read-write
    STATUS mandatory
    DESCRIPTION
        "Name or IP address of the TCP server which accepts the system trap."
    ::= { wtWebioAn2PrtclSNMP 3 }
    
wtWebioAn2SystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2-7: unused"
    ::= { wtWebioAn2PrtclSNMP 4 }
    
wtWebioAn2PrtclHttpPort OBJECT-TYPE
    SYNTAX INTEGER (1..65535)
    ACCESS read-write
    STATUS mandatory
    DESCRIPTION
        "HTTP port to which the HTTP queries GET Single can be sent"
    ::= { wtWebioAn2PrtclHttp 1 }        

-- wtWebioAn2Enable Group
----------------------------

wtWebioAn2Enables OBJECT-TYPE
    SYNTAX OCTET STRING (SIZE(4))
    ACCESS read-write
    STATUS mandatory
    DESCRIPTION
        "Binary coded trigger conditions:
        Octet 1: unused
        Octet 2: unused
        Octet 3: unused
        Octet 4:
	        Bit 0: Update enable
	        Bit 1: Mail enable
	        Bit 2: Snmp enable
	        Bit 3: UDP enable
	        Bit 4: Get Single Header enable
	        Bit 5: Apply Timezone
	        Bit 6: Apply Summertime
	        Bit 7: Apply TimeServer"
    ::= { wtWebioAn2Enable 1 }

-- wtWebioAn2Startup Group
----------------------------

wtWebioAn2StartupSite OBJECT-TYPE
    SYNTAX OCTET STRING (SIZE(4))
    ACCESS read-write
    STATUS mandatory
    DESCRIPTION
        "Binary coded start page:
        Octet 1: unused
        Octet 2: unused
        Octet 3: unused
        Octet 4:
	        Bit 1: Index.htm
	        Bit 2: Home.htm
	        Bit 3: User.htm
	Only one page may be selected at a time."
    ::= { wtWebioAn2Startup 1 }

-- wtWebioAn2Ports Group
----------------------------

-- Table

wtWebioAn2PortTable OBJECT-TYPE
    SYNTAX SEQUENCE OF WtWebioAn2PortEntry
    ACCESS not-accessible
    STATUS mandatory
    DESCRIPTION
        "List of settings depending on the sensor number."
    ::= { wtWebioAn2Ports 1 }

wtWebioAn2PortEntry OBJECT-TYPE
    SYNTAX WtWebioAn2PortEntry
    ACCESS not-accessible
    STATUS mandatory
    DESCRIPTION
        "Sensor parameters for the individual sensor."
    INDEX  { wtWebioAn2SensorNo }
    ::= { wtWebioAn2PortTable 1 }

WtWebioAn2PortEntry ::= SEQUENCE {
    wtWebioAn2PortName		OCTET STRING,
    wtWebioAn2PortText		OCTET STRING,
    wtWebioAn2PortOffset1	OCTET STRING,
    wtWebioAn2PortTemperature1	OCTET STRING,
    wtWebioAn2PortOffset2	OCTET STRING,
    wtWebioAn2PortTemperature2	OCTET STRING,
    wtWebioAn2PortComment	OCTET STRING
    
}

wtWebioAn2PortName OBJECT-TYPE
    SYNTAX OCTET STRING 
    ACCESS read-write
    STATUS mandatory
    DESCRIPTION
        "Name of the sensor."
    ::= { wtWebioAn2PortEntry 1 }

wtWebioAn2PortText OBJECT-TYPE
    SYNTAX OCTET STRING 
    ACCESS read-write
    STATUS mandatory
    DESCRIPTION
        "Description of the sensor."
    ::= { wtWebioAn2PortEntry 2 }

wtWebioAn2PortOffset1 OBJECT-TYPE
    SYNTAX OCTET STRING 
    ACCESS read-write
    STATUS mandatory
    DESCRIPTION
        "Offset calibration: Offset in degrees with maximum 2 decimal places at temperature 1."
    ::= { wtWebioAn2PortEntry 3 }

wtWebioAn2PortTemperature1 OBJECT-TYPE
    SYNTAX OCTET STRING 
    ACCESS read-write
    STATUS mandatory
    DESCRIPTION
        "Offset calibration: Reference temperature 1 in degrees with maximum 2 decimal places."
    ::= { wtWebioAn2PortEntry 4 }

wtWebioAn2PortOffset2 OBJECT-TYPE
    SYNTAX OCTET STRING 
    ACCESS read-write
    STATUS mandatory
    DESCRIPTION
        "Offset calibration: Offset in degrees with maximum 2 decimal places at temperature 2."
    ::= { wtWebioAn2PortEntry 5 }

wtWebioAn2PortTemperature2 OBJECT-TYPE
    SYNTAX OCTET STRING 
    ACCESS read-write
    STATUS mandatory
    DESCRIPTION
        "Offset calibration: Reference temperature 1 in degrees with maximum 2 decimal places."
    ::= { wtWebioAn2PortEntry 6 }

wtWebioAn2PortComment OBJECT-TYPE
    SYNTAX OCTET STRING 
    ACCESS read-write
    STATUS mandatory
    DESCRIPTION
        "Offset calibration: informations of date, name of operator, reference devices."
    ::= { wtWebioAn2PortEntry 7 }   
    
-- wtWebioAn2Manufact Group
----------------------------

wtWebioAn2MfName OBJECT-TYPE
    SYNTAX OCTET STRING 
    ACCESS read-write
    STATUS mandatory
    DESCRIPTION
        "Manufacturer company name"
    ::= { wtWebioAn2Manufact 1 }

wtWebioAn2MfAddr OBJECT-TYPE
    SYNTAX OCTET STRING 
    ACCESS read-write
    STATUS mandatory
    DESCRIPTION
        "Manufacturer address."
    ::= { wtWebioAn2Manufact 2 }

wtWebioAn2MfHotline OBJECT-TYPE
    SYNTAX OCTET STRING 
    ACCESS read-write
    STATUS mandatory
    DESCRIPTION
        "Manufacturer hotline."
    ::= { wtWebioAn2Manufact 3 }

wtWebioAn2MfInternet OBJECT-TYPE
    SYNTAX OCTET STRING 
    ACCESS read-write
    STATUS mandatory
    DESCRIPTION
        "Manufacturer Internet address."
    ::= { wtWebioAn2Manufact 4 }

wtWebioAn2MfDeviceTyp OBJECT-TYPE
    SYNTAX OCTET STRING 
    ACCESS read-write
    STATUS mandatory
    DESCRIPTION
        "Manufacturer device name (model number)."
    ::= { wtWebioAn2Manufact 5 }

wtWebioAn2MfOrderNo OBJECT-TYPE
    SYNTAX OCTET STRING 
    ACCESS read-write
    STATUS mandatory
    DESCRIPTION
        "Manufacturer part number."
    ::= { wtWebioAn2Manufact 6 }

-- TRAP DEFINITIONS

-- Diese SNMP-Traps werden gesendet, wenn die Alarmtriggerbedingungen zutreffen 

wtWebioAn2Alert1 TRAP-TYPE
    ENTERPRISE  wtWebioAn2
    VARIABLES   { wtWebioAn2AlarmTrapText }
    DESCRIPTION
        "This SNMP trap is generated when Alarm 1 was triggered,
        SNMP trap enable is set and
        SNMP is enabled."
    -- NMS trap annotation
    --#TYPE "WebThermometer Alarm 1"
    --#SUMMARY "Alarm 1: %s"
    --#ARGUMENTS {0}
    --#SEVERITY INFORMATIONAL
    --#TIMEINDEX 99
    --#STATE OPERATIONAL    
    ::= 21

wtWebioAn2Alert2 TRAP-TYPE
    ENTERPRISE  wtWebioAn2
    VARIABLES   { wtWebioAn2AlarmTrapText }
    DESCRIPTION
        "This SNMP trap is generated when Alarm 2 was triggered,
        SNMP trap enable is set and
        SNMP is enabled."
    -- NMS trap annotation
    --#TYPE "WebThermometer Alarm 2"
    --#SUMMARY "Alarm 2: %s"
    --#ARGUMENTS {0}
    --#SEVERITY INFORMATIONAL
    --#TIMEINDEX 99
    --#STATE OPERATIONAL    
    ::= 22

wtWebioAn2Alert3 TRAP-TYPE
    ENTERPRISE  wtWebioAn2
    VARIABLES   { wtWebioAn2AlarmTrapText }
    DESCRIPTION
        "This SNMP trap is generated when Alarm 3 was triggered,
        SNMP trap enable is set and
        SNMP is enabled."
    -- NMS trap annotation
    --#TYPE "WebThermometer Alarm 3"
    --#SUMMARY "Alarm 3: %s"
    --#ARGUMENTS {0}
    --#SEVERITY INFORMATIONAL
    --#TIMEINDEX 99
    --#STATE OPERATIONAL    
    ::= 23

wtWebioAn2Alert4 TRAP-TYPE
    ENTERPRISE  wtWebioAn2
    VARIABLES   { wtWebioAn2AlarmTrapText }
    DESCRIPTION
        "This SNMP trap is generated when Alarm 4 was triggered,
        SNMP trap enable is set and
        SNMP is enabled."
    -- NMS trap annotation
    --#TYPE "WebThermometer Alarm 4"
    --#SUMMARY "Alarm 4: %s"
    --#ARGUMENTS {0}
    --#SEVERITY INFORMATIONAL
    --#TIMEINDEX 99
    --#STATE OPERATIONAL    
    ::= 24

wtWebioAn2Alert5 TRAP-TYPE
    ENTERPRISE  wtWebioAn2
    VARIABLES   { wtWebioAn2AlarmTrapText }
    DESCRIPTION
        "This SNMP trap is generated when Alarm 5 was triggered,
        SNMP trap enable is set and
        SNMP is enabled."
    -- NMS trap annotation
    --#TYPE "WebThermometer Alarm 5"
    --#SUMMARY "Alarm 5: %s"
    --#ARGUMENTS {0}
    --#SEVERITY INFORMATIONAL
    --#TIMEINDEX 99
    --#STATE OPERATIONAL    
    ::= 25

wtWebioAn2Alert6 TRAP-TYPE
    ENTERPRISE  wtWebioAn2
    VARIABLES   { wtWebioAn2AlarmTrapText }
    DESCRIPTION
        "This SNMP trap is generated when Alarm 6 was triggered,
        SNMP trap enable is set and
        SNMP is enabled."
    -- NMS trap annotation
    --#TYPE "WebThermometer Alarm 6"
    --#SUMMARY "Alarm 6: %s"
    --#ARGUMENTS {0}
    --#SEVERITY INFORMATIONAL
    --#TIMEINDEX 99
    --#STATE OPERATIONAL    
    ::= 26

wtWebioAn2Alert7 TRAP-TYPE
    ENTERPRISE  wtWebioAn2
    VARIABLES   { wtWebioAn2AlarmTrapText }
    DESCRIPTION
        "This SNMP trap is generated when Alarm 7 was triggered,
        SNMP trap enable is set and
        SNMP is enabled."
    -- NMS trap annotation
    --#TYPE "WebThermometer Alarm 7"
    --#SUMMARY "Alarm 7: %s"
    --#ARGUMENTS {0}
    --#SEVERITY INFORMATIONAL
    --#TIMEINDEX 99
    --#STATE OPERATIONAL    
    ::= 27

wtWebioAn2Alert8 TRAP-TYPE
    ENTERPRISE  wtWebioAn2
    VARIABLES   { wtWebioAn2AlarmTrapText }
    DESCRIPTION
        "This SNMP trap is generated when Alarm 8 was triggered,
        SNMP trap enable is set and
        SNMP is enabled."
    -- NMS trap annotation
    --#TYPE "WebThermometer Alarm 8"
    --#SUMMARY "Alarm 8: %s"
    --#ARGUMENTS {0}
    --#SEVERITY INFORMATIONAL
    --#TIMEINDEX 99
    --#STATE OPERATIONAL    
    ::= 28
    
wtWebioAn2Alert9 TRAP-TYPE
    ENTERPRISE  wtWebioAn2
    VARIABLES   { wtWebioAn2AlarmClearTrapText }
    DESCRIPTION
        "This SNMP trap is generated when Alarm 1 was cleared,
        SNMP trap enable is set and
        SNMP is enabled."
    -- NMS trap annotation
    --#TYPE "WebThermometer Release Alarm 1"
    --#SUMMARY "Alarm 1: %s"
    --#ARGUMENTS {0}
    --#SEVERITY INFORMATIONAL
    --#TIMEINDEX 99
    --#STATE OPERATIONAL    
    ::= 81

wtWebioAn2Alert10 TRAP-TYPE
    ENTERPRISE  wtWebioAn2
    VARIABLES   { wtWebioAn2AlarmClearTrapText }
    DESCRIPTION
        "This SNMP trap is generated when Alarm 2 was cleared,
        SNMP trap enable is set and
        SNMP is enabled."
    -- NMS trap annotation
    --#TYPE "WebThermometer Release Alarm 2"
    --#SUMMARY "Alarm 2: %s"
    --#ARGUMENTS {0}
    --#SEVERITY INFORMATIONAL
    --#TIMEINDEX 99
    --#STATE OPERATIONAL    
    ::= 82

wtWebioAn2Alert11 TRAP-TYPE
    ENTERPRISE  wtWebioAn2
    VARIABLES   { wtWebioAn2AlarmClearTrapText }
    DESCRIPTION
        "This SNMP trap is generated when Alarm 3 was cleared,
        SNMP trap enable is set and
        SNMP is enabled."
    -- NMS trap annotation
    --#TYPE "WebThermometer Release Alarm 3"
    --#SUMMARY "Alarm 3: %s"
    --#ARGUMENTS {0}
    --#SEVERITY INFORMATIONAL
    --#TIMEINDEX 99
    --#STATE OPERATIONAL    
    ::= 83

wtWebioAn2Alert12 TRAP-TYPE
    ENTERPRISE  wtWebioAn2
    VARIABLES   { wtWebioAn2AlarmClearTrapText }
    DESCRIPTION
        "This SNMP trap is generated when Alarm 4 was cleared,
        SNMP trap enable is set and
        SNMP is enabled."
    -- NMS trap annotation
    --#TYPE "WebThermometer Release Alarm 4"
    --#SUMMARY "Alarm 4: %s"
    --#ARGUMENTS {0}
    --#SEVERITY INFORMATIONAL
    --#TIMEINDEX 99
    --#STATE OPERATIONAL    
    ::= 84

wtWebioAn2Alert13 TRAP-TYPE
    ENTERPRISE  wtWebioAn2
    VARIABLES   { wtWebioAn2AlarmClearTrapText }
    DESCRIPTION
        "This SNMP trap is generated when Alarm 5 was cleared,
        SNMP trap enable is set and
        SNMP is enabled."
    -- NMS trap annotation
    --#TYPE "WebThermometer Release Alarm 5"
    --#SUMMARY "Alarm 5: %s"
    --#ARGUMENTS {0}
    --#SEVERITY INFORMATIONAL
    --#TIMEINDEX 99
    --#STATE OPERATIONAL    
    ::= 85

wtWebioAn2Alert14 TRAP-TYPE
    ENTERPRISE  wtWebioAn2
    VARIABLES   { wtWebioAn2AlarmClearTrapText }
    DESCRIPTION
        "This SNMP trap is generated when Alarm 6 was cleared,
        SNMP trap enable is set and
        SNMP is enabled."
    -- NMS trap annotation
    --#TYPE "WebThermometer Release Alarm 6"
    --#SUMMARY "Alarm 6: %s"
    --#ARGUMENTS {0}
    --#SEVERITY INFORMATIONAL
    --#TIMEINDEX 99
    --#STATE OPERATIONAL    
    ::= 86

wtWebioAn2Alert15 TRAP-TYPE
    ENTERPRISE  wtWebioAn2
    VARIABLES   { wtWebioAn2AlarmClearTrapText }
    DESCRIPTION
        "This SNMP trap is generated when Alarm 7 was cleared,
        SNMP trap enable is set and
        SNMP is enabled."
    -- NMS trap annotation
    --#TYPE "WebThermometer Release Alarm 7"
    --#SUMMARY "Alarm 7: %s"
    --#ARGUMENTS {0}
    --#SEVERITY INFORMATIONAL
    --#TIMEINDEX 99
    --#STATE OPERATIONAL    
    ::= 87

wtWebioAn2Alert16 TRAP-TYPE
    ENTERPRISE  wtWebioAn2
    VARIABLES   { wtWebioAn2AlarmClearTrapText }
    DESCRIPTION
        "This SNMP trap is generated when Alarm 8 was cleared,
        SNMP trap enable is set and
        SNMP is enabled."
    -- NMS trap annotation
    --#TYPE "WebThermometer Release Alarm 8"
    --#SUMMARY "Alarm 8: %s"
    --#ARGUMENTS {0}
    --#SEVERITY INFORMATIONAL
    --#TIMEINDEX 99
    --#STATE OPERATIONAL    
    ::= 88
--------------------------------------------------------------------------------
--------------------------------------------------------------------------------
--------------------------------------------------------------------------------

-- wtWebioAn1Temp Group
------------------------

wtWebioAn1Sensors OBJECT-TYPE
    SYNTAX INTEGER (1..8)
    ACCESS read-only
    STATUS mandatory
    DESCRIPTION
        "Number of temperature sensors"
    ::= { wtWebioAn1Temp 1 }

-- Interface Table

wtWebioAn1SensorTable OBJECT-TYPE
    SYNTAX SEQUENCE OF WtWebioAn1SensorEntry
    ACCESS not-accessible
    STATUS mandatory
    DESCRIPTION
        "List of sensors."
    ::= { wtWebioAn1Temp 2 }

wtWebioAn1SensorEntry OBJECT-TYPE
    SYNTAX WtWebioAn1SensorEntry
    ACCESS not-accessible
    STATUS mandatory
    DESCRIPTION
        "Temperature sensor numbers."
    INDEX  { wtWebioAn1SensorNo }
    ::= { wtWebioAn1SensorTable 1 }

WtWebioAn1SensorEntry ::= SEQUENCE {
    wtWebioAn1SensorNo INTEGER (1)
}

wtWebioAn1SensorNo OBJECT-TYPE
    SYNTAX INTEGER (1)
    ACCESS read-only
    STATUS mandatory
    DESCRIPTION
        "Temperature sensor number."
    ::= { wtWebioAn1SensorEntry 1 }


-- wtWebioAn1TempValue Table

wtWebioAn1TempValueTable OBJECT-TYPE
    SYNTAX SEQUENCE OF WtWebioAn1TempValueEntry
    ACCESS not-accessible
    STATUS mandatory
    DESCRIPTION
        "List of temperature values corresponding to the channel numbers."
    ::= { wtWebioAn1Temp 3 }

wtWebioAn1TempValueEntry OBJECT-TYPE
    SYNTAX WtWebioAn1TempValueEntry
    ACCESS not-accessible
    STATUS mandatory
    DESCRIPTION
        "Temperatures of the sensors."
    INDEX  { wtWebioAn1SensorNo }
    ::= { wtWebioAn1TempValueTable 1 }

WtWebioAn1TempValueEntry ::= SEQUENCE{
    wtWebioAn1TempValue OCTET STRING (SIZE (5))
}

wtWebioAn1TempValue OBJECT-TYPE
    SYNTAX OCTET STRING (SIZE (5))
    ACCESS read-only
    STATUS mandatory
    DESCRIPTION
        "Temperature value of the sensor, ASCII, 5 characters in length."
    ::= { wtWebioAn1TempValueEntry 1 }

-- wtWebioAn1BinaryTempValue Table

wtWebioAn1BinaryTempValueTable OBJECT-TYPE
    SYNTAX SEQUENCE OF WtWebioAn1BinaryTempValueEntry
    ACCESS not-accessible
    STATUS mandatory
    DESCRIPTION
        "List of binary temperature values corresponding to the channel numbers."
    ::= { wtWebioAn1Temp 4 }

wtWebioAn1BinaryTempValueEntry OBJECT-TYPE
    SYNTAX WtWebioAn1BinaryTempValueEntry
    ACCESS not-accessible
    STATUS mandatory
    DESCRIPTION
        "Binary temperature values of the sensors."
    INDEX  { wtWebioAn1SensorNo }
    ::= { wtWebioAn1BinaryTempValueTable 1 }

WtWebioAn1BinaryTempValueEntry ::= SEQUENCE{
    wtWebioAn1BinaryTempValue INTEGER
}    

wtWebioAn1BinaryTempValue OBJECT-TYPE
    SYNTAX INTEGER
    ACCESS read-only
    STATUS mandatory
    DESCRIPTION
        "Binary temperature value of the sensor in 1/10 degrees Celsius,
        signed number, 0x7FFF indicates an 
        invalid measured value."
    ::= { wtWebioAn1BinaryTempValueEntry 1 }

-- wtWebioAn1SessCntrl Group
--------------------------------

wtWebioAn1SessCntrlPassword OBJECT-TYPE
    SYNTAX OCTET STRING 
    ACCESS read-write
    STATUS mandatory
    DESCRIPTION
        "Entering this password opens a session which is ended by writing a 1 to 
        wtWebioAn1SessCntrlLogout. When read this variable provides a string of
        length zero."
    ::= { wtWebioAn1SessCntrl 1 }

wtWebioAn1SessCntrlConfigMode OBJECT-TYPE
    SYNTAX INTEGER {
    wtWebioAn1SessCntrl-NoSession(0),
    wtWebioAn1SessCntrl-Session(1)
    }
    ACCESS read-only
    STATUS mandatory
    DESCRIPTION
        "When the device is in SNMP configuration mode, the value 1 is
        returned, otherwise 0. If the read value is 0 even though the
        password was written, the device is already in config mode and the
        variables can only be read."
    ::= { wtWebioAn1SessCntrl 2 }

wtWebioAn1SessCntrlLogout OBJECT-TYPE
    SYNTAX INTEGER 
    ACCESS read-write
    STATUS mandatory
    DESCRIPTION
        "If the device is in configuration mode and the session was opened by
        this SNMP Manager, writing a 1 to this variable will end the session 
        and all parameters are stored.
        Writing a 2 discards all entries again.
        When read this variable provides the value 0."
    ::= { wtWebioAn1SessCntrl 3 }

wtWebioAn1SessCntrlAdminPassword OBJECT-TYPE
    SYNTAX OCTET STRING 
    ACCESS read-write
    STATUS mandatory
    DESCRIPTION
        "This password protects access to the variables with administrator rights.
        It can only be changed by the administrator. If no password was assigned,
        the valid password is public."
    ::= { wtWebioAn1SessCntrl 4 }

wtWebioAn1SessCntrlConfigPassword OBJECT-TYPE
    SYNTAX OCTET STRING 
    ACCESS read-write
    STATUS mandatory
    DESCRIPTION
        "This password protects access to the variables with configurator rights. It can
        be changed by the administrator and by the configurator. If no password was assigned, 
        the valid password is public. When read this variable provides a null-pointer."
    ::= { wtWebioAn1SessCntrl 5 }
    

-- wtWebioAn1Network Group
------------------------

wtWebioAn1IpAddress OBJECT-TYPE
    SYNTAX IpAddress
    ACCESS read-write
    STATUS mandatory
    DESCRIPTION
        "IP address of the Webio"
    ::= { wtWebioAn1Network 1 }

wtWebioAn1SubnetMask OBJECT-TYPE
    SYNTAX IpAddress
    ACCESS read-write
    STATUS mandatory
    DESCRIPTION
        "Subnet mask of the Webio"
    ::= { wtWebioAn1Network 2 }

wtWebioAn1Gateway OBJECT-TYPE
    SYNTAX IpAddress
    ACCESS read-write
    STATUS mandatory
    DESCRIPTION
        "Gateway of the Webio"
    ::= { wtWebioAn1Network 3 }

wtWebioAn1DnsServer1 OBJECT-TYPE
    SYNTAX OCTET STRING 
    ACCESS read-write
    STATUS mandatory
    DESCRIPTION
        "IP address of the 1st DNS server in ASCII"
    ::= { wtWebioAn1Network 4 }

wtWebioAn1DnsServer2 OBJECT-TYPE
    SYNTAX OCTET STRING 
    ACCESS read-write
    STATUS mandatory
    DESCRIPTION
        "IP address of the 2nd DNS server in ASCII"
    ::= { wtWebioAn1Network 5 }

wtWebioAn1AddConfig OBJECT-TYPE
    SYNTAX OCTET STRING 
    ACCESS read-write
    STATUS mandatory
    DESCRIPTION
        "Additional configuration (1=ON):
        Octet 1: unused
        Octet 2: unused
        Octet 3: unused
        Octet 4:
	        Bit 0: BOOTP disable
	        "
    ::= { wtWebioAn1Network 6 }

-- wtWebioAn1Text Group
------------------------

wtWebioAn1DeviceName OBJECT-TYPE
    SYNTAX OCTET STRING 
    ACCESS read-write
    STATUS mandatory
    DESCRIPTION
        "Name of the Webio, which is user definable."
    ::= { wtWebioAn1Text 1 }

wtWebioAn1DeviceText OBJECT-TYPE
    SYNTAX OCTET STRING 
    ACCESS read-write
    STATUS mandatory
    DESCRIPTION
        "Description of the Webio, which is user definable."
    ::= { wtWebioAn1Text 2 }

wtWebioAn1DeviceLocation OBJECT-TYPE
    SYNTAX OCTET STRING 
    ACCESS read-write
    STATUS mandatory
    DESCRIPTION
        "Description of the location of the Webio, which is user definable."
    ::= { wtWebioAn1Text 3 }

wtWebioAn1DeviceContact OBJECT-TYPE
    SYNTAX OCTET STRING 
    ACCESS read-write
    STATUS mandatory
    DESCRIPTION
        "Contact address of the system operator of the Webio, which is user definable."
    ::= { wtWebioAn1Text 4 }

-- wtWebioAn1TimeZone Group
----------------------------

wtWebioAn1TzName OBJECT-TYPE
    SYNTAX OCTET STRING 
    ACCESS read-write
    STATUS mandatory
    DESCRIPTION
        "Name of the time zone (winter time)."
    ::= { wtWebioAn1TimeZone 1 }

wtWebioAn1TzOffsetHrs OBJECT-TYPE
    SYNTAX INTEGER 
    ACCESS read-write
    STATUS mandatory
    DESCRIPTION
        "Offset hours for the time zone (winter time) with respect to UTC."
    ::= { wtWebioAn1TimeZone 2 }

wtWebioAn1TzOffsetMin OBJECT-TYPE
    SYNTAX INTEGER 
    ACCESS read-write
    STATUS mandatory
    DESCRIPTION
        "Offset minutes for the time zone (winter time) with respect to UTC."
    ::= { wtWebioAn1TimeZone 3 }

wtWebioAn1StTzName OBJECT-TYPE
    SYNTAX OCTET STRING 
    ACCESS read-write
    STATUS mandatory
    DESCRIPTION
        "Name of the time zone (summer time)."
    ::= { wtWebioAn1TimeZone 4 }

wtWebioAn1StTzOffsetHrs OBJECT-TYPE
    SYNTAX INTEGER 
    ACCESS read-write
    STATUS mandatory
    DESCRIPTION
        "Offset hours of the time zone (summer time) with respect to UTC."
    ::= { wtWebioAn1TimeZone 5 }

wtWebioAn1StTzOffsetMin OBJECT-TYPE
    SYNTAX INTEGER 
    ACCESS read-write
    STATUS mandatory
    DESCRIPTION
        "Offset minutes of the time zone (summer time) with respect to UTC."
    ::= { wtWebioAn1TimeZone 6 }
    
wtWebioAn1StTzStartMonth OBJECT-TYPE
    SYNTAX INTEGER {
    	wtWebioAn1StartMonth-January(1),
    	wtWebioAn1StartMonth-February(2),
    	wtWebioAn1StartMonth-March(3),
    	wtWebioAn1StartMonth-April(4),
    	wtWebioAn1StartMonth-May(5),
    	wtWebioAn1StartMonth-June(6),
    	wtWebioAn1StartMonth-July(7),
    	wtWebioAn1StartMonth-August(8),
    	wtWebioAn1StartMonth-September(9),
    	wtWebioAn1StartMonth-October(10),
    	wtWebioAn1StartMonth-November(11),
    	wtWebioAn1StartMonth-December(12)
    	}
    	
    ACCESS read-write
    STATUS mandatory
    DESCRIPTION
        "Month in which the change is made from winter time to summer time."
    ::= { wtWebioAn1TimeZone 7 }

wtWebioAn1StTzStartMode OBJECT-TYPE
    SYNTAX INTEGER {
    	wtWebioAn1StartMode-first(1),
    	wtWebioAn1StartMode-second(2),
    	wtWebioAn1StartMode-third(3),
    	wtWebioAn1StartMode-fourth(4),
    	wtWebioAn1StartMode-last(5)
    	}
    	
    ACCESS read-write
    STATUS mandatory
    DESCRIPTION
        "Mode of the day of the week for which the change is made from winter time to summer time."
    ::= { wtWebioAn1TimeZone 8 }

wtWebioAn1StTzStartWday OBJECT-TYPE
    SYNTAX INTEGER {
    	wtWebioAn1StartWday-Sunday(1),
    	wtWebioAn1StartWday-Monday(2),
    	wtWebioAn1StartWday-Tuesday(3),
    	wtWebioAn1StartWday-Thursday(4),
    	wtWebioAn1StartWday-Wednesday(5),
    	wtWebioAn1StartWday-Friday(6),
    	wtWebioAn1StartWday-Saturday(7)
    	}
    	
    ACCESS read-write
    STATUS mandatory
    DESCRIPTION
        "Day of the week on which the change is made from winter time to summer time"
    ::= { wtWebioAn1TimeZone 9 }
    
wtWebioAn1StTzStartHrs OBJECT-TYPE
    SYNTAX INTEGER 
    ACCESS read-write
    STATUS mandatory
    DESCRIPTION
        "Hour in which the time zone is changed from winter to summer time with
        respect to UTC."
    ::= { wtWebioAn1TimeZone 10 }

wtWebioAn1StTzStartMin OBJECT-TYPE
    SYNTAX INTEGER 
    ACCESS read-write
    STATUS mandatory
    DESCRIPTION
        "Minute in which the time zone is changed from winter to summer time with
        respect to UTC."
    ::= { wtWebioAn1TimeZone 11 }
 
wtWebioAn1StTzStopMonth OBJECT-TYPE
    SYNTAX INTEGER {
    	wtWebioAn1StopMonth-January(1),
    	wtWebioAn1StopMonth-February(2),
    	wtWebioAn1StopMonth-March(3),
    	wtWebioAn1StopMonth-April(4),
    	wtWebioAn1StopMonth-May(5),
    	wtWebioAn1StopMonth-June(6),
    	wtWebioAn1StopMonth-July(7),
    	wtWebioAn1StopMonth-August(8),
    	wtWebioAn1StopMonth-September(9),
    	wtWebioAn1StopMonth-October(10),
    	wtWebioAn1StopMonth-November(11),
    	wtWebioAn1StopMonth-December(12)
    	}
    ACCESS read-write
    STATUS mandatory
    DESCRIPTION
        "Month in which the change is made from summer time to winter time."
   ::= { wtWebioAn1TimeZone 12 }

wtWebioAn1StTzStopMode OBJECT-TYPE
    SYNTAX INTEGER {
    	wtWebioAn1StopMode-first(1),
    	wtWebioAn1StopMode-second(2),
    	wtWebioAn1StopMode-third(3),
    	wtWebioAn1StopMode-fourth(4),
    	wtWebioAn1StopMode-last(5)
    	}
    ACCESS read-write
    STATUS mandatory
    DESCRIPTION
        "Mode of the week day on which the change is made from summer time to winter time."
    ::= { wtWebioAn1TimeZone 13 }

wtWebioAn1StTzStopWday OBJECT-TYPE
    SYNTAX INTEGER {
    	wtWebioAn1StopWday-Sunday(1),
    	wtWebioAn1StopWday-Monday(2),
    	wtWebioAn1StopWday-Tuesday(3),
    	wtWebioAn1StopWday-Thursday(4),
    	wtWebioAn1StopWday-Wednesday(5),
    	wtWebioAn1StopWday-Friday(6),
    	wtWebioAn1StopWday-Saturday(7)
    	}
    ACCESS read-write
    STATUS mandatory
    DESCRIPTION
        "Day of the week on which the change is made from summer time to winter time."
    ::= { wtWebioAn1TimeZone 14 }
    
wtWebioAn1StTzStopHrs OBJECT-TYPE
    SYNTAX INTEGER 
    ACCESS read-write
    STATUS mandatory
    DESCRIPTION
        "Hour at which the time zone is changed from summer to winter time with
        respect to UTC."
    ::= { wtWebioAn1TimeZone 15 }

wtWebioAn1StTzStopMin OBJECT-TYPE
    SYNTAX INTEGER 
    ACCESS read-write
    STATUS mandatory
    DESCRIPTION
        "Minute at which the time zone is changed from summer to winter time with
        respect to UTC."
    ::= { wtWebioAn1TimeZone 16 }

-- wtWebioAn1TimeServer Group
----------------------------

wtWebioAn1TimeServer1 OBJECT-TYPE
    SYNTAX OCTET STRING 
    ACCESS read-write
    STATUS mandatory
    DESCRIPTION
        "IP address or name of the 1st time server in ASCII"
    ::= { wtWebioAn1TimeServer 1 }

wtWebioAn1TimeServer2 OBJECT-TYPE
    SYNTAX OCTET STRING 
    ACCESS read-write
    STATUS mandatory
    DESCRIPTION
        "IP address or name of the 2nd time server in ASCII"
    ::= { wtWebioAn1TimeServer 2 }
    
-- wtWebioAn1DeviceClock Group
----------------------------

wtWebioAn1ClockHrs OBJECT-TYPE
    SYNTAX INTEGER (0..23)
    ACCESS read-write
    STATUS mandatory
    DESCRIPTION
        "Clock hours taking into account the time zone settings."
    ::= { wtWebioAn1DeviceClock 1 }

wtWebioAn1ClockMin OBJECT-TYPE
    SYNTAX INTEGER (0..59)
    ACCESS read-write
    STATUS mandatory
    DESCRIPTION
        "Clock minutes taking into account the time zone settings."
    ::= { wtWebioAn1DeviceClock 2 }

wtWebioAn1ClockDay OBJECT-TYPE
    SYNTAX INTEGER (1..31)
    ACCESS read-write
    STATUS mandatory
    DESCRIPTION
        "Date: Day of the month, taking into account the time zone settings."
    ::= { wtWebioAn1DeviceClock 3 }

wtWebioAn1ClockMonth OBJECT-TYPE
   SYNTAX INTEGER {
    	wtWebioAn1ClockMonth-January(1),
    	wtWebioAn1ClockMonth-February(2),
    	wtWebioAn1ClockMonth-March(3),
    	wtWebioAn1ClockMonth-April(4),
    	wtWebioAn1ClockMonth-May(5),
    	wtWebioAn1ClockMonth-June(6),
    	wtWebioAn1ClockMonth-July(7),
    	wtWebioAn1ClockMonth-August(8),
    	wtWebioAn1ClockMonth-September(9),
    	wtWebioAn1ClockMonth-October(10),
    	wtWebioAn1ClockMonth-November(11),
    	wtWebioAn1ClockMonth-December(12)
    	}
    ACCESS read-write
    STATUS mandatory
    DESCRIPTION
        "Date: Month, taking into account the time zone settings."
    ::= { wtWebioAn1DeviceClock 4 }

wtWebioAn1ClockYear OBJECT-TYPE
    SYNTAX INTEGER (0..65535)
    ACCESS read-write
    STATUS mandatory
    DESCRIPTION
        "Date: Year, taking into account the time zone settings."
    ::= { wtWebioAn1DeviceClock 5 }
    
-- wtWebioAn1MailAdmin Group
--------------------------------

wtWebioAn1MailAdName OBJECT-TYPE
    SYNTAX OCTET STRING 
    ACCESS read-write
    STATUS mandatory
    DESCRIPTION
        "Device name for mail administration."
    ::= { wtWebioAn1MailAdmin 1 }
    
wtWebioAn1MailReply OBJECT-TYPE
    SYNTAX OCTET STRING 
    ACCESS read-write
    STATUS mandatory
    DESCRIPTION
        "Reply address for the mail server."
    ::= { wtWebioAn1MailAdmin 2 }
    
wtWebioAn1MailServer OBJECT-TYPE
    SYNTAX OCTET STRING 
    ACCESS read-write
    STATUS mandatory
    DESCRIPTION
        "Name or IP address of the mail server."
    ::= { wtWebioAn1MailAdmin 3 }
    

-- wtWebioAn1Alarm Group
----------------------------

wtWebioAn1AlarmCount OBJECT-TYPE
    SYNTAX INTEGER (1..8)
    ACCESS read-only
    STATUS mandatory
    DESCRIPTION
        "Number of independent alarms."
    ::= { wtWebioAn1Alarm 1 }
    
-- Alarm Interface Table

wtWebioAn1AlarmIfTable OBJECT-TYPE
    SYNTAX SEQUENCE OF WtWebioAn1AlarmIfEntry
    ACCESS not-accessible
    STATUS mandatory
    DESCRIPTION
        "List of alarm indices."
    ::= { wtWebioAn1Alarm 2 }

wtWebioAn1AlarmIfEntry OBJECT-TYPE
    SYNTAX WtWebioAn1AlarmIfEntry
    ACCESS not-accessible
    STATUS mandatory
    DESCRIPTION
        "Numbers of the alarms."
    INDEX  { wtWebioAn1AlarmNo }
    ::= { wtWebioAn1AlarmIfTable 1 }

WtWebioAn1AlarmIfEntry ::= SEQUENCE {
    wtWebioAn1AlarmNo INTEGER (1..8)
}

wtWebioAn1AlarmNo OBJECT-TYPE
    SYNTAX INTEGER (1..8)
    ACCESS read-only
    STATUS mandatory
    DESCRIPTION
        "Alarm number."
    ::= { wtWebioAn1AlarmIfEntry 1 }

-- Alarm Table

wtWebioAn1AlarmTable OBJECT-TYPE
    SYNTAX SEQUENCE OF WtWebioAn1AlarmEntry
    ACCESS not-accessible
    STATUS mandatory
    DESCRIPTION
        "List of settings depending on the alarm number."
    ::= { wtWebioAn1Alarm 3 }

wtWebioAn1AlarmEntry OBJECT-TYPE
    SYNTAX WtWebioAn1AlarmEntry
    ACCESS not-accessible
    STATUS mandatory
    DESCRIPTION
        "Alarm parameters of the individual alarms."
    INDEX  { wtWebioAn1AlarmNo }
    ::= { wtWebioAn1AlarmTable 1 }

WtWebioAn1AlarmEntry ::= SEQUENCE {
    wtWebioAn1AlarmTrigger		OCTET STRING,
    wtWebioAn1AlarmMin			OCTET STRING,
    wtWebioAn1AlarmMax			OCTET STRING,
    wtWebioAn1AlarmInterval		OCTET STRING,
    wtWebioAn1AlarmEnable		OCTET STRING,
    wtWebioAn1AlarmEMailAddr		OCTET STRING,
    wtWebioAn1AlarmMailSubject		OCTET STRING,
    wtWebioAn1AlarmMailText		OCTET STRING,
    wtWebioAn1AlarmManagerIP		OCTET STRING,
    wtWebioAn1AlarmTrapText		OCTET STRING,
    wtWebioAn1AlarmMailOptions		OCTET STRING,
    wtWebioAn1AlarmTcpIpAddr		OCTET STRING,
    wtWebioAn1AlarmTcpPort		INTEGER,
    wtWebioAn1AlarmTcpText		OCTET STRING,
    wtWebioAn1AlarmHystersis		OCTET STRING,
    wtWebioAn1AlarmClearMailSubject	OCTET STRING,
    wtWebioAn1AlarmClearMailText	OCTET STRING,
    wtWebioAn1AlarmClearTrapText	OCTET STRING,
    wtWebioAn1AlarmClearTcpText		OCTET STRING
}

wtWebioAn1AlarmTrigger OBJECT-TYPE
    SYNTAX OCTET STRING (SIZE(4))
    ACCESS read-write
    STATUS mandatory
    DESCRIPTION
        "Binary coded trigger condition:
        Octet 1: unused
        Octet 2: unused
        Octet 3: unused
        Octet 4:
        	Bit 0: Sensor 1
        	Bit 1: Timer
        	Bit 2: ColdStart
        	Bit 3: WarmStart"
    ::= { wtWebioAn1AlarmEntry 1 }

wtWebioAn1AlarmMin OBJECT-TYPE
    SYNTAX OCTET STRING 
    ACCESS read-write
    STATUS mandatory
    DESCRIPTION
        "Minimum temperature in degrees with maximum 2 decimal places."
    ::= { wtWebioAn1AlarmEntry 2 }

wtWebioAn1AlarmMax OBJECT-TYPE
    SYNTAX OCTET STRING 
    ACCESS read-write
    STATUS mandatory
    DESCRIPTION
        "Maximum temperature in degrees with maximum 2 decimal places."
    ::= { wtWebioAn1AlarmEntry 3 }

wtWebioAn1AlarmInterval OBJECT-TYPE
    SYNTAX OCTET STRING 
    ACCESS read-write
    STATUS mandatory
    DESCRIPTION
        "Send interval for alarm messages."
    ::= { wtWebioAn1AlarmEntry 4 }

wtWebioAn1AlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  TCP Client enable"
    ::= { wtWebioAn1AlarmEntry 5 }

wtWebioAn1AlarmEMailAddr OBJECT-TYPE
    SYNTAX OCTET STRING 
    ACCESS read-write
    STATUS mandatory
    DESCRIPTION
        "E-Mail address for sending the alarm mail to."
    ::= { wtWebioAn1AlarmEntry 6 }

wtWebioAn1AlarmMailSubject OBJECT-TYPE
    SYNTAX OCTET STRING 
    ACCESS read-write
    STATUS mandatory
    DESCRIPTION
        "Subject line for alarm mail."
    ::= { wtWebioAn1AlarmEntry 7 }

wtWebioAn1AlarmMailText OBJECT-TYPE
    SYNTAX OCTET STRING 
    ACCESS read-write
    STATUS mandatory
    DESCRIPTION
        "Alarm mail text: <T1> provides the current temperature.
        <Z> provides the current time."
    ::= { wtWebioAn1AlarmEntry 8 }

wtWebioAn1AlarmManagerIP OBJECT-TYPE
    SYNTAX OCTET STRING 
    ACCESS read-write
    STATUS mandatory
    DESCRIPTION
        "Name or IP address of the SNMP Manager which accepts the trap."
    ::= { wtWebioAn1AlarmEntry 9 }

wtWebioAn1AlarmTrapText OBJECT-TYPE
    SYNTAX OCTET STRING 
    ACCESS read-write
    STATUS mandatory
    DESCRIPTION
        "This text is sent in the trap body."
    ::= { wtWebioAn1AlarmEntry 10 }
    
wtWebioAn1AlarmMailOptions OBJECT-TYPE
    SYNTAX OCTET STRING (SIZE(4))
    ACCESS read-write
    STATUS mandatory
    DESCRIPTION
        "Binary coded options:
        Octet 1: unused
        Octet 2: unused
        Octet 3: unused
        Octet 4:
		Bit 0  :	Attach Thermo.csv Enable
        	Bit 1-7:	unused"
    ::= { wtWebioAn1AlarmEntry 11 } 
    
wtWebioAn1AlarmTcpIpAddr OBJECT-TYPE
    SYNTAX OCTET STRING 
    ACCESS read-write
    STATUS mandatory
    DESCRIPTION
        "Name or IP address of the TCP server which accepts the trap."
    ::= { wtWebioAn1AlarmEntry 12 }    

wtWebioAn1AlarmTcpPort OBJECT-TYPE
    SYNTAX INTEGER (1..65535) 
    ACCESS read-write
    STATUS mandatory
    DESCRIPTION
        "Port number of the TCP server which accepts the trap."
    ::= { wtWebioAn1AlarmEntry 13 }    

wtWebioAn1AlarmTcpText OBJECT-TYPE
    SYNTAX OCTET STRING 
    ACCESS read-write
    STATUS mandatory
    DESCRIPTION
        "This text is sent in the TCP trap body."
    ::= { wtWebioAn1AlarmEntry 14 }

wtWebioAn1AlarmHysteresis OBJECT-TYPE
    SYNTAX OCTET STRING 
    ACCESS read-write
    STATUS mandatory
    DESCRIPTION
        "Temperature changes of this size clears the alarm state (MAX-hyst, MIN+hyst.)
        , in degrees with maximum 2 decimal places."
    ::= { wtWebioAn1AlarmEntry 15 }
    
wtWebioAn1AlarmClearMailSubject OBJECT-TYPE
    SYNTAX OCTET STRING 
    ACCESS read-write
    STATUS mandatory
    DESCRIPTION
        "Subject line for alarm clear mail."
    ::= { wtWebioAn1AlarmEntry 16 }

wtWebioAn1AlarmClearMailText OBJECT-TYPE
    SYNTAX OCTET STRING 
    ACCESS read-write
    STATUS mandatory
    DESCRIPTION
        "Alarm clear mail text: <Tn> provides the current temperature; n = 1..8.
        <Z> provides the current time."
    ::= { wtWebioAn1AlarmEntry 17 }

wtWebioAn1AlarmClearTrapText OBJECT-TYPE
    SYNTAX OCTET STRING 
    ACCESS read-write
    STATUS mandatory
    DESCRIPTION
        "This text is sent in the trap body."
    ::= { wtWebioAn1AlarmEntry 18 }

wtWebioAn1AlarmClearTcpText OBJECT-TYPE
    SYNTAX OCTET STRING 
    ACCESS read-write
    STATUS mandatory
    DESCRIPTION
        "This text is sent in the TCP trap body."
    ::= { wtWebioAn1AlarmEntry 19 }


-- wtWebioAn1Datalogger Group
--------------------------------

wtWebioAn1LoggerTimebase OBJECT-TYPE
    SYNTAX INTEGER {
    wtWebioAn1Datalogger-1Min(1),
    wtWebioAn1Datalogger-5Min(2),
    wtWebioAn1Datalogger-15Min(3),
    wtWebioAn1Datalogger-60Min(4)
    }
    ACCESS read-write
    STATUS mandatory
    DESCRIPTION
        "Time base of the data logger"
    ::= { wtWebioAn1Datalogger 1 }

wtWebioAn1LoggerSensorSel OBJECT-TYPE
    SYNTAX OCTET STRING (SIZE(4))
    ACCESS read-write
    STATUS mandatory
    DESCRIPTION
        "Binary coded trigger conditions:
        Octet 1: unused
        Octet 2: unused
        Octet 3: unused
        Octet 4:
        	Bit 0: Sensor 1"
    ::= { wtWebioAn1Datalogger 2 }

-- wtWebioAn1Protocol Group
----------------------------

wtWebioAn1PrtclUdpPort OBJECT-TYPE
    SYNTAX INTEGER (1..65535)
    ACCESS read-write
    STATUS mandatory
    DESCRIPTION
        "Udp port to which the Udp queries GET Single can be sent"
    ::= { wtWebioAn1PrtclUDP 1 }

wtWebioAn1PrtclSnmpCommunityStringRead OBJECT-TYPE
    SYNTAX OCTET STRING
    ACCESS read-write
    STATUS mandatory
    DESCRIPTION
        "Community string read only"
    ::= { wtWebioAn1PrtclSNMP 1 }

wtWebioAn1PrtclSnmpCommunityStringReadWrite OBJECT-TYPE
    SYNTAX OCTET STRING
    ACCESS read-write
    STATUS mandatory
    DESCRIPTION
        "Community string read / write"
    ::= { wtWebioAn1PrtclSNMP 2 }

wtWebioAn1SystemTrapManagerIP OBJECT-TYPE
    SYNTAX OCTET STRING 
    ACCESS read-write
    STATUS mandatory
    DESCRIPTION
        "Name or IP address of the TCP server which accepts the system trap."
    ::= { wtWebioAn1PrtclSNMP 3 }
    
wtWebioAn1SystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2-7: unused"
    ::= { wtWebioAn1PrtclSNMP 4 }
    
wtWebioAn1PrtclHttpPort OBJECT-TYPE
    SYNTAX INTEGER (1..65535)
    ACCESS read-write
    STATUS mandatory
    DESCRIPTION
        "HTTP port to which the HTTP queries GET Single can be sent"
    ::= { wtWebioAn1PrtclHttp 1 }        

-- wtWebioAn1Enable Group
----------------------------

wtWebioAn1Enables OBJECT-TYPE
    SYNTAX OCTET STRING (SIZE(4))
    ACCESS read-write
    STATUS mandatory
    DESCRIPTION
        "Binary coded trigger conditions:
        Octet 1: unused
        Octet 2: unused
        Octet 3: unused
        Octet 4:
	        Bit 0: Update enable
	        Bit 1: Mail enable
	        Bit 2: Snmp enable
	        Bit 3: UDP enable
	        Bit 4: Get Singel Header enable
	        Bit 5: Apply Timezone
	        Bit 6: Apply Summertime
	        Bit 7: Apply TimeServer"
    ::= { wtWebioAn1Enable 1 }

-- wtWebioAn1Startup Group
----------------------------

wtWebioAn1StartupSite OBJECT-TYPE
    SYNTAX OCTET STRING (SIZE(4))
    ACCESS read-write
    STATUS mandatory
    DESCRIPTION
        "Binary coded start page:
        Octet 1: unused
        Octet 2: unused
        Octet 3: unused
        Octet 4:
	        Bit 1: Index.htm
	        Bit 2: Home.htm
	        Bit 3: User.htm
	Only one page may be selected at a time."
    ::= { wtWebioAn1Startup 1 }

-- wtWebioAn1Ports Group
----------------------------

-- Table

wtWebioAn1PortTable OBJECT-TYPE
    SYNTAX SEQUENCE OF WtWebioAn1PortEntry
    ACCESS not-accessible
    STATUS mandatory
    DESCRIPTION
        "List of settings depending on the sensor number."
    ::= { wtWebioAn1Ports 1 }

wtWebioAn1PortEntry OBJECT-TYPE
    SYNTAX WtWebioAn1PortEntry
    ACCESS not-accessible
    STATUS mandatory
    DESCRIPTION
        "Sensor parameters for the individual sensors."
    INDEX  { wtWebioAn1SensorNo }
    ::= { wtWebioAn1PortTable 1 }

WtWebioAn1PortEntry ::= SEQUENCE {
    wtWebioAn1PortName		OCTET STRING,
    wtWebioAn1PortText		OCTET STRING,
    wtWebioAn1PortOffset1	OCTET STRING,
    wtWebioAn1PortTemperature1	OCTET STRING,
    wtWebioAn1PortOffset2	OCTET STRING,
    wtWebioAn1PortTemperature2	OCTET STRING,
    wtWebioAn1PortComment	OCTET STRING
    
}

wtWebioAn1PortName OBJECT-TYPE
    SYNTAX OCTET STRING 
    ACCESS read-write
    STATUS mandatory
    DESCRIPTION
        "Name of the sensor."
    ::= { wtWebioAn1PortEntry 1 }

wtWebioAn1PortText OBJECT-TYPE
    SYNTAX OCTET STRING 
    ACCESS read-write
    STATUS mandatory
    DESCRIPTION
        "Description of the sensor."
    ::= { wtWebioAn1PortEntry 2 }

wtWebioAn1PortOffset1 OBJECT-TYPE
    SYNTAX OCTET STRING 
    ACCESS read-write
    STATUS mandatory
    DESCRIPTION
        "Offset calibration: Offset in degrees with maximum 2 decimal places at temperature 1."
    ::= { wtWebioAn1PortEntry 3 }

wtWebioAn1PortTemperature1 OBJECT-TYPE
    SYNTAX OCTET STRING 
    ACCESS read-write
    STATUS mandatory
    DESCRIPTION
        "Offset calibration: Reference temperature 1 in degrees with maximum 2 decimal places."
    ::= { wtWebioAn1PortEntry 4 }

wtWebioAn1PortOffset2 OBJECT-TYPE
    SYNTAX OCTET STRING 
    ACCESS read-write
    STATUS mandatory
    DESCRIPTION
        "Offset calibration: Offset in degrees with maximum 2 decimal places at temperature 2."
    ::= { wtWebioAn1PortEntry 5 }

wtWebioAn1PortTemperature2 OBJECT-TYPE
    SYNTAX OCTET STRING 
    ACCESS read-write
    STATUS mandatory
    DESCRIPTION
        "Offset calibration: Reference temperature 1 in degrees with maximum 2 decimal places."
    ::= { wtWebioAn1PortEntry 6 }

wtWebioAn1PortComment OBJECT-TYPE
    SYNTAX OCTET STRING 
    ACCESS read-write
    STATUS mandatory
    DESCRIPTION
        "Offset calibration: informations of date, name of operator, reference devices."
    ::= { wtWebioAn1PortEntry 7 }   
    
-- wtWebioAn1Manufact Group
----------------------------

wtWebioAn1MfName OBJECT-TYPE
    SYNTAX OCTET STRING 
    ACCESS read-write
    STATUS mandatory
    DESCRIPTION
        "Manufacturer company name"
    ::= { wtWebioAn1Manufact 1 }

wtWebioAn1MfAddr OBJECT-TYPE
    SYNTAX OCTET STRING 
    ACCESS read-write
    STATUS mandatory
    DESCRIPTION
        "Manufacturer address."
    ::= { wtWebioAn1Manufact 2 }

wtWebioAn1MfHotline OBJECT-TYPE
    SYNTAX OCTET STRING 
    ACCESS read-write
    STATUS mandatory
    DESCRIPTION
        "Manufacturer hotline."
    ::= { wtWebioAn1Manufact 3 }

wtWebioAn1MfInternet OBJECT-TYPE
    SYNTAX OCTET STRING 
    ACCESS read-write
    STATUS mandatory
    DESCRIPTION
        "Manufacturer Internet address."
    ::= { wtWebioAn1Manufact 4 }

wtWebioAn1MfDeviceTyp OBJECT-TYPE
    SYNTAX OCTET STRING 
    ACCESS read-write
    STATUS mandatory
    DESCRIPTION
        "Manufacturer device name (model number)."
    ::= { wtWebioAn1Manufact 5 }

wtWebioAn1MfOrderNo OBJECT-TYPE
    SYNTAX OCTET STRING 
    ACCESS read-write
    STATUS mandatory
    DESCRIPTION
        "Manufacturer part number."
    ::= { wtWebioAn1Manufact 6 }



-- TRAP DEFINITIONS

-- Diese SNMP-Traps werden gesendet, wenn die Alarmtriggerbedingungen zutreffen 

wtWebioAn1Alert1 TRAP-TYPE
    ENTERPRISE  wtWebioAn1
    VARIABLES   { wtWebioAn1AlarmTrapText }
    DESCRIPTION
        "This SNMP trap is generated when Alarm 1 was triggered,
        SNMP trap enable is set and
        SNMP is enabled."
    -- NMS trap annotation
    --#TYPE "WebThermometer Alarm 1"
    --#SUMMARY "Alarm 1: %s"
    --#ARGUMENTS {0}
    --#SEVERITY INFORMATIONAL
    --#TIMEINDEX 99
    --#STATE OPERATIONAL    
    ::= 31

wtWebioAn1Alert2 TRAP-TYPE
    ENTERPRISE  wtWebioAn1
    VARIABLES   { wtWebioAn1AlarmTrapText }
    DESCRIPTION
        "This SNMP trap is generated when Alarm 2 was triggered,
        SNMP trap enable is set and
        SNMP is enabled."
    -- NMS trap annotation
    --#TYPE "WebThermometer Alarm 2"
    --#SUMMARY "Alarm 2: %s"
    --#ARGUMENTS {0}
    --#SEVERITY INFORMATIONAL
    --#TIMEINDEX 99
    --#STATE OPERATIONAL    
    ::= 32

wtWebioAn1Alert3 TRAP-TYPE
    ENTERPRISE  wtWebioAn1
    VARIABLES   { wtWebioAn1AlarmTrapText }
    DESCRIPTION
        "This SNMP trap is generated when Alarm 3 was triggered,
        SNMP trap enable is set and
        SNMP is enabled."
    -- NMS trap annotation
    --#TYPE "WebThermometer Alarm 3"
    --#SUMMARY "Alarm 3: %s"
    --#ARGUMENTS {0}
    --#SEVERITY INFORMATIONAL
    --#TIMEINDEX 99
    --#STATE OPERATIONAL    
    ::= 33

wtWebioAn1Alert4 TRAP-TYPE
    ENTERPRISE  wtWebioAn1
    VARIABLES   { wtWebioAn1AlarmTrapText }
    DESCRIPTION
        "This SNMP trap is generated when Alarm 4 was triggered,
        SNMP trap enable is set and
        SNMP is enabled."
    -- NMS trap annotation
    --#TYPE "WebThermometer Alarm 4"
    --#SUMMARY "Alarm 4: %s"
    --#ARGUMENTS {0}
    --#SEVERITY INFORMATIONAL
    --#TIMEINDEX 99
    --#STATE OPERATIONAL    
    ::= 34

wtWebioAn1Alert5 TRAP-TYPE
    ENTERPRISE  wtWebioAn1
    VARIABLES   { wtWebioAn1AlarmTrapText }
    DESCRIPTION
        "This SNMP trap is generated when Alarm 5 was triggered,
        SNMP trap enable is set and
        SNMP is enabled."
    -- NMS trap annotation
    --#TYPE "WebThermometer Alarm 5"
    --#SUMMARY "Alarm 5: %s"
    --#ARGUMENTS {0}
    --#SEVERITY INFORMATIONAL
    --#TIMEINDEX 99
    --#STATE OPERATIONAL    
    ::= 35

wtWebioAn1Alert6 TRAP-TYPE
    ENTERPRISE  wtWebioAn1
    VARIABLES   { wtWebioAn1AlarmTrapText }
    DESCRIPTION
        "This SNMP trap is generated when Alarm 6 was triggered,
        SNMP trap enable is set and
        SNMP is enabled."
    -- NMS trap annotation
    --#TYPE "WebThermometer Alarm 6"
    --#SUMMARY "Alarm 6: %s"
    --#ARGUMENTS {0}
    --#SEVERITY INFORMATIONAL
    --#TIMEINDEX 99
    --#STATE OPERATIONAL    
    ::= 36

wtWebioAn1Alert7 TRAP-TYPE
    ENTERPRISE  wtWebioAn1
    VARIABLES   { wtWebioAn1AlarmTrapText }
    DESCRIPTION
        "This SNMP trap is generated when Alarm 7 was triggered,
        SNMP trap enable is set and
        SNMP is enabled."
    -- NMS trap annotation
    --#TYPE "WebThermometer Alarm 7"
    --#SUMMARY "Alarm 7: %s"
    --#ARGUMENTS {0}
    --#SEVERITY INFORMATIONAL
    --#TIMEINDEX 99
    --#STATE OPERATIONAL    
    ::= 37

wtWebioAn1Alert8 TRAP-TYPE
    ENTERPRISE  wtWebioAn1
    VARIABLES   { wtWebioAn1AlarmTrapText }
    DESCRIPTION
        "This SNMP trap is generated when Alarm 8 was triggered,
        SNMP trap enable is set and
        SNMP is enabled."
    -- NMS trap annotation
    --#TYPE "WebThermometer Alarm 8"
    --#SUMMARY "Alarm 8: %s"
    --#ARGUMENTS {0}
    --#SEVERITY INFORMATIONAL
    --#TIMEINDEX 99
    --#STATE OPERATIONAL    
    ::= 38

    
wtWebioAn1Alert9 TRAP-TYPE
    ENTERPRISE  wtWebioAn1
    VARIABLES   { wtWebioAn1AlarmClearTrapText }
    DESCRIPTION
        "This SNMP trap is generated when Alarm 1 was cleared,
        SNMP trap enable is set and
        SNMP is enabled."
    -- NMS trap annotation
    --#TYPE "WebThermometer Release Alarm 1"
    --#SUMMARY "Alarm 1: %s"
    --#ARGUMENTS {0}
    --#SEVERITY INFORMATIONAL
    --#TIMEINDEX 99
    --#STATE OPERATIONAL    
    ::= 91

wtWebioAn1Alert10 TRAP-TYPE
    ENTERPRISE  wtWebioAn1
    VARIABLES   { wtWebioAn1AlarmClearTrapText }
    DESCRIPTION
        "This SNMP trap is generated when Alarm 2 was cleared,
        SNMP trap enable is set and
        SNMP is enabled."
    -- NMS trap annotation
    --#TYPE "WebThermometer Release Alarm 2"
    --#SUMMARY "Alarm 2: %s"
    --#ARGUMENTS {0}
    --#SEVERITY INFORMATIONAL
    --#TIMEINDEX 99
    --#STATE OPERATIONAL    
    ::= 92

wtWebioAn1Alert11 TRAP-TYPE
    ENTERPRISE  wtWebioAn1
    VARIABLES   { wtWebioAn1AlarmClearTrapText }
    DESCRIPTION
        "This SNMP trap is generated when Alarm 3 was cleared,
        SNMP trap enable is set and
        SNMP is enabled."
    -- NMS trap annotation
    --#TYPE "WebThermometer Release Alarm 3"
    --#SUMMARY "Alarm 3: %s"
    --#ARGUMENTS {0}
    --#SEVERITY INFORMATIONAL
    --#TIMEINDEX 99
    --#STATE OPERATIONAL    
    ::= 93

wtWebioAn1Alert12 TRAP-TYPE
    ENTERPRISE  wtWebioAn1
    VARIABLES   { wtWebioAn1AlarmClearTrapText }
    DESCRIPTION
        "This SNMP trap is generated when Alarm 4 was cleared,
        SNMP trap enable is set and
        SNMP is enabled."
    -- NMS trap annotation
    --#TYPE "WebThermometer Release Alarm 4"
    --#SUMMARY "Alarm 4: %s"
    --#ARGUMENTS {0}
    --#SEVERITY INFORMATIONAL
    --#TIMEINDEX 99
    --#STATE OPERATIONAL    
    ::= 94

wtWebioAn1Alert13 TRAP-TYPE
    ENTERPRISE  wtWebioAn1
    VARIABLES   { wtWebioAn1AlarmClearTrapText }
    DESCRIPTION
        "This SNMP trap is generated when Alarm 5 was cleared,
        SNMP trap enable is set and
        SNMP is enabled."
    -- NMS trap annotation
    --#TYPE "WebThermometer Release Alarm 5"
    --#SUMMARY "Alarm 5: %s"
    --#ARGUMENTS {0}
    --#SEVERITY INFORMATIONAL
    --#TIMEINDEX 99
    --#STATE OPERATIONAL    
    ::= 95

wtWebioAn1Alert14 TRAP-TYPE
    ENTERPRISE  wtWebioAn1
    VARIABLES   { wtWebioAn1AlarmClearTrapText }
    DESCRIPTION
        "This SNMP trap is generated when Alarm 6 was cleared,
        SNMP trap enable is set and
        SNMP is enabled."
    -- NMS trap annotation
    --#TYPE "WebThermometer Release Alarm 6"
    --#SUMMARY "Alarm 6: %s"
    --#ARGUMENTS {0}
    --#SEVERITY INFORMATIONAL
    --#TIMEINDEX 99
    --#STATE OPERATIONAL    
    ::= 96

wtWebioAn1Alert15 TRAP-TYPE
    ENTERPRISE  wtWebioAn1
    VARIABLES   { wtWebioAn1AlarmClearTrapText }
    DESCRIPTION
        "This SNMP trap is generated when Alarm 7 was cleared,
        SNMP trap enable is set and
        SNMP is enabled."
    -- NMS trap annotation
    --#TYPE "WebThermometer Release Alarm 7"
    --#SUMMARY "Alarm 7: %s"
    --#ARGUMENTS {0}
    --#SEVERITY INFORMATIONAL
    --#TIMEINDEX 99
    --#STATE OPERATIONAL    
    ::= 97

wtWebioAn1Alert16 TRAP-TYPE
    ENTERPRISE  wtWebioAn1
    VARIABLES   { wtWebioAn1AlarmClearTrapText }
    DESCRIPTION
        "This SNMP trap is generated when Alarm 8 was cleared,
        SNMP trap enable is set and
        SNMP is enabled."
    -- NMS trap annotation
    --#TYPE "WebThermometer Release Alarm 8"
    --#SUMMARY "Alarm 8: %s"
    --#ARGUMENTS {0}
    --#SEVERITY INFORMATIONAL
    --#TIMEINDEX 99
    --#STATE OPERATIONAL    
    ::= 98


END

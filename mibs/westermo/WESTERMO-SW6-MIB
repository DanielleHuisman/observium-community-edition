-- *****************************************************************
-- WESTERMO-SW6-MIB :
-- SNMP configuration of Westermo devices with SW6.
--
-- Copyright (c) 2018 by Westermo Teleindustri AB
-- All rights reserved.
-- *****************************************************************

-- *****************************************************************
-- This script has been tested using the SMI checker smilint
-- the tool can be downloaded at
-- http://www.ibr.cs.tu-bs.de/projects/libsmi/smilint.html
-- or use alternatively the online version at:
-- http://www.simpleweb.org/ietf/mibs/validate/
--
-- smilint -m -s -l 6 -i nameLength-32 ./WESTERMO-SW6-MIB
-- Ensure that all needed MIBS are located in the SMIPATH.
-- *****************************************************************

-- **********************************************************************
-- * STANDARD MIB
-- **********************************************************************

WESTERMO-SW6-MIB DEFINITIONS ::= BEGIN

    IMPORTS
        MODULE-IDENTITY, OBJECT-TYPE,
        Counter32,
        IpAddress, Integer32, TimeTicks        FROM SNMPv2-SMI
        DisplayString                          FROM SNMPv2-TC
        MODULE-COMPLIANCE, OBJECT-GROUP        FROM SNMPv2-CONF
    ;

-- **********************************************************************
-- *  MODULE IDENTITY
-- **********************************************************************
base MODULE-IDENTITY
    LAST-UPDATED "201909060000Z"

    ORGANIZATION "Westermo Teleindustri AB"
    CONTACT-INFO "E-mail: info@westermo.com"
    DESCRIPTION  "MIB Module for the Westermo RT-300 Radio Modem Device - Base definitions"

    REVISION     "201909060000Z"
    DESCRIPTION  "Release 6.9.0-RC0"

    ::= { iso(1) org(3) dod(6) internet(1) private(4) enterprises(1)
          westermo(16177) products(1) rt(400) 1 }

-- **********************************************************************
-- *  Begin Major sections
-- * * * * * * * * * * * * * * * * * * * * * * * * * * * * * * * * * * *

--  Configuration
--  =============

    configuration        OBJECT IDENTIFIER ::= { base 1 }
     cfgSystem           OBJECT IDENTIFIER ::= { configuration 1 }
     cfgNetwork          OBJECT IDENTIFIER ::= { configuration 2 }
     cfgWireless         OBJECT IDENTIFIER ::= { configuration 3 }
     cfgRouting          OBJECT IDENTIFIER ::= { configuration 4 }
     cfgIpTables         OBJECT IDENTIFIER ::= { configuration 5 }
     cfgQos              OBJECT IDENTIFIER ::= { configuration 6 }
     cfgLogging          OBJECT IDENTIFIER ::= { configuration 11 }
     cfgSnmp             OBJECT IDENTIFIER ::= { configuration 12 }
     cfgDhcp             OBJECT IDENTIFIER ::= { configuration 13 }
     cfgNtp              OBJECT IDENTIFIER ::= { configuration 14 }
     cfgHttp             OBJECT IDENTIFIER ::= { configuration 15 }
     cfgLldp             OBJECT IDENTIFIER ::= { configuration 16 }
     cfgMdns             OBJECT IDENTIFIER ::= { configuration 17 }
     cfgNlm              OBJECT IDENTIFIER ::= { configuration 40 }
     cfgCli              OBJECT IDENTIFIER ::= { configuration 100 }
     cfgCellular         OBJECT IDENTIFIER ::= { configuration 101 }

--  RPCs Remote Procedure Calls
--  ==========================

    rpc                  OBJECT IDENTIFIER ::= { base 3 }
     rpcConfiguration    OBJECT IDENTIFIER ::= { rpc 1 }
     rpcFirmware         OBJECT IDENTIFIER ::= { rpc 2 }
     rpcSystem           OBJECT IDENTIFIER ::= { rpc 3 }
     rpcCertificate      OBJECT IDENTIFIER ::= { rpc 4 }
     rpcDriver           OBJECT IDENTIFIER ::= { rpc 6 }

--  Settings
--  ========

    settings             OBJECT IDENTIFIER ::= { base 4 }
      setConfiguration   OBJECT IDENTIFIER ::= { settings 1 }
      setWireless        OBJECT IDENTIFIER ::= { settings 3 }
      setConfmgmtd       OBJECT IDENTIFIER ::= { settings 4 }
      setFirmware        OBJECT IDENTIFIER ::= { settings 5 }
      setCertificate     OBJECT IDENTIFIER ::= { settings 6 }
      setSystem          OBJECT IDENTIFIER ::= { settings 7 }

--  Hardware
--  ========

    hardware             OBJECT IDENTIFIER ::= { base 5 }
      hwSystem           OBJECT IDENTIFIER ::= { hardware 1 }
      hwNetwork          OBJECT IDENTIFIER ::= { hardware 2 }
      hwWireless         OBJECT IDENTIFIER ::= { hardware 3 }
      hwBaseBoard        OBJECT IDENTIFIER ::= { hardware 10 }
      hwIfaceBoard       OBJECT IDENTIFIER ::= { hardware 11 }
      hwSensor           OBJECT IDENTIFIER ::= { hardware 21 }

--  Software
--  ========

    software             OBJECT IDENTIFIER ::= { base 6 }
     swFirmware          OBJECT IDENTIFIER ::= { software 2 }
     swSystem            OBJECT IDENTIFIER ::= { software 3 }
     swOperatingSystem   OBJECT IDENTIFIER ::= { software 4 }
     swDriver            OBJECT IDENTIFIER ::= { software 5 }
     swRdm               OBJECT IDENTIFIER ::= { software 6 }
     swBootloader        OBJECT IDENTIFIER ::= { software 20 }
     swConfiguration     OBJECT IDENTIFIER ::= { software 30 }

--  Conformance Information
--  =======================

    conformance           OBJECT IDENTIFIER ::= { base 100 }
     groups               OBJECT IDENTIFIER ::= { conformance 1 }
      groupConfiguration  OBJECT IDENTIFIER ::= { groups 1 }
      groupStatus         OBJECT IDENTIFIER ::= { groups 2 }
      groupRpc            OBJECT IDENTIFIER ::= { groups 3 }
      groupSettings       OBJECT IDENTIFIER ::= { groups 4 }
      groupHardware       OBJECT IDENTIFIER ::= { groups 5 }
      groupSoftware       OBJECT IDENTIFIER ::= { groups 6 }
      groupFeatures       OBJECT IDENTIFIER ::= { groups 7 }

     compliances          OBJECT IDENTIFIER ::= { conformance 2 }


-- * * * * * * * * * * * * * * * * * * * * * * * * * * * * * * * * * * *
-- *  End Major Sections
-- **********************************************************************

-- **********************************************************************
-- *  Begin Object Types
-- * * * * * * * * * * * * * * * * * * * * * * * * * * * * * * * * * * *

-- Configuration
-- =============

-- System

    cfgSysHostname OBJECT-TYPE
        SYNTAX DisplayString (SIZE(1..255))
        MAX-ACCESS read-write
        STATUS     current
        DESCRIPTION
            "The hostname of the device.

             Applies to AP and STA."
        ::= { cfgSystem 1 }

    cfgSysTimezone OBJECT-TYPE
        SYNTAX DisplayString (SIZE(1..255))
        MAX-ACCESS read-write
        STATUS     current
        DESCRIPTION
            "POSIX timezone string. Defines the local time.

             For more strings also see
             http://wiki.openwrt.org/doc/uci/system#time_zones

             **Example**

             Europe/Zurich: CET-1CEST,M3.5.0,M10.5.0/3

             Applies to AP and STA."
        ::= { cfgSystem 2 }

-- =============================================================================

-- Network

    cfgNetEthernetTable OBJECT-TYPE
        SYNTAX  SEQUENCE OF CfgNetEthernetTableSeq
        MAX-ACCESS not-accessible
        STATUS     current
        DESCRIPTION
            "Ethernet Network Interfaces."
        ::= { cfgNetwork 1 }

    cfgNetEthernetTableEntry OBJECT-TYPE
        SYNTAX  CfgNetEthernetTableSeq
        MAX-ACCESS not-accessible
        STATUS     current
        DESCRIPTION
            "Ethernet Network Interfaces."
        INDEX {cfgNetEthIndex}
        ::= { cfgNetEthernetTable 1 }

    CfgNetEthernetTableSeq ::=
        SEQUENCE {  cfgNetEthIndex Integer32,
                    cfgNetEthName DisplayString,
                    cfgNetEthEnabled INTEGER,
                    cfgNetEthBridge Integer32,
                    cfgNetEthAutoneg INTEGER,
                    cfgNetEthSpeed Integer32,
                    cfgNetEthTrunk DisplayString,
                    cfgNetEthTag Integer32,
                    cfgNetEthVlanMode INTEGER,
                    cfgNetEthLldpEnabled INTEGER
                 }

    cfgNetEthIndex OBJECT-TYPE
        SYNTAX Integer32 (0..9)
        MAX-ACCESS not-accessible
        STATUS     current
        DESCRIPTION
            "Entry index of table."
        ::= { cfgNetEthernetTableEntry 1 }

    cfgNetEthName OBJECT-TYPE
        SYNTAX DisplayString (SIZE(1..255))
        MAX-ACCESS read-only
        STATUS     current
        DESCRIPTION
            "Name of the ethernet interface.

             Applies to AP and STA."
        ::= { cfgNetEthernetTableEntry 2 }

    cfgNetEthEnabled OBJECT-TYPE
        SYNTAX INTEGER { disabled(0), enabled(1) }
        MAX-ACCESS read-write
        STATUS     current
        DESCRIPTION
            "Ethernet interface disabled or enabled.

             Applies to AP and STA."
        ::= { cfgNetEthernetTableEntry 3 }

    cfgNetEthBridge OBJECT-TYPE
        SYNTAX Integer32
        MAX-ACCESS read-write
        STATUS     current
        DESCRIPTION
            "If set to other than -1 the interface is part of bridge:

             * -1: none
             * 0: br0
             * 1: br1
             * X: brX

             Bridges with an index >=100 are special bridges which forward
             link local traffic. This can be used for wireless links in 4addr
             mode which should act as a cable-replacement.

             **Note:** Such a bridge may only contain 2 interfaces!

             **Example**

             * wlan0 and eth0 in br100, with eth1 as management interface.

             Applies to AP and STA."
        ::= { cfgNetEthernetTableEntry 7 }

    cfgNetEthAutoneg OBJECT-TYPE
        SYNTAX INTEGER { forced(0), auto(1) }
        MAX-ACCESS read-write
        STATUS     current
        DESCRIPTION
            "Enables or disables auto negotiation of the PHY.

             * **forced(0):** Forces the speed and duplex defined by
               `cfgNetEthSpeed`. Only 10Mbit and 100Mbit rates are
                allowed in forced mode. 1000Mbit requires the mode to be
                auto.
             * **auto(1):**  Advertises the supported auto negotiation
               defined by `cfgNetEthSpeed`.

             Applies to AP and STA."
        ::= { cfgNetEthernetTableEntry 8 }

    cfgNetEthSpeed OBJECT-TYPE
        SYNTAX Integer32
        MAX-ACCESS read-write
        STATUS     current
        DESCRIPTION
            "Defines a bitmask containing the possible speed/duplex combinations.

             * 0x01  (1) = 10Mbit/Half
             * 0x02  (2) = 10Mbit/Full
             * 0x04  (4) = 100Mbit/Half
             * 0x08  (8) = 100Mbit/Full
             * 0x20 (32) = 1000Mbit/Full

             When `cfgNetEthSpeed` is **forced(0)** only a single bit may be
             active. Only 10Mbit and 100Mbit rates are allowed in forced mode.
             1000Mbit requires the mode to be auto.
             When `cfgNetEthSpeed` is **auto(1)** multiple bits may be set which
             are used to advertise the supported speed/duplex.
             1000Mbit/Half is not supported.

             Applies to AP and STA."
        ::= { cfgNetEthernetTableEntry 9 }

    cfgNetEthTrunk OBJECT-TYPE
        SYNTAX DisplayString (SIZE(1..255))
        MAX-ACCESS read-write
        STATUS     current
        DESCRIPTION
            "This entry is active when `cfgNetEthVlanMode` is set to
             **trunk(0)** or **nativeuntagged(3)**.

             It specifies which 802.1q vlans are accepted ingress and egress on
             the respective port. All unspecified vlans are dropped.
             Set this entry to -1 to allow all vlans.
             Untagged traffic is considered as vlan 0.

             The format of this entry is a space or comma separated list.
             To describe ranges the character '-' can be used.

             **Examples**

             '0,12,24,69' or '7 56 127' or '0, 84, 99, 2000' or
             '0, 12-17, 3000-4000' or '0-99 101-199 201-299, 301-4094'

             Applies to AP and STA."
        ::= { cfgNetEthernetTableEntry 10 }

    cfgNetEthTag OBJECT-TYPE
        SYNTAX Integer32 (-1..4094)
        MAX-ACCESS read-write
        STATUS     current
        DESCRIPTION
            "This entry is active when `cfgNetEthVlanMode` is set to
             **access(1)** or **nativeuntagged(3)**. It specifies which 802.1q
             VLAN should be used for untagged ingress and egress traffic. Set
             this entry to -1 to disable it.

             Applies to AP and STA."
        ::= { cfgNetEthernetTableEntry 11 }

    cfgNetEthVlanMode OBJECT-TYPE
        SYNTAX INTEGER { trunk(0), access(1), nativeuntagged(3) }
        MAX-ACCESS read-write
        STATUS     current
        DESCRIPTION
            "This entry specifies how the port should behave.

             * **trunk(0):** A trunk port carries packets on one or more specified
               VLANs specified in the cfgNetEthTrunk entry.
               A packet that ingresses on a trunk port is in the VLAN specified
               in its 802.1q header, or VLAN 0 if the packet has no 802.1q header
               (untagged frame). A packet that egresses through a trunk port will
               have an 802.1q header if it has a nonzero VLAN ID.
               Frames egressing on VLAN 0 have their tag stripped (egress untagged).
               Any packet that ingresses on a trunk port tagged with a
               VLAN that the port does not trunk is dropped.
             * **access(1):** An access port carries packets on exactly one VLAN
               specified in `cfgNetEthTag`. Packets egressing on an access
               port have no 802.1q header (egress untagged).
               Any packet with an 802.1q header with a nonzero VLAN ID that
               ingresses on an access port is dropped, regardless of whether
               the VLAN ID in the header is the access port's VLAN ID or not.
             * **nativeuntagged(3):** A native-untagged port resembles a trunk port,
               with the exception that a packet without an 802.1q header
               (ingress untagged) is automatically in the native VLAN specified
               in `cfgNetEthTag`. Frames egressing in the native VLAN are
               automatically untagged (egress untagged).

             Applies to AP and STA."
        ::= { cfgNetEthernetTableEntry 12 }

    cfgNetEthLldpEnabled OBJECT-TYPE
        SYNTAX INTEGER { disabled(0), enabled(1) }
        MAX-ACCESS read-write
        STATUS     current
        DESCRIPTION
            "When `cfgLldpEnabled` is enabled, this parameter controls if
             the interface takes part in LLDP operation.

             Applies to AP and STA."
        ::= { cfgNetEthernetTableEntry 15 }

-- -----------------------------------------------------------------------------

    cfgNetWlanTable OBJECT-TYPE
        SYNTAX  SEQUENCE OF CfgNetWlanTableSeq
        MAX-ACCESS not-accessible
        STATUS     current
        DESCRIPTION
            "WLAN Network Interfaces."
        ::= { cfgNetwork 2 }

    cfgNetWlanTableEntry OBJECT-TYPE
        SYNTAX  CfgNetWlanTableSeq
        MAX-ACCESS not-accessible
        STATUS     current
        DESCRIPTION
            "WLAN Network Interfaces."
        INDEX {cfgNetWlanIndex}
        ::= { cfgNetWlanTable 1 }

    CfgNetWlanTableSeq ::=
        SEQUENCE {  cfgNetWlanIndex Integer32,
                    cfgNetWlanName DisplayString,
                    cfgNetWlanEnabled INTEGER,
                    cfgNetWlanBridge Integer32,
                    cfgNetWlanTrunk DisplayString,
                    cfgNetWlanTag Integer32,
                    cfgNetWlanVlanMode INTEGER,
                    cfgNetWlanLldpEnabled INTEGER
                 }

    cfgNetWlanIndex OBJECT-TYPE
        SYNTAX Integer32 (0..63)
        MAX-ACCESS not-accessible
        STATUS     current
        DESCRIPTION
            "Entry index of Table."
        ::= { cfgNetWlanTableEntry 1 }

    cfgNetWlanName OBJECT-TYPE
        SYNTAX DisplayString (SIZE(1..255))
        MAX-ACCESS read-only
        STATUS     current
        DESCRIPTION
            "Name of the wireless interface.

             Applies to AP and STA."
        ::= { cfgNetWlanTableEntry 2 }

    cfgNetWlanEnabled OBJECT-TYPE
        SYNTAX INTEGER { disabled(0), enabled(1) }
        MAX-ACCESS read-write
        STATUS     current
        DESCRIPTION
            "Wireless interface disabled or enabled.

             Applies to AP and STA."
        ::= { cfgNetWlanTableEntry 3 }

    cfgNetWlanBridge OBJECT-TYPE
        SYNTAX Integer32
        MAX-ACCESS read-write
        STATUS     current
        DESCRIPTION
            "If set to other than -1 the interface is part of bridge:

             * -1: none
             * 0: br0
             * 1: br1
             * X: brX

             Bridges with an index >=100 are special bridges which forward
             link local traffic. This can be used for wireless links in 4addr
             mode which should act as a cable-replacement.

             **Note:** such a bridge may only contain 2 interfaces!

             **Example**

             wlan0 and eth0 in br100, with eth1 as managment interface.

             Applies to AP and STA."
        ::= { cfgNetWlanTableEntry 7 }

    cfgNetWlanTrunk OBJECT-TYPE
        SYNTAX DisplayString (SIZE(1..255))
        MAX-ACCESS read-write
        STATUS     current
        DESCRIPTION
            "This entry is active when `cfgNetWlanVlanMode` is set to
             **trunk(0)** or **nativeuntagged(3)**.

             It specifies which 802.1q vlans are accepted ingress and egress on
             the respective port. All unspecified vlans are dropped.
             Set this entry to -1 to allow all vlans.
             Untagged traffic is considered as vlan 0.

             The format of this entry is a space or comma separated list.
             To describe ranges the character '-' can be used.

             **Examples**

             '0,12,24,69' or '7 56 127' or '0, 84, 99, 2000' or
             '0, 12-17, 3000-4000' or '0-99 101-199 201-299, 301-4094'

             Applies to AP and STA."
        ::= { cfgNetWlanTableEntry 10 }

    cfgNetWlanTag OBJECT-TYPE
        SYNTAX Integer32 (-1..4094)
        MAX-ACCESS read-write
        STATUS     current
        DESCRIPTION
            "This entry is active when `cfgNetWlanVlanMode` is set to
             **access(1)** or **nativeuntagged(3)**. It specifies which 802.1q
             VLAN should be used for untagged ingress and egress traffic. Set
             this entry to -1 to disable it.

             Applies to AP and STA."
        ::= { cfgNetWlanTableEntry 11 }

    cfgNetWlanVlanMode OBJECT-TYPE
        SYNTAX INTEGER { trunk(0), access(1), nativeuntagged(3) }
        MAX-ACCESS read-write
        STATUS     current
        DESCRIPTION
            "This entry specifies how the port should behave.

             * **trunk(0):** A trunk port carries packets on one or more specified
               VLANs specified in the cfgNetWlanTrunk entry.
               A packet that ingresses on a trunk port is in the VLAN specified
               in its 802.1q header, or VLAN 0 if the packet has no 802.1q header
               (untagged frame). A packet that egresses through a trunk port will
               have an 802.1q header if it has a nonzero VLAN ID.
               Frames egressing on VLAN 0 have their tag stripped (egress untagged).
               Any packet that ingresses on a trunk port tagged with a
               VLAN that the port does not trunk is dropped.
             * **access(1):** An access port carries packets on exactly one VLAN
               specified in the cfgNetWlanTag. Packets egressing on an access
               port have no 802.1q header (egress untagged).
               Any packet with an 802.1q header with a nonzero VLAN ID that
               ingresses on an access port is dropped, regardless of whether
               the VLAN ID in the header is the access port's VLAN ID.
             * **nativeuntagged(3):** A native-untagged port resembles a trunk port,
               with the exception that a packet without an 802.1q header
               (ingress untagged) is automatically in the native VLAN specified
               in cfgNetWlanTag. Frames egressing in the native VLAN are
               automatically untagged (egress untagged).

             Applies to AP and STA."
        ::= { cfgNetWlanTableEntry 12 }

    cfgNetWlanLldpEnabled OBJECT-TYPE
        SYNTAX INTEGER { disabled(0), enabled(1) }
        MAX-ACCESS read-write
        STATUS     current
        DESCRIPTION
            "When `cfgLldpEnabled` is enabled, this parameter controls if
             the interface takes part in LLDP operation.

             Applies to AP and STA."
        ::= { cfgNetWlanTableEntry 15 }

-- -----------------------------------------------------------------------------

    cfgNetVlanTable OBJECT-TYPE
        SYNTAX  SEQUENCE OF CfgNetVlanTableSeq
        MAX-ACCESS not-accessible
        STATUS     current
        DESCRIPTION
            "VLAN Network Interfaces."
        ::= { cfgNetwork 3 }

    cfgNetVlanTableEntry OBJECT-TYPE
        SYNTAX  CfgNetVlanTableSeq
        MAX-ACCESS not-accessible
        STATUS     current
        DESCRIPTION
            "VLAN Network Interfaces."
        INDEX {cfgNetVlanIndex}
        ::= { cfgNetVlanTable 1 }

    CfgNetVlanTableSeq ::=
        SEQUENCE {  cfgNetVlanIndex Integer32,
                    cfgNetVlanName DisplayString,
                    cfgNetVlanEnabled INTEGER,
                    cfgNetVlanBridge Integer32,
                    cfgNetVlanParent DisplayString,
                    cfgNetVlanVid Integer32
                 }

    cfgNetVlanIndex OBJECT-TYPE
        SYNTAX Integer32 (0..127)
        MAX-ACCESS not-accessible
        STATUS     current
        DESCRIPTION
            "Entry index of table."
        ::= { cfgNetVlanTableEntry 1 }

    cfgNetVlanName OBJECT-TYPE
        SYNTAX DisplayString (SIZE(1..255))
        MAX-ACCESS read-only
        STATUS     current
        DESCRIPTION
            "Name of the VLAN interface.

             Applies to AP and STA."
        ::= { cfgNetVlanTableEntry 2 }

    cfgNetVlanEnabled OBJECT-TYPE
        SYNTAX INTEGER { disabled(0), enabled(1) }
        MAX-ACCESS read-write
        STATUS     current
        DESCRIPTION
            "VLAN interface disabled or enabled.

             Applies to AP and STA."
        ::= { cfgNetVlanTableEntry 3 }

    cfgNetVlanBridge OBJECT-TYPE
        SYNTAX Integer32
        MAX-ACCESS read-write
        STATUS     current
        DESCRIPTION
            "The number of the bridge the VLAN interface is applied to.

             VLAN interfaces are always of type access.

             Applies to AP and STA."
        ::= { cfgNetVlanTableEntry 7 }

    cfgNetVlanParent OBJECT-TYPE
        SYNTAX DisplayString (SIZE(1..255))
        MAX-ACCESS read-write
        STATUS     current
        DESCRIPTION
            "Name of the physical parent interface on which the VLAN resides.

             This entry is only active when the VLAN interface is not part of
             a bridge (cfgNetVlanBridge = -1).

             Applies to AP and STA."
        ::= { cfgNetVlanTableEntry 8 }

    cfgNetVlanVid OBJECT-TYPE
        SYNTAX Integer32 (0..4094)
        MAX-ACCESS read-write
        STATUS     current
        DESCRIPTION
            "ID of the VLAN.

             Applies to AP and STA."
        ::= { cfgNetVlanTableEntry 9 }

-- -----------------------------------------------------------------------------

    cfgNetIpTable OBJECT-TYPE
        SYNTAX  SEQUENCE OF CfgNetIpTableSeq
        MAX-ACCESS not-accessible
        STATUS     current
        DESCRIPTION
            "IP address configuration."
        ::= { cfgNetwork 6 }

    cfgNetIpTableEntry OBJECT-TYPE
        SYNTAX  CfgNetIpTableSeq
        MAX-ACCESS not-accessible
        STATUS     current
        DESCRIPTION
            "IP address configuration."
        INDEX {cfgNetIpIndex}
        ::= { cfgNetIpTable 1 }

    CfgNetIpTableSeq ::=
        SEQUENCE {  cfgNetIpIndex Integer32,
                    cfgNetIpEnabled INTEGER,
                    cfgNetIpAddr DisplayString,
                    cfgNetIpProto INTEGER,
                    cfgNetIpInterface DisplayString,
                    cfgNetIpCarpId Integer32
                 }

    cfgNetIpIndex OBJECT-TYPE
        SYNTAX Integer32 (0..127)
        MAX-ACCESS not-accessible
        STATUS     current
        DESCRIPTION
            "Entry index of table."
        ::= { cfgNetIpTableEntry 1 }

    cfgNetIpEnabled OBJECT-TYPE
        SYNTAX INTEGER { disabled(0), enabled(1) }
        MAX-ACCESS read-write
        STATUS     current
        DESCRIPTION
            "IP disabled or enabled.

             Applies to AP and STA."
        ::= { cfgNetIpTableEntry 3 }

    cfgNetIpAddr OBJECT-TYPE
        SYNTAX DisplayString (SIZE(9..19))
        MAX-ACCESS read-write
        STATUS     current
        DESCRIPTION
            "The IPv4 address (using CIDR notation) of the interface specified
             in cfgNetIpInterface.

             Applies to AP and STA."
        ::= { cfgNetIpTableEntry 4 }

    cfgNetIpProto OBJECT-TYPE
        SYNTAX INTEGER {static(0), dhcp(1), dhcpForceRenew(2), dhcpForceRelease(3), linkLocal(4), carp(5)}
        MAX-ACCESS read-write
        STATUS     current
        DESCRIPTION
            "This parameter defines which protocol is used to get the IPv4
             settings for this interface.

             * **static(0):** Indicates that the address is manually configured to a
               specified address given by the IPv4 address parameter of this interface
               configuration.
             * **dhcp(1):** Indicates that an IPv4 address will be obtained by
               the DHCP client. In case the DHCP client is unable to get
               a valid IPv4 address the static IP address will be used
               as a fallback.
             * **linkLocal(4):** Indicates that an IPv4 link local address
               (an address in the range of 169.254.0.1 to 169.254.255.254,
               randomly chosen by the system) will be used on this
               interface. `cfgNetIpAddr` is then not used for the interface.
               **Note:** Only one interface of the device can use a linkLocal
               protocol.
             * **carp(5):** Indicates that an IPv4 address will be set by the
               CARP instance specified in `cfgNetIpCarpId`, when the CARP
               instance has the state MASTER.

             **Note:** Only one interface of the device can use a link
            local protocol.

             For wireless interfaces, the following additional modes are available:

             * **dhcpForceRenew(2):** Indicates that an IPv4 address will
               be obtained by the DHCP client. In case the DHCP client is
               unable to get a valid IPv4 address the static IP address
               will be used as a fallback. On a STA this mode will
               perform a DHCP RENEW after every connection to an AP.
               This is useful if the device is roaming between different
               DHCP servers.
             * **dhcpForceRelease(3):**  Indicates that an IPv4 address
               will be obtained by the DHCP client. In case the DHCP
               client is unable to get a valid IPv4 address, the static
               IP address will be used as a fallback. On a STA this mode
               will perform a DHCP RELEASE followed by a DHCP DISCOVER
               after every connection to an AP. This is useful if the
               device is roaming between different DHCP servers which
               don't send NAK to an unknown device sending RENEW.

             Applies to AP and STA."
        ::= { cfgNetIpTableEntry 6 }

    cfgNetIpInterface OBJECT-TYPE
        SYNTAX DisplayString (SIZE(1..255))
        MAX-ACCESS read-write
        STATUS     current
        DESCRIPTION
            "Name of the interface on which the IP resides.

             Applies to AP and STA."
        ::= { cfgNetIpTableEntry 8 }

    cfgNetIpCarpId OBJECT-TYPE
        SYNTAX Integer32 (0..15)
        MAX-ACCESS read-write
        STATUS     current
        DESCRIPTION
            "Id which references the CARP-instance by `cfgNetCarpIndex`.

             This parameter is only active when `cfgNetIpProto` is set to carp(5).
             Indicates that the referenced CARP instance processes this IP.

             Applies to AP and STA."
        ::= { cfgNetIpTableEntry 10 }

-- -----------------------------------------------------------------------------

    cfgNetCarpTable OBJECT-TYPE
        SYNTAX  SEQUENCE OF CfgNetCarpTableSeq
        MAX-ACCESS not-accessible
        STATUS     current
        DESCRIPTION
            "Redundant IP Addresses with the Common Address Redundancy Protocol (CARP)."
        ::= { cfgNetwork 7 }

    cfgNetCarpTableEntry OBJECT-TYPE
        SYNTAX  CfgNetCarpTableSeq
        MAX-ACCESS not-accessible
        STATUS     current
        DESCRIPTION
            "Redundant IP Addresses with the Common Address Redundancy Protocol (CARP)."
        INDEX {cfgNetCarpIndex}
        ::= { cfgNetCarpTable 1 }

    CfgNetCarpTableSeq ::=
        SEQUENCE {  cfgNetCarpIndex Integer32,
                    cfgNetCarpEnabled INTEGER,
                    cfgNetCarpVhid Integer32,
                    cfgNetCarpPassword DisplayString,
                    cfgNetCarpAdvbase Integer32,
                    cfgNetCarpAdvskew Integer32,
                    cfgNetCarpAdvdivider Integer32,
                    cfgNetCarpRatio Integer32,
                    cfgNetCarpPreempt INTEGER,
                    cfgNetCarpPreemptdemote INTEGER,
                    cfgNetCarpLocalInterfaceGroup Integer32,
                    cfgNetCarpSyncInterface DisplayString,
                    cfgNetCarpMcastIp IpAddress
                 }

    cfgNetCarpIndex OBJECT-TYPE
        SYNTAX Integer32 (0..15)
        MAX-ACCESS not-accessible
        STATUS     current
        DESCRIPTION
            "Entry index of Table."
        ::= { cfgNetCarpTableEntry 1 }

    cfgNetCarpEnabled OBJECT-TYPE
        SYNTAX INTEGER { disabled(0), enabled(1) }
        MAX-ACCESS read-write
        STATUS     current
        DESCRIPTION
            "CARP interface disabled or enabled.

             Applies to AP and STA."
        ::= { cfgNetCarpTableEntry 3 }

    cfgNetCarpVhid OBJECT-TYPE
        SYNTAX Integer32 (1..255)
        MAX-ACCESS read-write
        STATUS     current
        DESCRIPTION
            "The Virtual Host ID.

             This is a unique number that is used to identify the redundancy
             group to other nodes in the group, and to distinguish between
             groups on the same network.

             This must be the same on all members of the group.

             Applies to AP and STA."
        ::= { cfgNetCarpTableEntry 10 }

    cfgNetCarpPassword OBJECT-TYPE
        SYNTAX DisplayString (SIZE(1..255))
        MAX-ACCESS read-write
        STATUS     current
        DESCRIPTION
            "The CARP authentication password.

             This is the password which is used to encrypt the CARP frames
             when talking to other CARP-enabled hosts in this redundancy group.

             This must be the same on all members of the group.

             Applies to AP and STA."
        ::= { cfgNetCarpTableEntry 11 }

    cfgNetCarpAdvbase OBJECT-TYPE
        SYNTAX Integer32 (1..255)
        MAX-ACCESS read-write
        STATUS     current
        DESCRIPTION
            "Advertisement base in seconds.

             This parameter specifies how often to transmit advertisement frames
             that we're a member of the redundancy group.

             This time is divided with `cfgNetCarpAdvdivider` to decrease
             the failovertime of the redundancy group.

             Applies to AP and STA."
        ::= { cfgNetCarpTableEntry 12 }

    cfgNetCarpAdvskew OBJECT-TYPE
        SYNTAX Integer32 (0..254)
        MAX-ACCESS read-write
        STATUS     current
        DESCRIPTION
            "Advertisement base in 1/255th of a second.

             This parameter specifies how much to skew the advbase when
             sending CARP advertisements.

             By manipulating advskew, the master of a CARP group can be chosen.
             The higher the number, the less often frames are transmitted and
             the less preferred the host will be when determining the master.

             This time is divided with `cfgNetCarpAdvdivider` to decrease
             the failovertime of the redundancy group.

             Applies to AP and STA."
        ::= { cfgNetCarpTableEntry 13 }

    cfgNetCarpAdvdivider OBJECT-TYPE
        SYNTAX Integer32 (1..100)
        MAX-ACCESS read-write
        STATUS     current
        DESCRIPTION
            "Divider for `cfgNetCarpAdvbase` and `cfgNetCarpAdvskew`.

             This parameter specifies how much the Advbase and Advskew are
             divided to speed the algorithm up. With a factor of 1, the
             Advbase and Advskew are unchanged.

             Increasing the Advdivider to 10 speeds the algorithm up to allow a
             minimum advertisie time of 100ms instead of 1s.

             This must be the same on all members of the group.

             Applies to AP and STA."
        ::= { cfgNetCarpTableEntry 14 }

    cfgNetCarpRatio OBJECT-TYPE
        SYNTAX Integer32 (1..100)
        MAX-ACCESS read-write
        STATUS     current
        DESCRIPTION
            "The dead ratio after which an existing master is considered dead.

             A slave device will wait:

             `cfgNetCarpRatio` * (`cfgNetCarpAdvbase` + `cfgNetCarpAdvskew`)

             before considering the current master as dead and attempt to become
             the new master. Since The locally configured values for Advbase and
             Advskew are used, if there is a better suited master (lower
             Advbase/Advskew), it will start advertising before the local device.

             Applies to AP and STA."
        ::= { cfgNetCarpTableEntry 15 }

    cfgNetCarpPreempt OBJECT-TYPE
        SYNTAX INTEGER { disabled(0), enabled(1) }
        MAX-ACCESS read-write
        STATUS     current
        DESCRIPTION
            "Preempt other masters when the local device is better.

             Allow hosts within a redundancy group that have a better Advbase
             and Advskew to preempt the current master.

             Applies to AP and STA."
        ::= { cfgNetCarpTableEntry 16 }

    cfgNetCarpPreemptdemote OBJECT-TYPE
        SYNTAX INTEGER { disabled(0), enabled(1) }
        MAX-ACCESS read-write
        STATUS     current
        DESCRIPTION
            "Preempt other master when they demote theself.

             Allow hosts within a redundancy group that have a better Advbase
             and Advskew to preempt the current master when it demotes itself
             (skew >= 240).

             Preemptdemote only works when `cfgNetCarpPreempt` is used.

             Preemptdemote also controls if a master demotes itself when another
             CARP-instance in the same `cfgNetCarpLocalInterfaceGroup` goes
             down or is demoted.

             Applies to AP and STA."
        ::= { cfgNetCarpTableEntry 17 }

    cfgNetCarpLocalInterfaceGroup OBJECT-TYPE
        SYNTAX Integer32 (1..255)
        MAX-ACCESS read-write
        STATUS     current
        DESCRIPTION
            "The local carp interface group the carp interface belongs to.

             When `cfgNetCarpPreempt` or `cfgNetCarpPreemptdemote` is set to
             enabled, the interface will demote itself (skew = 240) when another
             interface within the same local group goes down or is demoted.

             Applies to AP and STA."
        ::= { cfgNetCarpTableEntry 18 }

    cfgNetCarpSyncInterface OBJECT-TYPE
        SYNTAX DisplayString (SIZE(1..255))
        MAX-ACCESS read-write
        STATUS     current
        DESCRIPTION
            "Name of the CARP control interface.

             This interface is used to transmit and receive CARP advertisements.

             This interface is required to have its own unique IP address.

             Applies to AP and STA."
        ::= { cfgNetCarpTableEntry 19 }

    cfgNetCarpMcastIp OBJECT-TYPE
        SYNTAX IpAddress
        MAX-ACCESS read-write
        STATUS     current
        DESCRIPTION
            "Multicast address on which CARP advertisments are transmitted.

             The default multicast address for CARP is 224.0.0.18.

             Use this parameter to specify a custom multicast destination.

             Applies to AP and STA."
        ::= { cfgNetCarpTableEntry 21 }

-- -----------------------------------------------------------------------------

    cfgNetMacVlanTable OBJECT-TYPE
        SYNTAX  SEQUENCE OF CfgNetMacVlanTableSeq
        MAX-ACCESS not-accessible
        STATUS     current
        DESCRIPTION
            "MACVLAN Network Interfaces."
        ::= { cfgNetwork 9 }

    cfgNetMacVlanTableEntry OBJECT-TYPE
        SYNTAX  CfgNetMacVlanTableSeq
        MAX-ACCESS not-accessible
        STATUS     current
        DESCRIPTION
            "MACVLAN Network Interfaces."
        INDEX {cfgNetMacVlanIndex}
        ::= { cfgNetMacVlanTable 1 }

    CfgNetMacVlanTableSeq ::=
        SEQUENCE {  cfgNetMacVlanIndex Integer32,
                    cfgNetMacVlanName DisplayString,
                    cfgNetMacVlanEnabled INTEGER,
                    cfgNetMacVlanParent DisplayString,
                    cfgNetMacVlanMac DisplayString
                 }

    cfgNetMacVlanIndex OBJECT-TYPE
        SYNTAX Integer32 (0..63)
        MAX-ACCESS not-accessible
        STATUS     current
        DESCRIPTION
            "Entry index of Table."
        ::= { cfgNetMacVlanTableEntry 1 }

    cfgNetMacVlanName OBJECT-TYPE
        SYNTAX DisplayString (SIZE(1..255))
        MAX-ACCESS read-only
        STATUS     current
        DESCRIPTION
            "Name of the MACVLAN interface.

             Applies to AP and STA."
        ::= { cfgNetMacVlanTableEntry 2 }

    cfgNetMacVlanEnabled OBJECT-TYPE
        SYNTAX INTEGER { disabled(0), enabled(1) }
        MAX-ACCESS read-write
        STATUS     current
        DESCRIPTION
            "MACVLAN interface disabled or enabled.

             Applies to AP and STA."
        ::= { cfgNetMacVlanTableEntry 3 }

    cfgNetMacVlanParent OBJECT-TYPE
        SYNTAX DisplayString (SIZE(1..255))
        MAX-ACCESS read-write
        STATUS     current
        DESCRIPTION
            "Name of the parent interface on which the MACVLAN resides.

             Applies to AP and STA."
        ::= { cfgNetMacVlanTableEntry 8 }

    cfgNetMacVlanMac OBJECT-TYPE
        SYNTAX DisplayString (SIZE(17))
        MAX-ACCESS read-write
        STATUS     current
        DESCRIPTION
            "MAC address of the MACVLAN.
             Set `00:00:00:00:00:00` to use a random MAC address.

             **Format:** `00:14:5a:02:10:42`

             Applies to AP and STA."
        ::= { cfgNetMacVlanTableEntry 15 }

-- -----------------------------------------------------------------------------

-- -----------------------------------------------------------------------------

    cfgNetWwanTable OBJECT-TYPE
        SYNTAX  SEQUENCE OF CfgNetWwanTableSeq
        MAX-ACCESS not-accessible
        STATUS     current
        DESCRIPTION
            "WWAN (Cellular) Network Interfaces.

             Applies to LTE products only.
            "
        ::= { cfgNetwork 11 }

    cfgNetWwanTableEntry OBJECT-TYPE
        SYNTAX  CfgNetWwanTableSeq
        MAX-ACCESS not-accessible
        STATUS     current
        DESCRIPTION
            "WWAN (Cellular) Network Interfaces.

             Applies to LTE products only.
            "
        INDEX {cfgNetWwanIndex}
        ::= { cfgNetWwanTable 1 }

    CfgNetWwanTableSeq ::=
        SEQUENCE {  cfgNetWwanIndex Integer32,
                    cfgNetWwanName DisplayString,
                    cfgNetWwanEnabled INTEGER,
                    cfgNetWwanPrimarySim Integer32,
                    cfgNetWwanSecondarySim Integer32
                 }

    cfgNetWwanIndex OBJECT-TYPE
        SYNTAX Integer32 (0..1)
        MAX-ACCESS not-accessible
        STATUS     current
        DESCRIPTION
            "Entry index of Table.

             Applies to LTE products only.
            "
        ::= { cfgNetWwanTableEntry 1 }

    cfgNetWwanName OBJECT-TYPE
        SYNTAX DisplayString (SIZE(4..5))
        MAX-ACCESS read-only
        STATUS     current
        DESCRIPTION
            "Name of the WWAN interface

             Applies to LTE products only."
        ::= { cfgNetWwanTableEntry 2 }

    cfgNetWwanEnabled OBJECT-TYPE
        SYNTAX INTEGER { disabled(0), enabled(1) }
        MAX-ACCESS read-write
        STATUS     current
        DESCRIPTION
            "WWAN interface disabled or enabled

             Applies to LTE products only."
        ::= { cfgNetWwanTableEntry 3 }

    cfgNetWwanPrimarySim OBJECT-TYPE
        SYNTAX Integer32
        MAX-ACCESS read-write
        STATUS     current
        DESCRIPTION
            "SIM parameter entry for the primary SIM

            This value references the `cfgCellSimIndex` of the desired entry in
            the `cfgCellSimTable` for the primary SIM.

             Applies to LTE products only."
        ::= { cfgNetWwanTableEntry 4 }

    cfgNetWwanSecondarySim OBJECT-TYPE
        SYNTAX Integer32
        MAX-ACCESS read-write
        STATUS     current
        DESCRIPTION
            "SIM parameter entry for the secondary SIM

            This value references the `cfgCellSimIndex` of the desired entry in
            the `cfgCellSimTable` for the secondary SIM.

             Applies to LTE products only."
        ::= { cfgNetWwanTableEntry 5 }

-- =============================================================================

-- Wireless

    cfgWlanDeviceTable OBJECT-TYPE
        SYNTAX  SEQUENCE OF CfgWlanDeviceTableSeq
        MAX-ACCESS not-accessible
        STATUS     current
        DESCRIPTION
            "Wireless Hardware Modules."
        ::= { cfgWireless 1 }

    cfgWlanDeviceTableEntry OBJECT-TYPE
        SYNTAX  CfgWlanDeviceTableSeq
        MAX-ACCESS not-accessible
        STATUS     current
        DESCRIPTION
            "Wireless Hardware Modules."
        INDEX {cfgWlanDevIndex}
        ::= { cfgWlanDeviceTable 1 }

    CfgWlanDeviceTableSeq ::=
        SEQUENCE {  cfgWlanDevIndex Integer32,
                    cfgWlanDevName DisplayString,
                    cfgWlanDevModulation INTEGER,
                    cfgWlanDevBandwidth INTEGER,
                    cfgWlanDevFrequency Integer32,
                    cfgWlanDevPower Integer32,
                    cfgWlanDevDistance Integer32,
                    cfgWlanDevRts Integer32,
                    cfgWlanDevFragments Integer32,
                    cfgWlanDevShortRetry Integer32,
                    cfgWlanDevLongRetry Integer32,
                    cfgWlanDevAntennaGain Integer32,
                    cfgWlanDevTxAntenna Integer32,
                    cfgWlanDevRxAntenna Integer32,
                    cfgWlanDevPhy DisplayString,
                    cfgWlanDevHtCapabilities Integer32,
                    cfgWlanDevQmrrString DisplayString
                 }

    cfgWlanDevIndex OBJECT-TYPE
        SYNTAX Integer32 (0..1)
        MAX-ACCESS not-accessible
        STATUS     current
        DESCRIPTION
            "Entry index of table."
        ::= { cfgWlanDeviceTableEntry 1 }

    cfgWlanDevName OBJECT-TYPE
        SYNTAX DisplayString (SIZE(1..255))
        MAX-ACCESS read-only
        STATUS     current
        DESCRIPTION
            "Name of the wireless device.

             Applies to AP and STA."
        ::= { cfgWlanDeviceTableEntry 2 }

    cfgWlanDevModulation OBJECT-TYPE
        SYNTAX INTEGER { g(2), bg(3), a(4), ng(10), na(12), ac(28)}
        MAX-ACCESS read-write
        STATUS     current
        DESCRIPTION
            "The modulation modes of the physical wireless device are:

             * **g(2):**  This modulation mode uses OFDM data rates up
               to 54 MBit/s in the frequency band between 2.4 and 2.4835 GHz.
               It supports the 802.11g standard.
             * **bg(3):** This modulation mode uses data rates up to
               54 MBit/s in the frequency band between 2.4 and 2.4835 GHz.
               It supports the 802.11bg standard. The modulation is
               either DSSS for the slower rates or OFDM for the faster ones.
             * **a(4):** Mode supports data rates up to 54 MBit/s in the
               5GHz frequency band and only OFDM modulation.
             * **n(8):**  Mode supports data rates up to 300 MBit/s in
               the 2.4GHz and 5GHz frequency band and only OFDM modulation.
               Mode **n(8)** cannot be used as such. It has to be combined
               with g or a  to specify which frequency band shall be used.
             * **ng(10):** For 2.4GHz
             * **na(12):** For 5GHz.
             * **ac(28):** 11ac mode for 5GHz.

             **Note:** Some products do not support all modulations.
             Please check the data-sheet of your product.

             Applies to AP and STA."
        ::= { cfgWlanDeviceTableEntry 4 }

    cfgWlanDevBandwidth OBJECT-TYPE
        SYNTAX INTEGER { bw20(0), bw40Plus(1), bw40Minus(2), bwQuarter(3), bwHalf(4),
                         bw80(5), bw160(6), bw8080(7), bwAuto(8) }
        MAX-ACCESS read-write
        STATUS     current
        DESCRIPTION
            "Wireless Bandwidth Mode specifies the Bandwidth of the Channel.

             * **bw20(0):** for 20MHz wide channel.
             * **bw40Plus(1):** for 40MHz wide channel with the side
               channel on the top.
             * **bw40Minus(2):** for 40MHz wide channel with the side
               channel on the bottom.
             * **bwQuarter(3):** for 5MHz wide channel (quarter rate).
             * **bwHalf(4):** for 10MHz wide channel (half rate).
             * **bw80(5):** 80MHz wide channel (only in 11ac mode)
             * **bw160(6):** 160MHz wide channel (only in 11ac mode)
             * **bw8080(7):** 80+80MHz wide channel (only in 11ac mode)
             * **bwAuto(8):** automatic channel width (only in 11ac mode)

             **Note:** **bw40Plus(1)** and **bw40Minus(2)** may not be
                       usable on all channels.

             **Examples**

             The following table shows examples of which channels may be used.
             The full list can be found in IEEE 802.11n Annex J. Depending on
             the country, not all frequencies may be available.

             | Band       | **bw40Plus(1)**         | **bw40Minus(2)**       |
             |------------|-------------------------|------------------------|
             | 2.4 GHz    | 2412 to 2452            | 2432 to 2472           |
             | 5 GHz      | 5180, 5220, 5260, etc.  | 5200, 5240, 5280, etc. |

             **Note:** Some products do not support all bandwidths.
             Please check the data-sheet of your product.

             Applies to AP and STA."
        ::= { cfgWlanDeviceTableEntry 5 }

    cfgWlanDevFrequency OBJECT-TYPE
        SYNTAX Integer32
        MAX-ACCESS read-write
        STATUS     current
        DESCRIPTION
            "Wireless Frequency in MHz.

             In AP mode, setting the wireless frequency to zero(0) enables the
             automatic channel selection (ACS) feature. This forces the AP to choose
             the best channel for operation.

             In STA mode, the `cfgWlanIfaceScanList` is used to configure which
             frequencies are to be scanned (802.11n products only).

             Applies to AP and STA."
        ::= { cfgWlanDeviceTableEntry 6 }

    cfgWlanDevPower OBJECT-TYPE
        SYNTAX Integer32 (6..50)
        MAX-ACCESS read-write
        STATUS     current
        DESCRIPTION
            "Max. limit for wireless output power as effective isotropic radiated power
             (EIRP) in dBm including array gain and antenna gain.

             **Note:** This parameter only limits the maximum output power. The effective
             output power might be lower (regulatory limits, rate depended limits).

             EIRP (dBm) = antenna port power (dBm) + array gain (dB) + antenna gain (dBi)

             - The antenna port power in dBm defines the power transmitted per antenna port
             (chain).
             - The array gain in dB defines the gain which is achieved by the use of multiple
             antenna ports (chains). The number of active antenna ports (chains) is defined by
             `cfgWlanDevTxAntenna`. The array gain depends on number of active antenna ports
             (chains) as following:
                 - One antenna port (chain) = 0 dB
                 - Two antenna ports (chains) = 3 dB
                 - Three antenna ports (chains) = 5 dB
                 - Four antenna ports (chains) = 6 dB
             - The antenna gain in dBi defines the gain which is achieved by the antenna.
             The antenna gain is configured by `cfgWlanDevAntennaGain`.

             Applies to AP and STA."
        ::= { cfgWlanDeviceTableEntry 8 }

    cfgWlanDevDistance OBJECT-TYPE
        SYNTAX Integer32 (0..114750)
        MAX-ACCESS read-write
        STATUS     current
        DESCRIPTION
            "Maximum distance in meters a client can be apart from the access
             point. Even though the distance is set in meters, the slot time
             settings change in 450m steps.

             Applies to AP and STA. 802.11n products only."
        ::= { cfgWlanDeviceTableEntry 10 }

    cfgWlanDevRts OBJECT-TYPE
        SYNTAX Integer32 (-1..65535)
        MAX-ACCESS read-write
        STATUS     current
        DESCRIPTION
            "Frames equal or longer in bytes than this value require a
             RTS/CTS handshake.

             RTS/CTS is used in hidden node situations. In 11bg and b mode,
             these frames are sent in DSSS modulation at 11b data rates.
             Otherwise (pure-g and a) OFDM rates are used.

             The following settings are special:

             * **-1** disable value, RTS/CTS is disabled.
             * **0** minimum value, RTS/CTS is always used.
             * **2346** maximum value legacy-rates, RTS/CTS is enabled for
               maximum sized frames.
             * **65535** maximum value n-rates, RTS/CTS is enabled for maximal
               aggregate sized frames.

             **Note:** It is not recommended to use RTS/CTS in AP mode.

             Applies to AP and STA."
        ::= { cfgWlanDeviceTableEntry 11 }

    cfgWlanDevFragments OBJECT-TYPE
        SYNTAX Integer32 (-1..2346)
        MAX-ACCESS read-write
        STATUS     current
        DESCRIPTION
            "Frames longer in bytes than this threshold will be fragmented.

             Fragmentation can be used to reduce the number of retransmissions.
             The following settings are special

             * **-1** disable value, fragmentation is disabled
             * **256** minimum value, frames above 256 are fragmented.
             * **2346** maximum value, essentially the same as disabled.

             Applies to AP and STA. 802.11n products only."
        ::= { cfgWlanDeviceTableEntry 12 }

    cfgWlanDevShortRetry OBJECT-TYPE
        SYNTAX Integer32 (1..10)
        MAX-ACCESS read-write
        STATUS     current
        DESCRIPTION
            "Number of times the transmission of the RTS frame will be retried
             if there is no CTS received from the AP.

             Applies to AP and STA. 802.11n products only."
        ::= { cfgWlanDeviceTableEntry 13 }

    cfgWlanDevLongRetry OBJECT-TYPE
        SYNTAX Integer32 (1..10)
        MAX-ACCESS read-write
        STATUS     current
        DESCRIPTION
            "Number of times the unicast data frames will be retried if there is
             no ACK from the receiver.

             Applies to AP and STA. 802.11n products only."
        ::= { cfgWlanDeviceTableEntry 14 }

    cfgWlanDevAntennaGain OBJECT-TYPE
        SYNTAX Integer32
        MAX-ACCESS read-write
        STATUS     current
        DESCRIPTION
            "Antenna gain in dBi.

             If multiple antennas with different gains are connected, the value
             of the antenna with the highest gain shall be configured.

             Applies to AP and STA."
        ::= { cfgWlanDeviceTableEntry 15 }

    cfgWlanDevTxAntenna OBJECT-TYPE
        SYNTAX Integer32
        MAX-ACCESS read-write
        STATUS     current
        DESCRIPTION
            "Configure the number of wireless transmission antenna ports.

             This is a bitmask to enable/disable the chains.

             **Example**

             * 1(0001) = A1 (chain 0) enabled
             * 3(0011) = A1 and A2 (chain 0 and 1) enabled
             * 7(0111) = A1, A2 and A3 (chain 0, 1 and 2) enabled
             * 15(1111) = A1, A2, A3 and A4 (chain 0, 1, 2 and 3) enabled

             **Note:** Number of available antennas depends on the product.
             Please check the data-sheet of your product.

             Applies to AP and STA."
        ::= { cfgWlanDeviceTableEntry 16 }

    cfgWlanDevRxAntenna OBJECT-TYPE
        SYNTAX Integer32
        MAX-ACCESS read-write
        STATUS     current
        DESCRIPTION
            "Configure the number of wireless receiver antennas.

            This is a bitmask to enable/disable the chains.

            **Example**

            * 1(0001) = A1 (chain 0) enabled
            * 3(0011) = A1 and A2 chain 0 and 1) enabled
            * 7(0111) = A1, A2 and A3 (chain 0, 1 and 2) enabled
            * 15(1111) = A1, A2, A3 and A4 (chain 0, 1, 2 and 3) enabled

             **Note:** Number of available antennas depends on the product.
             Please check the data-sheet of your product.

            Applies to AP and STA."
        ::= { cfgWlanDeviceTableEntry 17 }

    cfgWlanDevPhy OBJECT-TYPE
        SYNTAX DisplayString (SIZE(1..255))
        MAX-ACCESS read-only
        STATUS     current
        DESCRIPTION
            "The map between physical device and radio.

             Applies to AP and STA."
        ::= { cfgWlanDeviceTableEntry 18 }

    cfgWlanDevHtCapabilities OBJECT-TYPE
        SYNTAX Integer32 (0..65535)
        MAX-ACCESS read-write
        STATUS     current
        DESCRIPTION
            "HT capability flags:

             * [LDPC]          = 1      Enable support for LDPC coding
             * [SHORT-GI-20]   = 32     Allow short GI for 20 MHz
             * [SHORT-GI-40]   = 64     Allow short GI for 40 MHz
             * [TX-STBC]       = 128    Enable support for TX-STBC
             * [RX-STBC1]      = 256    Enable support for RX-STBC1
             * [DSSS_CCK-40]   = 4096   Enable support for DSSS/CCK Mode in 40 MHz
             * [40-INTOLERANT] = 16384  Advertise 40 MHz intolerance

             Applies to AP. 802.11n products only."
        ::= { cfgWlanDeviceTableEntry 24 }

    cfgWlanDevQmrrString OBJECT-TYPE
        SYNTAX DisplayString
        MAX-ACCESS read-write
        STATUS     current
        DESCRIPTION
            "A list of rate controller quadruples per queue.

             Each quadruple consist of
             (mcs-rate [0-31], tries [0-15], rts_cts [0-1], sgi [0-1])
             with 4 entries per queue.

             16 values together are for a single queue.

             The values are in the form:
             rate1, try1, rts_cts1, sgi1, rate2, ..., rate4, try4, rts_cts4, sgi4.

             The order of the queues is VO, VI, BE, BK.

             QMRR override for a specific queue is disabled when its
             respective try1 value is 0.

             When QMRR override is disabled, the normal minstrel or
             other configured overrides, are used.

             All characters other than numbers are ignored

             **Example:**

             [(7 1 0 0) (4 2 0 0) (2 3 0 0) (0 4 1 0)] \
             [(7 1 0 0) (4 1 0 1) (2 1 0 1) (0 1 1 1)] \
             [(7 1 0 0) (4 1 0 0) (0 0 0 0) (0 0 0 0)] \
             [(7 1 0 0) (0 0 0 0) (0 0 0 0) (0 0 0 0)]

             Applies to AP and STA. 802.11n products only."

        ::= { cfgWlanDeviceTableEntry 26 }

-- -----------------------------------------------------------------------------

    cfgWlanInterfaceTable OBJECT-TYPE
        SYNTAX  SEQUENCE OF CfgWlanInterfaceTableSeq
        MAX-ACCESS not-accessible
        STATUS     current
        DESCRIPTION
            "Wireless Virtual Interfaces."
        ::= { cfgWireless 2 }

    cfgWlanInterfaceTableEntry OBJECT-TYPE
        SYNTAX  CfgWlanInterfaceTableSeq
        MAX-ACCESS not-accessible
        STATUS     current
        DESCRIPTION
            "Wireless Virtual Interface Entry."
        INDEX {cfgWlanIfaceIndex}
        ::= { cfgWlanInterfaceTable 1 }

    CfgWlanInterfaceTableSeq ::=
        SEQUENCE {  cfgWlanIfaceIndex Integer32,
                    cfgWlanIfaceName DisplayString,
                    cfgWlanIfaceDevice INTEGER,
                    cfgWlanIfaceMode INTEGER,
                    cfgWlanIfaceSsid DisplayString,
                    cfgWlanIfaceEncryption INTEGER,
                    cfgWlanIfacePassword DisplayString,
                    cfgWlanIfacePassiveScanning INTEGER,
                    cfgWlanIfaceBeaconMiss Integer32,
                    cfgWlanIfaceDtim Integer32,
                    cfgWlanIfaceBitrates DisplayString,
                    cfgWlanIfaceBeaconInterval Integer32,
                    cfgWlanIfaceWmeParameter Integer32,
                    cfgWlanIfaceWmeEnabled INTEGER,
                    cfgWlanIfaceScanList Integer32,
                    cfgWlanIfaceIgnoreBroadcastSsid INTEGER,
                    cfgWlanIfaceMacaddrAcl INTEGER,
                    cfgWlanIfaceMaxNumSta Integer32,
                    cfgWlanIfaceBssid DisplayString,
                    cfgWlanIfaceLegacyRates Integer32,
                    cfgWlanIface4addr INTEGER,
                    cfgWlanIfaceInactivityTimeout Integer32,
                    cfgWlanIfaceUseVendorSsid INTEGER,
                    cfgWlanIfaceIeee80211w INTEGER,
                    cfgWlanIfaceIeee80211wMaxTimeout Integer32,
                    cfgWlanIfaceIeee80211wRetryTimeout Integer32,
                    cfgWlanIfaceAcsList Integer32,
                    cfgWlanIfaceNeighbourReport INTEGER,
                    cfgWlanIfaceNeighbourParameter Integer32,
                    cfgWlanIfaceL2nat INTEGER,
                    cfgWlanIfaceL2natLearningMode INTEGER,
                    cfgWlanIfaceL2natDefaultDestination DisplayString,
                    cfgWlanIfaceTimeAdvertisement INTEGER,
                    cfgWlanIfaceApIsolate INTEGER
                 }

    cfgWlanIfaceIndex OBJECT-TYPE
        SYNTAX Integer32 (0..63)
        MAX-ACCESS not-accessible
        STATUS     current
        DESCRIPTION
            "Entry index of table."
        ::= { cfgWlanInterfaceTableEntry 1 }

    cfgWlanIfaceName OBJECT-TYPE
        SYNTAX DisplayString (SIZE(1..255))
        MAX-ACCESS read-only
        STATUS     current
        DESCRIPTION
            "Name of the virtual wireless interface.

             Applies to AP and STA."
        ::= { cfgWlanInterfaceTableEntry 2 }

    cfgWlanIfaceDevice OBJECT-TYPE
        SYNTAX INTEGER { radio0(0), radio1(1)}
        MAX-ACCESS read-write
        STATUS     current
        DESCRIPTION
            "Maps the virtual wireless interface to the radio device.

             Applies to AP and STA."
        ::= { cfgWlanInterfaceTableEntry 3 }

    cfgWlanIfaceMode OBJECT-TYPE
        SYNTAX INTEGER { ap(0), sta(1), monitor(2)}
        MAX-ACCESS read-write
        STATUS     current
        DESCRIPTION
            "Wireless Operation Mode.

             Allowed modes are:

             * **ap(0):** defines the interface as Access Point (AP)
             * **sta(1):** defines the interface as Station (STA)
             * **monitor(2):** defines the interface as Monitor (MON)

             **Note:** Some products do not support all modes.
             Please check the data-sheet of your product.

             Applies to AP and STA."
        ::= { cfgWlanInterfaceTableEntry 4 }

    cfgWlanIfaceSsid OBJECT-TYPE
        SYNTAX DisplayString (SIZE(1..32))
        MAX-ACCESS read-write
        STATUS     current
        DESCRIPTION
            "The Service Set Identifier (SSID) of the wireless interface is the
             arbitrary name of the wireless network this interface is part of.

             Applies to AP and STA."
        ::= { cfgWlanInterfaceTableEntry 5 }

    cfgWlanIfaceEncryption OBJECT-TYPE
        SYNTAX INTEGER { open(0), wpa2(3), wpa2eap(6), sae(7) }
        MAX-ACCESS read-write
        STATUS     current
        DESCRIPTION
            "Wireless Encryption Mode.

             Following encryption modes are supported: **open(0)**, **wpa2(3)**,
             **wpa2eap(6)** and **sae(7)**.

             **Note:** WPA2 EAP enables 802.1X support.

             **Note:** **sae(7)** is supported for 802.11n products only.

             Applies to AP and STA."
        ::= { cfgWlanInterfaceTableEntry 6 }

    cfgWlanIfacePassword OBJECT-TYPE
        SYNTAX DisplayString (SIZE(8..63))
        MAX-ACCESS read-write
        STATUS     current
        DESCRIPTION
            "Wireless password if an encryption is in use.

             Each character in the pass-phrase must have an
             encoding in the range of 32 to 126 (decimal),
             inclusive. (IEEE Std. 802.11i-2004, Annex H.4.1)
             The space character is included in this range.

             Applies to AP and STA."
        ::= { cfgWlanInterfaceTableEntry 7 }

    cfgWlanIfacePassiveScanning OBJECT-TYPE
        SYNTAX INTEGER { active(0), passive(1) }
        MAX-ACCESS read-write
        STATUS     current
        DESCRIPTION
            "Wireless Scanning Mode.

             If the scanning mode is set to active(0) the station will send
             a probe request to detect available access points if it's allowed
             by the country code.

             If the scanning mode is set to passive(1) the station will always
             perform passive scanning to detect available access points.

             Applies to STA. 802.11n products only."
        ::= { cfgWlanInterfaceTableEntry 8 }

    cfgWlanIfaceBeaconMiss OBJECT-TYPE
        SYNTAX Integer32
        MAX-ACCESS read-write
        STATUS     current
        DESCRIPTION
            "Number of misses on consecutive beacons before the station will
             disconnect from the associated access point.

             Applies to STA. 802.11n products only."
        ::= { cfgWlanInterfaceTableEntry 9 }

    cfgWlanIfaceDtim OBJECT-TYPE
        SYNTAX Integer32 (1..255)
        MAX-ACCESS read-write
        STATUS     current
        DESCRIPTION
            "This attribute shall specify the number of beacon intervals that
             shall elapse between transmission of beacons frames containing a
             TIM element whose DTIM count field is 0. This value is transmitted
             in the DTIM Period field of Beacon frames.

             Applies to AP. 802.11n products only."
        ::= { cfgWlanInterfaceTableEntry 10 }

    cfgWlanIfaceBitrates OBJECT-TYPE
        SYNTAX  DisplayString
        MAX-ACCESS read-write
        STATUS     current
        DESCRIPTION
            "Fixed MCS index for 802.11n rates.

             Set to -1 to disable (leave on auto). Allows for entering multiple
             indices divided by a space which are then used in auto rate.
             This entry is only active when an n-rate is set in
             cfgWlanDevModulation (not only g-rate or only a-rate).

             Applies to AP and STA. 802.11n products only."
        ::= { cfgWlanInterfaceTableEntry 11 }

    cfgWlanIfaceBeaconInterval OBJECT-TYPE
        SYNTAX  Integer32 (15..1000)
        MAX-ACCESS read-write
        STATUS     current
        DESCRIPTION
            "Time in kus (1.024 ms) between the sending of beacon frames.

             Applies to AP. 802.11n products only."
        ::= { cfgWlanInterfaceTableEntry 12 }

    cfgWlanIfaceWmeParameter OBJECT-TYPE
        SYNTAX Integer32
        MAX-ACCESS read-write
        STATUS     current
        DESCRIPTION
            "Reference ID to the WME parameter table.

             Uses all parameters in the cfgWlanWmeTable which have as
             cfgWlanWmeId the value set here.

             Applies to AP and STA. 802.11n products only."
        ::= { cfgWlanInterfaceTableEntry 13 }

    cfgWlanIfaceWmeEnabled OBJECT-TYPE
        SYNTAX INTEGER { disabled(0), enabled(1) }
        MAX-ACCESS read-write
        STATUS     current
        DESCRIPTION
            "Enables usage of the WME parameter table.

             When using legacy rates (a-rates and g-rates) this is optional.
             When using n-rates this has to be enabled at all times.

             Applies to AP. 802.11n products only."
        ::= { cfgWlanInterfaceTableEntry 14 }

    cfgWlanIfaceScanList OBJECT-TYPE
        SYNTAX Integer32
        MAX-ACCESS read-write
        STATUS     current
        DESCRIPTION
            "Index to specify a frequency list with frequencies to be scanned
             when in STA mode. To only scan the frequency defined in
             cfgWlanDevFrequency set to -1. To scan all frequencies allowed by
             the configured country code set to -2.

             Applies to STA. 802.11n products only."
        ::= { cfgWlanInterfaceTableEntry 15 }

    cfgWlanIfaceIgnoreBroadcastSsid OBJECT-TYPE
        SYNTAX INTEGER { disabled(0), enabled(1) }
        MAX-ACCESS read-write
        STATUS     current
        DESCRIPTION
            "Send empty SSID in beacons and ignore probe request frames that
             do not specify the full SSID, i.e., require stations to know SSID.

             Applies to AP."
        ::= { cfgWlanInterfaceTableEntry 16 }

    cfgWlanIfaceMacaddrAcl OBJECT-TYPE
        SYNTAX INTEGER { acceptunlessdeny(0), denyunlessaccept(1), radius(2) }
        MAX-ACCESS read-write
        STATUS     current
        DESCRIPTION
            "Mode of the MAC access control list.

             * **acceptunlessdeny(0):** Accept unless deny filter. Accept
               every MAC unless it is on the list defined in
               `cfgWlanAclBlackTable`.
             * **denyunlessaccept(1):** Deny unless accept filter. Deny
               every MAC unless it is on the list defined in
               `cfgWlanAclWhiteTable`.
             * **radius(2):** Use RADIUS to accept/deny clients.

             Applies to AP. 802.11n products only."
        ::= { cfgWlanInterfaceTableEntry 17 }

    cfgWlanIfaceMaxNumSta OBJECT-TYPE
        SYNTAX Integer32 (1..255)
        MAX-ACCESS read-write
        STATUS     current
        DESCRIPTION
            "Maximum number of allowed stations which can connect to this AP.

             Applies to AP. 802.11n products only."
        ::= { cfgWlanInterfaceTableEntry 18 }

    cfgWlanIfaceBssid OBJECT-TYPE
        SYNTAX DisplayString (SIZE(17))
        MAX-ACCESS read-write
        STATUS     current
        DESCRIPTION
            "BSSID of AP.

             Set 00:00:00:00:00:00 to use the MAC address stored in the flash of
             the wireless card itself. If this is the second virtual AP on this
             card it will automatically set the locally assigned bit. If there
             are more than 2 virtual APs on a single card this field MUST be
             set.

             When the device is operating in STA mode the MAC address of the
             wireless interface can be configured.

             **Format:** `00:14:5a:02:10:42`

             Applies to AP and STA."
        ::= { cfgWlanInterfaceTableEntry 19 }

    cfgWlanIfaceLegacyRates OBJECT-TYPE
        SYNTAX Integer32 (0..2048)
        MAX-ACCESS read-write
        STATUS     current
        DESCRIPTION
            "Wireless legacy data rates:

             * **11b:** 1, 2, 5.5, 11 Mbps
             * **11a/g:** 6, 9, 12, 18, 24, 36, 48, 54 Mbps

             The values are interpreted as flags:

             * auto(0), 1Mbps(1), 2Mbps(2), 5.5Mbps(4), 6Mbps(8), 9Mbps(16),
             * 11Mbps(32), 12Mbps(64), 18Mbps(128), 24Mbps(256), 36Mbps(512),
             * 48Mbps(1024), 54Mbps(2048)

             When cfgWlanDevBandwidth is equal 3 (quarter rates) the rate is
             quarter i.e. 36Mbps becomes 9MBps. When cfgWlanDevBandwidth is
             equal 4 (half rates) the rate is halved i.e. 36Mbps becomes 18MBps.
             This entry is only active when g-rates or a-rates are selected in
             cfgWlanDevModulation (disabled with n-rates).

             Applies to AP and STA. 802.11n products only."
        ::= { cfgWlanInterfaceTableEntry 20 }

    cfgWlanIface4addr OBJECT-TYPE
        SYNTAX INTEGER { disabled(0), enabled(1) }
        MAX-ACCESS read-write
        STATUS     current
        DESCRIPTION
            "This option allows to bridge the STA side.

             When used on the STA, the corresponding AP has to enable this
             feature as well.

             Applies to AP and STA. 802.11n products only."
        ::= { cfgWlanInterfaceTableEntry 21 }

    cfgWlanIfaceInactivityTimeout OBJECT-TYPE
        SYNTAX Integer32 (15..65535)
        MAX-ACCESS read-write
        STATUS     current
        DESCRIPTION
            "If a station does not send anything in ap_max_inactivity seconds,
             an empty data frame is sent to it in order to verify whether it is
             still in range. If this frame is not ACKed, the station will be
             disassociated and then deauthenticated. This feature is used to
             clear the station table of old entries when the STAs move out of
             range.

             Applies to AP. 802.11n products only."
        ::= { cfgWlanInterfaceTableEntry 23 }

   cfgWlanIfaceUseVendorSsid OBJECT-TYPE
        SYNTAX  INTEGER { disabled(0), enabled(1) }
        MAX-ACCESS read-write
        STATUS     current
        DESCRIPTION
            "When cfgWlanIfaceIgnoreBroadcastSsid is enabled, a passively
             scanning STA (forced or because of DFS) has no way of detecting
             the AP it tries to find. On an AP this options adds the hidden
             SSID as vendor element. On a STA this options allows it to use the
             vendor element in the beacon.

             Applies to AP and STA. 802.11n products only."
        ::= { cfgWlanInterfaceTableEntry 26 }

    cfgWlanIfaceIeee80211w OBJECT-TYPE
        SYNTAX INTEGER { disabled(0), optional(1), required(2) }
        MAX-ACCESS read-write
        STATUS     current
        DESCRIPTION
            "Controls usage of 802.11w Management Frame Protection (MFP)
             mechanism. If set to optional on AP, MFP will be enabled only
             for clients which have it also enabled. If set to required, only
             MFP enabled clients will be able to connect.

             Applies to AP and STA."
        ::= { cfgWlanInterfaceTableEntry 30 }

    cfgWlanIfaceIeee80211wMaxTimeout OBJECT-TYPE
        SYNTAX  Integer32 (1..4000)
        MAX-ACCESS read-write
        STATUS     current
        DESCRIPTION
            "802.11w Management Frame Protection (MFP)

             Association SA query maximum timeout (in TU = 1.024 ms; for MFP)
             (maximum time to wait for a SA query response)

             Applies to AP."
        ::= { cfgWlanInterfaceTableEntry 31 }

    cfgWlanIfaceIeee80211wRetryTimeout OBJECT-TYPE
        SYNTAX  Integer32 (1..4000)
        MAX-ACCESS read-write
        STATUS     current
        DESCRIPTION
            "802.11w Management Frame Protection (MFP)

             Association SA query retry timeout (in TU = 1.024 ms; for MFP)
             (time between two subsequent SA query requests)

             Applies to AP."
        ::= { cfgWlanInterfaceTableEntry 32 }

    cfgWlanIfaceAcsList OBJECT-TYPE
        SYNTAX Integer32
        MAX-ACCESS read-write
        STATUS     current
        DESCRIPTION
            "Index to specify a frequency list for Automated Channel Selection
             (ACS) support when in AP mode. To disable set to -1.

             Applies to AP. 802.11n products only."
        ::= { cfgWlanInterfaceTableEntry 40 }

    cfgWlanIfaceNeighbourReport OBJECT-TYPE
        SYNTAX INTEGER { disabled(0), enabled(1) }
        MAX-ACCESS read-write
        STATUS     current
        DESCRIPTION
            "Enable/disable neighbour reporting.

             A STA can request the neighbour table from an AP and use this
             information to improve its handoff decision.

             Applies to AP. 802.11n products only."
        ::= { cfgWlanInterfaceTableEntry 60 }

    cfgWlanIfaceNeighbourParameter OBJECT-TYPE
        SYNTAX Integer32
        MAX-ACCESS read-write
        STATUS     current
        DESCRIPTION
            "Reference ID to the neighbour table. Uses all neighbours in the
             `cfgWlanNeighbourTable` which have as `cfgWlanNeighbourId` the value set here.

             Applies to AP. 802.11n products only."
        ::= { cfgWlanInterfaceTableEntry 61 }

    cfgWlanIfaceL2nat OBJECT-TYPE
        SYNTAX INTEGER { disabled(0), enabled(1) }
        MAX-ACCESS read-write
        STATUS     current
        DESCRIPTION
            "This option allows to bridge the STA side.

             It is intended to be used in setups where the STA is doing
             handoff between multiple APs. There is no configuration on the APs
             required. This is an alternative to `cfgWlanIface4addr`.
             This option may not be enabled together with `cfgWlanIface4addr`.

             Applies to STA."
        ::= { cfgWlanInterfaceTableEntry 80 }

    cfgWlanIfaceL2natLearningMode OBJECT-TYPE
        SYNTAX INTEGER { both(0), arp(1) }
        MAX-ACCESS read-write
        STATUS     current
        DESCRIPTION
            "From which type of frames the IP/MAC table may be learned.

             When `cfgWlanIfaceL2nat` is enabled a table of the association
             between IP-addresses and MAC-addresses is kept. This options
             specifies from which type of frames this association may be learned:

             * **both(0):** MAC/IP association is learned from ARP frames and
                            from IP frames.
             * **arp(1):** MAC/IP association is learned only from ARP frames.

             Applies to STA."
        ::= { cfgWlanInterfaceTableEntry 81 }

    cfgWlanIfaceL2natDefaultDestination OBJECT-TYPE
        SYNTAX DisplayString (SIZE(17))
        MAX-ACCESS read-write
        STATUS     current
        DESCRIPTION
            "This option defines the default MAC address to send frames to.

             Whenever a unicast frame is received for which no learned entry
             exists, or which isn't a L3 frame (e.g a custom L2 protocol), the
             frame will be sent to the address specified here.

             This address is by default the broadcast address.

             **Format:** `ff:ff:ff:ff:ff:ff`

             Applies to STA."
        ::= { cfgWlanInterfaceTableEntry 82 }

    cfgWlanIfaceTimeAdvertisement OBJECT-TYPE
        SYNTAX INTEGER { disabled(0), enabled(1) }
        MAX-ACCESS read-write
        STATUS     current
        DESCRIPTION
            "Enable AP to include local time in association response frames.

             This provides a mean for APs to distribute its local system
             time to STAs in setups where devices have no RTC and start
             up with an invalid system time.

             If configured, AP embeds its current system time as IE in
             association response frames, which STAs can use to update to
             before they get access to trusted time sources like NTP.

             Note that enabling this feature increases the size of response
             frames, therefore this feature shall only be activated where
             required and defaults to disabled.

             Applies to AP. 802.11n products only."
        ::= { cfgWlanInterfaceTableEntry 90 }

    cfgWlanIfaceApIsolate OBJECT-TYPE
        SYNTAX INTEGER { disabled(0), enabled(1) }
        MAX-ACCESS read-write
        STATUS     current
        DESCRIPTION
            "Enable AP clients isolation.

             If enabled, clients connected to this AP can't communicate
             to each other.

             Applies to AP."
        ::= { cfgWlanInterfaceTableEntry 100 }

-- -----------------------------------------------------------------------------

    cfgWlanHandoffTable OBJECT-TYPE
        SYNTAX  SEQUENCE OF CfgWlanHandoffTableSeq
        MAX-ACCESS not-accessible
        STATUS     current
        DESCRIPTION
            "Wireless handoff parameters.

             Applies to STA.  802.11n products only."
        ::= { cfgWireless 3 }

    cfgWlanHandoffTableEntry OBJECT-TYPE
        SYNTAX  CfgWlanHandoffTableSeq
        MAX-ACCESS not-accessible
        STATUS     current
        DESCRIPTION
            "Wireless handoff parameters entry.

             Applies to  STA. 802.11n products only."
        INDEX {cfgWlanHoIndex}
        ::= { cfgWlanHandoffTable 1 }

    CfgWlanHandoffTableSeq ::=
        SEQUENCE {  cfgWlanHoIndex Integer32,
                    cfgWlanHoIfaceName DisplayString,
                    cfgWlanHoProfile INTEGER,
                    cfgWlanHoScanningLevel Integer32,
                    cfgWlanHoBeacons Integer32,
                    cfgWlanHoRecovery Integer32,
                    cfgWlanHoFilterMode INTEGER,
                    cfgWlanHoFilterLongX Integer32,
                    cfgWlanHoFilterLongY Integer32,
                    cfgWlanHoScanRateLimitTime Integer32,
                    cfgWlanHoScanRateLimitTries Integer32,
                    cfgWlanHoPassiveChanTime Integer32,
                    cfgWlanHoLevelLow Integer32,
                    cfgWlanHoLevelHigh Integer32,
                    cfgWlanHoDistanceNear Integer32,
                    cfgWlanHoDistanceFar Integer32,
                    cfgWlanHoDistanceMeasurementPeriod Integer32,
                    cfgWlanHoDistanceFilterX Integer32,
                    cfgWlanHoDistanceFilterY Integer32
                 }

    cfgWlanHoIndex OBJECT-TYPE
        SYNTAX Integer32 (0..63)
        MAX-ACCESS not-accessible
        STATUS     current
        DESCRIPTION
            "Entry index of table.

             Applies to STA. 802.11n products only."
        ::= { cfgWlanHandoffTableEntry 1 }

    cfgWlanHoIfaceName OBJECT-TYPE
        SYNTAX DisplayString (SIZE(1..255))
        MAX-ACCESS read-only
        STATUS     current
        DESCRIPTION
            "Name of the virtual wireless interface.

            Applies to STA. 802.11n products only."
        ::= { cfgWlanHandoffTableEntry 2 }

    cfgWlanHoProfile OBJECT-TYPE
        SYNTAX INTEGER { t2gv1(1), t2gv2(2), t2gv2fg(3), t2gv3(4) }
        MAX-ACCESS read-write
        STATUS     current
        DESCRIPTION
            "Handoff profile.

            * **t2gv1(1):** Train to Ground v1
            * **t2gv2(2):** Train to Ground v2
            * **t2gv2fg(3):** Train to Ground v2 fg scan
            * **t2gv3(4):** Train to Ground v3 (RSSI high/low, Distance near/far)

            Applies to STA. 802.11n products only."
        ::= { cfgWlanHandoffTableEntry 3 }

    cfgWlanHoScanningLevel OBJECT-TYPE
        SYNTAX Integer32 (0..95)
        MAX-ACCESS read-write
        STATUS     current
        DESCRIPTION
            "Scanning level in RSSI.

            When the RSSI level of the currently connected access point drops
            below the value configured in this parameter, the STA will scan
            for better access points on all frequencies specified by the
            scan list configured in cfgWlanIfaceScanList and cfgWlanFreqTable.

            Applies to STA. 802.11n products only."
        ::= { cfgWlanHandoffTableEntry 5 }

    cfgWlanHoBeacons OBJECT-TYPE
        SYNTAX Integer32 (4..20)
        MAX-ACCESS read-write
        STATUS     current
        DESCRIPTION
            "Number of beacons which have to be received from an AP before a
            decision about handoff is allowed. Essentially forces the STA to
            stay on a given AP for <cfgWlanHoBeacons * cfgWlanIfaceBeaconInterval>
            before doing another handoff.

            Applies to STA. 802.11n products only."
        ::= { cfgWlanHandoffTableEntry 6 }

    cfgWlanHoRecovery OBJECT-TYPE
        SYNTAX Integer32 (0..2000)
        MAX-ACCESS read-write
        STATUS     current
        DESCRIPTION
            "Recovery time in milliseconds after a successful handoff.

            During this time no further handoff will be executed.

            Applies to STA. 802.11n products only."
        ::= { cfgWlanHandoffTableEntry 7 }

    cfgWlanHoFilterMode OBJECT-TYPE
        SYNTAX INTEGER { short(0), long(1) }
        MAX-ACCESS read-write
        STATUS     current
        DESCRIPTION
            "RSSI filter mode.

            * **short(0):** high responsive static IIR RSSI filter.
            * **long(1):** configurable IIR RSSI filter.

            Applies to STA. 802.11n products only."
        ::= { cfgWlanHandoffTableEntry 9 }

    cfgWlanHoFilterLongX OBJECT-TYPE
        SYNTAX Integer32
        MAX-ACCESS read-write
        STATUS     current
        DESCRIPTION
            "IIR Filter Parameter x for long RSSI filter.

            Applies to STA. 802.11n products only."
        ::= { cfgWlanHandoffTableEntry 10 }

    cfgWlanHoFilterLongY OBJECT-TYPE
        SYNTAX Integer32
        MAX-ACCESS read-write
        STATUS     current
        DESCRIPTION
            "IIR Filter Parameter y for long RSSI filter.

            Applies to STA. 802.11n products only."
        ::= { cfgWlanHandoffTableEntry 11 }

    cfgWlanHoScanRateLimitTime OBJECT-TYPE
        SYNTAX Integer32
        MAX-ACCESS read-write
        STATUS     current
        DESCRIPTION
            "Time in milliseconds (4ms steps) in which a number of attempts to connect
            to an AP can be tried.

            Applies to STA. 802.11n products only."
        ::= { cfgWlanHandoffTableEntry 12 }

    cfgWlanHoScanRateLimitTries OBJECT-TYPE
        SYNTAX Integer32
        MAX-ACCESS read-write
        STATUS     current
        DESCRIPTION
            "Number of attempts to connect to an AP before the AP is blacklisted
            and ignored. The AP is removed from the blacklist after
            `cfgWlanHoScanRateLimitTime` since the first attempt.

            Applies to STA. 802.11n products only."
        ::= { cfgWlanHandoffTableEntry 13 }

    cfgWlanHoPassiveChanTime OBJECT-TYPE
        SYNTAX Integer32(1..65535)
        MAX-ACCESS read-write
        STATUS     current
        DESCRIPTION
            "Time in milliseconds (4ms steps) we stay on a channel during passive
            scanning and wait for beacons.

            Applies to STA. 802.11n products only."
        ::= { cfgWlanHandoffTableEntry 16 }

    cfgWlanHoLevelLow OBJECT-TYPE
        SYNTAX Integer32
        MAX-ACCESS read-write
        STATUS     current
        DESCRIPTION
            "Scanning level low in RSSI.

            When the RSSI level to the current connected AP is below this value,
            perform a handoff to the next AP.

            This value is only active when `cfgWlanHoProfile` is set to T2Gv3.
            When configured on an AP, this value is advertised for clients to use.
            When configured on a STA, this is the default value which is used
            when the currently connected AP doesn't provide a different value.

            Applies to AP and STA. 802.11n products only."
        ::= { cfgWlanHandoffTableEntry 18 }

    cfgWlanHoLevelHigh OBJECT-TYPE
        SYNTAX Integer32
        MAX-ACCESS read-write
        STATUS     current
        DESCRIPTION
            "Scanning level high in RSSI.

            When the RSSI level to the current connected AP is above this value,
            perform a handoff to the next AP.

            This value is only active when `cfgWlanHoProfile` is set to T2Gv3.
            When configured on an AP, this value is advertised for clients to use.
            When configured on a STA, this is the default value which is used
            when the currently connected AP doesn't provide a different value.

            Applies to AP and STA. 802.11n products only."
        ::= { cfgWlanHandoffTableEntry 19 }

    cfgWlanHoDistanceNear OBJECT-TYPE
        SYNTAX Integer32 (0..114750)
        MAX-ACCESS read-write
        STATUS     current
        DESCRIPTION
            "Distance level near.

            When the measured distance to the current connected AP is below
            this value in meters, perform a handoff to the next AP.

            This value is only active when `cfgWlanHoProfile` is set to T2Gv3.
            When configured on an AP, this value is advertised for clients to use.
            When configured on a STA, this is the default value which is used
            when the currently connected AP doesn't provide a different value.

            **Note:** Distance value is not in meters.

            Applies to AP and STA. 802.11n products only."
        ::= { cfgWlanHandoffTableEntry 20 }

    cfgWlanHoDistanceFar OBJECT-TYPE
        SYNTAX Integer32 (0..114750)
        MAX-ACCESS read-write
        STATUS     current
        DESCRIPTION
            "Distance level far.

            When the measured distance to the current connected AP is above
            this value in meters, perform a handoff to the next AP.

            This value is only active when `cfgWlanHoProfile` is set to T2Gv3.
            When configured on an AP, this value is advertised for clients to use.
            When configured on a STA, this is the default value which is used
            when the currently connected AP doesn't provide a different value.

            **Note:** Distance value is not in meters.

            Applies to AP and STA. 802.11n products only."
        ::= { cfgWlanHandoffTableEntry 21 }

    cfgWlanHoDistanceMeasurementPeriod OBJECT-TYPE
        SYNTAX Integer32 (0..100000)
        MAX-ACCESS read-write
        STATUS     current
        DESCRIPTION
            "Distance ranging measurement period in milliseconds.

             Setting zero disables distance handoff. This value is only active
             when `cfgWlanHoProfile` is set to T2Gv3.

             Typical ranging measurement period values are in the range from
             200 ms to 1000 ms. Values lower than 100 ms are not recommended.

            Applies to STA. 802.11n products only."
        ::= { cfgWlanHandoffTableEntry 22 }

    cfgWlanHoDistanceFilterX OBJECT-TYPE
        SYNTAX Integer32
        MAX-ACCESS read-write
        STATUS     current
        DESCRIPTION
            "IIR Filter Parameter x for distance measurement.

            This value is only active when `cfgWlanHoProfile` is set to T2Gv3.

            Applies to STA. 802.11n products only."
        ::= { cfgWlanHandoffTableEntry 23 }

    cfgWlanHoDistanceFilterY OBJECT-TYPE
        SYNTAX Integer32
        MAX-ACCESS read-write
        STATUS     current
        DESCRIPTION
            "IIR Filter Parameter y for distance measurements.

            This value is only active when `cfgWlanHoProfile` is set to T2Gv3.

            Applies to STA. 802.11n products only."
        ::= { cfgWlanHandoffTableEntry 24 }


-- -----------------------------------------------------------------------------

    cfgWlanFreqTable OBJECT-TYPE
        SYNTAX  SEQUENCE OF CfgWlanFreqTableSeq
        MAX-ACCESS not-accessible
        STATUS     current
        DESCRIPTION
            "Frequency list entry."
        ::= { cfgWireless 4 }

    cfgWlanFreqTableEntry OBJECT-TYPE
        SYNTAX  CfgWlanFreqTableSeq
        MAX-ACCESS not-accessible
        STATUS     current
        DESCRIPTION
            "Frequency list entry."
        INDEX {cfgWlanFIndex}
        ::= { cfgWlanFreqTable 1 }

    CfgWlanFreqTableSeq ::=
        SEQUENCE {  cfgWlanFIndex Integer32,
                    cfgWlanFFreq0 Integer32,
                    cfgWlanFFreq1 Integer32,
                    cfgWlanFFreq2 Integer32,
                    cfgWlanFFreq3 Integer32,
                    cfgWlanFFreq4 Integer32,
                    cfgWlanFFreq5 Integer32,
                    cfgWlanFFreq6 Integer32,
                    cfgWlanFFreq7 Integer32,
                    cfgWlanFFreq8 Integer32,
                    cfgWlanFFreq9 Integer32,
                    cfgWlanFFreq10 Integer32,
                    cfgWlanFFreq11 Integer32,
                    cfgWlanFFreq12 Integer32,
                    cfgWlanFFreq13 Integer32,
                    cfgWlanFFreq14 Integer32,
                    cfgWlanFFreq15 Integer32,
                    cfgWlanFFreq16 Integer32,
                    cfgWlanFFreq17 Integer32,
                    cfgWlanFFreq18 Integer32,
                    cfgWlanFFreq19 Integer32,
                    cfgWlanFFreq20 Integer32,
                    cfgWlanFFreq21 Integer32,
                    cfgWlanFFreq22 Integer32,
                    cfgWlanFFreq23 Integer32
                 }

    cfgWlanFIndex OBJECT-TYPE
        SYNTAX Integer32 (0..23)
        MAX-ACCESS not-accessible
        STATUS     current
        DESCRIPTION
            "Entry index of table"
        ::= { cfgWlanFreqTableEntry 1 }

    cfgWlanFFreq0 OBJECT-TYPE
        SYNTAX Integer32
        MAX-ACCESS read-write
        STATUS     current
        DESCRIPTION
            "Frequency in MHz, 0 is interpreted as empty.

             Applies to AP and STA."
        ::= { cfgWlanFreqTableEntry 2 }

    cfgWlanFFreq1 OBJECT-TYPE
        SYNTAX Integer32
        MAX-ACCESS read-write
        STATUS     current
        DESCRIPTION
            "Frequency in MHz, 0 is interpreted as empty.

             Applies to AP and STA."
        ::= { cfgWlanFreqTableEntry 3 }

    cfgWlanFFreq2 OBJECT-TYPE
        SYNTAX Integer32
        MAX-ACCESS read-write
        STATUS     current
        DESCRIPTION
            "Frequency in MHz, 0 is interpreted as empty.

             Applies to AP and STA."
        ::= { cfgWlanFreqTableEntry 4 }

    cfgWlanFFreq3 OBJECT-TYPE
        SYNTAX Integer32
        MAX-ACCESS read-write
        STATUS     current
        DESCRIPTION
            "Frequency in MHz, 0 is interpreted as empty.

             Applies to AP and STA."
        ::= { cfgWlanFreqTableEntry 5 }

    cfgWlanFFreq4 OBJECT-TYPE
        SYNTAX Integer32
        MAX-ACCESS read-write
        STATUS     current
        DESCRIPTION
            "Frequency in MHz, 0 is interpreted as empty.

             Applies to AP and STA."
        ::= { cfgWlanFreqTableEntry 6 }

    cfgWlanFFreq5 OBJECT-TYPE
        SYNTAX Integer32
        MAX-ACCESS read-write
        STATUS     current
        DESCRIPTION
            "Frequency in MHz, 0 is interpreted as empty.

             Applies to AP and STA."
        ::= { cfgWlanFreqTableEntry 7 }

    cfgWlanFFreq6 OBJECT-TYPE
        SYNTAX Integer32
        MAX-ACCESS read-write
        STATUS     current
        DESCRIPTION
            "Frequency in MHz, 0 is interpreted as empty.

             Applies to AP and STA."
        ::= { cfgWlanFreqTableEntry 8 }

    cfgWlanFFreq7 OBJECT-TYPE
        SYNTAX Integer32
        MAX-ACCESS read-write
        STATUS     current
        DESCRIPTION
            "Frequency in MHz, 0 is interpreted as empty.

             Applies to AP and STA."
        ::= { cfgWlanFreqTableEntry 9 }

    cfgWlanFFreq8 OBJECT-TYPE
        SYNTAX Integer32
        MAX-ACCESS read-write
        STATUS     current
        DESCRIPTION
            "Frequency in MHz, 0 is interpreted as empty.

             Applies to AP and STA."
        ::= { cfgWlanFreqTableEntry 10 }

    cfgWlanFFreq9 OBJECT-TYPE
        SYNTAX Integer32
        MAX-ACCESS read-write
        STATUS     current
        DESCRIPTION
            "Frequency in MHz, 0 is interpreted as empty.

             Applies to AP and STA."
        ::= { cfgWlanFreqTableEntry 11 }

    cfgWlanFFreq10 OBJECT-TYPE
        SYNTAX Integer32
        MAX-ACCESS read-write
        STATUS     current
        DESCRIPTION
            "Frequency in MHz, 0 is interpreted as empty.

             Applies to AP and STA."
        ::= { cfgWlanFreqTableEntry 12 }

    cfgWlanFFreq11 OBJECT-TYPE
        SYNTAX Integer32
        MAX-ACCESS read-write
        STATUS     current
        DESCRIPTION
            "Frequency in MHz, 0 is interpreted as empty.

             Applies to AP and STA."
        ::= { cfgWlanFreqTableEntry 13 }

    cfgWlanFFreq12 OBJECT-TYPE
        SYNTAX Integer32
        MAX-ACCESS read-write
        STATUS     current
        DESCRIPTION
            "Frequency in MHz, 0 is interpreted as empty.

             Applies to AP and STA."
        ::= { cfgWlanFreqTableEntry 14 }

    cfgWlanFFreq13 OBJECT-TYPE
        SYNTAX Integer32
        MAX-ACCESS read-write
        STATUS     current
        DESCRIPTION
            "Frequency in MHz, 0 is interpreted as empty.

             Applies to AP and STA."
        ::= { cfgWlanFreqTableEntry 15 }

    cfgWlanFFreq14 OBJECT-TYPE
        SYNTAX Integer32
        MAX-ACCESS read-write
        STATUS     current
        DESCRIPTION
            "Frequency in MHz, 0 is interpreted as empty.

             Applies to AP and STA."
        ::= { cfgWlanFreqTableEntry 16 }

    cfgWlanFFreq15 OBJECT-TYPE
        SYNTAX Integer32
        MAX-ACCESS read-write
        STATUS     current
        DESCRIPTION
            "Frequency in MHz, 0 is interpreted as empty.

             Applies to AP and STA."
        ::= { cfgWlanFreqTableEntry 17 }

    cfgWlanFFreq16 OBJECT-TYPE
        SYNTAX Integer32
        MAX-ACCESS read-write
        STATUS     current
        DESCRIPTION
            "Frequency in MHz, 0 is interpreted as empty.

             Applies to AP and STA."
        ::= { cfgWlanFreqTableEntry 18 }

    cfgWlanFFreq17 OBJECT-TYPE
        SYNTAX Integer32
        MAX-ACCESS read-write
        STATUS     current
        DESCRIPTION
            "Frequency in MHz, 0 is interpreted as empty.

             Applies to AP and STA."
        ::= { cfgWlanFreqTableEntry 19 }

    cfgWlanFFreq18 OBJECT-TYPE
        SYNTAX Integer32
        MAX-ACCESS read-write
        STATUS     current
        DESCRIPTION
            "Frequency in MHz, 0 is interpreted as empty.

             Applies to AP and STA."
        ::= { cfgWlanFreqTableEntry 20 }

    cfgWlanFFreq19 OBJECT-TYPE
        SYNTAX Integer32
        MAX-ACCESS read-write
        STATUS     current
        DESCRIPTION
            "Frequency in MHz, 0 is interpreted as empty.

             Applies to AP and STA."
        ::= { cfgWlanFreqTableEntry 21 }

    cfgWlanFFreq20 OBJECT-TYPE
        SYNTAX Integer32
        MAX-ACCESS read-write
        STATUS     current
        DESCRIPTION
            "Frequency in MHz, 0 is interpreted as empty.

             Applies to AP and STA."
        ::= { cfgWlanFreqTableEntry 22 }

    cfgWlanFFreq21 OBJECT-TYPE
        SYNTAX Integer32
        MAX-ACCESS read-write
        STATUS     current
        DESCRIPTION
            "Frequency in MHz, 0 is interpreted as empty.

             Applies to AP and STA."
        ::= { cfgWlanFreqTableEntry 23 }

    cfgWlanFFreq22 OBJECT-TYPE
        SYNTAX Integer32
        MAX-ACCESS read-write
        STATUS     current
        DESCRIPTION
            "Frequency in MHz, 0 is interpreted as empty.

             Applies to AP and STA."
        ::= { cfgWlanFreqTableEntry 24 }

    cfgWlanFFreq23 OBJECT-TYPE
        SYNTAX Integer32
        MAX-ACCESS read-write
        STATUS     current
        DESCRIPTION
            "Frequency in MHz, 0 is interpreted as empty.

             Applies to AP and STA."
        ::= { cfgWlanFreqTableEntry 25 }

-- -----------------------------------------------------------------------------

    cfgWlanWmeTable OBJECT-TYPE
        SYNTAX  SEQUENCE OF CfgWlanWmeTableSeq
        MAX-ACCESS not-accessible
        STATUS     current
        DESCRIPTION
            "Wireless Multimedia Extensions (WME) based on the IEEE 802.11e
             standard. It provides basic Quality of Service (QoS) features to
             IEEE 802.11 networks.

             The levels of priority in EDCA are called access categories (ACs).
             The contention window (CW) can be set according to the traffic
             expected for each access category, with a wider window needed for
             categories with heavier traffic.

             Applies to AP. 802.11n products only."
        ::= { cfgWireless 5 }

    cfgWlanWmeTableEntry OBJECT-TYPE
        SYNTAX  CfgWlanWmeTableSeq
        MAX-ACCESS not-accessible
        STATUS     current
        DESCRIPTION
            "WME entry."
        INDEX {cfgWlanWmeIndex}
        ::= { cfgWlanWmeTable 1 }


    CfgWlanWmeTableSeq ::=
        SEQUENCE {  cfgWlanWmeIndex Integer32,
                    cfgWlanWmeId Integer32,
                    cfgWlanWmeAc INTEGER,
                    cfgWlanWmeCwMin Integer32,
                    cfgWlanWmeCwMax Integer32,
                    cfgWlanWmeAifs Integer32,
                    cfgWlanWmeTxOpMax Integer32,
                    cfgWlanWmeApCwMin Integer32,
                    cfgWlanWmeApCwMax Integer32,
                    cfgWlanWmeApAifs Integer32,
                    cfgWlanWmeApBurst Integer32
                 }

    cfgWlanWmeIndex OBJECT-TYPE
        SYNTAX Integer32 (0..31)
        MAX-ACCESS not-accessible
        STATUS     current
        DESCRIPTION
            "Entry index of table."
        ::= { cfgWlanWmeTableEntry 1 }

    cfgWlanWmeId OBJECT-TYPE
        SYNTAX Integer32
        MAX-ACCESS read-write
        STATUS     current
        DESCRIPTION
            "ID of the WME parameter table. The virtual wireless interface
             references to this ID.

             Applies to AP. 802.11n products only."
        ::= { cfgWlanWmeTableEntry 2 }

    cfgWlanWmeAc OBJECT-TYPE
        SYNTAX INTEGER { none(0), background(1), besteffort(2), video(3), voice(4) }
        MAX-ACCESS read-write
        STATUS     current
        DESCRIPTION
            "Access category (background, besteffort, video, voice).

             Applies to AP. 802.11n products only."
        ::= { cfgWlanWmeTableEntry 3 }

    cfgWlanWmeCwMin OBJECT-TYPE
        SYNTAX Integer32 (0..12)
        MAX-ACCESS read-write
        STATUS     current
        DESCRIPTION
            "Contention window minimum in exponential form.

             Is used on STAs connected to this AP: `Real value = (2^n)-1`

             Applies to AP. 802.11n products only."
        ::= { cfgWlanWmeTableEntry 4 }

    cfgWlanWmeCwMax OBJECT-TYPE
        SYNTAX Integer32 (0..12)
        MAX-ACCESS read-write
        STATUS     current
        DESCRIPTION
            "Contention window maximum in exponential form.

             Is used on STAs connected to this AP: `Real value = (2^n)-1`

             Applies to AP. 802.11n products only."
        ::= { cfgWlanWmeTableEntry 5 }

    cfgWlanWmeAifs OBJECT-TYPE
        SYNTAX Integer32 (1..255)
        MAX-ACCESS read-write
        STATUS     current
        DESCRIPTION
            "Arbitration inter-frame space.

             Is used on STAs connected to this AP.

             Applies to AP. 802.11n products only."
        ::= { cfgWlanWmeTableEntry 6 }

    cfgWlanWmeTxOpMax OBJECT-TYPE
        SYNTAX Integer32 (0..255)
        MAX-ACCESS read-write
        STATUS     current
        DESCRIPTION
            "A Transmit Opportunity (TXOP) is a bound time interval during which
             a station can send as many frames as possible (as long as the
             duration of the transmissions does not exceed the maximum duration
             of the TXOP). A value of 0 indicates that a single MSDU or MMPDU in
             addition to a possible RTS/CTS or CTS to itself may be transmitted
             at any PHY rate for each TXOP. This value is in units of 32 us. Is
             used on STAs connected to this AP.

             Applies to AP. 802.11n products only."
        ::= { cfgWlanWmeTableEntry 7 }

    cfgWlanWmeApCwMin OBJECT-TYPE
        SYNTAX Integer32 (1..1023)
        MAX-ACCESS read-write
        STATUS     current
        DESCRIPTION
            "Contention window minimum.

             Allowed values: 1, 3, 7, 15, 31, 63, 127, 255, 511, 1023.

             Is used on the AP itself.

             Applies to AP. 802.11n products only."
        ::= { cfgWlanWmeTableEntry 8 }

    cfgWlanWmeApCwMax OBJECT-TYPE
        SYNTAX Integer32 (1..1023)
        MAX-ACCESS read-write
        STATUS     current
        DESCRIPTION
            "Contention window maximum.

             Allowed values: 1, 3, 7, 15, 31, 63, 127, 255, 511, 1023

             cwMax has to be greater or equal cwMin. Is used on the AP itself.

             Applies to AP. 802.11n products only."
        ::= { cfgWlanWmeTableEntry 9 }

    cfgWlanWmeApAifs OBJECT-TYPE
        SYNTAX Integer32 (0..255)
        MAX-ACCESS read-write
        STATUS     current
        DESCRIPTION
            "Arbitration inter-frame space.

             Is used on the AP itself.

             Applies to AP."
        ::= { cfgWlanWmeTableEntry 10 }

    cfgWlanWmeApBurst OBJECT-TYPE
        SYNTAX Integer32 (0..255)
        MAX-ACCESS read-write
        STATUS     current
        DESCRIPTION
            "Maximum length for bursting (equivalent to TxOpLimit).

             This value is in units of 32us.
             Is used on the AP itself.

             Applies to AP. 802.11n products only."
        ::= { cfgWlanWmeTableEntry 11 }

-- -----------------------------------------------------------------------------

    cfgWlanDbgTable OBJECT-TYPE
        SYNTAX  SEQUENCE OF CfgWlanDbgTableSeq
        MAX-ACCESS not-accessible
        STATUS     current
        DESCRIPTION
            "Wireless Handoff Debug Parameters."
        ::= { cfgWireless 6 }

    cfgWlanDbgTableEntry OBJECT-TYPE
        SYNTAX  CfgWlanDbgTableSeq
        MAX-ACCESS not-accessible
        STATUS     current
        DESCRIPTION
            "Wireless Handoff Debug Parameters Entry."
        INDEX {cfgWlanDbgIndex}
        ::= { cfgWlanDbgTable 1 }

    CfgWlanDbgTableSeq ::=
        SEQUENCE {  cfgWlanDbgIndex Integer32,
                    cfgWlanDbgIfaceName DisplayString,
                    cfgWlanDbgHandoff INTEGER,
                    cfgWlanDbgScan INTEGER,
                    cfgWlanDbgMlme INTEGER,
                    cfgWlanDbgEvents INTEGER,
                    cfgWlanDbgBeaconrssi INTEGER,
                    cfgWlanDbgAckrssi INTEGER,
                    cfgWlanDbgBeaconfiltered INTEGER,
                    cfgWlanDbgRatelimit INTEGER,
                    cfgWlanDbgLinkmonitor INTEGER,
                    cfgWlanDbgBeacontsf INTEGER,
                    cfgWlanDbgRange INTEGER,
                    cfgWlanDbgReports INTEGER
                 }

    cfgWlanDbgIndex OBJECT-TYPE
        SYNTAX Integer32 (0..63)
        MAX-ACCESS not-accessible
        STATUS     current
        DESCRIPTION
            "Entry index of table."
        ::= { cfgWlanDbgTableEntry 1 }

    cfgWlanDbgIfaceName OBJECT-TYPE
        SYNTAX DisplayString (SIZE(1..255))
        MAX-ACCESS read-only
        STATUS     current
        DESCRIPTION
            "Name of the virtual wireless interface.

            Applies to STA. 802.11n products only."
        ::= { cfgWlanDbgTableEntry 2 }

    cfgWlanDbgHandoff OBJECT-TYPE
        SYNTAX INTEGER { disabled(0), enabled(1) }
        MAX-ACCESS read-write
        STATUS     current
        DESCRIPTION
            "Persistent default value to enable/disable the handoff messages in
            syslog. These log messages are subject to change. DO NOT PARSE!

            Applies to STA. 802.11n products only."
        ::= { cfgWlanDbgTableEntry 3 }

    cfgWlanDbgScan OBJECT-TYPE
        SYNTAX INTEGER { disabled(0), enabled(1) }
        MAX-ACCESS read-write
        STATUS     current
        DESCRIPTION
            "Persistent default value to enable/disable the scan messages in
            syslog. These log messages are subject to change. DO NOT PARSE!

            Applies to STA. 802.11n products only."
        ::= { cfgWlanDbgTableEntry 4 }

    cfgWlanDbgMlme OBJECT-TYPE
        SYNTAX INTEGER { disabled(0), enabled(1) }
        MAX-ACCESS read-write
        STATUS     current
        DESCRIPTION
            "Persistent default value to enable/disable the MLME messages in
            syslog. These log messages are subject to change. DO NOT PARSE!

            Applies to STA. 802.11n products only."
        ::= { cfgWlanDbgTableEntry 5 }

    cfgWlanDbgEvents OBJECT-TYPE
        SYNTAX INTEGER { disabled(0), enabled(1) }
        MAX-ACCESS read-write
        STATUS     current
        DESCRIPTION
            "Persistent default value to enable/disable the events messages in
            syslog. These log messages are subject to change. DO NOT PARSE!

            Applies to STA. 802.11n products only."
        ::= { cfgWlanDbgTableEntry 6 }

    cfgWlanDbgBeaconrssi OBJECT-TYPE
        SYNTAX INTEGER { disabled(0), enabled(1) }
        MAX-ACCESS read-write
        STATUS     current
        DESCRIPTION
            "Persistent default value to enable/disable the beacon RSSI messages
            in syslog. These log messages are subject to change. DO NOT PARSE!

            Applies to STA. 802.11n products only."
        ::= { cfgWlanDbgTableEntry 7 }

    cfgWlanDbgAckrssi OBJECT-TYPE
        SYNTAX INTEGER { disabled(0), enabled(1) }
        MAX-ACCESS read-write
        STATUS     current
        DESCRIPTION
            "Persistent default value to enable/disable the ACK RSSI messages in
            syslog. These log messages are subject to change. DO NOT PARSE!

            Applies to STA. 802.11n products only."
        ::= { cfgWlanDbgTableEntry 8 }

    cfgWlanDbgBeaconfiltered OBJECT-TYPE
        SYNTAX INTEGER { disabled(0), enabled(1) }
        MAX-ACCESS read-write
        STATUS     current
        DESCRIPTION
            "Persistent default value to enable/disable the beacon filtered RSSI
            messages in syslog. These log messages are subject to change. DO
            NOT PARSE!

            Applies to STA. 802.11n products only."
        ::= { cfgWlanDbgTableEntry 9 }

    cfgWlanDbgRatelimit OBJECT-TYPE
        SYNTAX INTEGER { disabled(0), enabled(1) }
        MAX-ACCESS read-write
        STATUS     current
        DESCRIPTION
            "Persistent default value to enable/disable the rate limiter
            messages in syslog. These log messages are subject to change. DO
            NOT PARSE!

            Applies to STA. 802.11n products only."
        ::= { cfgWlanDbgTableEntry 10 }

    cfgWlanDbgLinkmonitor OBJECT-TYPE
        SYNTAX INTEGER { disabled(0), enabled(1) }
        MAX-ACCESS read-write
        STATUS     current
        DESCRIPTION
            "Periodically sends a trap containing link information of all
            connected devices on this interface.

            Applies to both AP and STA. 802.11n products only."
        ::= { cfgWlanDbgTableEntry 11 }

    cfgWlanDbgBeacontsf OBJECT-TYPE
        SYNTAX INTEGER { disabled(0), enabled(1) }
        MAX-ACCESS read-write
        STATUS     current
        DESCRIPTION
            "Persistent default value to enable/disable the beacon RSSI messages
            in syslog. These log messages are subject to change. DO NOT PARSE!
            TS files is the TSF of the station.

            Applies to STA. 802.11n products only."
        ::= { cfgWlanDbgTableEntry 12 }

    cfgWlanDbgRange OBJECT-TYPE
        SYNTAX INTEGER { disabled(0), enabled(1) }
        MAX-ACCESS read-write
        STATUS     current
        DESCRIPTION
            "Persistent setting for distance measurement messages in syslog.

            **Note:** Distance value is not in meters.

            Applies to STA. 802.11n products only."
        ::= { cfgWlanDbgTableEntry 13 }

    cfgWlanDbgReports OBJECT-TYPE
        SYNTAX INTEGER { disabled(0), enabled(1) }
        MAX-ACCESS read-write
        STATUS     current
        DESCRIPTION
            "Persistent setting for periodical WLAN debug data reporting.

            Applies to STA. 802.11n products only."
        ::= { cfgWlanDbgTableEntry 14 }

-- -----------------------------------------------------------------------------

    cfgWlanAclWhiteTable OBJECT-TYPE
        SYNTAX  SEQUENCE OF CfgWlanAclWhiteTableSeq
        MAX-ACCESS not-accessible
        STATUS     current
        DESCRIPTION
            "Wireless MAC Access Control Whitelist"
        ::= { cfgWireless 7 }

    cfgWlanAclWhiteTableEntry OBJECT-TYPE
        SYNTAX  CfgWlanAclWhiteTableSeq
        MAX-ACCESS not-accessible
        STATUS     current
        DESCRIPTION
            "Wireless MAC Access Control Whitelist Entry."
        INDEX {cfgWlanAclWhiteIndex}
        ::= { cfgWlanAclWhiteTable 1 }

    CfgWlanAclWhiteTableSeq ::=
        SEQUENCE {  cfgWlanAclWhiteIndex Integer32,
                    cfgWlanAclWhiteEnabled INTEGER,
                    cfgWlanAclWhiteInterface DisplayString,
                    cfgWlanAclWhiteAddr DisplayString,
                    cfgWlanAclWhiteMask Integer32
                 }

    cfgWlanAclWhiteIndex OBJECT-TYPE
        SYNTAX Integer32 (0..63)
        MAX-ACCESS not-accessible
        STATUS     current
        DESCRIPTION
            "Entry index of table."
        ::= { cfgWlanAclWhiteTableEntry 1 }

    cfgWlanAclWhiteEnabled OBJECT-TYPE
        SYNTAX INTEGER { disabled(0), enabled(1) }
        MAX-ACCESS read-write
        STATUS     current
        DESCRIPTION
            "Enable this entry in the ACL.

             Applies to AP."
        ::= { cfgWlanAclWhiteTableEntry 2 }

    cfgWlanAclWhiteInterface OBJECT-TYPE
        SYNTAX DisplayString (SIZE(1..255))
        MAX-ACCESS read-write
        STATUS     current
        DESCRIPTION
            "Name of the virtual wireless interface on which this entry is
             active.

             Applies to AP."
        ::= { cfgWlanAclWhiteTableEntry 3 }

    cfgWlanAclWhiteAddr OBJECT-TYPE
        SYNTAX DisplayString (SIZE(17))
        MAX-ACCESS read-write
        STATUS     current
        DESCRIPTION
            "MAC address in the ACL.

             **Format:** `00:14:5a:02:10:42`

             Applies to AP."
        ::= { cfgWlanAclWhiteTableEntry 4 }

    cfgWlanAclWhiteMask OBJECT-TYPE
        SYNTAX Integer32 (0..48)
        MAX-ACCESS read-write
        STATUS     current
        DESCRIPTION
            "Mask of the MAC address to specify ranges of MAC addresses. To be
             used like CIDR notation of IP addresses.

             Applies to AP."
        ::= { cfgWlanAclWhiteTableEntry 5 }

    cfgWlanAclBlackTable OBJECT-TYPE
        SYNTAX  SEQUENCE OF CfgWlanAclBlackTableSeq
        MAX-ACCESS not-accessible
        STATUS     current
        DESCRIPTION
            "Wireless MAC Access Control Blacklist."
        ::= { cfgWireless 8 }

    cfgWlanAclBlackTableEntry OBJECT-TYPE
        SYNTAX  CfgWlanAclBlackTableSeq
        MAX-ACCESS not-accessible
        STATUS     current
        DESCRIPTION
            "Wireless MAC Access Control Blacklist Entry."
        INDEX {cfgWlanAclBlackIndex}
        ::= { cfgWlanAclBlackTable 1 }

    CfgWlanAclBlackTableSeq ::=
        SEQUENCE {  cfgWlanAclBlackIndex Integer32,
                    cfgWlanAclBlackEnabled INTEGER,
                    cfgWlanAclBlackInterface DisplayString,
                    cfgWlanAclBlackAddr DisplayString,
                    cfgWlanAclBlackMask Integer32
                 }

    cfgWlanAclBlackIndex OBJECT-TYPE
        SYNTAX Integer32 (0..63)
        MAX-ACCESS not-accessible
        STATUS     current
        DESCRIPTION
            "Entry index of table."
        ::= { cfgWlanAclBlackTableEntry 1 }

    cfgWlanAclBlackEnabled OBJECT-TYPE
        SYNTAX INTEGER { disabled(0), enabled(1) }
        MAX-ACCESS read-write
        STATUS     current
        DESCRIPTION
            "Enable this entry in the ACL.

             Applies to AP."
        ::= { cfgWlanAclBlackTableEntry 2 }

    cfgWlanAclBlackInterface OBJECT-TYPE
        SYNTAX DisplayString (SIZE(1..255))
        MAX-ACCESS read-write
        STATUS     current
        DESCRIPTION
            "Name of the virtual wireless interface on which this entry is
             active.

             Applies to AP."
        ::= { cfgWlanAclBlackTableEntry 3 }

    cfgWlanAclBlackAddr OBJECT-TYPE
        SYNTAX DisplayString (SIZE(17))
        MAX-ACCESS read-write
        STATUS     current
        DESCRIPTION
            "MAC address in the ACL.

             **Format:** `00:14:5a:02:10:42`

             Applies to AP."
        ::= { cfgWlanAclBlackTableEntry 4 }

    cfgWlanAclBlackMask OBJECT-TYPE
        SYNTAX Integer32 (0..48)
        MAX-ACCESS read-write
        STATUS     current
        DESCRIPTION
            "Mask of the MAC address to enable the use of ranges of MAC
             addresses. To be used like CIDR notation of IP addresses.

             Applies to AP."
        ::= { cfgWlanAclBlackTableEntry 5 }

-- -----------------------------------------------------------------------------

    cfgWlanGlobal     OBJECT IDENTIFIER ::= { cfgWireless 9 }

    cfgWlanGlblCountry OBJECT-TYPE
        SYNTAX DisplayString (SIZE(1..255))
        MAX-ACCESS read-write
        STATUS     current
        DESCRIPTION
            "Wireless country code.

             **Note:** Refer to documentation which countries are supported
             for your device.

             Applies to AP and STA."
        ::= { cfgWlanGlobal 1 }

    cfgWlanGlblLinkmonitorInterval OBJECT-TYPE
        SYNTAX Integer32 (200..60000)
        MAX-ACCESS read-write
        STATUS     current
        DESCRIPTION
            "LinkMonitor interval in milliseconds.

             A new trap is sent every <interval> milliseconds.

             **Note:** A short interval and/or numerous connections may affect
             system performance negatively.

             Applies to AP and STA. 802.11n products only."
        ::= { cfgWlanGlobal 2 }

    cfgWlanGlblLinkmonitorQmrrlogging OBJECT-TYPE
        SYNTAX INTEGER { disabled(0), enabled(1) }
        MAX-ACCESS read-write
        STATUS     current
        DESCRIPTION
            "LinkMonitor QMRR logging.

             If enabled, the QMRR statistics collected for phy0
             are periodically printed to syslog at the interval
             set in `cfgWlanGlblLinkmonitorInterval`.

             Applies to AP and STA. 802.11n products only."
        ::= { cfgWlanGlobal 3 }

    cfgWlanGlblConnectionStatusWlanInterface OBJECT-TYPE
        SYNTAX DisplayString (SIZE(4..17))
        MAX-ACCESS read-write
        STATUS     current
        DESCRIPTION
            "Persistent default of the volatile setting `swDrvConStatWlanIf`

             The value set here is used to initialize `swDrvConStatWlanIf`.
             Initialisation happens on startup or configuration change.

             Applies to AP and STA."
        ::= { cfgWlanGlobal 4 }

-- -----------------------------------------------------------------------------

    cfgWlan802dot1xTable OBJECT-TYPE
        SYNTAX  SEQUENCE OF CfgWlan802dot1xTableSeq
        MAX-ACCESS not-accessible
        STATUS     current
        DESCRIPTION
            "Wireless 802dot1x."
        ::= { cfgWireless 10 }

    cfgWlan802dot1xTableEntry OBJECT-TYPE
        SYNTAX  CfgWlan802dot1xTableSeq
        MAX-ACCESS not-accessible
        STATUS     current
        DESCRIPTION
            "Wireless 802dot1x entry."
        INDEX {cfgWlan802dot1xIndex}
        ::= { cfgWlan802dot1xTable 1 }

    CfgWlan802dot1xTableSeq ::=
        SEQUENCE {  cfgWlan802dot1xIndex Integer32,
                    cfgWlan802dot1xName DisplayString,
                    cfgWlan802dot1xOwnIpAddr IpAddress,
                    cfgWlan802dot1xAuthServerParameter Integer32,
                    cfgWlan802dot1xAcctServerParameter Integer32,
                    cfgWlan802dot1xRetryPrimaryInterval Integer32,
                    cfgWlan802dot1xInterimAccountingInterval Integer32,
                    cfgWlan802dot1xNasId DisplayString,
                    cfgWlan802dot1xEapType INTEGER,
                    cfgWlan802dot1xIdentity DisplayString,
                    cfgWlan802dot1xClientKeyPassword DisplayString,
                    cfgWlan802dot1xTlsControlParams Integer32
                 }

    cfgWlan802dot1xIndex OBJECT-TYPE
        SYNTAX Integer32 (0..63)
        MAX-ACCESS not-accessible
        STATUS     current
        DESCRIPTION
            "Entry index of table"
        ::= { cfgWlan802dot1xTableEntry 1 }

    cfgWlan802dot1xName OBJECT-TYPE
        SYNTAX DisplayString (SIZE(1..255))
        MAX-ACCESS read-only
        STATUS     current
        DESCRIPTION
            "Name of the virtual wireless interface.

             Applies to AP and STA."
        ::= { cfgWlan802dot1xTableEntry 2 }

    cfgWlan802dot1xOwnIpAddr OBJECT-TYPE
        SYNTAX IpAddress
        MAX-ACCESS read-write
        STATUS     current
        DESCRIPTION
            "The own IP address of the authenticator.
             This field is used as NAS-IP-Address RADIUS attribute.
             Set this to the IP address with which the authenticator will
             communicate with the RADIUS server.

             Applies to AP."
        ::= { cfgWlan802dot1xTableEntry 3 }

    cfgWlan802dot1xAuthServerParameter OBJECT-TYPE
        SYNTAX Integer32
        MAX-ACCESS read-write
        STATUS     current
        DESCRIPTION
            "Reference ID to the radius auth server table. Uses all parameters
             in the cfgWlan802dot1xAuthServerTable which have as
             cfgWlan802dot1xAuthSrvId the value set here.

             Applies to AP."
        ::= { cfgWlan802dot1xTableEntry 4 }

    cfgWlan802dot1xAcctServerParameter OBJECT-TYPE
        SYNTAX Integer32
        MAX-ACCESS read-write
        STATUS     current
        DESCRIPTION
            "Reference ID to the radius acct server table. Uses all parameters
             in the cfgWlan802dot1xAcctServerTable which have as
             cfgWlan802dot1xAcctSrvId the value set here.

             Applies to AP."
        ::= { cfgWlan802dot1xTableEntry 5 }

    cfgWlan802dot1xRetryPrimaryInterval OBJECT-TYPE
        SYNTAX Integer32 (0..86400)
        MAX-ACCESS read-write
        STATUS     current
        DESCRIPTION
            "Retry interval for trying to return to the primary RADIUS server
             (in seconds). RADIUS client code will automatically try to use the
             next server when the current server is not replying to requests.
             If this interval is set, primary server will be retried after
             configured amount of time even if the currently used secondary
             server is still working. Set to 0 to disable.

             Applies to AP."
        ::= { cfgWlan802dot1xTableEntry 6 }

    cfgWlan802dot1xInterimAccountingInterval OBJECT-TYPE
        SYNTAX Integer32 (0..86400)
        MAX-ACCESS read-write
        STATUS     current
        DESCRIPTION
            "Interim accounting update interval in seconds.

             If this is set (larger than 0) and acct_server is configured,
             hostapd will send interim accounting updates every N seconds. Set
             to 0 to disable.

             **Note:** If set, this overrides possible Acct-Interim-Interval
             attribute in Access-Accept message. Thus, this value should not
             be configured in hostapd.conf if RADIUS server is used to control
             the interim interval. This value should not be less 600
             (10 minutes) and must not be less than 60 (1 minute).

             Applies to AP."
        ::= { cfgWlan802dot1xTableEntry 7 }

    cfgWlan802dot1xNasId OBJECT-TYPE
        SYNTAX DisplayString (SIZE(1..48))
        MAX-ACCESS read-write
        STATUS     current
        DESCRIPTION
            "Optional NAS identifier string for RADIUS messages. When used,
             this should be unique to the NAS within the scope of the RADIUS
             server. For example, a fully qualified domain name can be used
             here. When using IEEE 802.11r, nas_identifier must be set and must
             be between 1 and 48 octets long.

             Applies to AP."
        ::= { cfgWlan802dot1xTableEntry 8 }

    cfgWlan802dot1xEapType OBJECT-TYPE
        SYNTAX INTEGER { tls(0), peap(1), ttls(2) }
        MAX-ACCESS read-write
        STATUS     current
        DESCRIPTION
            "Specify the EAP type.

             Applies to STA."
        ::= { cfgWlan802dot1xTableEntry 9 }

    cfgWlan802dot1xIdentity OBJECT-TYPE
        SYNTAX DisplayString (SIZE(1..255))
        MAX-ACCESS read-write
        STATUS     current
        DESCRIPTION
            "The identity string for EAP.

             Applies to STA."
        ::= { cfgWlan802dot1xTableEntry 10 }

    cfgWlan802dot1xClientKeyPassword OBJECT-TYPE
        SYNTAX DisplayString
        MAX-ACCESS read-write
        STATUS     current
        DESCRIPTION
            "The password to unlock the private key.

             This is only required if the key is encrypted.

             Applies to STA."
        ::= { cfgWlan802dot1xTableEntry 17 }

    cfgWlan802dot1xTlsControlParams OBJECT-TYPE
        SYNTAX Integer32 (0..3)
        MAX-ACCESS read-write
        STATUS     current
        DESCRIPTION
            "Bitfield to control TLS behaviour.

             * **0x1** ignore certificate validity time
             * **0x2** ignore ca certificate

             Applies to STA."
        ::= { cfgWlan802dot1xTableEntry 18 }

-- -----------------------------------------------------------------------------

    cfgWlan802dot1xAuthServerTable OBJECT-TYPE
        SYNTAX  SEQUENCE OF CfgWlan802dot1xAuthServerTableSeq
        MAX-ACCESS not-accessible
        STATUS     current
        DESCRIPTION
            "Wireless 802dot1x AuthServer."
        ::= { cfgWireless 11 }

    cfgWlan802dot1xAuthServerTableEntry OBJECT-TYPE
        SYNTAX  CfgWlan802dot1xAuthServerTableSeq
        MAX-ACCESS not-accessible
        STATUS     current
        DESCRIPTION
            "Wireless 802dot1x AuthServer entry."
        INDEX {cfgWlan802dot1xAuthSrvIndex}
        ::= { cfgWlan802dot1xAuthServerTable 1 }

    CfgWlan802dot1xAuthServerTableSeq ::=
        SEQUENCE {  cfgWlan802dot1xAuthSrvIndex Integer32,
                    cfgWlan802dot1xAuthSrvEnabled INTEGER,
                    cfgWlan802dot1xAuthSrvId Integer32,
                    cfgWlan802dot1xAuthSrvIpAddr IpAddress,
                    cfgWlan802dot1xAuthSrvPort Integer32,
                    cfgWlan802dot1xAuthSrvSharedSecret DisplayString
                 }

    cfgWlan802dot1xAuthSrvIndex OBJECT-TYPE
        SYNTAX Integer32 (0..255)
        MAX-ACCESS not-accessible
        STATUS     current
        DESCRIPTION
            "Entry index of table."
        ::= { cfgWlan802dot1xAuthServerTableEntry 1 }

    cfgWlan802dot1xAuthSrvEnabled OBJECT-TYPE
        SYNTAX INTEGER { disabled(0), enabled(1) }
        MAX-ACCESS read-write
        STATUS     current
        DESCRIPTION
            "Enable this entry in the auth server list.

             Applies to AP."
        ::= { cfgWlan802dot1xAuthServerTableEntry 2 }

    cfgWlan802dot1xAuthSrvId OBJECT-TYPE
        SYNTAX Integer32
        MAX-ACCESS read-write
        STATUS     current
        DESCRIPTION
            "ID of the authorisation server table. The configuration item
             cfgWlan802dot1xAuthServerParameter references to this ID.

             Applies to AP."
        ::= { cfgWlan802dot1xAuthServerTableEntry 3 }

    cfgWlan802dot1xAuthSrvIpAddr OBJECT-TYPE
        SYNTAX IpAddress
        MAX-ACCESS read-write
        STATUS     current
        DESCRIPTION
            "IP of the RADIUS server against which will be authenticated.

             Applies to AP."
        ::= { cfgWlan802dot1xAuthServerTableEntry 4 }

    cfgWlan802dot1xAuthSrvPort OBJECT-TYPE
        SYNTAX Integer32
        MAX-ACCESS read-write
        STATUS     current
        DESCRIPTION
            "Port of the RADIUS server against which will be authenticated.

             Applies to AP."
        ::= { cfgWlan802dot1xAuthServerTableEntry 5 }

    cfgWlan802dot1xAuthSrvSharedSecret OBJECT-TYPE
        SYNTAX DisplayString (SIZE(1..255))
        MAX-ACCESS read-write
        STATUS     current
        DESCRIPTION
            "Password to connect to the specified RADIUS server.

             Applies to AP."
        ::= { cfgWlan802dot1xAuthServerTableEntry 6 }

-- -----------------------------------------------------------------------------

    cfgWlan802dot1xAcctServerTable OBJECT-TYPE
        SYNTAX  SEQUENCE OF CfgWlan802dot1xAcctServerTableSeq
        MAX-ACCESS not-accessible
        STATUS     current
        DESCRIPTION
            "Wireless 802dot1x AcctServer."
        ::= { cfgWireless 12 }

    cfgWlan802dot1xAcctServerTableEntry OBJECT-TYPE
        SYNTAX  CfgWlan802dot1xAcctServerTableSeq
        MAX-ACCESS not-accessible
        STATUS     current
        DESCRIPTION
            "Wireless 802dot1x AcctServer entry."
        INDEX {cfgWlan802dot1xAcctSrvIndex}
        ::= { cfgWlan802dot1xAcctServerTable 1 }

    CfgWlan802dot1xAcctServerTableSeq ::=
        SEQUENCE {  cfgWlan802dot1xAcctSrvIndex Integer32,
                    cfgWlan802dot1xAcctSrvEnabled INTEGER,
                    cfgWlan802dot1xAcctSrvId Integer32,
                    cfgWlan802dot1xAcctSrvIpAddr IpAddress,
                    cfgWlan802dot1xAcctSrvPort Integer32,
                    cfgWlan802dot1xAcctSrvSharedSecret DisplayString
                 }

    cfgWlan802dot1xAcctSrvIndex OBJECT-TYPE
        SYNTAX Integer32 (0..255)
        MAX-ACCESS not-accessible
        STATUS     current
        DESCRIPTION
            "Entry index of table."
        ::= { cfgWlan802dot1xAcctServerTableEntry 1 }

    cfgWlan802dot1xAcctSrvEnabled OBJECT-TYPE
        SYNTAX INTEGER { disabled(0), enabled(1) }
        MAX-ACCESS read-write
        STATUS     current
        DESCRIPTION
            "Enable this entry in the acct server list.

             Applies to AP."
        ::= { cfgWlan802dot1xAcctServerTableEntry 2 }

    cfgWlan802dot1xAcctSrvId OBJECT-TYPE
        SYNTAX Integer32
        MAX-ACCESS read-write
        STATUS     current
        DESCRIPTION
            "ID of the accounting server table. The configuration item
             cfgWlan802dot1xAcctServerParameter refers to this ID.

             Applies to AP."
        ::= { cfgWlan802dot1xAcctServerTableEntry 3 }

    cfgWlan802dot1xAcctSrvIpAddr OBJECT-TYPE
        SYNTAX IpAddress
        MAX-ACCESS read-write
        STATUS     current
        DESCRIPTION
            "IP of the RADIUS accounting server.
             Set to 0.0.0.0 to disable.

             Applies to AP."
        ::= { cfgWlan802dot1xAcctServerTableEntry 4 }

    cfgWlan802dot1xAcctSrvPort OBJECT-TYPE
        SYNTAX Integer32
        MAX-ACCESS read-write
        STATUS     current
        DESCRIPTION
            "Port of the RADIUS accounting server.

             Applies to AP."
        ::= { cfgWlan802dot1xAcctServerTableEntry 5 }

    cfgWlan802dot1xAcctSrvSharedSecret OBJECT-TYPE
        SYNTAX DisplayString (SIZE(1..255))
        MAX-ACCESS read-write
        STATUS     current
        DESCRIPTION
            "Password to connect to the specified RADIUS accounting server.

             Applies to AP."
        ::= { cfgWlan802dot1xAcctServerTableEntry 6 }

-- =============================================================================

    cfgWlan802dot11rTable OBJECT-TYPE
        SYNTAX  SEQUENCE OF CfgWlan802dot11rTableSeq
        MAX-ACCESS not-accessible
        STATUS     current
        DESCRIPTION
            "Wireless 802dot11r."
        ::= { cfgWireless 13 }

    cfgWlan802dot11rTableEntry OBJECT-TYPE
        SYNTAX  CfgWlan802dot11rTableSeq
        MAX-ACCESS not-accessible
        STATUS     current
        DESCRIPTION
            "Wireless 802dot11r Entry."
        INDEX {cfgWlan802dot11rIndex}
        ::= { cfgWlan802dot11rTable 1 }

    CfgWlan802dot11rTableSeq ::=
        SEQUENCE {  cfgWlan802dot11rIndex Integer32,
                    cfgWlan802dot11rName DisplayString,
                    cfgWlan802dot11rEnabled INTEGER,
                    cfgWlan802dot11rMobilityDomain DisplayString,
                    cfgWlan802dot11rPmkR0KeyHolderIdentifier DisplayString,
                    cfgWlan802dot11rPmkR0Lifetime Integer32,
                    cfgWlan802dot11rPmkR1KeyHolderIdentifier DisplayString,
                    cfgWlan802dot11rPmkR1Push INTEGER,
                    cfgWlan802dot11rR0KHParameter Integer32,
                    cfgWlan802dot11rR1KHParameter Integer32,
                    cfgWlan802dot11rExpirationEnabled INTEGER,
                    cfgWlan802dot11rExpirationTime DisplayString,
                    cfgWlan802dot11rVlan Integer32
                 }

    cfgWlan802dot11rIndex OBJECT-TYPE
        SYNTAX Integer32 (0..63)
        MAX-ACCESS not-accessible
        STATUS     current
        DESCRIPTION
            "Entry index of Table."
        ::= { cfgWlan802dot11rTableEntry 1 }

    cfgWlan802dot11rName OBJECT-TYPE
        SYNTAX DisplayString (SIZE(1..255))
        MAX-ACCESS read-only
        STATUS     current
        DESCRIPTION
            "Name of the virtual wireless interface.

             Applies to AP and STA. 802.11n products only."
        ::= { cfgWlan802dot11rTableEntry 2 }

    cfgWlan802dot11rEnabled OBJECT-TYPE
        SYNTAX INTEGER { disabled(0), enabled(1) }
        MAX-ACCESS read-write
        STATUS     current
        DESCRIPTION
            "Enable usage of 802.11r on this device.

             Applies to AP and STA. 802.11n products only."
        ::= { cfgWlan802dot11rTableEntry 3 }

    cfgWlan802dot11rMobilityDomain OBJECT-TYPE
        SYNTAX DisplayString (SIZE(4))
        MAX-ACCESS read-write
        STATUS     current
        DESCRIPTION
            "Mobility Domain identifier (dot11FTMobilityDomainID, MDID)
             MDID is used to indicate a group of APs (within an ESS, i.e.,
             sharing the same SSID) between which a STA can use Fast BSS
             Transition. 2-octet identifier as a hex string.

             **Example**

             mobility_domain=a1b2

             Applies to AP. 802.11n products only."
        ::= { cfgWlan802dot11rTableEntry 4 }

    cfgWlan802dot11rPmkR0KeyHolderIdentifier OBJECT-TYPE
        SYNTAX DisplayString (SIZE(1..48))
        MAX-ACCESS read-only
        STATUS     current
        DESCRIPTION
            "PMK-R0 Key Holder identifier (dot11FTR0KeyHolderID).

             Configure this in the field cfgWlan802dot1xNasId.

             Applies to AP. 802.11n products only."
        ::= { cfgWlan802dot11rTableEntry 5 }

    cfgWlan802dot11rPmkR0Lifetime OBJECT-TYPE
        SYNTAX Integer32 (0..2147483647)
        MAX-ACCESS read-write
        STATUS     current
        DESCRIPTION
            "PMK-RO lifetime in seconds (dot11FTR0KeyLifetime).

             When Session-Timeout attribute is provided by RADIUS server, then
             min(Session-Timeout, cfgWlan802dot11rPmkR0Lifetime) is used.

             **Ranges**

             * 0 - Infinite lifetime (disabled)
             * 1..59 - Reserved, do not use
             * 60..2147483647 - Allowed lifetime in seconds

             Applies to AP. 802.11n products only."
        ::= { cfgWlan802dot11rTableEntry 6 }

    cfgWlan802dot11rPmkR1KeyHolderIdentifier OBJECT-TYPE
        SYNTAX DisplayString (SIZE(12))
        MAX-ACCESS read-write
        STATUS     current
        DESCRIPTION
            "PMK-R1 Key Holder identifier (dot11FTR0KeyHolderID).

             6-octet identifier as a hex string. This may be the same as the
             local MAC address. Default magic number 000102030405 means use own
             mac address (bssid).

             **Format:** `020102030405`

             Applies to AP. 802.11n products only."
        ::= { cfgWlan802dot11rTableEntry 7 }

    cfgWlan802dot11rPmkR1Push OBJECT-TYPE
        SYNTAX INTEGER { donotpush(0), push(1) }
        MAX-ACCESS read-write
        STATUS     current
        DESCRIPTION
            "Whether PMK-R1 push is enabled at R0KH.

             * **0** do not push PMK-R1 to all configured R1KHs (default).
             * **1** push PMK-R1 to all configured R1KHs whenever a new PMK-R0 is derived.

             Applies to AP. 802.11n products only."
        ::= { cfgWlan802dot11rTableEntry 9 }

    cfgWlan802dot11rR0KHParameter OBJECT-TYPE
        SYNTAX Integer32
        MAX-ACCESS read-write
        STATUS     current
        DESCRIPTION
            "Reference ID to the R0KH parameter table. Uses all parameters in
             the cfgWlan802dot11rR0KHTable which have as
             cfgWlan802dot11rR0KHTblId the value set here.

             Applies to AP. 802.11n products only."
        ::= { cfgWlan802dot11rTableEntry 10 }

    cfgWlan802dot11rR1KHParameter OBJECT-TYPE
        SYNTAX Integer32
        MAX-ACCESS read-write
        STATUS     current
        DESCRIPTION
            "Reference ID to the R1KH parameter table. Uses all parameters in
             the cfgWlan802dot11rR1KHTable which have as
             cfgWlan802dot11rR1KHTblId the value set here.

             Applies to AP. 802.11n products only."
        ::= { cfgWlan802dot11rTableEntry 11 }

    cfgWlan802dot11rExpirationEnabled OBJECT-TYPE
        SYNTAX INTEGER { disabled(0), enabled(1) }
        MAX-ACCESS read-write
        STATUS     current
        DESCRIPTION
            "Enable/disable PMK-R0/-R1 expiration forcing.

             If set to **enabled(1)**, AP forces PMK-R0s and PMK-R1s
             expiration once a day (see `cfgWlan802dot11rExpirationTime`).

             Applies to AP. 802.11n products only."
        ::= { cfgWlan802dot11rTableEntry 12 }


    cfgWlan802dot11rExpirationTime OBJECT-TYPE
        SYNTAX DisplayString (SIZE(5..5))
        MAX-ACCESS read-write
        STATUS     current
        DESCRIPTION
            "Daily PMK-R0/-R1 expiration time.

             Define time (hour:minute) at which PMK-R0s and PMK-R1s
             expiration is daily forced (if `cfgWlan802dot11rExpirationEnabled`
             is **enabled(1)**).

             The time is referenced to the local time as define in
             `cfgSysTimezone`

             **Examples**

             * 00:00 - force expiration each day at midnight
             * 01:00 - force expiration each day at 01:00
             * 23:05 - force expiration each day at 23:05

             Applies to AP. 802.11n products only."
        ::= { cfgWlan802dot11rTableEntry 13 }

    cfgWlan802dot11rVlan OBJECT-TYPE
        SYNTAX Integer32 (0..4094)
        MAX-ACCESS read-write
        STATUS     current
        DESCRIPTION
            "The 802.1q VLAN tag of 802.11r backbone traffic.

             Defines the VLAN tag with which all 802.11r managment frames
             (ethertype 0x88b7) are transmitted on the backbone.

             Setting a value of 0 disables the VLAN header and transmits the
             frames untagged.

             The priority of all tagged frames is set to 0x7.

             When this value is set to a value other than 0, make sure that
             the VLAN mode of the wireless interface `cfgNetWlanVlanMode` allows
             tagged frames. Also ensure that `cfgNetWlanTrunk` includes
             all VLANs or this specific VLAN.

             Applies to AP. 802.11n products only."
        ::= { cfgWlan802dot11rTableEntry 14 }

-- -----------------------------------------------------------------------------

    cfgWlan802dot11rR0KHTable OBJECT-TYPE
        SYNTAX  SEQUENCE OF CfgWlan802dot11rR0KHTableSeq
        MAX-ACCESS not-accessible
        STATUS     current
        DESCRIPTION
            "Wireless 802dot11r R0KH.

             List of R0KHs in the same Mobility Domain. This list is used to map
             R0KH-ID (NAS Identifier) to a destination MAC address when
             requesting PMK-R1 key from the R0KH that the STA used during the
             Initial Mobility Domain Association.

             **Format:** `<MAC address> <NAS Identifier> <128-bit key as hex string>`

             **Example**

             ~~~
             r0kh=02:01:02:03:04:05 r0kh-1.example.com 000102030405060708090a0b0c0d0e0f
             r0kh=02:01:02:03:04:06 r0kh-2.example.com 00112233445566778899aabbccddeeff
             ~~~

             Applies to AP. 802.11n products only."
        ::= { cfgWireless 14 }

    cfgWlan802dot11rR0KHTableEntry OBJECT-TYPE
        SYNTAX  CfgWlan802dot11rR0KHTableSeq
        MAX-ACCESS not-accessible
        STATUS     current
        DESCRIPTION
            "Wireless 802dot11r R0KH Entry."
        INDEX {cfgWlan802dot11rR0KHIndex}
        ::= { cfgWlan802dot11rR0KHTable 1 }

    CfgWlan802dot11rR0KHTableSeq ::=
        SEQUENCE {  cfgWlan802dot11rR0KHIndex Integer32,
                    cfgWlan802dot11rR0KHId Integer32,
                    cfgWlan802dot11rR0KHEnabled INTEGER,
                    cfgWlan802dot11rR0KHDestinationMac DisplayString,
                    cfgWlan802dot11rR0KHHID DisplayString,
                    cfgWlan802dot11rR0KHKey DisplayString
                 }

    cfgWlan802dot11rR0KHIndex OBJECT-TYPE
        SYNTAX Integer32 (0..511)
        MAX-ACCESS not-accessible
        STATUS     current
        DESCRIPTION
            "Entry index of Table."
        ::= { cfgWlan802dot11rR0KHTableEntry 1 }

    cfgWlan802dot11rR0KHId OBJECT-TYPE
        SYNTAX Integer32
        MAX-ACCESS read-write
        STATUS     current
        DESCRIPTION
            "ID of the R0KH table.

             The configuration item cfgWlan802dot11rR0KHParameter references to
             this ID.

             Applies to AP. 802.11n products only."
        ::= { cfgWlan802dot11rR0KHTableEntry 2 }

    cfgWlan802dot11rR0KHEnabled OBJECT-TYPE
        SYNTAX INTEGER { disabled(0), enabled(1) }
        MAX-ACCESS read-write
        STATUS     current
        DESCRIPTION
            "Enable this entry in the R0KH list.

             Applies to AP. 802.11n products only."
        ::= { cfgWlan802dot11rR0KHTableEntry 3 }

    cfgWlan802dot11rR0KHDestinationMac OBJECT-TYPE
        SYNTAX DisplayString (SIZE(17))
        MAX-ACCESS read-write
        STATUS     current
        DESCRIPTION
            "MAC addresses of all possible R0KHs from which PMK-R1 can be requested.

             **Format:** `02:01:02:03:04:05`

             Applies to AP. 802.11n products only."
        ::= { cfgWlan802dot11rR0KHTableEntry 4 }

    cfgWlan802dot11rR0KHHID OBJECT-TYPE
        SYNTAX DisplayString (SIZE(1..48))
        MAX-ACCESS read-write
        STATUS     current
        DESCRIPTION
            "NAS Identifier of all R0KHs to map to the MAC address.

             See the field: cfgWlan802dot11rPmkR0KeyHolderIdentifier.

             Applies to AP. 802.11n products only."
        ::= { cfgWlan802dot11rR0KHTableEntry 5 }

    cfgWlan802dot11rR0KHKey OBJECT-TYPE
        SYNTAX DisplayString (SIZE(32))
        MAX-ACCESS read-write
        STATUS     current
        DESCRIPTION
            "Static Key of the R0KH.

             Connecting R1KHs need to have this key configured.

             **Format:** `000102030405060708090a0b0c0d0e0f`

             Applies to AP. 802.11n products only."
        ::= { cfgWlan802dot11rR0KHTableEntry 6 }

-- -----------------------------------------------------------------------------

    cfgWlan802dot11rR1KHTable OBJECT-TYPE
        SYNTAX  SEQUENCE OF CfgWlan802dot11rR1KHTableSeq
        MAX-ACCESS not-accessible
        STATUS     current
        DESCRIPTION
            "Wireless 802dot11r R1KH.

             List of R1KHs in the same Mobility Domain
             This list is used to map R1KH-ID to a destination MAC address when
             sending PMK-R1 key from the R0KH. This is also the list of
             authorized R1KHs in the MD that can request PMK-R1 keys.

             **Format:** `<MAC address> <R1KH-ID> <128-bit key as hex string>`

             **Example**

             ~~~
             r1kh=02:01:02:03:04:05 02:11:22:33:44:55 000102030405060708090a0b0c0d0e0f
             r1kh=02:01:02:03:04:06 02:11:22:33:44:66 00112233445566778899aabbccddeeff
             ~~~

             Applies to AP. 802.11n products only."
        ::= { cfgWireless 15 }

    cfgWlan802dot11rR1KHTableEntry OBJECT-TYPE
        SYNTAX  CfgWlan802dot11rR1KHTableSeq
        MAX-ACCESS not-accessible
        STATUS     current
        DESCRIPTION
            "Wireless 802dot11r R1KH Entry."
        INDEX {cfgWlan802dot11rR1KHIndex}
        ::= { cfgWlan802dot11rR1KHTable 1 }

    CfgWlan802dot11rR1KHTableSeq ::=
        SEQUENCE {  cfgWlan802dot11rR1KHIndex Integer32,
                    cfgWlan802dot11rR1KHId Integer32,
                    cfgWlan802dot11rR1KHEnabled INTEGER,
                    cfgWlan802dot11rR1KHDestinationMac DisplayString,
                    cfgWlan802dot11rR1KHHID DisplayString,
                    cfgWlan802dot11rR1KHKey DisplayString
                 }

    cfgWlan802dot11rR1KHIndex OBJECT-TYPE
        SYNTAX Integer32 (0..511)
        MAX-ACCESS not-accessible
        STATUS     current
        DESCRIPTION
            "Entry index of Table."
        ::= { cfgWlan802dot11rR1KHTableEntry 1 }

    cfgWlan802dot11rR1KHId OBJECT-TYPE
        SYNTAX Integer32
        MAX-ACCESS read-write
        STATUS     current
        DESCRIPTION
            "ID of the R1KH table.

             The configuration item cfgWlan802dot11rR1KHParameter references to
             this ID.

             Applies to AP."
        ::= { cfgWlan802dot11rR1KHTableEntry 2 }

    cfgWlan802dot11rR1KHEnabled OBJECT-TYPE
        SYNTAX INTEGER { disabled(0), enabled(1) }
        MAX-ACCESS read-write
        STATUS     current
        DESCRIPTION
            "Enable this entry in the R1KH list.

             Applies to AP. 802.11n products only."
        ::= { cfgWlan802dot11rR1KHTableEntry 3 }

    cfgWlan802dot11rR1KHDestinationMac OBJECT-TYPE
        SYNTAX DisplayString (SIZE(17))
        MAX-ACCESS read-write
        STATUS     current
        DESCRIPTION
            "MAC addresses of all R1KHs which can reqest PMK-R1 from the local
             R0KH.

             **Format:** `02:01:02:03:04:05`

             Applies to AP."
        ::= { cfgWlan802dot11rR1KHTableEntry 4 }

    cfgWlan802dot11rR1KHHID OBJECT-TYPE
        SYNTAX DisplayString (SIZE(17))
        MAX-ACCESS read-write
        STATUS     current
        DESCRIPTION
            "PMK-R1 Key Holder identifier (dot11FTR1KeyHolderID)

             6-octet identifier as a hex string to map to the MAC. This may be
             the same as the destination MAC. See the field
             cfgWlan802dot11rPmkR1KeyHolderIdentifier.

             **Format:** `02:01:02:03:04:05`

             Applies to AP. 802.11n products only."
        ::= { cfgWlan802dot11rR1KHTableEntry 5 }

    cfgWlan802dot11rR1KHKey OBJECT-TYPE
        SYNTAX DisplayString (SIZE(32))
        MAX-ACCESS read-write
        STATUS     current
        DESCRIPTION
            "Static Key of the R0KH.

             These keys are used wenn sending updates to R1KHs from the local
             R0KH. The respective key has to match the respective entry on the
             target in the field cfgWlan802dot11rR0KHKey.

             **Format:** `000102030405060708090a0b0c0d0e0f`

             Applies to AP. 802.11n products only."
        ::= { cfgWlan802dot11rR1KHTableEntry 6 }

-- -----------------------------------------------------------------------------

    cfgWlanNeighbourTable OBJECT-TYPE
        SYNTAX  SEQUENCE OF CfgWlanNeighbourTableSeq
        MAX-ACCESS not-accessible
        STATUS     current
        DESCRIPTION
            "Hostapd Neighbour Table."
        ::= { cfgWireless 16 }

    cfgWlanNeighbourTableEntry OBJECT-TYPE
        SYNTAX  CfgWlanNeighbourTableSeq
        MAX-ACCESS not-accessible
        STATUS     current
        DESCRIPTION
            "Hostapd Neighbour Table Entry."
        INDEX {cfgWlanNeighbourIndex}
        ::= { cfgWlanNeighbourTable 1 }

    CfgWlanNeighbourTableSeq ::=
        SEQUENCE {  cfgWlanNeighbourIndex Integer32,
                    cfgWlanNeighbourId Integer32,
                    cfgWlanNeighbourEnabled INTEGER,
                    cfgWlanNeighbourBSSID DisplayString,
                    cfgWlanNeighbourFrequency Integer32
                 }

    cfgWlanNeighbourIndex OBJECT-TYPE
        SYNTAX Integer32 (0..511)
        MAX-ACCESS not-accessible
        STATUS     current
        DESCRIPTION
            "Entry index of Table."
        ::= { cfgWlanNeighbourTableEntry 1 }

    cfgWlanNeighbourId OBJECT-TYPE
        SYNTAX Integer32
        MAX-ACCESS read-write
        STATUS     current
        DESCRIPTION
            "ID of the neighbour table. The configuration item
             `cfgWlanIfaceNeighbourParameter` references to this ID.

             Applies to AP. 802.11n products only."
        ::= { cfgWlanNeighbourTableEntry 2 }

    cfgWlanNeighbourEnabled OBJECT-TYPE
        SYNTAX INTEGER { disabled(0), enabled(1) }
        MAX-ACCESS read-write
        STATUS     current
        DESCRIPTION
            "Enable this entry in the list.

             Applies to AP. 802.11n products only."
        ::= { cfgWlanNeighbourTableEntry 3 }

    cfgWlanNeighbourBSSID OBJECT-TYPE
        SYNTAX DisplayString (SIZE(17))
        MAX-ACCESS read-write
        STATUS     current
        DESCRIPTION
            "BSSID (MAC address) of the neighbour.

             **Format:** `00:14:5a:02:10:42`

             Applies to AP."
        ::= { cfgWlanNeighbourTableEntry 4 }

    cfgWlanNeighbourFrequency OBJECT-TYPE
        SYNTAX Integer32 (1..6000)
        MAX-ACCESS read-write
        STATUS     current
        DESCRIPTION
            "Frequency in MHz of the neighbour.

             Applies to AP. 802.11n products only."
        ::= { cfgWlanNeighbourTableEntry 5 }
-- =============================================================================

-- Routing

    cfgRouteDefault     OBJECT IDENTIFIER ::= { cfgRouting 1 }

    cfgRouteDefGateway OBJECT-TYPE
        SYNTAX IpAddress
        MAX-ACCESS read-write
        STATUS     current
        DESCRIPTION
            "The default gateway defines the node on an IP network that serves
             as a router for any other network which is not defined in the
             routing table.

             Applies to AP and STA."
        ::= { cfgRouteDefault 1 }

    cfgRouteDefGwOverride OBJECT-TYPE
        SYNTAX INTEGER { disabled(0), enabled(1) }
        MAX-ACCESS read-write
        STATUS     current
        DESCRIPTION
            "Override a default gateway previously received via DHCP with the
             value in cfgRouteDefGateway. If this is disabled and a default
             gateway already exists it will not be changed.

             Applies to AP and STA."
        ::= { cfgRouteDefault 2 }

-- -----------------------------------------------------------------------------

    cfgRouteTable OBJECT-TYPE
        SYNTAX  SEQUENCE OF CfgRouteTableSeq
        MAX-ACCESS not-accessible
        STATUS     current
        DESCRIPTION
            "Static routes"
        ::= { cfgRouting 2 }

    cfgRouteTableEntry OBJECT-TYPE
        SYNTAX  CfgRouteTableSeq
        MAX-ACCESS not-accessible
        STATUS     current
        DESCRIPTION
            "Static route."
        INDEX {cfgRouteTableIndex}
        ::= { cfgRouteTable 1 }

    CfgRouteTableSeq ::=
        SEQUENCE {  cfgRouteTableIndex Integer32,
                    cfgRouteTableEnabled INTEGER,
                    cfgRouteTableDestinationNetwork DisplayString,
                    cfgRouteTableGateway IpAddress,
                    cfgRouteTableSource IpAddress,
                    cfgRouteTableCarpId Integer32
                 }

    cfgRouteTableIndex OBJECT-TYPE
        SYNTAX  Integer32 (0..265)
        MAX-ACCESS not-accessible
        STATUS     current
        DESCRIPTION
            "Entry index of table."
        ::= { cfgRouteTableEntry 1 }

    cfgRouteTableEnabled OBJECT-TYPE
        SYNTAX  INTEGER { disabled(0), enabled(1) }
        MAX-ACCESS read-write
        STATUS     current
        DESCRIPTION
            "Enable/Disable this route entry.

             Applies to AP and STA."
        ::= { cfgRouteTableEntry 2 }

    cfgRouteTableDestinationNetwork OBJECT-TYPE
        SYNTAX  DisplayString
        MAX-ACCESS read-write
        STATUS     current
        DESCRIPTION
            "Destination network in CIDR notation.

             Applies to AP and STA."
        ::= { cfgRouteTableEntry 3 }

    cfgRouteTableGateway OBJECT-TYPE
        SYNTAX  IpAddress
        MAX-ACCESS read-write
        STATUS     current
        DESCRIPTION
            "Gateway to destination network.

             Applies to AP and STA."
        ::= { cfgRouteTableEntry 5 }

    cfgRouteTableSource OBJECT-TYPE
        SYNTAX  IpAddress
        MAX-ACCESS read-write
        STATUS     current
        DESCRIPTION
            "Source for traffic to destination network.

             Optional. Use only if you have multiple possible sources.

             Applies to AP and STA."
        ::= { cfgRouteTableEntry 6 }

    cfgRouteTableCarpId OBJECT-TYPE
        SYNTAX  Integer32 (-1..15)
        MAX-ACCESS read-write
        STATUS     current
        DESCRIPTION
            "The CARP instance which brings this route up.

             Has to be set to -1 when this is a normal route and should not be
             handled by a CARP instance.
             All routes which have a value 0..15 are brought up by the respective
             CARP instance when it becomes a master for an IP.
             This allows to create routes which are routed over a CARP-Address.

             Applies to AP and STA."
        ::= { cfgRouteTableEntry 8 }


-- -----------------------------------------------------------------------------

    cfgMRouteTable OBJECT-TYPE
        SYNTAX  SEQUENCE OF CfgMRouteTableSeq
        MAX-ACCESS not-accessible
        STATUS     current
        DESCRIPTION
            "Static multicast routes."
        ::= { cfgRouting 3 }

    cfgMRouteTableEntry OBJECT-TYPE
        SYNTAX  CfgMRouteTableSeq
        MAX-ACCESS not-accessible
        STATUS     current
        DESCRIPTION
            "Static multicast routes."
        INDEX {cfgMRouteTableIndex}
        ::= { cfgMRouteTable 1 }

    CfgMRouteTableSeq ::=
        SEQUENCE {  cfgMRouteTableIndex Integer32,
                    cfgMRouteTableEnabled INTEGER,
                    cfgMRouteTableInput DisplayString,
                    cfgMRouteTableSource IpAddress,
                    cfgMRouteTableGroup IpAddress,
                    cfgMRouteTableOutput DisplayString
                 }

    cfgMRouteTableIndex OBJECT-TYPE
        SYNTAX  Integer32 (0..255)
        MAX-ACCESS not-accessible
        STATUS     current
        DESCRIPTION
            "Entry index of table."
        ::= { cfgMRouteTableEntry 1 }

    cfgMRouteTableEnabled OBJECT-TYPE
        SYNTAX  INTEGER { disabled(0), enabled(1) }
        MAX-ACCESS read-write
        STATUS     current
        DESCRIPTION
            "Enable/Disable this multicast route entry.

             Applies to AP and STA."
        ::= { cfgMRouteTableEntry 2 }

    cfgMRouteTableInput OBJECT-TYPE
        SYNTAX DisplayString (SIZE(1..255))
        MAX-ACCESS read-write
        STATUS     current
        DESCRIPTION
            "Input interface.

             Applies to AP and STA."
        ::= { cfgMRouteTableEntry 3 }


    cfgMRouteTableSource OBJECT-TYPE
        SYNTAX  IpAddress
        MAX-ACCESS read-write
        STATUS     current
        DESCRIPTION
            "Unicast source address to listen to.

             If it is set to 0.0.0.0 all multicast traffic will be forwarded.

             Applies to AP and STA."
        ::= { cfgMRouteTableEntry 4 }

    cfgMRouteTableGroup OBJECT-TYPE
        SYNTAX  IpAddress
        MAX-ACCESS read-write
        STATUS     current
        DESCRIPTION
            "Multicast group to forward.

             Applies to AP and STA."
        ::= { cfgMRouteTableEntry 5 }

    cfgMRouteTableOutput OBJECT-TYPE
        SYNTAX DisplayString (SIZE(1..255))
        MAX-ACCESS read-write
        STATUS     current
        DESCRIPTION
            "Output interface(s).

             Can be a list of interface names separated by spaces.

             Applies to AP and STA."
        ::= { cfgMRouteTableEntry 6 }

-- =============================================================================
-- Quality of Service (QoS)

    cfgQosL3PrioEnabled OBJECT-TYPE
        SYNTAX INTEGER { disabled(0), enabled(1) }
        MAX-ACCESS read-write
        STATUS     current
        DESCRIPTION
            "Layer 3 Prioritization. Controls IP Precedence based priority
             assignments.

             Actual prioritization on the wireless link only occurs if
             `cfgQosWmeEnabled` is enabled as well.

             Applies to AP and STA. 802.11n products only."
        ::= { cfgQos 1 }

    cfgQosDscpToTidMapTable OBJECT-TYPE
        SYNTAX  SEQUENCE OF CfgQosDscpToTidMapTableSeq
        MAX-ACCESS not-accessible
        STATUS     current
        DESCRIPTION
            "Mapping table from DSCP class selector (IP TOS) to
            wireless priority (TID)."
        ::= { cfgQos 2 }

    cfgQosDscpToTidMapTableEntry OBJECT-TYPE
        SYNTAX  CfgQosDscpToTidMapTableSeq
        MAX-ACCESS not-accessible
        STATUS     current
        DESCRIPTION
            "QoS DSCP to TID Mapping Table Entry."
        INDEX {cfgQosDscpToTidMapTableIndex}
        ::= { cfgQosDscpToTidMapTable 1 }

    CfgQosDscpToTidMapTableSeq ::=
        SEQUENCE {  cfgQosDscpToTidMapTableIndex  Integer32,
                    cfgQosDscpToTidMapValue  Integer32}

    cfgQosDscpToTidMapTableIndex OBJECT-TYPE
        SYNTAX  Integer32 (0..7)
        MAX-ACCESS not-accessible
        STATUS     current
        DESCRIPTION
            "QoS DSCP to TID Mapping Table Index."
        ::= { cfgQosDscpToTidMapTableEntry 1 }

    cfgQosDscpToTidMapValue OBJECT-TYPE
        SYNTAX  Integer32 (0..7)
        MAX-ACCESS read-write
        STATUS     current
        DESCRIPTION
            "Layer 2 priorities for IP precedence values 0-7.

             Applies to AP and STA. 802.11n products only."
        ::= { cfgQosDscpToTidMapTableEntry 2 }


    cfgQosVlanToTidMapTable OBJECT-TYPE
        SYNTAX  SEQUENCE OF CfgQosVlanToTidMapTableSeq
        MAX-ACCESS not-accessible
        STATUS     current
        DESCRIPTION
            "Mapping table from layer 2 priorities (802.1p)
             to wireless priority (TID)."
        ::= { cfgQos 3 }

    cfgQosVlanToTidMapTableEntry OBJECT-TYPE
        SYNTAX  CfgQosVlanToTidMapTableSeq
        MAX-ACCESS not-accessible
        STATUS     current
        DESCRIPTION
            "QoS Vlan to TID Priority Table Entry."
        INDEX {cfgQosVlanToTidMapTableIndex}
        ::= { cfgQosVlanToTidMapTable 1 }

    CfgQosVlanToTidMapTableSeq ::=
        SEQUENCE {  cfgQosVlanToTidMapTableIndex  Integer32,
                    cfgQosVlanToTidMapValue  Integer32}

    cfgQosVlanToTidMapTableIndex OBJECT-TYPE
        SYNTAX  Integer32 (0..7)
        MAX-ACCESS not-accessible
        STATUS     current
        DESCRIPTION
            "QoS Vlan to TID Priority Table Entry Index."
        ::= { cfgQosVlanToTidMapTableEntry 1 }

    cfgQosVlanToTidMapValue OBJECT-TYPE
        SYNTAX  Integer32 (0..7)
        MAX-ACCESS read-write
        STATUS     current
        DESCRIPTION
            "Layer 2 priorities for VLAN priorities 0-7.

             Applies to AP and STA. 802.11n products only."
        ::= { cfgQosVlanToTidMapTableEntry 2 }


    cfgQosIpToTidMapTable OBJECT-TYPE
        SYNTAX  SEQUENCE OF CfgQosIpToTidMapTableSeq
        MAX-ACCESS not-accessible
        STATUS     current
        DESCRIPTION
            "Mapping table from IP header (Source, Destination, Protocol, Port),
            to wireless priority (TID)."
        ::= { cfgQos 4 }

    cfgQosIpToTidMapTableEntry OBJECT-TYPE
        SYNTAX  CfgQosIpToTidMapTableSeq
        MAX-ACCESS not-accessible
        STATUS     current
        DESCRIPTION
            "IP to TID Priority Table Entry."
        INDEX {cfgQosIpToTidMapTableIndex}
        ::= { cfgQosIpToTidMapTable 1 }

    CfgQosIpToTidMapTableSeq ::=
        SEQUENCE {  cfgQosIpToTidMapTableIndex Integer32,
                    cfgQosIpToTidMapSrcNet     OCTET STRING,
                    cfgQosIpToTidMapDestNet    OCTET STRING,
                    cfgQosIpToTidMapProto      INTEGER,
                    cfgQosIpToTidMapSrcPort    Integer32,
                    cfgQosIpToTidMapDestPort   Integer32,
                    cfgQosIpToTidMapPrecedence Integer32,
                    cfgQosIpToTidMapEnabled    INTEGER}

    cfgQosIpToTidMapTableIndex OBJECT-TYPE
        SYNTAX  Integer32 (0..127)
        MAX-ACCESS not-accessible
        STATUS     current
        DESCRIPTION
            "IP to TID Priority Table Index."
        ::= { cfgQosIpToTidMapTableEntry 1 }

    cfgQosIpToTidMapSrcNet OBJECT-TYPE
        SYNTAX  OCTET STRING
        MAX-ACCESS read-write
        STATUS     current
        DESCRIPTION
            "Source network for ip prioritization rule, in CIDR format.

             Applies to AP and STA. 802.11n products only."
        ::= { cfgQosIpToTidMapTableEntry 2 }

    cfgQosIpToTidMapDestNet OBJECT-TYPE
        SYNTAX  OCTET STRING
        MAX-ACCESS read-write
        STATUS     current
        DESCRIPTION
            "Destination network for ip prioritization rule, in CIDR format.

             Applies to AP and STA. 802.11n products only."
        ::= { cfgQosIpToTidMapTableEntry 3 }

    cfgQosIpToTidMapProto OBJECT-TYPE
        SYNTAX INTEGER { any(0), udp(1), tcp(2) }
        MAX-ACCESS read-write
        STATUS     current
        DESCRIPTION
            "Protocol for ip prioritization rule, allowed protocols are:
             **any(0)**, **udp(1)** or **tcp(2)**.

             Applies to AP and STA. 802.11n products only."
        ::= { cfgQosIpToTidMapTableEntry 4 }

    cfgQosIpToTidMapSrcPort OBJECT-TYPE
        SYNTAX  Integer32 (-1..65536)
        MAX-ACCESS read-write
        STATUS     current
        DESCRIPTION
            "Source port for ip prioritization rule, use port -1 to match any
             port.

             This setting can only be used if the protocol is set to udp or tcp.

             Applies to AP and STA. 802.11n products only."
        ::= { cfgQosIpToTidMapTableEntry 5 }

    cfgQosIpToTidMapDestPort OBJECT-TYPE
        SYNTAX  Integer32 (-1..65536)
        MAX-ACCESS read-write
        STATUS     current
        DESCRIPTION
            "Destination port for ip prioritization rule, use port -1 to match
             any port.

             This setting can only be used if the protocol is set to udp or tcp.

             Applies to AP and STA. 802.11n products only."
        ::= { cfgQosIpToTidMapTableEntry 6 }

    cfgQosIpToTidMapPrecedence OBJECT-TYPE
        SYNTAX  Integer32 (0..7)
        MAX-ACCESS read-write
        STATUS     current
        DESCRIPTION
            "Precedence to set for ip prioritization rule.

             Applies to AP and STA. 802.11n products only."
        ::= { cfgQosIpToTidMapTableEntry 7 }

    cfgQosIpToTidMapEnabled OBJECT-TYPE
        SYNTAX INTEGER { disabled(0), enabled(1) }
        MAX-ACCESS read-write
        STATUS     current
        DESCRIPTION
            "Enable/disable ip prioritisation rules.

             Applies to AP and STA. 802.11n products only."
        ::= { cfgQosIpToTidMapTableEntry 8 }

-- =============================================================================

-- Logging

-- -----------------------------------------------------------------------------

    cfgLogRemote     OBJECT IDENTIFIER ::= { cfgLogging 2 }

    cfgLogRemoteTable OBJECT-TYPE
        SYNTAX  SEQUENCE OF CfgLogRemoteTableSeq
        MAX-ACCESS not-accessible
        STATUS     current
        DESCRIPTION
            "List of syslog destinations."
        ::= { cfgLogRemote 1 }

    cfgLogRemoteTableEntry OBJECT-TYPE
        SYNTAX  CfgLogRemoteTableSeq
        MAX-ACCESS not-accessible
        STATUS     current
        DESCRIPTION
            "List of syslog destinations."
        INDEX {cfgLogRemoteIndex}
        ::= { cfgLogRemoteTable 1 }

    CfgLogRemoteTableSeq ::=
        SEQUENCE {  cfgLogRemoteIndex Integer32,
                    cfgLogRemoteEnabled INTEGER,
                    cfgLogRemoteLevel INTEGER,
                    cfgLogRemoteProtocol INTEGER,
                    cfgLogRemoteIp IpAddress,
                    cfgLogRemotePort Integer32
                 }

    cfgLogRemoteIndex OBJECT-TYPE
        SYNTAX  Integer32 (0..1)
        MAX-ACCESS not-accessible
        STATUS     current
        DESCRIPTION
            "Entry index of table"
        ::= { cfgLogRemoteTableEntry 1 }

    cfgLogRemoteEnabled OBJECT-TYPE
        SYNTAX INTEGER { disabled(0), enabled(1) }
        MAX-ACCESS read-write
        STATUS     current
        DESCRIPTION
            "Log messages to file.

             Applies to AP and STA."
        ::= { cfgLogRemoteTableEntry 2 }

    cfgLogRemoteLevel OBJECT-TYPE
        SYNTAX INTEGER { emergency(0), alert(1), critical(2), error(3), warning(4), notice(5), info(6), debug(7) }
        MAX-ACCESS read-only
        STATUS     current
        DESCRIPTION
            "Log only messages with equal or higher priority than prio N (0-7).

             Applies to AP and STA."
        ::= { cfgLogRemoteTableEntry 3 }

    cfgLogRemoteProtocol OBJECT-TYPE
        SYNTAX INTEGER { udp(0), tcp(1) }
        MAX-ACCESS read-write
        STATUS     current
        DESCRIPTION
            "Protocol to send log messages. The udp(0) protocol complies with
             the standard syslog protocol.

             Applies to AP and STA."
        ::= { cfgLogRemoteTableEntry 4 }

    cfgLogRemoteIp OBJECT-TYPE
        SYNTAX IpAddress
        MAX-ACCESS read-write
        STATUS     current
        DESCRIPTION
            "Remote IP address.

             Applies to AP and STA."
        ::= { cfgLogRemoteTableEntry 5 }

    cfgLogRemotePort OBJECT-TYPE
        SYNTAX Integer32
        MAX-ACCESS read-write
        STATUS     current
        DESCRIPTION
            "Remote port.

             Applies to AP and STA."
        ::= { cfgLogRemoteTableEntry 6 }

-- =============================================================================

-- Snmp

    cfgSnmpd             OBJECT IDENTIFIER ::= { cfgSnmp 1 }

    cfgSnmpdLocation OBJECT-TYPE
        SYNTAX DisplayString (SIZE(1..255))
        MAX-ACCESS read-write
        STATUS     current
        DESCRIPTION
            "SNMP system location.

             Applies to AP and STA."
        ::= { cfgSnmpd 1 }

    cfgSnmpdContact OBJECT-TYPE
        SYNTAX DisplayString (SIZE(1..255))
        MAX-ACCESS read-write
        STATUS     current
        DESCRIPTION
            "SNMP contact.

             Applies to AP and STA."
        ::= { cfgSnmpd 2 }

    cfgSnmpdVersion OBJECT-TYPE
        SYNTAX INTEGER { v2c(0), v3usm(1) }
        MAX-ACCESS read-write
        STATUS     current
        DESCRIPTION
            "SNMP version, either **v2c(0)** or **v3usm(1)**, for the users
             admin, maintainer and monitor.

             Please refer to the user guide for more information about the
             access rights of the three predefined users.

             The User-based Security Model (USM), which is the default
             Security Module for SNMPv3, with the authentication type SHA1
             and the privacy protocol AES128 is implemented and can be chosen by
             setting this value to **v3usm(1)**.

             Setting **v3usm(1)** disables access to the device via SNMPv2.

             SNMPv3 USM configuration:

             * **User:** admin, maintainer or monitor
             * **Authentication Protocol:** SHA
             * **Privacy Protocol:** AES

             Applies to AP and STA."
        ::= { cfgSnmpd 3 }

    cfgSnmpdName OBJECT-TYPE
        SYNTAX DisplayString (SIZE(1..255))
        MAX-ACCESS read-write
        STATUS     current
        DESCRIPTION
            "SNMP node name often used in NMS.

             By convention, this is the node's fully-qualified domain name.

             Applies to AP and STA."
        ::= { cfgSnmpd 4 }

    cfgSnmpdEnabled OBJECT-TYPE
        SYNTAX INTEGER { disabled(0), enabled(1) }
        MAX-ACCESS read-write
        STATUS     current
        DESCRIPTION
            "Enable or disable the SNMP Agent.

             Applies to AP and STA."
        ::= { cfgSnmpd 5 }

    cfgSnmpdAddress OBJECT-TYPE
        SYNTAX DisplayString (SIZE(1..255))
        MAX-ACCESS read-write
        STATUS     current
        DESCRIPTION
            "Address to which the SNMP Agent binds.

             The default is 'udp:0.0.0.0:161'.
             When defining a configuration, default arguments may be ommited.
             Multiple space and/or comma separated tuples are allowed.

             Supported tranport protocols are:

             * UDP

             **Examples**

             * udp:192.168.1.20:161
             * 192.168.1.20, 10.0.0.1:10161, udp:172.16.32.32:30161
             * 192.168.1.20 10.0.0.1:10161 udp:172.16.32.32:30161

             More at http://www.net-snmp.org/docs/man/snmpd.examples.html#lbAE

             Applies to AP and STA."
        ::= { cfgSnmpd 6 }

-- -----------------------------------------------------------------------------

    cfgSnmpdCommunity     OBJECT IDENTIFIER ::= { cfgSnmpd 100 }

    cfgSnmpdComAdmin OBJECT-TYPE
        SYNTAX DisplayString (SIZE(1..255))
        MAX-ACCESS read-write
        STATUS     current
        DESCRIPTION
            "Password for the administrator.

             This is the community or the passphrase for the user administrator
             depending on the cfgSnmpdVersion:

             * **v2c:** community string for administrator
             * **v3usm:** passphrase for authentication and privacy for user admin

             Applies to AP and STA."
        ::= { cfgSnmpdCommunity 1 }

    cfgSnmpdComMaintainer OBJECT-TYPE
        SYNTAX DisplayString (SIZE(1..255))
        MAX-ACCESS read-write
        STATUS     current
        DESCRIPTION
            "Password for the maintainer.

             This is the community or the passphrase for the user maintainer
             depending on the cfgSnmpdVersion:

             * **v2c:** community string for maintainer
             * **v3usm:** passphrase for authentication and privacy for user
               maintainer

             Applies to AP and STA."
        ::= { cfgSnmpdCommunity 2 }

    cfgSnmpdComMonitor OBJECT-TYPE
        SYNTAX DisplayString (SIZE(1..255))
        MAX-ACCESS read-write
        STATUS     current
        DESCRIPTION
            "Password for the monitor.

             This is the community or the passphrase for the user monitor
             depending on the cfgSnmpdVersion:

             * **v2c:** community string for monitor
             * **v3usm:** passphrase for authentication and privacy for user
               monitor

             Applies to AP and STA."
        ::= { cfgSnmpdCommunity 3 }

-- -----------------------------------------------------------------------------

    cfgSnmpTrap     OBJECT IDENTIFIER ::= { cfgSnmp 10 }

    cfgSnmpTrapEnabled OBJECT-TYPE
        SYNTAX INTEGER { disabled(0), enabled(1) }
        MAX-ACCESS read-write
        STATUS     current
        DESCRIPTION
            "Enable sending of SNMP traps.

             Applies to AP and STA."
        ::= { cfgSnmpTrap 1 }

    cfgSnmpTrapVersion OBJECT-TYPE
        SYNTAX INTEGER { v1(0), v2c(1), v3usm(2) }
        MAX-ACCESS read-write
        STATUS     current
        DESCRIPTION
            "SNMP version with which traps are sent.

             Applies to AP and STA."
        ::= { cfgSnmpTrap 2 }

    cfgSnmpTrapCommunity OBJECT-TYPE
        SYNTAX DisplayString (SIZE(1..255))
        MAX-ACCESS read-write
        STATUS     current
        DESCRIPTION
            "SNMP community if SNMP v2c is used.

             If SNMP v3 is used the community string is the password.

             Applies to AP and STA."
        ::= { cfgSnmpTrap 3 }

    cfgSnmpTrapDest OBJECT-TYPE
        SYNTAX IpAddress
        MAX-ACCESS read-write
        STATUS     current
        DESCRIPTION
            "IP address of the trap receiver.

             Applies to AP and STA."
        ::= { cfgSnmpTrap 4 }

-- =============================================================================

-- DHCP

    cfgDhcpGlobal     OBJECT IDENTIFIER ::= { cfgDhcp 1 }

    cfgDhcpGlobalEnabled OBJECT-TYPE
        SYNTAX INTEGER { disabled(0), enabled(1) }
        MAX-ACCESS read-write
        STATUS     current
        DESCRIPTION
            "Enable DHCP server functionality.
            "
        ::= { cfgDhcpGlobal 1 }

-- -----------------------------------------------------------------------------

    cfgDhcpDnsmasqTable OBJECT-TYPE
        SYNTAX  SEQUENCE OF CfgDhcpDnsmasqTableSeq
        MAX-ACCESS not-accessible
        STATUS     current
        DESCRIPTION
            "DHCP Dnsmasq instances."
        ::= { cfgDhcp 2 }

    cfgDhcpDnsmasqTableEntry OBJECT-TYPE
        SYNTAX  CfgDhcpDnsmasqTableSeq
        MAX-ACCESS not-accessible
        STATUS     current
        DESCRIPTION
            "DHCP Dnsmasq instances."
        INDEX {cfgDhcpDnsmasqIndex}
        ::= { cfgDhcpDnsmasqTable 1 }

    CfgDhcpDnsmasqTableSeq ::=
        SEQUENCE {  cfgDhcpDnsmasqIndex Integer32,
                    cfgDhcpDnsmasqScopeParameter Integer32
                 }

    cfgDhcpDnsmasqIndex OBJECT-TYPE
        SYNTAX Integer32 (0..9)
        MAX-ACCESS not-accessible
        STATUS     current
        DESCRIPTION
            "Entry index of table."
        ::= { cfgDhcpDnsmasqTableEntry 1 }

    cfgDhcpDnsmasqScopeParameter OBJECT-TYPE
        SYNTAX Integer32 (0..8)
        MAX-ACCESS read-write
        STATUS     current
        DESCRIPTION
            "Parameter to set which scope ID to use for the DHCP server.

             This is used in conjunction with the scope ID parameter
             (see cfgDhcpScopeId).
            "
        ::= { cfgDhcpDnsmasqTableEntry 2 }

-- -----------------------------------------------------------------------------

    cfgDhcpScopeTable OBJECT-TYPE
        SYNTAX  SEQUENCE OF CfgDhcpScopeTableSeq
        MAX-ACCESS not-accessible
        STATUS     current
        DESCRIPTION
            "DHCP instance configs."
        ::= { cfgDhcp 3 }

    cfgDhcpScopeTableEntry OBJECT-TYPE
        SYNTAX  CfgDhcpScopeTableSeq
        MAX-ACCESS not-accessible
        STATUS     current
        DESCRIPTION
            "DHCP instance configs."
        INDEX {cfgDhcpScopeIndex}
        ::= { cfgDhcpScopeTable 1 }

    CfgDhcpScopeTableSeq ::=
        SEQUENCE {  cfgDhcpScopeIndex Integer32,
                    cfgDhcpScopeId Integer32,
                    cfgDhcpScopeInterface DisplayString,
                    cfgDhcpScopeStart Integer32,
                    cfgDhcpScopeLimit Integer32,
                    cfgDhcpScopeLeasetime DisplayString,
                    cfgDhcpScopeGateway IpAddress,
                    cfgDhcpScopeDnsServer1 IpAddress,
                    cfgDhcpScopeDnsServer2 IpAddress
                 }

    cfgDhcpScopeIndex OBJECT-TYPE
        SYNTAX Integer32 (0..7)
        MAX-ACCESS not-accessible
        STATUS     current
        DESCRIPTION
            "Entry index of table."
        ::= { cfgDhcpScopeTableEntry 1 }

    cfgDhcpScopeId OBJECT-TYPE
        SYNTAX Integer32 (0..8)
        MAX-ACCESS read-write
        STATUS     current
        DESCRIPTION
            "Several scopes can share the same ID.

             This is used in conjunction with the DHCP parameter
             (see cfgDhcpDnsmasqScopeParameter).

             Applies to AP and STA."
        ::= { cfgDhcpScopeTableEntry 2 }

    cfgDhcpScopeInterface OBJECT-TYPE
        SYNTAX DisplayString (SIZE(1..255))
        MAX-ACCESS read-write
        STATUS     current
        DESCRIPTION
            "Network interface (ETH, VLAN, WLAN) on which the DHCP server runs.

             If the interface is part of a bridge, the server will run on that
             bridge.

             Applies to AP and STA."
        ::= { cfgDhcpScopeTableEntry 3 }

    cfgDhcpScopeStart OBJECT-TYPE
        SYNTAX Integer32
        MAX-ACCESS read-write
        STATUS     current
        DESCRIPTION
            "Specifies the offset from the network address of the underlying
             interface to calculate the minimum address that may be leased to
             clients. It may be greater than 255 to span subnets.

             Applies to AP and STA."
        ::= { cfgDhcpScopeTableEntry 4 }

    cfgDhcpScopeLimit OBJECT-TYPE
        SYNTAX Integer32
        MAX-ACCESS read-write
        STATUS     current
        DESCRIPTION
            "Specifies the maximum allowable address that may be leased to
             clients, calculated as network address + 'start' + 'limit'.

             Applies to AP and STA."
        ::= { cfgDhcpScopeTableEntry 5 }

    cfgDhcpScopeLeasetime OBJECT-TYPE
        SYNTAX DisplayString (SIZE(1..255))
        MAX-ACCESS read-write
        STATUS     current
        DESCRIPTION
            "Specifies the lease time of addresses handed out to clients,
             e.g. 12h or 30m.

             Applies to AP and STA."
        ::= { cfgDhcpScopeTableEntry 6 }

    cfgDhcpScopeGateway OBJECT-TYPE
        SYNTAX IpAddress
        MAX-ACCESS read-write
        STATUS     current
        DESCRIPTION
            "Specifies the gateway address handed out to clients.

             A value of 0.0.0.0 means not used.

             Applies to AP and STA."
        ::= { cfgDhcpScopeTableEntry 7 }

    cfgDhcpScopeDnsServer1 OBJECT-TYPE
        SYNTAX IpAddress
        MAX-ACCESS read-write
        STATUS     current
        DESCRIPTION
            "Specifies the primary DNS server address handed out to clients.

             A value of 0.0.0.0 means not used.

             Applies to AP and STA."
        ::= { cfgDhcpScopeTableEntry 8 }

    cfgDhcpScopeDnsServer2 OBJECT-TYPE
        SYNTAX IpAddress
        MAX-ACCESS read-write
        STATUS     current
        DESCRIPTION
            "Specifies the secondary DNS server address handed out to clients.

             If the first DNS server is not used, this server will also be
             ignored. A value of 0.0.0.0 means not used.

             Applies to AP and STA."
        ::= { cfgDhcpScopeTableEntry 9 }

-- =============================================================================

-- NTP

    cfgNtpEnabled OBJECT-TYPE
        SYNTAX INTEGER { disabled(0), enabled(1) }
        MAX-ACCESS read-write
        STATUS     current
        DESCRIPTION
            "Synchronize the system time with given server.

             Applies to AP and STA."
        ::= { cfgNtp 1 }

    cfgNtpServer1 OBJECT-TYPE
        SYNTAX IpAddress
        MAX-ACCESS read-write
        STATUS     current
        DESCRIPTION
            "NTP server 1.

             If the IP is set to 0.0.0.0 the NTP client will only listen to
             broadcast packages.

             Applies to AP and STA."
        ::= { cfgNtp 2 }

    cfgNtpServer2 OBJECT-TYPE
        SYNTAX IpAddress
        MAX-ACCESS read-write
        STATUS     current
        DESCRIPTION
            "NTP server 2.

             Used as fallback if server 1 cannot be reached.

             Applies to AP and STA."
        ::= { cfgNtp 3 }

-- =============================================================================

-- HTTP

    cfgHttpUser OBJECT-TYPE
        SYNTAX DisplayString (SIZE(1..255))
        MAX-ACCESS read-only
        STATUS     current
        DESCRIPTION
            "Web administrator username.

             Applies to AP and STA."
        ::= { cfgHttp 1 }

    cfgHttpPassword OBJECT-TYPE
        SYNTAX DisplayString (SIZE(5..126))
        MAX-ACCESS read-write
        STATUS     current
        DESCRIPTION
            "Web administrator password.

             Applies to AP and STA."
        ::= { cfgHttp 2 }

    cfgHttpEnabled OBJECT-TYPE
        SYNTAX INTEGER { disabled(0), enabled(1) }
        MAX-ACCESS read-write
        STATUS     current
        DESCRIPTION
            "Configure if the webserver shall be started.

             When disabling the webserver, make sure you still have another way
             to access the device, e.g by CLI or via SNMP.

             Applies to AP and STA."
        ::= { cfgHttp 3 }

    cfgHttpRedirectEnabled OBJECT-TYPE
        SYNTAX INTEGER { disabled(0), enabled(1) }
        MAX-ACCESS read-write
        STATUS     current
        DESCRIPTION
            "If enabled, all access to `cfgHttpHttpAddress`
             shall be redirected to `cfgHttpHttpsAddress`.
             This does not disable http.

             Applies to AP and STA."
        ::= { cfgHttp 4 }

    cfgHttpHttpAddress OBJECT-TYPE
        SYNTAX DisplayString (SIZE(1..255))
        MAX-ACCESS read-write
        STATUS     current
        DESCRIPTION
            "Address to which the http server binds.

             The default is '0.0.0.0:80'.
             Multiple space and/or comma separated tuples are allowed.

             **Examples**

             * 192.168.1.20:80
             * 192.168.1.20:80, 192.168.2.20:8080, 172.16.32.32:10080
             * 192.168.1.20:80 192.168.2.20:8080 172.16.32.32:10080

             Applies to AP and STA."
        ::= { cfgHttp 5 }

    cfgHttpHttpsAddress OBJECT-TYPE
        SYNTAX DisplayString (SIZE(1..255))
        MAX-ACCESS read-write
        STATUS     current
        DESCRIPTION
            "Address to which the https server binds.

             The default is '0.0.0.0:443'.
             Multiple space and/or comma separated tuples are allowed.

             **Examples**

             * 192.168.1.20:443
             * 192.168.1.20:443, 192.168.2.20:8443, 172.16.32.32:10443
             * 192.168.1.20:443 192.168.2.20:8443 172.16.32.32:10443

             Applies to AP and STA."
        ::= { cfgHttp 6 }

-- =============================================================================

-- LLDP

    cfgLldpEnabled OBJECT-TYPE
        SYNTAX INTEGER { disabled(0), enabled(1) }
        MAX-ACCESS read-write
        STATUS     current
        DESCRIPTION
            "Enable LLDP.

            Applies to AP and STA."
        ::= { cfgLldp 1 }

    cfgLldpDescription OBJECT-TYPE
        SYNTAX DisplayString (SIZE(0..255))
        MAX-ACCESS read-write
        STATUS     current
        DESCRIPTION
            "LLDP Description

            Applies to AP and STA."
        ::= { cfgLldp 2 }

-- =============================================================================

-- mDNS

    cfgMdnsEnabled OBJECT-TYPE
        SYNTAX INTEGER { disabled(0), enabled(1) }
        MAX-ACCESS read-write
        STATUS     current
        DESCRIPTION
            "Enable mDNS.

             Applies to AP and STA."
        ::= { cfgMdns 1 }

    cfgMdnsNetwork OBJECT-TYPE
        SYNTAX DisplayString (SIZE(1..255))
        MAX-ACCESS read-write
        STATUS     current
        DESCRIPTION
            "Space separated list of mDNS aware network interfaces"
        ::= { cfgMdns 2 }

-- =============================================================================

-- NLM

    cfgNlmGlobal     OBJECT IDENTIFIER ::= { cfgNlm 1 }

    cfgNlmGlblEnabled  OBJECT-TYPE
        SYNTAX INTEGER { disabled(0), enabled(1) }
        MAX-ACCESS read-write
        STATUS     current
        DESCRIPTION
            "Enable the Network Link Monitor.

             Applies to AP and STA."
        ::= { cfgNlmGlobal 1 }

-- -----------------------------------------------------------------------------

    cfgNlmMonitorTable OBJECT-TYPE
        SYNTAX  SEQUENCE OF CfgNlmMonTableSeq
        MAX-ACCESS not-accessible
        STATUS     current
        DESCRIPTION
            "NLM Monitor Table."
        ::= { cfgNlm 2 }

    cfgNlmMonitorTableEntry OBJECT-TYPE
        SYNTAX  CfgNlmMonTableSeq
        MAX-ACCESS not-accessible
        STATUS     current
        DESCRIPTION
            "NLM Monitor Table Entry."
        INDEX {cfgNlmMonIndex}
        ::= { cfgNlmMonitorTable 1 }

    CfgNlmMonTableSeq ::=
        SEQUENCE {  cfgNlmMonIndex Integer32,
                    cfgNlmMonEnabled INTEGER,
                    cfgNlmMonInterval Integer32,
                    cfgNlmMonCount Integer32,
                    cfgNlmMonType INTEGER,
                    cfgNlmMonInterfaces DisplayString,
                    cfgNlmMonDestination IpAddress,
                    cfgNlmMonUpAction Integer32,
                    cfgNlmMonDownAction Integer32,
                    cfgNlmMonScanLoopInterval Integer32
                 }

    cfgNlmMonIndex OBJECT-TYPE
        SYNTAX Integer32 (0..255)
        MAX-ACCESS not-accessible
        STATUS     current
        DESCRIPTION
            "Entry index of Table."
        ::= { cfgNlmMonitorTableEntry 1 }

    cfgNlmMonEnabled OBJECT-TYPE
        SYNTAX INTEGER { disabled(0), enabled(1) }
        MAX-ACCESS read-write
        STATUS     current
        DESCRIPTION
            "Enable this entry in the monitor list.

             Applies to AP and STA."
        ::= { cfgNlmMonitorTableEntry 2 }

    cfgNlmMonInterval OBJECT-TYPE
        SYNTAX Integer32 (0..2147483647)
        MAX-ACCESS read-write
        STATUS     current
        DESCRIPTION
            "Execution interval of this monitor in milliseconds.

             In case of an event driven monitor (e.g. `cfgNlmMonType` set to
             **wlan(2)**), this defines a timeout.

             Applies to AP and STA."
        ::= { cfgNlmMonitorTableEntry 3 }

    cfgNlmMonCount OBJECT-TYPE
        SYNTAX Integer32 (0..65535)
        MAX-ACCESS read-write
        STATUS     current
        DESCRIPTION
            "NLM monitor counter.

             The number of times the measured criteria has to be down, until
             the monitor is reported as down.

             Applies to AP and STA."
        ::= { cfgNlmMonitorTableEntry 4 }

    cfgNlmMonType OBJECT-TYPE
        SYNTAX INTEGER { phy(0), icmp(1), wlan(2) }
        MAX-ACCESS read-write
        STATUS     current
        DESCRIPTION
            "Objects which can be monitored.

             * **phy(0)** monitor checks periodically the link status of the
               ethernet interfaces defined by `cfgNlmMonInterfaces`. If at least
               one interface in the list specified is up the monitor is
               considered up.
             * **icmp(1)** monitor pings periodically the destination defined by
               `cfgNlmMonDestination`. If the destination does reply to the ECHO
               request within the `cfgNlmMonInterval` the monitor is considered
               up.
             * **wlan(2)** monitor listens to link status events of the wireless
               interface defined by `cfgNlmMonInterfaces`.

               The wlan monitor consists of 3 components:
               **Long Handoff Detector** - Triggers when after disassociation no
                 authorization event is detected within the configured time in
                 `cfgNlmMonInterval`.
               **Scan Loop Detector** - Triggers immediately on trap 415. This
                 happens if there is no AP or only a single AP which stays
                 below/above the Handoff thresholds. This trap is only generated
                 when `cfgWlanHoProfile` is set to 2 or higher.
               **Handoff Loop Detector** - Triggers if there have been
                 `cfgNlmMonCount` number of Handoff events within
                 `cfgNlmMonCount` * (`cfgNlmMonInterval` + `cfgNlmMonScanLoopInterval`).

               The wlan monitor recovers:
               **Long Handoff Detector** - Immediately after the next successful
                 authorization.
               **Scan Loop Detector** - After the time of the last 415 trap
                 event + the configured `cfgNlmMonScanLoopInterval`. When down,
                 this is checked regularly in `cfgNlmMonScanLoopInterval`
                 intervals.
               **Handoff Loop Detector** - When there are less than
                 `cfgNlmMonCount` Handoff events within the time-window
                 `cfgNlmMonCount` * (`cfgNlmMonInterval` + `cfgNlmMonScanLoopInterval`).
                 When down, this is checked regularly in
                 `cfgNlmMonScanLoopInterval` intervals.

             **Note**: WLAN monitor is supported for  802.11n products only.

             Applies to AP and STA."
        ::= { cfgNlmMonitorTableEntry 5 }

    cfgNlmMonInterfaces OBJECT-TYPE
        SYNTAX DisplayString (SIZE(1..255))
        MAX-ACCESS read-write
        STATUS     current
        DESCRIPTION
            "NLM monitor interface(s).

             This parameter specifies the name of the interface(s)
             which is/are to be monitored.

             For the type **phy(0)** multiple interfaces are allowed.

             For the type **wlan(2)** a single interface (802.11n products only.).

             All other modes ignore this parameter.

             Applies to AP and STA."
        ::= { cfgNlmMonitorTableEntry 6 }

    cfgNlmMonDestination OBJECT-TYPE
        SYNTAX IpAddress
        MAX-ACCESS read-write
        STATUS     current
        DESCRIPTION
            "NLM monitor destination.

             This parameter specifies the IPv4 address which is to be monitored.

             It will only be used when `cfgNlmMonType` is set to **icmp(1)**.

             Applies to AP and STA."
        ::= { cfgNlmMonitorTableEntry 7 }

    cfgNlmMonUpAction OBJECT-TYPE
        SYNTAX Integer32 (0..2255)
        MAX-ACCESS read-write
        STATUS     current
        DESCRIPTION
            "NLM 'up' state monitor action.

             The action is executed on a monitor-state transition to 'up'.

             Set to 0 to disable (i.e. no action).

             Supported actions:

             **1xxx** (offset: 1000, x: CARP group from 1 to 255)
             Un-demote CARP group defined by `cfgNetCarpLocalInterfaceGroup`.

             **20xx** (offset: 2000, x: wlan interface from 0 to 15)
             Enable Access Point operation on the wireless interface.
             Note: Currently all wireless interfaces on radio0 are enabled.

             Applies to AP and STA."
        ::= { cfgNlmMonitorTableEntry 10 }

    cfgNlmMonDownAction OBJECT-TYPE
        SYNTAX Integer32 (0..2255)
        MAX-ACCESS read-write
        STATUS     current
        DESCRIPTION
            "NLM 'down' state monitor script.

             The action is executed on a monitor-state transition to 'down'.

             Set to 0 to disable (i.e. no action).

             Supported actions:

             **1xxx** (offset: 1000, x: CARP group from 1 to 255)
             Demote CARP group defined by `cfgNetCarpLocalInterfaceGroup`

             **20xx** (offset: 2000, x: wlan interface from 0 to 15)
             Disable Access Point operation on the wireless interface.
             Note: Currently all wireless interfaces on radio0 are disabled.

             Applies to AP and STA."
        ::= { cfgNlmMonitorTableEntry 11 }

    cfgNlmMonScanLoopInterval OBJECT-TYPE
        SYNTAX Integer32 (0..2147483647)
        MAX-ACCESS read-write
        STATUS     current
        DESCRIPTION
            "Scan loop debounce interval in milliseconds.

             If set to non-zero it will mark interface 'down' after
             receiving scan loop trap 415 and mark it 'up' after
             scan loop interval if no other 415 events have been
             received.

             Applies to STA. 802.11n products only."
        ::= { cfgNlmMonitorTableEntry 12 }


-- =============================================================================

-- CLI

    cfgCliEnabled OBJECT-TYPE
        SYNTAX INTEGER { disabled(0), enabled(1) }
        MAX-ACCESS read-write
        STATUS     current
        DESCRIPTION
            "CLI feature support configuration.

             Applies to AP and STA."
        ::= { cfgCli 1 }

    cfgCliUsername OBJECT-TYPE
        SYNTAX DisplayString (SIZE(1..31))
        MAX-ACCESS read-write
        STATUS     current
        DESCRIPTION
            "CLI username.

             Applies to AP and STA."
        ::= { cfgCli 2 }

    cfgCliPassword OBJECT-TYPE
        SYNTAX DisplayString (SIZE(0..63))
        MAX-ACCESS read-write
        STATUS     current
        DESCRIPTION
            "CLI password.

             For SSH, a password is mandatory. Accessing the device via telnet
             without using a password is done  by setting the password to an
             empty string (zero string).

             Applies to AP and STA."
        ::= { cfgCli 3 }

    cfgCliTelnetEnabled OBJECT-TYPE
        SYNTAX INTEGER { disabled(0), enabled(1) }
        MAX-ACCESS read-write
        STATUS     current
        DESCRIPTION
            "CLI telnet support configuration.

             Applies to AP and STA."
        ::= { cfgCli 4 }

    cfgCliSshEnabled OBJECT-TYPE
        SYNTAX INTEGER { disabled(0), enabled(1) }
        MAX-ACCESS read-write
        STATUS     current
        DESCRIPTION
            "CLI ssh support configuration.

             Applies to AP and STA."
        ::= { cfgCli 6 }

    cfgCliTelnetAddress OBJECT-TYPE
        SYNTAX DisplayString (SIZE(1..255))
        MAX-ACCESS read-write
        STATUS     current
        DESCRIPTION
            "Address to which the telnet server for CLI binds.

             The default is '0.0.0.0:23'.
             Multiple space and/or comma separated tuples are allowed.

             **Examples**

             * 192.168.1.20:23
             * 192.168.1.20:23, 192.168.2.20:8023, 172.16.32.32:10023
             * 192.168.1.20:23 192.168.2.20:8023 172.16.32.32:10023

             Applies to AP and STA."
        ::= { cfgCli 8 }

    cfgCliSshAddress OBJECT-TYPE
        SYNTAX DisplayString (SIZE(1..255))
        MAX-ACCESS read-write
        STATUS     current
        DESCRIPTION
            "Address to which the ssh server for CLI binds.

             The default is '0.0.0.0:22'.
             Multiple space and/or comma separated tuples are allowed.

             **Examples**

             * 192.168.1.20:22
             * 192.168.1.20:22, 192.168.2.20:8022, 172.16.32.32:10022
             * 192.168.1.20:22 192.168.2.20:8022 172.16.32.32:10022

             Applies to AP and STA."
        ::= { cfgCli 9 }


-- =============================================================================

-- Cellular

-- -----------------------------------------------------------------------------

    cfgCellSimTable OBJECT-TYPE
        SYNTAX  SEQUENCE OF CfgCellSimTableSeq
        MAX-ACCESS not-accessible
        STATUS     current
        DESCRIPTION
            "SIM parameter table

             Applies to LTE products only.
            "
        ::= { cfgCellular 1 }

    cfgCellSimTableEntry OBJECT-TYPE
        SYNTAX  CfgCellSimTableSeq
        MAX-ACCESS not-accessible
        STATUS     current
        DESCRIPTION
            "SIM parameter table entry

             Applies to LTE products only.
            "
        INDEX {cfgCellSimIndex}
        ::= { cfgCellSimTable 1 }


    CfgCellSimTableSeq ::=
        SEQUENCE {  cfgCellSimIndex Integer32,
                    cfgCellSimApn DisplayString,
                    cfgCellSimUsername DisplayString,
                    cfgCellSimPassword DisplayString,
                    cfgCellSimPinEnabled INTEGER,
                    cfgCellSimPin DisplayString,
                    cfgCellSimAuthType INTEGER
                 }

    cfgCellSimIndex OBJECT-TYPE
        SYNTAX Integer32 (0..9)
        MAX-ACCESS not-accessible
        STATUS     current
        DESCRIPTION
            "SIM parameter table entry index

             Applies to LTE products only.
            "
        ::= { cfgCellSimTableEntry 1 }

    cfgCellSimApn OBJECT-TYPE
        SYNTAX DisplayString (SIZE(1..255))
        MAX-ACCESS read-write
        STATUS     current
        DESCRIPTION
            "APN (Access Point Name)

             **Example**

             * gprs.swisscom.ch

             Applies to LTE products only."
        ::= { cfgCellSimTableEntry 2 }

    cfgCellSimUsername OBJECT-TYPE
        SYNTAX DisplayString (SIZE(1..255))
        MAX-ACCESS read-write
        STATUS     current
        DESCRIPTION
            "Username

             Applies to LTE products only."
        ::= { cfgCellSimTableEntry 3 }

    cfgCellSimPassword OBJECT-TYPE
        SYNTAX DisplayString (SIZE(1..255))
        MAX-ACCESS read-write
        STATUS     current
        DESCRIPTION
            "Password

             Applies to LTE products only."
        ::= { cfgCellSimTableEntry 4 }

    cfgCellSimPinEnabled OBJECT-TYPE
        SYNTAX INTEGER { disabled(0), enabled(1) }
        MAX-ACCESS read-write
        STATUS     current
        DESCRIPTION
            "PIN authentication enabled

             Set to enabled if PIN authentication is required for this SIM.

             Applies to LTE products only."
        ::= { cfgCellSimTableEntry 5 }

    cfgCellSimPin OBJECT-TYPE
        SYNTAX DisplayString (SIZE(4))
        MAX-ACCESS read-write
        STATUS     current
        DESCRIPTION
            "SIM PIN

             Applies to LTE products only."
        ::= { cfgCellSimTableEntry 6 }

    cfgCellSimAuthType OBJECT-TYPE
        SYNTAX INTEGER { none(0), pap(1), chap(2), both(3) }
        MAX-ACCESS read-write
        STATUS     current
        DESCRIPTION
            "Authentication type

             Applies to LTE products only."
        ::= { cfgCellSimTableEntry 7 }


-- *****************************************************************************

-- RPCs Remote Procedure Calls
-- ===========================

-- Configuration Management Control

    rpcCfgRevert OBJECT-TYPE
        SYNTAX INTEGER { allError(-1), nop(0), all(1) }
        MAX-ACCESS read-write
        STATUS     current
        DESCRIPTION
            "In case there are any changes in the configuration section, which
             are not applied yet, they can be all reverted by writing **all(1)**
             to this parameter.

             Reading this parameter will show the status of the last RPC. A
             value less than 0 means an error occurred. A value of 0 is
             returned if the revert process was successful.

             Applies to AP and STA."
        ::= { rpcConfiguration 1 }

    rpcCfgApply OBJECT-TYPE
        SYNTAX INTEGER { allError(-1), nop(0), all(1) }
        MAX-ACCESS read-write
        STATUS     current
        DESCRIPTION
            "All changes to any parameter in the configuration section have to
             be applied before they come into operation. To apply all new
             parameters to the device, set this parameter to **all(1)**.

             Reading this parameter will show the status of the apply process.
             A value less then 0 indicates that an error occurred during
             the last apply process, **nop(0)** means no operation and indicates
             that no apply process is in operation and no error has occurred.
             The return value all(1) means the apply process is still running.

             Applies to AP and STA."
        ::= { rpcConfiguration 2 }

    rpcCfgFile OBJECT-TYPE
        SYNTAX INTEGER { errorImport(-2), errorExport(-1), nop(0), export(1), import(2) }
        MAX-ACCESS read-write
        STATUS     current
        DESCRIPTION
            "Export or import a configuration to or from a file respectively.

             Please refer to setCfgFileUrl for more information on how
             to set the configuration file.

             Reading this parameter will show the status of the process. A value
             less than 0 indicates the occurrence of an error during the last
             process, **nop(0)** means no operation and indicates that no
             process is in operation and no error has occurred. A return value
             greater than 0 means the process is still running.

             Applies to AP and STA."
        ::= { rpcConfiguration 4 }

-- =============================================================================

  -- Firmware

     rpcFwFlash OBJECT-TYPE
        SYNTAX INTEGER { flashError(-2), downloadError(-1), nop(0), download(1), flash(2), flashWithConfig(3) }
        MAX-ACCESS read-write
        STATUS     current
        DESCRIPTION
            "Start download/flash of a new firmware.

             To flash a new firmware to the device, define a valid URL
             accessible by the device. Change the firmware URL parameter
             `setFwFileUrl` in the settings section, if needed.

             * Writing **flash(2)** to this parameter will download and validate
               the new firmware file. if the downloaded file is recognized as a
               valid firmware for this device, it will be flashed to the file
               system of the device.
             * Writing **flashWithConfig(3)** to this parameter will download
               the firmware and the custom config defined with setCfgFileUrl
               and validate the new firmware file. If the download is
               recognized as a valid firmware for this device, it will
               be written to the file system of the device. The supplied
               custom config will be applied after the upgrade.

             Reading this parameter will return the status of the firmware flash
             process. A value of **flashError(-2)** indicates that the flash
             process failed during writing. A return value of
             **downloadError(-1)** indicates the occurrence of an error during
             download or validation of the firmware/config. A value of
             **flash(2)** indicates that the device is currently writing the
             firmware to the file system.

             Applies to AP and STA."
        ::= { rpcFirmware 1 }

-- =============================================================================

  -- System

     rpcSysReboot OBJECT-TYPE
        SYNTAX Integer32
        MAX-ACCESS read-write
        STATUS     current
        DESCRIPTION
            "Reboot system after n seconds.

             Applies to AP and STA."
        ::= { rpcSystem 1 }

     rpcSysFactoryReset OBJECT-TYPE
        SYNTAX INTEGER { nop(0), reset(1) }
        MAX-ACCESS read-write
        STATUS     current
        DESCRIPTION
            "Perform a factory reset (i.e. reset device configuration,
             including administrator password and HTTPS/802.1x certificates,
             to its default state).

             **Note:** You will not be able to communicate with the device
             until the factory reset has finished and the device has booted
             again.

             Applies to AP and STA."
        ::= { rpcSystem 2 }

     rpcSysErrorReset OBJECT-TYPE
        SYNTAX INTEGER { nop(0), reset(1) }
        MAX-ACCESS read-write
        STATUS     current
        DESCRIPTION
            "Writing **reset(1)** to this parameter will reset all logged
             warning and errors of the system. The device LEDs will indicate
             normal operating state after result.

             Applies to AP and STA."
        ::= { rpcSystem 3 }

    rpcSysKernelLogReset OBJECT-TYPE
        SYNTAX INTEGER { nop(0), reset(1) }
        MAX-ACCESS read-write
        STATUS     current
        DESCRIPTION
            "Reset kernel logs.

             * Writing **reset(1)** to this parameter will clear all kernel logs.
             * Reading this parameter will show the status of the process.
               A **nop(0)** means no operation and points out that there is no
               process in operation. In case the return value is greater then 0
               the process is still running.

             Applies to AP and STA."
        ::= { rpcSystem 4 }

-- =============================================================================

  -- Certificate

    rpcCrtFile OBJECT-TYPE
        SYNTAX INTEGER { validateerror(-4), deleteerror(-3), exporterror(-2), importerror(-1), nop(0), import(1), export(2), delete(3) }
        MAX-ACCESS read-write
        STATUS     current
        DESCRIPTION
            "Import or export a HTTPS/802.1X certification/key to or from a file
             respectively.

             Please refer to setCrtFileUrl for more information on how to set
             the certification/key file URL.

             Reading this parameter will show the status of the process.
             A value less than 0 indicates that an error has occurred during
             the last process, **nop(0)** means no operation and points out that
             there is no process in operation and no error has occurred. A
             return value greater than 0 means the process is still running.

             Applies to AP and STA."
        ::= { rpcCertificate 1 }

-- =============================================================================

  -- Report

-- =============================================================================

  -- Driver

    rpcDrvTable OBJECT-TYPE
        SYNTAX  SEQUENCE OF RpcDrvTableSeq
        MAX-ACCESS not-accessible
        STATUS     current
        DESCRIPTION
            "RPC driver module"
        ::= { rpcDriver 1 }

    rpcDrvTableEntry OBJECT-TYPE
        SYNTAX  RpcDrvTableSeq
        MAX-ACCESS not-accessible
        STATUS     current
        DESCRIPTION
            "RPC driver module"
        INDEX {rpcDrvIndex}
        ::= { rpcDrvTable 1 }

    RpcDrvTableSeq ::=
        SEQUENCE {  rpcDrvIndex Integer32,
                    rpcDrvName DisplayString,
                    rpcDrvDfsSimulateRadar INTEGER
                 }

    rpcDrvIndex OBJECT-TYPE
        SYNTAX Integer32 (0..1)
        MAX-ACCESS not-accessible
        STATUS     current
        DESCRIPTION
            "Entry index of table"
        ::= { rpcDrvTableEntry 1 }

    rpcDrvName OBJECT-TYPE
        SYNTAX DisplayString (SIZE(1..255))
        MAX-ACCESS read-only
        STATUS     current
        DESCRIPTION
            "Name of the radio device

             Applies to AP."
        ::= { rpcDrvTableEntry 2 }

    rpcDrvDfsSimulateRadar OBJECT-TYPE
        SYNTAX INTEGER { nop(0), fire(1) }
        MAX-ACCESS read-write
        STATUS     current
        DESCRIPTION
            "Simulate a radar detection on the current channel.

             Applies to AP."
        ::= { rpcDrvTableEntry 5 }


-- *****************************************************************************

-- Settings
-- ========

-- Configuration

    setCfgFileUrl OBJECT-TYPE
        SYNTAX DisplayString (SIZE(1..255))
        MAX-ACCESS read-write
        STATUS     current
        DESCRIPTION
            "The configuration file URL defines to or from which location the
             configuration file will be exported or imported. At the moment only
             TFTP protocol is supported.

             **Example**

             * tftp://192.168.1.1/device.cfg

             Applies to AP and STA."
        ::= { setConfiguration 1 }

-- =============================================================================

-- Wireless

    setWlanDeviceTable OBJECT-TYPE
        SYNTAX  SEQUENCE OF SetWlanDeviceTableSeq
        MAX-ACCESS not-accessible
        STATUS     current
        DESCRIPTION
            "Wireless hardware modules."
        ::= { setWireless 1 }

    setWlanDeviceTableEntry OBJECT-TYPE
        SYNTAX  SetWlanDeviceTableSeq
        MAX-ACCESS not-accessible
        STATUS     current
        DESCRIPTION
            "Wireless hardware module."
        INDEX {setWlanDevIndex}
        ::= { setWlanDeviceTable 1 }

    SetWlanDeviceTableSeq ::=
        SEQUENCE {  setWlanDevIndex Integer32,
                    setWlanDevName DisplayString,
                    setWlanDevRfOutput INTEGER,
                    setWlanDevFrequency Integer32,
                    setWlanDevPower Integer32
                 }

    setWlanDevIndex OBJECT-TYPE
        SYNTAX Integer32 (0..1)
        MAX-ACCESS not-accessible
        STATUS     current
        DESCRIPTION
            "Entry index of table"
        ::= { setWlanDeviceTableEntry 1 }

    setWlanDevName OBJECT-TYPE
        SYNTAX DisplayString (SIZE(1..255))
        MAX-ACCESS read-only
        STATUS     current
        DESCRIPTION
            "Name of the wireless device.

             Applies to AP and STA."
        ::= { setWlanDeviceTableEntry 2 }

    setWlanDevRfOutput OBJECT-TYPE
        SYNTAX INTEGER { disabled(0), enabled(1) }
        MAX-ACCESS read-write
        STATUS     current
        DESCRIPTION
            "Enable/disable RF output.

             Applies to AP and STA. 802.11n products only."
        ::= { setWlanDeviceTableEntry 3 }

    setWlanDevFrequency OBJECT-TYPE
        SYNTAX Integer32
        MAX-ACCESS read-write
        STATUS     current
        DESCRIPTION
            "Wireless frequency in MHz.

             Applies to AP and STA. 802.11n products only."
        ::= { setWlanDeviceTableEntry 6 }

    setWlanDevPower OBJECT-TYPE
        SYNTAX Integer32
        MAX-ACCESS read-write
        STATUS     current
        DESCRIPTION
            "Wireless output power as effective isotropic radiated power (EIRP) in dBm
             including antenna gain.


             Applies to AP and STA. 802.11n products only."
        ::= { setWlanDeviceTableEntry 8 }

     setWlanDbgTable OBJECT-TYPE
        SYNTAX  SEQUENCE OF SetWlanDbgTableSeq
        MAX-ACCESS not-accessible
        STATUS     current
        DESCRIPTION
            "Wireless handoff debug parameters."
        ::= { setWireless 6 }

    setWlanDbgTableEntry OBJECT-TYPE
        SYNTAX  SetWlanDbgTableSeq
        MAX-ACCESS not-accessible
        STATUS     current
        DESCRIPTION
            "Wireless handoff debug parameters entry."
        INDEX {setWlanDbgIndex}
        ::= { setWlanDbgTable 1 }

    SetWlanDbgTableSeq ::=
        SEQUENCE {  setWlanDbgIndex Integer32,
                    setWlanDbgIfaceName DisplayString,
                    setWlanDbgHandoff INTEGER,
                    setWlanDbgScan INTEGER,
                    setWlanDbgMlme INTEGER,
                    setWlanDbgEvents INTEGER,
                    setWlanDbgBeaconrssi INTEGER,
                    setWlanDbgAckrssi INTEGER,
                    setWlanDbgBeaconfiltered INTEGER,
                    setWlanDbgRatelimit INTEGER,
                    setWlanDbgBeacontsf INTEGER,
                    setWlanDbgRange INTEGER,
                    setWlanDbgReports INTEGER
                 }

    setWlanDbgIndex OBJECT-TYPE
        SYNTAX Integer32 (0..63)
        MAX-ACCESS not-accessible
        STATUS     current
        DESCRIPTION
            "Entry index of table"
        ::= { setWlanDbgTableEntry 1 }

    setWlanDbgIfaceName OBJECT-TYPE
        SYNTAX DisplayString (SIZE(1..255))
        MAX-ACCESS read-only
        STATUS     current
        DESCRIPTION
            "Name of the virtual wireless interface.

             Applies to AP and STA. 802.11n products only."
        ::= { setWlanDbgTableEntry 2 }

    setWlanDbgHandoff OBJECT-TYPE
        SYNTAX INTEGER { disabled(0), enabled(1) }
        MAX-ACCESS read-write
        STATUS     current
        DESCRIPTION
            "Volatile setting to enable/disable the handoff messages in syslog.

            Applies to STA. 802.11n products only."
        ::= { setWlanDbgTableEntry 3 }

    setWlanDbgScan OBJECT-TYPE
        SYNTAX INTEGER { disabled(0), enabled(1) }
        MAX-ACCESS read-write
        STATUS     current
        DESCRIPTION
            "Volatile setting to enable/disable the scan messages in syslog.

            Applies to STA. 802.11n products only."
        ::= { setWlanDbgTableEntry 4 }

    setWlanDbgMlme OBJECT-TYPE
        SYNTAX INTEGER { disabled(0), enabled(1) }
        MAX-ACCESS read-write
        STATUS     current
        DESCRIPTION
            "Volatile setting to enable/disable the MLME messages in syslog.

            Applies to STA. 802.11n products only."
        ::= { setWlanDbgTableEntry 5 }

    setWlanDbgEvents OBJECT-TYPE
        SYNTAX INTEGER { disabled(0), enabled(1) }
        MAX-ACCESS read-write
        STATUS     current
        DESCRIPTION
            "Volatile setting to enable/disable the Events messages in syslog.

            Applies to STA. 802.11n products only."
        ::= { setWlanDbgTableEntry 6 }

    setWlanDbgBeaconrssi OBJECT-TYPE
        SYNTAX INTEGER { disabled(0), enabled(1) }
        MAX-ACCESS read-write
        STATUS     current
        DESCRIPTION
            "Volatile setting to enable/disable the Beacon RSSI messages in
             syslog.

            Applies to STA. 802.11n products only."
        ::= { setWlanDbgTableEntry 7 }

    setWlanDbgAckrssi OBJECT-TYPE
        SYNTAX INTEGER { disabled(0), enabled(1) }
        MAX-ACCESS read-write
        STATUS     current
        DESCRIPTION
            "Volatile setting to enable/disable the ACK RSSI messages in syslog.

            Applies to STA. 802.11n products only."
        ::= { setWlanDbgTableEntry 8 }

    setWlanDbgBeaconfiltered OBJECT-TYPE
        SYNTAX INTEGER { disabled(0), enabled(1) }
        MAX-ACCESS read-write
        STATUS     current
        DESCRIPTION
            "Volatile setting to enable/disable the Beacon filtered RSSI
             messages in syslog.

            Applies to STA. 802.11n products only."
        ::= { setWlanDbgTableEntry 9 }

    setWlanDbgRatelimit OBJECT-TYPE
        SYNTAX INTEGER { disabled(0), enabled(1) }
        MAX-ACCESS read-write
        STATUS     current
        DESCRIPTION
            "Volatile value to enable/disable the rate limiter messages in syslog.
             These log messages are subject to change. DO NOT PARSE!

             Applies to STA. 802.11n products only."
        ::= { setWlanDbgTableEntry 10 }

    setWlanDbgBeacontsf OBJECT-TYPE
        SYNTAX INTEGER { disabled(0), enabled(1) }
        MAX-ACCESS read-write
        STATUS     current
        DESCRIPTION
            "Volatile setting to enable/disable the beacon RSSI messages in syslog.
             These log messages are subject to change. DO NOT PARSE! TS is internal TSF.

             Applies to STA. 802.11n products only."
        ::= { setWlanDbgTableEntry 12 }

    setWlanDbgRange OBJECT-TYPE
        SYNTAX INTEGER { disabled(0), enabled(1) }
        MAX-ACCESS read-write
        STATUS     current
        DESCRIPTION
            "Volatile setting for distance measurement messages in syslog.

             **Note:** Distance value is not in meters.

             Applies to STA. 802.11n products only."
        ::= { setWlanDbgTableEntry 13 }

    setWlanDbgReports OBJECT-TYPE
        SYNTAX INTEGER { disabled(0), enabled(1) }
        MAX-ACCESS read-write
        STATUS     current
        DESCRIPTION
            "Volatile setting for periodical WLAN debug data reporting.

             Applies to STA. 802.11n products only."
        ::= { setWlanDbgTableEntry 14 }

-- -----------------------------------------------------------------------------

-- Configuration Management Daemon (confmgmtd)

    setCfgdLogLevel OBJECT-TYPE
        SYNTAX Integer32
        MAX-ACCESS read-write
        STATUS     current
        DESCRIPTION
            "Log message level,  N = 0-8.

            Applies to AP and STA."
        ::= { setConfmgmtd 1 }

-- Firmware

    setFwFileUrl OBJECT-TYPE
        SYNTAX DisplayString (SIZE(1..255))
        MAX-ACCESS read-write
        STATUS     current
        DESCRIPTION
            "Download firmware from this URL.

             Applies to AP and STA."
        ::= { setFirmware 1 }

    setFwKeepConfig OBJECT-TYPE
        SYNTAX INTEGER { reset(0), keep(1)}
        MAX-ACCESS read-write
        STATUS     current
        DESCRIPTION
            "Try to import configuration from the previous firmware version.

             Applies to AP and STA."
        ::= { setFirmware 2 }

-- =============================================================================

-- Certificate

    setCrtFileUrl OBJECT-TYPE
        SYNTAX DisplayString (SIZE(1..255))
        MAX-ACCESS read-write
        STATUS     current
        DESCRIPTION
            "Download/upload URL for HTTPS/802.1x certificats and keys

            The certification/key (for HTTPS/802.1X) file-URL defines
            the location of the certification/key file where it will
            be downloaded from or uploaded to. At the moment only the TFTP
            protocol is supported.

            **Example**

            * tftp://192.168.1.1/uttpd.crt

            Applies to AP and STA."
        ::= { setCertificate 1 }

    setCrtFileSelector OBJECT-TYPE
        SYNTAX Integer32 (0..10715)
        MAX-ACCESS read-write
        STATUS     current
        DESCRIPTION
            "Set this field to select which file should be downloaded/uploaded
            via the rpcCrtFile.

            * **0** means legacy HTTPS. Upload/download certificate and key from
            the same url with a .crt and .key extension.
            * **1** means HTTPS certificate
            * **2** means HTTPS key
            * **100** means certificate for wlan0, 101 for wlan1 and so on
            * **200** means private key for wlan0, 201 for wlan1 and so on
            * **300** means CA certificate for wlan0, 301 for wlan1 and so on
            * **400** means CA2 certificate for wlan0, 401 for wlan1 and so on
            * **500** means CRL certificate for wlan0, 501 for wlan1 and so on
            * **600** means CRL2 certificate for wlan0, 601 for wlan1 and so on
            * **700** means PKCS#12 container for wlan0, 701 for wlan1 and so
            on
            * **10xxx** means upload/download the 'next' file which will be
            installed during next reboot or by calling `rpcCrtRefresh`. So a
            value of **10203** means next private key for wlan3.

            To disable the CA certificate verification on 802.1X write the
            following string into the ca file (e.g. wlan0ca(300)):

            ~~~
            DISABLE CA CERTIFICATE VERIFICATION. THIS WILL ALLOW A 3RD PARTY TO CAPTURE MY PASSWORD. I KNOW WHAT I AM DOING.
            ~~~

            Applies to AP and STA."
        ::= { setCertificate 2 }

    setCrtFileFormat OBJECT-TYPE
        SYNTAX INTEGER { pem(0), der(1) }
        MAX-ACCESS read-write
        STATUS     current
        DESCRIPTION
            "Set the certificate/key file format for `rpcCrtFile` actions

            * **0** means the imported/exported certificate/key will be in the
            PEM format.
            * **1** means the imported/exported certificate/key will be in the
            DER format.

            Applies to AP and STA."
        ::= { setCertificate 3 }

    setCrtFilePkcs12Passphrase OBJECT-TYPE
        SYNTAX DisplayString (SIZE(1..255))
        MAX-ACCESS read-write
        STATUS     current
        DESCRIPTION
            "Set the PKCS#12 passphrase used to import with `rpcCertFile`

            This passphrase will be used during the import to decrypt the
            container data. The `cfgWlan802dot1xClientKeyPassword` will then be
            used to encrypt the client key on the device.

            Applies to AP and STA."
        ::= { setCertificate 4 }

-- -----------------------------------------------------------------------------
-- System

    setSysTime OBJECT-TYPE
        SYNTAX Integer32
        MAX-ACCESS read-write
        STATUS     current
        DESCRIPTION
            "System time as epoch."
        ::= { setSystem 1 }


-- *****************************************************************************

-- Hardware
-- ========

  -- System

     hwSysProduct OBJECT-TYPE
        SYNTAX DisplayString (SIZE(1..255))
        MAX-ACCESS read-only
        STATUS     current
        DESCRIPTION
            "Product type.

             Applies to AP and STA."
        ::= { hwSystem 1 }

     hwSysSerial OBJECT-TYPE
        SYNTAX DisplayString (SIZE(1..255))
        MAX-ACCESS read-only
        STATUS     current
        DESCRIPTION
            "Serial number of the product.

             Applies to AP and STA."
        ::= { hwSystem 2 }

     hwSysRevision OBJECT-TYPE
        SYNTAX Integer32
        MAX-ACCESS read-only
        STATUS     current
        DESCRIPTION
            "ERP revision of the product.

             Applies to AP and STA."
        ::= { hwSystem 3 }

     hwSysVersion OBJECT-TYPE
        SYNTAX Integer32
        MAX-ACCESS read-only
        STATUS     current
        DESCRIPTION
            "Version of the product.

             Applies to AP and STA."
        ::= { hwSystem 4 }

-- =============================================================================

  -- Network

    hwNetEthernetTable OBJECT-TYPE
        SYNTAX  SEQUENCE OF HwNetEthernetTableSeq
        MAX-ACCESS not-accessible
        STATUS     current
        DESCRIPTION
            "Ethernet network interfaces"
        ::= { hwNetwork 1 }

    hwNetEthernetTableEntry OBJECT-TYPE
        SYNTAX  HwNetEthernetTableSeq
        MAX-ACCESS not-accessible
        STATUS     current
        DESCRIPTION
            "Ethernet network interface"
        INDEX {hwNetEthIndex}
        ::= { hwNetEthernetTable 1 }

    HwNetEthernetTableSeq ::=
        SEQUENCE {  hwNetEthIndex Integer32,
                    hwNetEthName DisplayString,
                    hwNetEthAssembled INTEGER,
                    hwNetEthMacAddress DisplayString,
                    hwNetEthOperation INTEGER,
                    hwNetEthSpeed Integer32,
                    hwNetEthHwIndex Integer32
                 }

    hwNetEthIndex OBJECT-TYPE
        SYNTAX Integer32 (0..2)
        MAX-ACCESS not-accessible
        STATUS     current
        DESCRIPTION
            "Entry index of table"
        ::= { hwNetEthernetTableEntry 1 }

    hwNetEthName OBJECT-TYPE
        SYNTAX DisplayString (SIZE(1..255))
        MAX-ACCESS read-only
        STATUS     current
        DESCRIPTION
            "Name of the ethernet interface.

             Applies to AP and STA."
        ::= { hwNetEthernetTableEntry 2 }

    hwNetEthAssembled OBJECT-TYPE
        SYNTAX INTEGER { inexistent(0), present(1) }
        MAX-ACCESS read-only
        STATUS     current
        DESCRIPTION
            "Ethernet interface present or not.

             Applies to AP and STA."
        ::= { hwNetEthernetTableEntry 3 }

    hwNetEthMacAddress OBJECT-TYPE
        SYNTAX DisplayString (SIZE(1..255))
        MAX-ACCESS read-only
        STATUS     current
        DESCRIPTION
            "Ethernet MAC address..

             Applies to AP and STA."
        ::= { hwNetEthernetTableEntry 4 }

    hwNetEthOperation OBJECT-TYPE
        SYNTAX INTEGER { down(0), up(1) }
        MAX-ACCESS read-only
        STATUS     current
        DESCRIPTION
            "Ethernet interface plugged or unplugged.

             Applies to AP and STA."
        ::= { hwNetEthernetTableEntry 5 }

    hwNetEthSpeed OBJECT-TYPE
        SYNTAX Integer32
        MAX-ACCESS read-only
        STATUS     current
        DESCRIPTION
            "Ethernet speed in Mbps.

             Applies to AP and STA."
        ::= { hwNetEthernetTableEntry 6 }

    hwNetEthHwIndex OBJECT-TYPE
        SYNTAX Integer32
        MAX-ACCESS read-only
        STATUS     current
        DESCRIPTION
            "The physical address of the Ethernet interface of the base board,
             since not all products are assembled the same way this is to
             describe how the wiring is done.

             Applies to AP and STA."
        ::= { hwNetEthernetTableEntry 7 }

-- =============================================================================

  -- Wireless

    hwWlanDeviceTable OBJECT-TYPE
        SYNTAX  SEQUENCE OF HwWlanDeviceTableSeq
        MAX-ACCESS not-accessible
        STATUS     current
        DESCRIPTION
            "Hardware information of the wireless LAN devices."
        ::= { hwWireless 1 }

    hwWlanDeviceTableEntry OBJECT-TYPE
        SYNTAX  HwWlanDeviceTableSeq
        MAX-ACCESS not-accessible
        STATUS     current
        DESCRIPTION
            "Wireless LAN devices"
        INDEX {hwWlanDevIndex}
        ::= { hwWlanDeviceTable 1 }

    HwWlanDeviceTableSeq ::=
        SEQUENCE {  hwWlanDevIndex Integer32,
                    hwWlanDevAssembled INTEGER,
                    hwWlanDevType DisplayString,
                    hwWlanDevSerial DisplayString,
                    hwWlanDevRevision Integer32,
                    hwWlanDevVersion Integer32,
                    hwWlanDevPcbId Integer32,
                    hwWlanDevAssemblyId Integer32,
                    hwWlanDevMacAddress DisplayString,
                    hwWlanDevAntennaProfileId Integer32,
                    hwWlanDevAntennaGain Integer32,
                    hwWlanDevCableLoss Integer32
                 }

    hwWlanDevIndex OBJECT-TYPE
        SYNTAX Integer32 (0..1)
        MAX-ACCESS not-accessible
        STATUS     current
        DESCRIPTION
            "Entry index of table"
        ::= { hwWlanDeviceTableEntry 1 }

    hwWlanDevAssembled OBJECT-TYPE
        SYNTAX INTEGER { inexistent(0), present(1) }
        MAX-ACCESS read-only
        STATUS     current
        DESCRIPTION
            "Wireless device present or not.

             Applies to AP and STA."
        ::= { hwWlanDeviceTableEntry 2 }

    hwWlanDevType OBJECT-TYPE
        SYNTAX DisplayString (SIZE(1..255))
        MAX-ACCESS read-only
        STATUS     current
        DESCRIPTION
            "Type of the wireless device.

             Applies to AP and STA."
        ::= { hwWlanDeviceTableEntry 3 }

    hwWlanDevSerial OBJECT-TYPE
        SYNTAX DisplayString (SIZE(1..255))
        MAX-ACCESS read-only
        STATUS     current
        DESCRIPTION
            "Serial number / customer field.

             Applies to AP and STA."
        ::= { hwWlanDeviceTableEntry 4 }

    hwWlanDevRevision OBJECT-TYPE
        SYNTAX Integer32
        MAX-ACCESS read-only
        STATUS     current
        DESCRIPTION
            "ERP revision of the RF board.

             Applies to AP and STA."
        ::= { hwWlanDeviceTableEntry 5 }

    hwWlanDevVersion OBJECT-TYPE
        SYNTAX Integer32
        MAX-ACCESS read-only
        STATUS     current
        DESCRIPTION
            "Version of the RF board.

             Applies to AP and STA."
        ::= { hwWlanDeviceTableEntry 6 }

     hwWlanDevPcbId OBJECT-TYPE
        SYNTAX Integer32
        MAX-ACCESS read-only
        STATUS     current
        DESCRIPTION
            "Hardware assembly ID.

             Applies to AP and STA."
        ::= { hwWlanDeviceTableEntry 7 }

     hwWlanDevAssemblyId OBJECT-TYPE
        SYNTAX Integer32
        MAX-ACCESS read-only
        STATUS     current
        DESCRIPTION
            "Hardware assembly ID.

             Applies to AP and STA."
        ::= { hwWlanDeviceTableEntry 8 }

    hwWlanDevMacAddress OBJECT-TYPE
        SYNTAX DisplayString (SIZE(1..255))
        MAX-ACCESS read-only
        STATUS     current
        DESCRIPTION
            "MAC address.

             Applies to AP and STA."
        ::= { hwWlanDeviceTableEntry 9 }

    hwWlanDevAntennaProfileId OBJECT-TYPE
        SYNTAX Integer32
        MAX-ACCESS read-only
        STATUS     current
        DESCRIPTION
            "Antenna profile ID.

             Please check the user manual for antenna details.

             Applies to AP and STA."
        ::= { hwWlanDeviceTableEntry 10 }

     hwWlanDevAntennaGain OBJECT-TYPE
        SYNTAX Integer32
        MAX-ACCESS read-only
        STATUS     current
        DESCRIPTION
            "Antenna gain in dBi.

             Applies to AP and STA."
        ::= { hwWlanDeviceTableEntry 11 }

     hwWlanDevCableLoss OBJECT-TYPE
        SYNTAX Integer32
        MAX-ACCESS read-only
        STATUS     current
        DESCRIPTION
            "Cable loss in dB.

             Applies to AP and STA."
        ::= { hwWlanDeviceTableEntry 12 }

    hwWlanGlobal     OBJECT IDENTIFIER ::= { hwWireless 2 }

    hwWlanGlblRegulatoryRegionId OBJECT-TYPE
        SYNTAX DisplayString (SIZE(1..255))
        MAX-ACCESS read-only
        STATUS     current
        DESCRIPTION
            "Regulatory region ID.

             Applies to AP and STA."
        ::= { hwWlanGlobal 2 }

-- =============================================================================

  -- Base Board

    hwBbType OBJECT-TYPE
        SYNTAX DisplayString (SIZE(1..255))
        MAX-ACCESS read-only
        STATUS     current
        DESCRIPTION
            "Product type of the base board.

             Applies to AP and STA."
        ::= { hwBaseBoard 1 }

     hwBbSerial OBJECT-TYPE
        SYNTAX DisplayString (SIZE(1..255))
        MAX-ACCESS read-only
        STATUS     current
        DESCRIPTION
            "Serial number of the base board.

             Applies to AP and STA."
        ::= { hwBaseBoard 2 }

     hwBbRevision OBJECT-TYPE
        SYNTAX Integer32
        MAX-ACCESS read-only
        STATUS     current
        DESCRIPTION
            "ERP revision of the base board.

             Applies to AP and STA."
        ::= { hwBaseBoard 3 }

     hwBbVersion OBJECT-TYPE
        SYNTAX Integer32
        MAX-ACCESS read-only
        STATUS     current
        DESCRIPTION
            "Version of the base board.

             Applies to AP and STA."
        ::= { hwBaseBoard 4 }

     hwBbPcbId OBJECT-TYPE
        SYNTAX Integer32
        MAX-ACCESS read-only
        STATUS     current
        DESCRIPTION
            "Hardware assembly ID.

             Applies to AP and STA."
        ::= { hwBaseBoard 5 }

     hwBbAssemblyId OBJECT-TYPE
        SYNTAX Integer32
        MAX-ACCESS read-only
        STATUS     current
        DESCRIPTION
            "Hardware assembly ID.

             Applies to AP and STA."
        ::= { hwBaseBoard 6 }

-- =============================================================================

  -- Interface Board

    hwIfBrdAssembled OBJECT-TYPE
        SYNTAX INTEGER { inexistent(0), present(1) }
        MAX-ACCESS read-only
        STATUS     current
        DESCRIPTION
            "Interface board present or not.

             Applies to AP and STA."
        ::= { hwIfaceBoard 1 }

    hwIfBrdType OBJECT-TYPE
        SYNTAX DisplayString (SIZE(1..255))
        MAX-ACCESS read-only
        STATUS     current
        DESCRIPTION
            "Product type of the interface board.

             Applies to AP and STA."
        ::= { hwIfaceBoard 2 }

     hwIfBrdSerial OBJECT-TYPE
        SYNTAX DisplayString (SIZE(1..255))
        MAX-ACCESS read-only
        STATUS     current
        DESCRIPTION
            "Serial number of the interface board.

             Applies to AP and STA."
        ::= { hwIfaceBoard 3 }

     hwIfBrdRevision OBJECT-TYPE
        SYNTAX Integer32
        MAX-ACCESS read-only
        STATUS     current
        DESCRIPTION
            "ERP Revision of the interface board.

             Applies to AP and STA."
        ::= { hwIfaceBoard 4 }

     hwIfBrdVersion OBJECT-TYPE
        SYNTAX Integer32
        MAX-ACCESS read-only
        STATUS     current
        DESCRIPTION
            "Version of the interface board.

             Applies to AP and STA."
        ::= { hwIfaceBoard 5 }

     hwIfBrdPcbId OBJECT-TYPE
        SYNTAX Integer32
        MAX-ACCESS read-only
        STATUS     current
        DESCRIPTION
            "Hardware assembly ID.

             Applies to AP and STA."
        ::= { hwIfaceBoard 6 }

     hwIfBrdAssemblyId OBJECT-TYPE
        SYNTAX Integer32
        MAX-ACCESS read-only
        STATUS     current
        DESCRIPTION
            "Hardware assembly ID.

             Applies to AP and STA."
        ::= { hwIfaceBoard 7 }

  -- Hardware Sensors

    hwSensorTable OBJECT-TYPE
        SYNTAX  SEQUENCE OF HwSensorTableSeq
        MAX-ACCESS not-accessible
        STATUS     current
        DESCRIPTION
            "Hardware sensor information table."
        ::= { hwSensor 1 }

    hwSensorTableEntry OBJECT-TYPE
        SYNTAX  HwSensorTableSeq
        MAX-ACCESS not-accessible
        STATUS     current
        DESCRIPTION
            "Hardware sensor entry.
            "
        INDEX {hwSensorIndex}
        ::= { hwSensorTable 1 }

    HwSensorTableSeq ::=
        SEQUENCE {  hwSensorIndex Integer32,
                    hwSensorName DisplayString,
                    hwSensorUnit DisplayString,
                    hwSensorValue DisplayString
                 }

    hwSensorIndex OBJECT-TYPE
        SYNTAX Integer32 (0..15)
        MAX-ACCESS not-accessible
        STATUS     current
        DESCRIPTION
            "Entry index of table.
            "
        ::= { hwSensorTableEntry 1 }

    hwSensorName OBJECT-TYPE
        SYNTAX DisplayString (SIZE(1..255))
        MAX-ACCESS read-only
        STATUS     current
        DESCRIPTION
            "Name of the hardware sensor.

             Applies to AP and STA."
        ::= { hwSensorTableEntry 2 }

    hwSensorUnit OBJECT-TYPE
        SYNTAX DisplayString (SIZE(1..255))
        MAX-ACCESS read-only
        STATUS     current
        DESCRIPTION
            "Unit of the hardware sensor.

             Applies to AP and STA."
        ::= { hwSensorTableEntry 3 }

    hwSensorValue OBJECT-TYPE
        SYNTAX DisplayString (SIZE(1..255))
        MAX-ACCESS read-only
        STATUS     current
        DESCRIPTION
            "Value of the hardware sensor.

             Applies to AP and STA."
        ::= { hwSensorTableEntry 4 }


-- *****************************************************************************

-- Software
-- ========

  -- Firmware

     swFwName OBJECT-TYPE
        SYNTAX DisplayString (SIZE(1..255))
        MAX-ACCESS read-only
        STATUS     current
        DESCRIPTION
            "Firmware name.

             Applies to AP and STA."
        ::= { swFirmware 1 }

     swFwVersion OBJECT-TYPE
        SYNTAX DisplayString (SIZE(1..255))
        MAX-ACCESS read-only
        STATUS     current
        DESCRIPTION
            "Firmware name.

             Applies to AP and STA."
        ::= { swFirmware 2 }

     swFwRevision OBJECT-TYPE
        SYNTAX DisplayString (SIZE(1..255))
        MAX-ACCESS read-only
        STATUS     current
        DESCRIPTION
            "Firmware name.

             Applies to AP and STA."
        ::= { swFirmware 3 }

-- =============================================================================

-- System

    swSysRebootReason OBJECT-TYPE
        SYNTAX INTEGER { coldstart(0), warmstart(1), watchdog(2), oops(3), unknown(9) }
        MAX-ACCESS read-only
        STATUS     current
        DESCRIPTION
            "Reason for the reboot of the system.

             Applies to AP and STA."
        ::= { swSystem 1 }

    swSysBootStatus OBJECT-TYPE
        SYNTAX INTEGER { done(0), booting(1) }
        MAX-ACCESS read-only
        STATUS     current
        DESCRIPTION
            "The boot status indicates whether the booting sequence of
             the device has been completed."
        ::= { swSystem 2 }

    swSysMessageTable OBJECT-TYPE
        SYNTAX  SEQUENCE OF SwSysMessageTableSeq
        MAX-ACCESS not-accessible
        STATUS     current
        DESCRIPTION
            "System messages (e.g. errors, warnings)."
        ::= { swSystem 100 }

    swSysMessageTableEntry OBJECT-TYPE
        SYNTAX  SwSysMessageTableSeq
        MAX-ACCESS not-accessible
        STATUS     current
        DESCRIPTION
            "System message entry"
        INDEX {swSysMsgIndex}
        ::= { swSysMessageTable 1 }

    SwSysMessageTableSeq ::=
        SEQUENCE {  swSysMsgIndex Integer32,
                    swSysMsgPriority INTEGER,
                    swSysMsgCode Integer32,
                    swSysMsgText DisplayString
                 }

    swSysMsgIndex OBJECT-TYPE
        SYNTAX Integer32 (0..63)
        MAX-ACCESS not-accessible
        STATUS     current
        DESCRIPTION
            "Entry index of table."
        ::= { swSysMessageTableEntry 1 }

    swSysMsgPriority OBJECT-TYPE
        SYNTAX INTEGER { emergency(0), alert(1), critical(2), error(3), warning(4), notice(5), info(6), debug(7) }
        MAX-ACCESS read-only
        STATUS     current
        DESCRIPTION
            "Message priority/level.

             Applies to AP and STA."
        ::= { swSysMessageTableEntry 2 }

    swSysMsgCode OBJECT-TYPE
        SYNTAX Integer32
        MAX-ACCESS read-only
        STATUS     current
        DESCRIPTION
            "Message code.

             Applies to AP and STA."
        ::= { swSysMessageTableEntry 3 }

    swSysMsgText OBJECT-TYPE
        SYNTAX DisplayString (SIZE(1..255))
        MAX-ACCESS read-only
        STATUS     current
        DESCRIPTION
            "Message.

             Applies to AP and STA."
        ::= { swSysMessageTableEntry 4 }

-- =============================================================================

-- Operating System

     swOsName OBJECT-TYPE
        SYNTAX DisplayString (SIZE(1..255))
        MAX-ACCESS read-only
        STATUS     current
        DESCRIPTION
            "Operating system name.

             Applies to AP and STA."
        ::= { swOperatingSystem 1 }

     swOsVersion OBJECT-TYPE
        SYNTAX DisplayString (SIZE(1..255))
        MAX-ACCESS read-only
        STATUS     current
        DESCRIPTION
            "Operating system version.

             Applies to AP and STA."
        ::= { swOperatingSystem 2 }

     swOsRevision OBJECT-TYPE
        SYNTAX DisplayString (SIZE(1..255))
        MAX-ACCESS read-only
        STATUS     current
        DESCRIPTION
            "Operating system revision.

             Applies to AP and STA."
        ::= { swOperatingSystem 3 }

     swOsUptime OBJECT-TYPE
        SYNTAX TimeTicks
        MAX-ACCESS read-only
        STATUS     current
        DESCRIPTION
            "Up time of the operating system.

             Applies to AP and STA."
        ::= { swOperatingSystem 4 }


-- Driver

    swDrvDfsTable OBJECT-TYPE
        SYNTAX  SEQUENCE OF SwDrvDfsTableSeq
        MAX-ACCESS not-accessible
        STATUS     current
        DESCRIPTION
            "DFS driver statistics"
        ::= { swDriver 1 }

    swDrvDfsTableEntry OBJECT-TYPE
        SYNTAX  SwDrvDfsTableSeq
        MAX-ACCESS not-accessible
        STATUS     current
        DESCRIPTION
            "DFS driver statistics"
        INDEX {swDrvDfsIndex}
        ::= { swDrvDfsTable 1 }

    SwDrvDfsTableSeq ::=
        SEQUENCE {  swDrvDfsIndex Integer32,
                    swDrvDfsName DisplayString,
                    swDrvDfsPulsesDetected Integer32,
                    swDrvDfsPulsesProcessed Integer32,
                    swDrvDfsRadarDetected Integer32
                 }

    swDrvDfsIndex OBJECT-TYPE
        SYNTAX Integer32 (0..1)
        MAX-ACCESS not-accessible
        STATUS     current
        DESCRIPTION
            "Entry index of table.
            "
        ::= { swDrvDfsTableEntry 1 }

    swDrvDfsName OBJECT-TYPE
        SYNTAX DisplayString (SIZE(1..255))
        MAX-ACCESS read-only
        STATUS     current
        DESCRIPTION
            "Name of the wireless device.

             Applies to AP and STA. 802.11n products only."
        ::= { swDrvDfsTableEntry 2 }

    swDrvDfsPulsesDetected OBJECT-TYPE
        SYNTAX Integer32
        MAX-ACCESS read-write
        STATUS     current
        DESCRIPTION
            "Pulses detected by the wireless device.

             Applies to AP. 802.11n products only."
        ::= { swDrvDfsTableEntry 3 }

    swDrvDfsPulsesProcessed OBJECT-TYPE
        SYNTAX Integer32
        MAX-ACCESS read-write
        STATUS     current
        DESCRIPTION
            "Pulses processed by the wireless device.

             Applies to AP. 802.11n products only."
        ::= { swDrvDfsTableEntry 4 }

    swDrvDfsRadarDetected OBJECT-TYPE
        SYNTAX Integer32
        MAX-ACCESS read-write
        STATUS     current
        DESCRIPTION
            "Radar sequences detected by the wireless device.

             Applies to AP. 802.11n products only."
        ::= { swDrvDfsTableEntry 5 }

    swDrvCntWlanMacTable OBJECT-TYPE
        SYNTAX  SEQUENCE OF SwDrvCntWlanMacTableSeq
        MAX-ACCESS not-accessible
        STATUS     current
        DESCRIPTION
            "Wireless MAC layer statistics."
        ::= { swDriver 4 }

    swDrvCntWlanMacTableEntry OBJECT-TYPE
        SYNTAX  SwDrvCntWlanMacTableSeq
        MAX-ACCESS not-accessible
        STATUS     current
        DESCRIPTION
            "Wireless MAC layer statistics."
        INDEX {swDrvCntWlanMacIndex}
        ::= { swDrvCntWlanMacTable 1 }

    SwDrvCntWlanMacTableSeq ::=
        SEQUENCE {
                swDrvCntWlanMacIndex                     Integer32,
                swDrvCntWlanMacName                      DisplayString,
                swDrvCntWlanMacTxHandlersDrop            Integer32,
                swDrvCntWlanMacTxHandlersQueued          Integer32,
                swDrvCntWlanMacTxHandlersDropUnencrypted Integer32,
                swDrvCntWlanMacTxHandlersDropFragment    Integer32,
                swDrvCntWlanMacTxHandlersDropWep         Integer32,
                swDrvCntWlanMacTxHandlersDropNotAssoc    Integer32,
                swDrvCntWlanMacTxHandlersDropUnauthPort  Integer32,
                swDrvCntWlanMacRxHandlersDrop            Integer32,
                swDrvCntWlanMacRxHandlersQueued          Integer32,
                swDrvCntWlanMacRxHandlersDropNullfunc    Integer32,
                swDrvCntWlanMacRxHandlersDropDefrag      Integer32,
                swDrvCntWlanMacRxHandlersDropShort       Integer32,
                swDrvCntWlanMacTxExpandSkbHead           Integer32,
                swDrvCntWlanMacTxExpandSkbHeadCloned     Integer32,
                swDrvCntWlanMacRxExpandSkbHead           Integer32,
                swDrvCntWlanMacRxExpandSkbHead2          Integer32,
                swDrvCntWlanMacRxHandlersFragments       Integer32,
                swDrvCntWlanMacTxstatusDrop              Integer32
                }

    swDrvCntWlanMacIndex OBJECT-TYPE
        SYNTAX Integer32 (0..63)
        MAX-ACCESS not-accessible
        STATUS     current
        DESCRIPTION
            "Entry index of table."
        ::= { swDrvCntWlanMacTableEntry 1 }

    swDrvCntWlanMacName OBJECT-TYPE
        SYNTAX DisplayString (SIZE(1..255))
        MAX-ACCESS read-only
        STATUS     current
        DESCRIPTION
            "Name of the wireless device.

             Applies to AP and STA. 802.11n products only."
        ::= { swDrvCntWlanMacTableEntry 2 }

    swDrvCntWlanMacTxHandlersDrop OBJECT-TYPE
        SYNTAX Integer32
        MAX-ACCESS read-only
        STATUS     current
        DESCRIPTION
            "MAC debug entry.

             Applies to AP and STA. 802.11n products only."
        ::= { swDrvCntWlanMacTableEntry 3 }

    swDrvCntWlanMacTxHandlersQueued OBJECT-TYPE
        SYNTAX Integer32
        MAX-ACCESS read-only
        STATUS     current
        DESCRIPTION
            "MAC debug entry.

             Applies to AP and STA. 802.11n products only."
        ::= { swDrvCntWlanMacTableEntry 4 }

    swDrvCntWlanMacTxHandlersDropUnencrypted OBJECT-TYPE
        SYNTAX Integer32
        MAX-ACCESS read-only
        STATUS     current
        DESCRIPTION
            "MAC debug entry.

             Applies to AP and STA. 802.11n products only."
        ::= { swDrvCntWlanMacTableEntry 5 }

    swDrvCntWlanMacTxHandlersDropFragment OBJECT-TYPE
        SYNTAX Integer32
        MAX-ACCESS read-only
        STATUS     current
        DESCRIPTION
            "MAC debug entry.

             Applies to AP and STA. 802.11n products only."
        ::= { swDrvCntWlanMacTableEntry 6 }

    swDrvCntWlanMacTxHandlersDropWep OBJECT-TYPE
        SYNTAX Integer32
        MAX-ACCESS read-only
        STATUS     current
        DESCRIPTION
            "MAC debug entry.

             Applies to AP and STA. 802.11n products only."
        ::= { swDrvCntWlanMacTableEntry 7 }

    swDrvCntWlanMacTxHandlersDropNotAssoc OBJECT-TYPE
        SYNTAX Integer32
        MAX-ACCESS read-only
        STATUS     current
        DESCRIPTION
            "MAC debug entry.

             Applies to AP and STA. 802.11n products only."
        ::= { swDrvCntWlanMacTableEntry 8 }

    swDrvCntWlanMacTxHandlersDropUnauthPort OBJECT-TYPE
        SYNTAX Integer32
        MAX-ACCESS read-only
        STATUS     current
        DESCRIPTION
            "MAC debug entry.

             Applies to AP and STA. 802.11n products only."
        ::= { swDrvCntWlanMacTableEntry 9 }

    swDrvCntWlanMacRxHandlersDrop OBJECT-TYPE
        SYNTAX Integer32
        MAX-ACCESS read-only
        STATUS     current
        DESCRIPTION
            "MAC debug entry.

             Applies to AP and STA. 802.11n products only."
        ::= { swDrvCntWlanMacTableEntry 10 }

    swDrvCntWlanMacRxHandlersQueued OBJECT-TYPE
        SYNTAX Integer32
        MAX-ACCESS read-only
        STATUS     current
        DESCRIPTION
            "MAC debug entry.

             Applies to AP and STA. 802.11n products only."
        ::= { swDrvCntWlanMacTableEntry 11 }

    swDrvCntWlanMacRxHandlersDropNullfunc OBJECT-TYPE
        SYNTAX Integer32
        MAX-ACCESS read-only
        STATUS     current
        DESCRIPTION
            "MAC debug entry.

             Applies to AP and STA. 802.11n products only."
        ::= { swDrvCntWlanMacTableEntry 12 }

    swDrvCntWlanMacRxHandlersDropDefrag OBJECT-TYPE
        SYNTAX Integer32
        MAX-ACCESS read-only
        STATUS     current
        DESCRIPTION
            "MAC debug entry.

             Applies to AP and STA. 802.11n products only."
        ::= { swDrvCntWlanMacTableEntry 13 }

    swDrvCntWlanMacRxHandlersDropShort OBJECT-TYPE
        SYNTAX Integer32
        MAX-ACCESS read-only
        STATUS     current
        DESCRIPTION
            "MAC debug entry.

             Applies to AP and STA. 802.11n products only."
        ::= { swDrvCntWlanMacTableEntry 14 }

    swDrvCntWlanMacTxExpandSkbHead OBJECT-TYPE
        SYNTAX Integer32
        MAX-ACCESS read-only
        STATUS     current
        DESCRIPTION
            "MAC debug entry.

             Applies to AP and STA. 802.11n products only."
        ::= { swDrvCntWlanMacTableEntry 15 }

    swDrvCntWlanMacTxExpandSkbHeadCloned OBJECT-TYPE
        SYNTAX Integer32
        MAX-ACCESS read-only
        STATUS     current
        DESCRIPTION
            "MAC debug entry.

             Applies to AP and STA. 802.11n products only."
        ::= { swDrvCntWlanMacTableEntry 16 }

    swDrvCntWlanMacRxExpandSkbHead OBJECT-TYPE
        SYNTAX Integer32
        MAX-ACCESS read-only
        STATUS     current
        DESCRIPTION
            "MAC debug entry.

             Applies to AP and STA. 802.11n products only."
        ::= { swDrvCntWlanMacTableEntry 17 }

    swDrvCntWlanMacRxExpandSkbHead2 OBJECT-TYPE
        SYNTAX Integer32
        MAX-ACCESS read-only
        STATUS     current
        DESCRIPTION
            "MAC debug entry.

             Applies to AP and STA. 802.11n products only."
        ::= { swDrvCntWlanMacTableEntry 18 }

    swDrvCntWlanMacRxHandlersFragments OBJECT-TYPE
        SYNTAX Integer32
        MAX-ACCESS read-only
        STATUS     current
        DESCRIPTION
            "MAC debug entry.

             Applies to AP and STA. 802.11n products only."
        ::= { swDrvCntWlanMacTableEntry 19 }

    swDrvCntWlanMacTxstatusDrop OBJECT-TYPE
        SYNTAX Integer32
        MAX-ACCESS read-only
        STATUS     current
        DESCRIPTION
            "MAC debug entry.

             Applies to AP and STA. 802.11n products only."
        ::= { swDrvCntWlanMacTableEntry 20 }

    swDrvCntWlanWmmTable OBJECT-TYPE
        SYNTAX  SEQUENCE OF SwDrvWlanCntWmmTableSeq
        MAX-ACCESS not-accessible
        STATUS     current
        DESCRIPTION
            "WMM statistics."
        ::= { swDriver 6 }

    swDrvCntWlanWmmTableEntry OBJECT-TYPE
        SYNTAX  SwDrvWlanCntWmmTableSeq
        MAX-ACCESS not-accessible
        STATUS     current
        DESCRIPTION
            "WMM statistics."
        INDEX {swDrvCntWlanWmmTableIndex}
        ::= { swDrvCntWlanWmmTable 1 }

    SwDrvWlanCntWmmTableSeq ::=
        SEQUENCE {  swDrvCntWlanWmmTableIndex Integer32,
                    swDrvCntWlanWmmName DisplayString,
                    swDrvCntWlanWmmTx Integer32,
                    swDrvCntWlanWmmRx Integer32,
                    swDrvCntWlanWmmShortRetries Integer32,
                    swDrvCntWlanWmmLongRetries Integer32,
                    swDrvCntWlanWmmExceededRetries Integer32
                 }

    swDrvCntWlanWmmTableIndex OBJECT-TYPE
        SYNTAX Integer32 (0..4)
        MAX-ACCESS not-accessible
        STATUS     current
        DESCRIPTION
            "Entry index of table."
        ::= { swDrvCntWlanWmmTableEntry 1 }

    swDrvCntWlanWmmName OBJECT-TYPE
        SYNTAX DisplayString (SIZE(1..255))
        MAX-ACCESS read-only
        STATUS     current
        DESCRIPTION
            "Name of the queue.

             Applies to AP and STA. 802.11n products only."
        ::= { swDrvCntWlanWmmTableEntry 2 }

    swDrvCntWlanWmmTx OBJECT-TYPE
        SYNTAX Integer32
        MAX-ACCESS read-only
        STATUS     current
        DESCRIPTION
            "Number of frames sent in this queue.

             Applies to AP and STA. 802.11n products only."
        ::= { swDrvCntWlanWmmTableEntry 3 }

    swDrvCntWlanWmmRx OBJECT-TYPE
        SYNTAX Integer32
        MAX-ACCESS read-only
        STATUS     current
        DESCRIPTION
            "Number of frames received in this queue.

             Applies to AP and STA. 802.11n products only."
        ::= { swDrvCntWlanWmmTableEntry 4 }

    swDrvCntWlanWmmShortRetries OBJECT-TYPE
        SYNTAX Integer32
        MAX-ACCESS read-only
        STATUS     current
        DESCRIPTION
            "Number of retries for frames shorter than RTS.

             Applies to AP and STA. 802.11n products only."
        ::= { swDrvCntWlanWmmTableEntry 5 }

    swDrvCntWlanWmmLongRetries OBJECT-TYPE
        SYNTAX Integer32
        MAX-ACCESS read-only
        STATUS     current
        DESCRIPTION
            "Number of retries for frames longer than RTS.

             Applies to AP and STA. 802.11n products only."
        ::= { swDrvCntWlanWmmTableEntry 6 }

    swDrvCntWlanWmmExceededRetries OBJECT-TYPE
        SYNTAX Integer32
        MAX-ACCESS read-only
        STATUS     current
        DESCRIPTION
            "Number of failed transmissions due to exceeding of the retry limit.

             Applies to AP and STA. 802.11n products only."
        ::= { swDrvCntWlanWmmTableEntry 7 }


    swDrvConStatTable OBJECT-TYPE
        SYNTAX SEQUENCE OF SwDrvConStatTableSeq
        MAX-ACCESS     not-accessible
        STATUS         current
        DESCRIPTION
            "Connection Status Information."
        ::= { swDriver 8 }

    swDrvConStatTableEntry OBJECT-TYPE
        SYNTAX SwDrvConStatTableSeq
        MAX-ACCESS not-accessible
        STATUS     current
        DESCRIPTION
            "Connection Status Information per Station."
        INDEX { swDrvConStatIndex
              }
        ::= { swDrvConStatTable 1 }

    swDrvConStatWlanIf OBJECT-TYPE
        SYNTAX      DisplayString (SIZE(4..17))
        MAX-ACCESS  read-write
        STATUS      current
        DESCRIPTION
            "Volatile wlan interface selector for `swDrvConStatTable`.

             Changes made here will be lost upon reconfiguration or a reboot.
             Use `cfgWlanGlblConnectionStatusWlanInterface` to set a persistent
             value which is used during initialisation.

             Applies to AP and STA."
        ::= { swDriver 7 }

    SwDrvConStatTableSeq ::=
        SEQUENCE {  swDrvConStatIndex Integer32,
                    swDrvConStatWlanName DisplayString,
                    swDrvConStatMacName DisplayString,

                    swDrvConStatRxBrExtra DisplayString,
                    swDrvConStatRxBrType DisplayString,
                    swDrvConStatRxBrValue Integer32,
                    swDrvConStatRxBytes Integer32,
                    swDrvConStatRxPackets Integer32,

                    swDrvConStatTxBrExtra DisplayString,
                    swDrvConStatTxBrType DisplayString,
                    swDrvConStatTxBrValue Integer32,
                    swDrvConStatTxBytes Integer32,
                    swDrvConStatTxPackets Integer32,

                    swDrvConStatSigChain0 Integer32,
                    swDrvConStatSigChain1 Integer32,
                    swDrvConStatSigChain2 Integer32,
                    swDrvConStatSigAvgChain0 Integer32,
                    swDrvConStatSigAvgChain1 Integer32,
                    swDrvConStatSigAvgChain2 Integer32,

                    swDrvConStatTxRetries Integer32,
                    swDrvConStatTxFailed Integer32,

                    swDrvConStatCacheNo Integer32,

                    swDrvConStatSigCombined Integer32,
                    swDrvConStatSigAvgCombined Integer32
                 }

    swDrvConStatIndex OBJECT-TYPE
        SYNTAX     Integer32 (0..9)
        MAX-ACCESS not-accessible
        STATUS     current
        DESCRIPTION
            "Entry index of Table."
        ::= { swDrvConStatTableEntry 1 }

    swDrvConStatWlanName OBJECT-TYPE
        SYNTAX     DisplayString (SIZE(4..5))
        MAX-ACCESS read-only
        STATUS     current
        DESCRIPTION
            "WLAN interface name.

             Applies to AP and STA. 802.11n products only."
        ::= { swDrvConStatTableEntry 2 }

    swDrvConStatMacName OBJECT-TYPE
        SYNTAX     DisplayString (SIZE(1..17))
        MAX-ACCESS read-only
        STATUS     current
        DESCRIPTION
            "Station MAC address.

             In AP mode this is the MAC address of the connected
             client (STA). In client (STA) mode this is the
             MAC address of the AP to which the client is
             connected.

             Applies to AP and STA. 802.11n products only."
        ::= { swDrvConStatTableEntry 3 }

    swDrvConStatRxBrExtra OBJECT-TYPE
        SYNTAX     DisplayString (SIZE(1..255))
        MAX-ACCESS read-only
        STATUS     current
        DESCRIPTION
            "Station rx bitrate extra.

             Applies to AP and STA. 802.11n products only."
        ::= { swDrvConStatTableEntry 4 }

    swDrvConStatRxBrType OBJECT-TYPE
        SYNTAX     DisplayString (SIZE(1..255))
        MAX-ACCESS read-only
        STATUS     current
        DESCRIPTION
            "Station rx bitrate type.

             Applies to AP and STA. 802.11n products only."
        ::= { swDrvConStatTableEntry 5 }

    swDrvConStatRxBrValue OBJECT-TYPE
        SYNTAX     Integer32
        MAX-ACCESS read-only
        STATUS     current
        DESCRIPTION
            "Station rx bitrate value.

             Multiplied by 10 if `swDrvConStatRxBrType` is 'legacy'.

             Applies to AP and STA. 802.11n products only."
        ::= { swDrvConStatTableEntry 6 }

    swDrvConStatRxBytes OBJECT-TYPE
        SYNTAX     Integer32
        MAX-ACCESS read-only
        STATUS     current
        DESCRIPTION
            "Station rx bytes.

             Applies to AP and STA. 802.11n products only."
        ::= { swDrvConStatTableEntry 7 }

    swDrvConStatRxPackets OBJECT-TYPE
        SYNTAX     Integer32
        MAX-ACCESS read-only
        STATUS     current
        DESCRIPTION
            "Station rx packets.

             Applies to AP and STA. 802.11n products only."
        ::= { swDrvConStatTableEntry 8 }

    swDrvConStatTxBrExtra OBJECT-TYPE
        SYNTAX     DisplayString (SIZE(1..255))
        MAX-ACCESS read-only
        STATUS     current
        DESCRIPTION
            "Station tx bitrate extra.

             Applies to AP and STA. 802.11n products only."
        ::= { swDrvConStatTableEntry 9 }

    swDrvConStatTxBrType OBJECT-TYPE
        SYNTAX     DisplayString (SIZE(1..255))
        MAX-ACCESS read-only
        STATUS     current
        DESCRIPTION
            "Station tx bitrate type.

             Applies to AP and STA. 802.11n products only."
        ::= { swDrvConStatTableEntry 10 }

    swDrvConStatTxBrValue OBJECT-TYPE
        SYNTAX     Integer32
        MAX-ACCESS read-only
        STATUS     current
        DESCRIPTION
            "Station tx bitrate value.

             Multiplied by 10 if `swDrvConStatTxBrType` is 'legacy'.

             Applies to AP and STA. 802.11n products only."
        ::= { swDrvConStatTableEntry 11 }

    swDrvConStatTxBytes OBJECT-TYPE
        SYNTAX     Integer32
        MAX-ACCESS read-only
        STATUS     current
        DESCRIPTION
            "Station tx bytes.

             Applies to AP and STA. 802.11n products only."
        ::= { swDrvConStatTableEntry 12 }

    swDrvConStatTxPackets OBJECT-TYPE
        SYNTAX     Integer32
        MAX-ACCESS read-only
        STATUS     current
        DESCRIPTION
            "Station tx packets.

             Applies to AP and STA. 802.11n products only."
        ::= { swDrvConStatTableEntry 13 }

    swDrvConStatSigChain0 OBJECT-TYPE
        SYNTAX     Integer32
        MAX-ACCESS read-only
        STATUS     current
        DESCRIPTION
            "Station signal chain 0 in dBm.

             Applies to AP and STA. 802.11n products only."
        ::= { swDrvConStatTableEntry 14 }

    swDrvConStatSigChain1 OBJECT-TYPE
        SYNTAX     Integer32
        MAX-ACCESS read-only
        STATUS     current
        DESCRIPTION
            "Station signal chain 1 in dBm.

             Applies to AP and STA. 802.11n products only."
        ::= { swDrvConStatTableEntry 15 }

    swDrvConStatSigChain2 OBJECT-TYPE
        SYNTAX     Integer32
        MAX-ACCESS read-only
        STATUS     current
        DESCRIPTION
            "Station signal chain 2 in dBm.

             Applies to AP and STA. 802.11n products only."
        ::= { swDrvConStatTableEntry 16 }

    swDrvConStatSigAvgChain0 OBJECT-TYPE
        SYNTAX     Integer32
        MAX-ACCESS read-only
        STATUS     current
        DESCRIPTION
            "Station signal average chain 0 in dBm.

             Applies to AP and STA. 802.11n products only."
        ::= { swDrvConStatTableEntry 17 }

    swDrvConStatSigAvgChain1 OBJECT-TYPE
        SYNTAX     Integer32
        MAX-ACCESS read-only
        STATUS     current
        DESCRIPTION
            "Station signal average chain 1 in dBm.

             Applies to AP and STA. 802.11n products only."
        ::= { swDrvConStatTableEntry 18 }

    swDrvConStatSigAvgChain2 OBJECT-TYPE
        SYNTAX     Integer32
        MAX-ACCESS read-only
        STATUS     current
        DESCRIPTION
            "Station signal average chain 2 in dBm.

             Applies to AP and STA. 802.11n products only."
        ::= { swDrvConStatTableEntry 19 }

    swDrvConStatTxRetries OBJECT-TYPE
        SYNTAX     Integer32
        MAX-ACCESS read-only
        STATUS     current
        DESCRIPTION
            "Station tx retries.

             Applies to AP and STA."
        ::= { swDrvConStatTableEntry 20 }

    swDrvConStatTxFailed OBJECT-TYPE
        SYNTAX     Integer32
        MAX-ACCESS read-only
        STATUS     current
        DESCRIPTION
            "Station tx failed.

             Applies to AP and STA. 802.11n products only."
        ::= { swDrvConStatTableEntry 21 }

    swDrvConStatCacheNo OBJECT-TYPE
       SYNTAX     Integer32
       MAX-ACCESS read-only
       STATUS     current
       DESCRIPTION
            "Station Dump Cache Access Number.

             The cache gets refreshed if it is older than 5 seconds.

             Applies to AP and STA. 802.11n products only."
       ::= { swDrvConStatTableEntry 22 }

    swDrvConStatSigCombined OBJECT-TYPE
        SYNTAX     Integer32
        MAX-ACCESS read-only
        STATUS     current
        DESCRIPTION
            "Station signal combined of all active chains in dBm.

            Applies to AP and STA. 802.11n products only."
        ::= { swDrvConStatTableEntry 23 }

    swDrvConStatSigAvgCombined OBJECT-TYPE
        SYNTAX     Integer32
        MAX-ACCESS read-only
        STATUS     current
        DESCRIPTION
            "Station signal average combined of all active chains in dBm.

             Applies to AP and STA. 802.11n products only."
        ::= { swDrvConStatTableEntry 24 }

--------------------------------------------------------------------------------
    swDrvCntWlanTable OBJECT-TYPE
        SYNTAX  SEQUENCE OF SwDrvCntWlanTableSeq
        MAX-ACCESS not-accessible
        STATUS     current
        DESCRIPTION
            "Wireless Dev Counters"
        ::= { swDriver 9 }

    swDrvCntWlanTableEntry OBJECT-TYPE
        SYNTAX  SwDrvCntWlanTableSeq
        MAX-ACCESS not-accessible
        STATUS     current
        DESCRIPTION
            "Wireless Dev Counters"
        INDEX {swDrvCntWlanIndex}
        ::= { swDrvCntWlanTable 1 }

    SwDrvCntWlanTableSeq ::=
        SEQUENCE {  swDrvCntWlanIndex Integer32,
                    swDrvCntWlanName DisplayString,
                    swDrvCntWlanAssocSuccess Counter32,
                    swDrvCntWlanAssocFailure Counter32,
                    swDrvCntWlanAssocFailureMaxSta Counter32,
                    swDrvCntWlanNumAssocSta Counter32,
                    swDrvCntWlanEapAuthStarted Counter32,
                    swDrvCntWlanEapAuthFailed Counter32,
                    swDrvCntWlanChannelActive Counter32,
                    swDrvCntWlanChannelBusy Counter32,
                    swDrvCntWlanChannelTransmit Counter32,
                    swDrvCntWlanChannelReceive Counter32,
                    swDrvCntWlanChannelNoise Counter32,
                    swDrvCntWlanEapAuthStartedFT Counter32,
                    swDrvCntWlanEapAuthStartedFILS Counter32,
                    swDrvCntWlanEapAuthStartedPKMSA Counter32
                 }

    swDrvCntWlanIndex OBJECT-TYPE
        SYNTAX Integer32 (0..63)
        MAX-ACCESS not-accessible
        STATUS     current
        DESCRIPTION
            "Entry index of Table"
        ::= { swDrvCntWlanTableEntry 1 }

    swDrvCntWlanName OBJECT-TYPE
        SYNTAX DisplayString (SIZE(1..255))
        MAX-ACCESS read-only
        STATUS     current
        DESCRIPTION
            "Name of the wireless Dev"
        ::= { swDrvCntWlanTableEntry 2 }

    swDrvCntWlanAssocSuccess OBJECT-TYPE
        SYNTAX Counter32
        MAX-ACCESS read-only
        STATUS     current
        DESCRIPTION
            "Number of successful associations. 802.11n products only."
        ::= { swDrvCntWlanTableEntry 4 }

    swDrvCntWlanAssocFailure OBJECT-TYPE
        SYNTAX Counter32
        MAX-ACCESS read-only
        STATUS     current
        DESCRIPTION
            "Number of unsuccessful associations. 802.11n products only."
        ::= { swDrvCntWlanTableEntry 5 }

    swDrvCntWlanAssocFailureMaxSta OBJECT-TYPE
        SYNTAX Counter32
        MAX-ACCESS read-only
        STATUS     current
        DESCRIPTION
            "Number of times the maximum number of stations has been exceeded.

             Applies to AP. 802.11n products only.
            "
        ::= { swDrvCntWlanTableEntry 6 }

    swDrvCntWlanNumAssocSta OBJECT-TYPE
        SYNTAX Counter32
        MAX-ACCESS read-only
        STATUS     current
        DESCRIPTION
            "Number of associated STA.

             Applies to AP. 802.11n products only.
            "
        ::= { swDrvCntWlanTableEntry 7 }

    swDrvCntWlanEapAuthStarted OBJECT-TYPE
        SYNTAX Counter32
        MAX-ACCESS read-only
        STATUS     current
        DESCRIPTION
            "Number of EAP authentication sessions started since
             the AP has been started.

             Applies to AP. 802.11n products only.
            "
        ::= { swDrvCntWlanTableEntry 8 }

    swDrvCntWlanEapAuthFailed OBJECT-TYPE
        SYNTAX Counter32
        MAX-ACCESS read-only
        STATUS     current
        DESCRIPTION
            "Number of EAP authentication sessions that have
             failed since the AP has been started.

             Applies to AP. 802.11n products only.
            "
        ::= { swDrvCntWlanTableEntry 9 }

    swDrvCntWlanChannelActive OBJECT-TYPE
        SYNTAX Counter32
        MAX-ACCESS read-only
        STATUS     current
        DESCRIPTION
            "Time in ms during which the device has been on the current channel.

             On STA when it's no associated the current channel is the lowest
             channel of selected country code.

             Applies to AP and STA. 802.11n products only.
            "
        ::= { swDrvCntWlanTableEntry 10 }

    swDrvCntWlanChannelBusy OBJECT-TYPE
        SYNTAX Counter32
        MAX-ACCESS read-only
        STATUS     current
        DESCRIPTION
            "Time in ms during which the medium has been considered busy on the
             current channel.

             Applies to AP and STA. 802.11n products only.
            "
        ::= { swDrvCntWlanTableEntry 11 }

    swDrvCntWlanChannelTransmit OBJECT-TYPE
        SYNTAX Counter32
        MAX-ACCESS read-only
        STATUS     current
        DESCRIPTION
            "Time in ms during which the device has been in transmit mode on the
             current channel.

             Applies to AP and STA. 802.11n products only.
            "
        ::= { swDrvCntWlanTableEntry 12 }

    swDrvCntWlanChannelReceive OBJECT-TYPE
        SYNTAX Counter32
        MAX-ACCESS read-only
        STATUS     current
        DESCRIPTION
            "Time in ms during which the device has been in receive mode on the
             current channel.

             Applies to AP and STA. 802.11n products only.
            "
        ::= { swDrvCntWlanTableEntry 13 }

    swDrvCntWlanChannelNoise OBJECT-TYPE
        SYNTAX Counter32
        MAX-ACCESS read-only
        STATUS     current
        DESCRIPTION
            "Measured channel noise in 1 dB steps.

             **Notice:** This value is not an absolute power level but the
             internal representation of the measured noise floor.

             Applies to AP and STA. 802.11n products only.
            "
        ::= { swDrvCntWlanTableEntry 14 }

    swDrvCntWlanEapAuthStartedFT OBJECT-TYPE
        SYNTAX Counter32
        MAX-ACCESS read-only
        STATUS     current
        DESCRIPTION
            "EAP sessions started through FT.

             Applies to AP. 802.11n products only.
            "
        ::= { swDrvCntWlanTableEntry 20 }

    swDrvCntWlanEapAuthStartedFILS OBJECT-TYPE
        SYNTAX Counter32
        MAX-ACCESS read-only
        STATUS     current
        DESCRIPTION
            "EAP sessions started through FILS.

             Applies to AP. 802.11n products only.
            "
        ::= { swDrvCntWlanTableEntry 21 }

    swDrvCntWlanEapAuthStartedPKMSA OBJECT-TYPE
        SYNTAX Counter32
        MAX-ACCESS read-only
        STATUS     current
        DESCRIPTION
            "EAP sessions started through PKMSA.

             Applies to AP. 802.11n products only.
            "
        ::= { swDrvCntWlanTableEntry 22 }

-- =============================================================================

  -- Rdm

    swRdmMaxEirp OBJECT-TYPE
        SYNTAX Integer32
        MAX-ACCESS read-only
        STATUS     current
        DESCRIPTION
            "Maximal equivalent isotropically radiated power (EIRP) in dBm.

             This value shows the maximal aggregated transmit power over all
             configured chains.

             Applies to AP."
        ::= { swRdm 1 }

    swRdmMaxApp OBJECT-TYPE
        SYNTAX Integer32
        MAX-ACCESS read-only
        STATUS     current
        DESCRIPTION
            "Maximal antenna port power in dBm.

             This value shows the maximal transmit power of a single chain.

             Applies to AP."
        ::= { swRdm 2 }

-- =============================================================================

  -- Bootloader

    swBootName OBJECT-TYPE
        SYNTAX DisplayString (SIZE(1..255))
        MAX-ACCESS read-only
        STATUS     current
        DESCRIPTION
            "Name of the bootloader.

             Applies to AP and STA."
        ::= { swBootloader 1 }

    swBootVersion OBJECT-TYPE
        SYNTAX DisplayString (SIZE(1..255))
        MAX-ACCESS read-only
        STATUS     current
        DESCRIPTION
            "Version of the bootloader.

             Applies to AP and STA."
        ::= { swBootloader 2 }

    swBootBuildDate OBJECT-TYPE
        SYNTAX DisplayString (SIZE(1..255))
        MAX-ACCESS read-only
        STATUS     current
        DESCRIPTION
            "Date when the bootloader was built.

             Applies to AP and STA."
        ::= { swBootloader 3 }

-- =============================================================================

  -- Configuration

    swCfgChangesCount OBJECT-TYPE
        SYNTAX Integer32
        MAX-ACCESS read-only
        STATUS     current
        DESCRIPTION
            "Number of not yet applied device configuration changes.

             Applies to AP and STA."
        ::= { swConfiguration 1 }

-- * * * * * * * * * * * * * * * * * * * * * * * * * * * * * * * * * * *
-- *  End of Object Types
-- **********************************************************************

-- **********************************************************************
-- *  Begin GROUPS
-- * * * * * * * * * * * * * * * * * * * * * * * * * * * * * * * * * * *

    groupCfgSystem OBJECT-GROUP
        OBJECTS {
           cfgSysHostname,
           cfgSysTimezone
           }
        STATUS  current
        DESCRIPTION
            "System Settings"
        ::= { groupConfiguration 1 }


    groupCfgNetwork OBJECT IDENTIFIER ::= { groupConfiguration 2 }

    groupCfgNetEthernet OBJECT-GROUP
        OBJECTS {
           cfgNetEthName,
           cfgNetEthEnabled,
           cfgNetEthBridge,
           cfgNetEthAutoneg,
           cfgNetEthSpeed,
           cfgNetEthTrunk,
           cfgNetEthTag,
           cfgNetEthVlanMode,
           cfgNetEthLldpEnabled
           }
        STATUS  current
        DESCRIPTION
            "Network Ethernet Properties"
        ::= { groupCfgNetwork 1 }

    groupCfgNetWlan OBJECT-GROUP
        OBJECTS {
           cfgNetWlanName,
           cfgNetWlanEnabled,
           cfgNetWlanBridge,
           cfgNetWlanTrunk,
           cfgNetWlanTag,
           cfgNetWlanVlanMode,
           cfgNetWlanLldpEnabled
           }
        STATUS  current
        DESCRIPTION
            "Wireless Interface Properties"
        ::= { groupCfgNetwork 2 }

    groupCfgNetVlan OBJECT-GROUP
        OBJECTS {
           cfgNetVlanName,
           cfgNetVlanEnabled,
           cfgNetVlanBridge,
           cfgNetVlanParent,
           cfgNetVlanVid
           }
        STATUS  current
        DESCRIPTION
            "VLAN Properties"
        ::= { groupCfgNetwork 3 }

    groupCfgNetIp OBJECT-GROUP
        OBJECTS {
           cfgNetIpEnabled,
           cfgNetIpAddr,
           cfgNetIpProto,
           cfgNetIpInterface,
           cfgNetIpCarpId
           }
        STATUS  current
        DESCRIPTION
            "IP Properties"
        ::= { groupCfgNetwork 6 }

    groupCfgNetCarp OBJECT-GROUP
        OBJECTS {
           cfgNetCarpEnabled,
           cfgNetCarpVhid,
           cfgNetCarpPassword,
           cfgNetCarpAdvbase,
           cfgNetCarpAdvskew,
           cfgNetCarpAdvdivider,
           cfgNetCarpRatio,
           cfgNetCarpPreempt,
           cfgNetCarpPreemptdemote,
           cfgNetCarpLocalInterfaceGroup,
           cfgNetCarpSyncInterface,
           cfgNetCarpMcastIp
           }
        STATUS  current
        DESCRIPTION
            "IP Carp Properties"
        ::= { groupCfgNetwork 7 }

    groupCfgNetMacVLan OBJECT-GROUP
        OBJECTS {
           cfgNetMacVlanName,
           cfgNetMacVlanEnabled,
           cfgNetMacVlanParent,
           cfgNetMacVlanMac
           }
        STATUS  current
        DESCRIPTION
            "Mac Vlan Properties"
        ::= { groupCfgNetwork 9 }

    groupCfgNetWwan OBJECT-GROUP
        OBJECTS {
           cfgNetWwanName,
           cfgNetWwanEnabled,
           cfgNetWwanPrimarySim,
           cfgNetWwanSecondarySim
           }
        STATUS  current
        DESCRIPTION
            "Wwan Properties"
        ::= { groupCfgNetwork 11 }

    groupCfgWireless OBJECT IDENTIFIER ::= { groupConfiguration 3 }

    groupCfgWlanDevice OBJECT-GROUP
        OBJECTS {
           cfgWlanDevName,
           cfgWlanDevModulation,
           cfgWlanDevBandwidth,
           cfgWlanDevFrequency,
           cfgWlanDevPower,
           cfgWlanDevDistance,
           cfgWlanDevRts,
           cfgWlanDevFragments,
           cfgWlanDevShortRetry,
           cfgWlanDevLongRetry,
           cfgWlanDevAntennaGain,
           cfgWlanDevTxAntenna,
           cfgWlanDevRxAntenna,
           cfgWlanDevPhy,
           cfgWlanDevHtCapabilities,
           cfgWlanDevQmrrString
           }
        STATUS  current
        DESCRIPTION
            "Wireless Interface Properties"
        ::= { groupCfgWireless 1 }

    groupCfgWlanInterface OBJECT-GROUP
        OBJECTS {
           cfgWlanIfaceName,
           cfgWlanIfaceDevice,
           cfgWlanIfaceMode,
           cfgWlanIfaceSsid,
           cfgWlanIfaceEncryption,
           cfgWlanIfacePassword,
           cfgWlanIfacePassiveScanning,
           cfgWlanIfaceBeaconMiss,
           cfgWlanIfaceDtim,
           cfgWlanIfaceBitrates,
           cfgWlanIfaceBeaconInterval,
           cfgWlanIfaceWmeParameter,
           cfgWlanIfaceWmeEnabled,
           cfgWlanIfaceScanList,
           cfgWlanIfaceIgnoreBroadcastSsid,
           cfgWlanIfaceMacaddrAcl,
           cfgWlanIfaceMaxNumSta,
           cfgWlanIfaceBssid,
           cfgWlanIfaceLegacyRates,
           cfgWlanIface4addr,
           cfgWlanIfaceInactivityTimeout,
           cfgWlanIfaceUseVendorSsid,
           cfgWlanIfaceIeee80211w,
           cfgWlanIfaceIeee80211wMaxTimeout,
           cfgWlanIfaceIeee80211wRetryTimeout,
           cfgWlanIfaceAcsList,
           cfgWlanIfaceNeighbourReport,
           cfgWlanIfaceNeighbourParameter,
           cfgWlanIfaceL2nat,
           cfgWlanIfaceL2natLearningMode,
           cfgWlanIfaceL2natDefaultDestination,
           cfgWlanIfaceTimeAdvertisement,
           cfgWlanIfaceApIsolate
           }
        STATUS  current
        DESCRIPTION
            "Wireless Interface Properties"
        ::= { groupCfgWireless 2 }

    groupCfgWlanHandoff OBJECT-GROUP
        OBJECTS {
           cfgWlanHoIfaceName,
           cfgWlanHoProfile,
           cfgWlanHoScanningLevel,
           cfgWlanHoBeacons,
           cfgWlanHoRecovery,
           cfgWlanHoFilterMode,
           cfgWlanHoFilterLongX,
           cfgWlanHoFilterLongY,
           cfgWlanHoScanRateLimitTime,
           cfgWlanHoScanRateLimitTries,
           cfgWlanHoPassiveChanTime,
           cfgWlanHoLevelLow,
           cfgWlanHoLevelHigh,
           cfgWlanHoDistanceNear,
           cfgWlanHoDistanceFar,
           cfgWlanHoDistanceMeasurementPeriod,
           cfgWlanHoDistanceFilterX,
           cfgWlanHoDistanceFilterY
           }
        STATUS  current
        DESCRIPTION
            "Wireless Handoff Properties"
        ::= { groupCfgWireless 3 }

    groupCfgWlanScanFreq OBJECT-GROUP
        OBJECTS {
           cfgWlanFFreq0,
           cfgWlanFFreq1,
           cfgWlanFFreq2,
           cfgWlanFFreq3,
           cfgWlanFFreq4,
           cfgWlanFFreq5,
           cfgWlanFFreq6,
           cfgWlanFFreq7,
           cfgWlanFFreq8,
           cfgWlanFFreq9,
           cfgWlanFFreq10,
           cfgWlanFFreq11,
           cfgWlanFFreq12,
           cfgWlanFFreq13,
           cfgWlanFFreq14,
           cfgWlanFFreq15,
           cfgWlanFFreq16,
           cfgWlanFFreq17,
           cfgWlanFFreq18,
           cfgWlanFFreq19,
           cfgWlanFFreq20,
           cfgWlanFFreq21,
           cfgWlanFFreq22,
           cfgWlanFFreq23
           }
        STATUS  current
        DESCRIPTION
            "Wireless Scanlist Properties"
        ::= { groupCfgWireless 4 }

    groupCfgWlanWme OBJECT-GROUP
        OBJECTS {
           cfgWlanWmeId,
           cfgWlanWmeAc,
           cfgWlanWmeCwMin,
           cfgWlanWmeCwMax,
           cfgWlanWmeAifs,
           cfgWlanWmeTxOpMax,
           cfgWlanWmeApCwMin,
           cfgWlanWmeApCwMax,
           cfgWlanWmeApAifs,
           cfgWlanWmeApBurst
           }
        STATUS  current
        DESCRIPTION
            "Wireless WME properties"
        ::= { groupCfgWireless 5 }

    groupCfgWlanDbg OBJECT-GROUP
        OBJECTS {
           cfgWlanDbgIfaceName,
           cfgWlanDbgHandoff,
           cfgWlanDbgScan,
           cfgWlanDbgMlme,
           cfgWlanDbgEvents,
           cfgWlanDbgBeaconrssi,
           cfgWlanDbgAckrssi,
           cfgWlanDbgBeaconfiltered,
           cfgWlanDbgRatelimit,
           cfgWlanDbgLinkmonitor,
           cfgWlanDbgBeacontsf,
           cfgWlanDbgRange,
           cfgWlanDbgReports
           }
        STATUS  current
        DESCRIPTION
            "Wireless Debug Properties"
        ::= { groupCfgWireless 6 }

    groupCfgWlanAclBlack OBJECT-GROUP
        OBJECTS {
           cfgWlanAclBlackEnabled,
           cfgWlanAclBlackInterface,
           cfgWlanAclBlackAddr,
           cfgWlanAclBlackMask
           }
        STATUS  current
        DESCRIPTION
            "Wireless ACL Black Properties"
        ::= { groupCfgWireless 7 }

    groupCfgWlanAclWhite OBJECT-GROUP
        OBJECTS {
           cfgWlanAclWhiteEnabled,
           cfgWlanAclWhiteInterface,
           cfgWlanAclWhiteAddr,
           cfgWlanAclWhiteMask
           }
        STATUS  current
        DESCRIPTION
            "Wireless ACL White Properties"
        ::= { groupCfgWireless 8 }

    groupCfgWlanGlobal OBJECT-GROUP
        OBJECTS {
           cfgWlanGlblCountry,
           cfgWlanGlblLinkmonitorInterval,
           cfgWlanGlblLinkmonitorQmrrlogging,
           cfgWlanGlblConnectionStatusWlanInterface
           }
        STATUS  current
        DESCRIPTION
            "Wireless Global Properties"
        ::= { groupCfgWireless 9 }

    groupCfgWlan802dot1x OBJECT-GROUP
        OBJECTS {
           cfgWlan802dot1xName,
           cfgWlan802dot1xOwnIpAddr,
           cfgWlan802dot1xAuthServerParameter,
           cfgWlan802dot1xAcctServerParameter,
           cfgWlan802dot1xRetryPrimaryInterval,
           cfgWlan802dot1xInterimAccountingInterval,
           cfgWlan802dot1xNasId,
           cfgWlan802dot1xEapType,
           cfgWlan802dot1xIdentity,
           cfgWlan802dot1xClientKeyPassword,
           cfgWlan802dot1xTlsControlParams
           }
        STATUS  current
        DESCRIPTION
            "Wireless 802.1X Properties"
        ::= { groupCfgWireless 10 }

    groupCfgWlan802dot1xAuth OBJECT-GROUP
        OBJECTS {
           cfgWlan802dot1xAuthSrvEnabled,
           cfgWlan802dot1xAuthSrvId,
           cfgWlan802dot1xAuthSrvIpAddr,
           cfgWlan802dot1xAuthSrvPort,
           cfgWlan802dot1xAuthSrvSharedSecret
           }
        STATUS  current
        DESCRIPTION
            "Wireless 802.1X Auth Properties"
        ::= { groupCfgWireless 11 }

    groupCfgWlan802dot1xAcct OBJECT-GROUP
        OBJECTS {
           cfgWlan802dot1xAcctSrvEnabled,
           cfgWlan802dot1xAcctSrvId,
           cfgWlan802dot1xAcctSrvIpAddr,
           cfgWlan802dot1xAcctSrvPort,
           cfgWlan802dot1xAcctSrvSharedSecret
           }
        STATUS  current
        DESCRIPTION
            "Wireless 802.1X Acct Properties"
        ::= { groupCfgWireless 12 }

    groupCfgWlan802dot11r OBJECT-GROUP
        OBJECTS {
           cfgWlan802dot11rName,
           cfgWlan802dot11rEnabled,
           cfgWlan802dot11rMobilityDomain,
           cfgWlan802dot11rPmkR0KeyHolderIdentifier,
           cfgWlan802dot11rPmkR0Lifetime,
           cfgWlan802dot11rPmkR1KeyHolderIdentifier,
           cfgWlan802dot11rPmkR1Push,
           cfgWlan802dot11rR0KHParameter,
           cfgWlan802dot11rR1KHParameter,
           cfgWlan802dot11rExpirationEnabled,
           cfgWlan802dot11rExpirationTime,
           cfgWlan802dot11rVlan,
           cfgWlan802dot11rR0KHId,
           cfgWlan802dot11rR0KHEnabled,
           cfgWlan802dot11rR0KHDestinationMac,
           cfgWlan802dot11rR0KHHID,
           cfgWlan802dot11rR0KHKey,
           cfgWlan802dot11rR1KHId,
           cfgWlan802dot11rR1KHEnabled,
           cfgWlan802dot11rR1KHDestinationMac,
           cfgWlan802dot11rR1KHHID,
           cfgWlan802dot11rR1KHKey
           }
        STATUS  current
        DESCRIPTION
            "Wireless 802.11r properties"
        ::= { groupCfgWireless 13 }

    groupCfgWlanNeighbour OBJECT-GROUP
        OBJECTS {
           cfgWlanNeighbourId ,
           cfgWlanNeighbourEnabled,
           cfgWlanNeighbourBSSID,
           cfgWlanNeighbourFrequency
           }
        STATUS  current
        DESCRIPTION
            "Wireless neighbour properties"
        ::= { groupCfgWireless 14 }

    groupCfgRouting OBJECT IDENTIFIER ::= { groupConfiguration 4 }

    groupCfgRouteDefault OBJECT-GROUP
        OBJECTS {
           cfgRouteDefGateway,
           cfgRouteDefGwOverride
           }
        STATUS  current
        DESCRIPTION
            "Routing Default Route Properties"
        ::= { groupCfgRouting 1 }

    groupCfgRouteTable OBJECT-GROUP
        OBJECTS {
           cfgRouteTableDestinationNetwork,
           cfgRouteTableGateway,
           cfgRouteTableEnabled,
           cfgRouteTableSource,
           cfgRouteTableCarpId
           }
        STATUS  current
        DESCRIPTION
            "Static Routes Group"
        ::= { groupCfgRouting 2 }

    groupCfgMRouteTable OBJECT-GROUP
        OBJECTS {
           cfgMRouteTableEnabled,
           cfgMRouteTableInput,
           cfgMRouteTableSource,
           cfgMRouteTableGroup,
           cfgMRouteTableOutput
           }
        STATUS  current
        DESCRIPTION
            "Static Routes Group"
        ::= { groupCfgRouting 3 }

    groupCfgLogging OBJECT-GROUP
        OBJECTS {
           cfgLogRemoteEnabled,
           cfgLogRemoteLevel,
           cfgLogRemoteProtocol,
           cfgLogRemoteIp,
           cfgLogRemotePort
           }
        STATUS  current
        DESCRIPTION
            "Logging Properties"
        ::= { groupConfiguration 11 }

    groupCfgSnmp OBJECT IDENTIFIER
        ::= { groupConfiguration 12 }

    groupCfgSnmpd OBJECT-GROUP
        OBJECTS {
           cfgSnmpdLocation,
           cfgSnmpdContact,
           cfgSnmpdVersion,
           cfgSnmpdName,
           cfgSnmpdEnabled,
           cfgSnmpdAddress,
           cfgSnmpdComAdmin,
           cfgSnmpdComMaintainer,
           cfgSnmpdComMonitor
           }
        STATUS  current
        DESCRIPTION
            "SNMP Properties"
        ::= { groupCfgSnmp 1 }

    groupCfgSnmpTrap OBJECT-GROUP
        OBJECTS {
           cfgSnmpTrapEnabled,
           cfgSnmpTrapVersion,
           cfgSnmpTrapCommunity,
           cfgSnmpTrapDest
           }
        STATUS  current
        DESCRIPTION
            "SNMP Properties"
        ::= { groupCfgSnmp 10 }

    groupCfgDhcp OBJECT IDENTIFIER ::= { groupConfiguration 13 }

    groupCfgDhcpGlobal OBJECT-GROUP
        OBJECTS { cfgDhcpGlobalEnabled }
        STATUS  current
        DESCRIPTION
            "DHCP Global Properties"
        ::= { groupCfgDhcp 1 }

    groupCfgDhcpDnsmasq OBJECT-GROUP
        OBJECTS {
           cfgDhcpDnsmasqScopeParameter
           }
        STATUS  current
        DESCRIPTION
            "Dnsmasq Properties"
        ::= { groupCfgDhcp 2 }

    groupCfgDhcpScope OBJECT-GROUP
        OBJECTS {
           cfgDhcpScopeId,
           cfgDhcpScopeInterface,
           cfgDhcpScopeStart,
           cfgDhcpScopeLimit,
           cfgDhcpScopeLeasetime,
           cfgDhcpScopeGateway,
           cfgDhcpScopeDnsServer1,
           cfgDhcpScopeDnsServer2
           }
        STATUS  current
        DESCRIPTION
            "DHCP Individual Properties"
        ::= { groupCfgDhcp 3 }

   groupCfgNtp OBJECT-GROUP
       OBJECTS {
          cfgNtpEnabled,
          cfgNtpServer1,
          cfgNtpServer2
          }
       STATUS  current
       DESCRIPTION
           "NTP Client Properties"
       ::= { groupConfiguration 14 }

   groupCfgHttp OBJECT-GROUP
       OBJECTS {
          cfgHttpUser,
          cfgHttpPassword,
          cfgHttpEnabled,
          cfgHttpRedirectEnabled,
          cfgHttpHttpAddress,
          cfgHttpHttpsAddress
          }
       STATUS  current
       DESCRIPTION
           "HTTP Server Properties"
       ::= { groupConfiguration 15 }

   groupCfgLldp OBJECT-GROUP
       OBJECTS {
          cfgLldpEnabled,
          cfgLldpDescription
          }
       STATUS  current
       DESCRIPTION
           "HTTP Server Properties"
       ::= { groupConfiguration 16 }

   groupCfgMdns OBJECT-GROUP
       OBJECTS {
          cfgMdnsEnabled,
          cfgMdnsNetwork
          }
       STATUS  current
       DESCRIPTION
           "mDNS service properties"
       ::= { groupConfiguration 17 }

    groupCfgQos OBJECT IDENTIFIER ::= { groupConfiguration 18 }

    groupCfgQosGlobal OBJECT-GROUP
        OBJECTS {
           cfgQosL3PrioEnabled
           }
        STATUS  current
        DESCRIPTION
            "QoS general maintree properties"
        ::= { groupCfgQos 1 }

    groupCfgQosDscpToTidMapTable OBJECT-GROUP
        OBJECTS {
           cfgQosDscpToTidMapValue
           }
        STATUS  current
        DESCRIPTION
            "QoS L3 To L2 Map properties"
        ::= { groupCfgQos 2 }

    groupCfgQosVlanToTidMapTable OBJECT-GROUP
        OBJECTS {
           cfgQosVlanToTidMapValue
           }
        STATUS  current
        DESCRIPTION
            "Qos Vlan To L2 Priority properties"
        ::= { groupCfgQos 3 }

    groupCfgQosIpToTidMapTable OBJECT-GROUP
        OBJECTS {
           cfgQosIpToTidMapSrcNet,
           cfgQosIpToTidMapDestNet,
           cfgQosIpToTidMapProto,
           cfgQosIpToTidMapSrcPort,
           cfgQosIpToTidMapDestPort,
           cfgQosIpToTidMapPrecedence,
           cfgQosIpToTidMapEnabled
           }
        STATUS  current
        DESCRIPTION
            "QoS Flow Priority properties"
        ::= { groupCfgQos 4 }

   groupCfgNlm OBJECT-GROUP
       OBJECTS {
          cfgNlmGlblEnabled,
          cfgNlmMonEnabled,
          cfgNlmMonInterval,
          cfgNlmMonCount,
          cfgNlmMonType,
          cfgNlmMonInterfaces,
          cfgNlmMonDestination,
          cfgNlmMonUpAction,
          cfgNlmMonDownAction,
          cfgNlmMonScanLoopInterval
       }
       STATUS  current
       DESCRIPTION
           "Nlm properties"
       ::= { groupConfiguration 40 }

    groupCfgCli OBJECT-GROUP
       OBJECTS {
          cfgCliEnabled,
          cfgCliUsername,
          cfgCliPassword,
          cfgCliTelnetEnabled,
          cfgCliSshEnabled,
          cfgCliTelnetAddress,
          cfgCliSshAddress
          }
       STATUS  current
       DESCRIPTION
           "CLI Properties"
       ::= { groupConfiguration 100 }

    groupCfgCellular OBJECT IDENTIFIER ::= { groupConfiguration 101 }

    groupCfgCellSim OBJECT-GROUP
        OBJECTS {
           cfgCellSimApn,
           cfgCellSimUsername,
           cfgCellSimPassword,
           cfgCellSimPinEnabled,
           cfgCellSimPin,
           cfgCellSimAuthType
           }
        STATUS  current
        DESCRIPTION
            "Cellular Properties"
        ::= { groupCfgCellular 1 }

-- RPC Groups
-- ==========

    groupRpcConfiguration OBJECT-GROUP
        OBJECTS {
           rpcCfgRevert,
           rpcCfgApply,
           rpcCfgFile
           }
        STATUS  current
        DESCRIPTION
            "RPCs for Configuration"
        ::= { groupRpc 1 }

    groupRpcFirmware OBJECT-GROUP
        OBJECTS {
           rpcFwFlash
           }
        STATUS  current
        DESCRIPTION
            "RPCs for Firmware"
        ::= { groupRpc 2 }

    groupRpcSystem OBJECT-GROUP
        OBJECTS {
           rpcSysReboot,
           rpcSysFactoryReset,
           rpcSysErrorReset,
           rpcSysKernelLogReset
           }
        STATUS  current
        DESCRIPTION
            "RPCs for the System"
        ::= { groupRpc 3 }

    groupRpcCertificate OBJECT-GROUP
        OBJECTS {
           rpcCrtFile
           }
        STATUS  current
        DESCRIPTION
            "RPCs for HTTPS Certificate/Key"
        ::= { groupRpc 4 }

    groupRpcDriver OBJECT-GROUP
        OBJECTS {
           rpcDrvName,
           rpcDrvDfsSimulateRadar
           }
        STATUS  current
        DESCRIPTION
            "RPCs Software Driver"
        ::= { groupRpc 6 }

-- Settings Groups
-- ===============

    groupSetConfigurationFile OBJECT-GROUP
        OBJECTS {
           setCfgFileUrl
           }
        STATUS  current
        DESCRIPTION
            "Configuration File Settings"
        ::= { groupSettings 1 }

    groupSetWireless OBJECT-GROUP
        OBJECTS {
           setWlanDevName,
           setWlanDevRfOutput,
           setWlanDevFrequency,
           setWlanDevPower
           }
        STATUS  current
        DESCRIPTION
            "Wireless Settings"
        ::= { groupSettings 3 }

    groupSetWlanDbg OBJECT-GROUP
        OBJECTS {
           setWlanDbgIfaceName,
           setWlanDbgHandoff,
           setWlanDbgScan,
           setWlanDbgMlme,
           setWlanDbgEvents,
           setWlanDbgBeaconrssi,
           setWlanDbgAckrssi,
           setWlanDbgBeaconfiltered,
           setWlanDbgRatelimit,
           setWlanDbgBeacontsf,
           setWlanDbgRange,
           setWlanDbgReports
           }
        STATUS  current
        DESCRIPTION
            "Wireless Debug Properties"
        ::= { groupSettings 4 }

    groupSetConfmgmtd OBJECT-GROUP
        OBJECTS {
           setCfgdLogLevel
           }
        STATUS  current
        DESCRIPTION
            "Configuration Manager Daemon Settings"
        ::= { groupSettings 5 }

    groupSetFirmware OBJECT-GROUP
        OBJECTS {
           setFwFileUrl,
           setFwKeepConfig
           }
        STATUS  current
        DESCRIPTION
            "Firmware Settings"
        ::= { groupSettings 6 }

    groupSetCertificate OBJECT-GROUP
        OBJECTS {
           setCrtFileUrl,
           setCrtFileSelector,
           setCrtFileFormat,
           setCrtFilePkcs12Passphrase
           }
        STATUS  current
        DESCRIPTION
            "HTTPS Certificate/Key File Settings"
        ::= { groupSettings 7 }

    groupSetSystem OBJECT-GROUP
        OBJECTS {
           setSysTime
           }
        STATUS  current
        DESCRIPTION
            "System Settings"
        ::= { groupSettings 8 }


-- Hardware Groups
-- ===============

    groupHwSystem OBJECT-GROUP
        OBJECTS {
           hwSysProduct,
           hwSysSerial,
           hwSysRevision,
           hwSysVersion
           }
        STATUS  current
        DESCRIPTION
            "Hardware System"
        ::= { groupHardware 1 }

    groupHwNetwork OBJECT-GROUP
        OBJECTS {
           hwNetEthName,
           hwNetEthAssembled,
           hwNetEthMacAddress,
           hwNetEthOperation,
           hwNetEthSpeed,
           hwNetEthHwIndex
           }
        STATUS  current
        DESCRIPTION
            "Hardware Network"
        ::= { groupHardware 2 }

    groupHwWireless OBJECT-GROUP
        OBJECTS {
           hwWlanDevAssembled,
           hwWlanDevType,
           hwWlanDevSerial,
           hwWlanDevRevision,
           hwWlanDevVersion,
           hwWlanDevPcbId,
           hwWlanDevAssemblyId,
           hwWlanDevMacAddress,
           hwWlanDevAntennaProfileId,
           hwWlanDevAntennaGain,
           hwWlanDevCableLoss,
           hwWlanGlblRegulatoryRegionId
           }
        STATUS  current
        DESCRIPTION
            "Hardware Wireless"
        ::= { groupHardware 3 }

    groupHwBaseBoard OBJECT-GROUP
        OBJECTS {
           hwBbType,
           hwBbSerial,
           hwBbRevision,
           hwBbVersion,
           hwBbPcbId,
           hwBbAssemblyId
           }
        STATUS  current
        DESCRIPTION
            "Hardware Base Board"
        ::= { groupHardware 4 }

    groupHwIfaceBoard OBJECT-GROUP
        OBJECTS {
           hwIfBrdAssembled,
           hwIfBrdType,
           hwIfBrdSerial,
           hwIfBrdRevision,
           hwIfBrdVersion,
           hwIfBrdPcbId,
           hwIfBrdAssemblyId
           }
        STATUS  current
        DESCRIPTION
            "Hardware Interface Board"
        ::= { groupHardware 5 }

    groupHwSensor OBJECT-GROUP
        OBJECTS {
           hwSensorName,
           hwSensorUnit,
           hwSensorValue
           }
        STATUS  current
        DESCRIPTION
            "Hardware Sensors"
        ::= { groupHardware 7 }


-- Software Groups
-- ===============

    groupSwFirmware OBJECT-GROUP
        OBJECTS {
           swFwName,
           swFwVersion,
           swFwRevision
           }
        STATUS  current
        DESCRIPTION
            "Software Firmware"
        ::= { groupSoftware 1 }

    groupSwSystem OBJECT-GROUP
        OBJECTS {
           swSysRebootReason,
           swSysBootStatus,
           swSysMsgPriority,
           swSysMsgCode,
           swSysMsgText
           }
        STATUS  current
        DESCRIPTION
            "Software System"
        ::= { groupSoftware 2 }

    groupSwOperatingSystem OBJECT-GROUP
        OBJECTS {
           swOsName,
           swOsVersion,
           swOsRevision,
           swOsUptime
           }
        STATUS  current
        DESCRIPTION
            "Software System"
        ::= { groupSoftware 3 }

    groupSwDrvDfs OBJECT-GROUP
        OBJECTS {
           swDrvDfsName,
           swDrvDfsPulsesDetected,
           swDrvDfsPulsesProcessed,
           swDrvDfsRadarDetected
           }
        STATUS  current
        DESCRIPTION
            "Software Driver DFS Statistics"
        ::= { groupSoftware 4 }

    groupSwDrvCntWlanMac OBJECT-GROUP
        OBJECTS {
           swDrvCntWlanMacName,
           swDrvCntWlanMacTxHandlersDrop,
           swDrvCntWlanMacTxHandlersQueued,
           swDrvCntWlanMacTxHandlersDropUnencrypted,
           swDrvCntWlanMacTxHandlersDropFragment,
           swDrvCntWlanMacTxHandlersDropWep,
           swDrvCntWlanMacTxHandlersDropNotAssoc,
           swDrvCntWlanMacTxHandlersDropUnauthPort,
           swDrvCntWlanMacRxHandlersDrop,
           swDrvCntWlanMacRxHandlersQueued,
           swDrvCntWlanMacRxHandlersDropNullfunc,
           swDrvCntWlanMacRxHandlersDropDefrag,
           swDrvCntWlanMacRxHandlersDropShort,
           swDrvCntWlanMacTxExpandSkbHead,
           swDrvCntWlanMacTxExpandSkbHeadCloned,
           swDrvCntWlanMacRxExpandSkbHead,
           swDrvCntWlanMacRxExpandSkbHead2,
           swDrvCntWlanMacRxHandlersFragments,
           swDrvCntWlanMacTxstatusDrop
           }
        STATUS  current
        DESCRIPTION
            "Software Driver DFS Statistics"
        ::= { groupSoftware 7 }

    groupSwDrvCntWlanWmm OBJECT-GROUP
        OBJECTS {
           swDrvCntWlanWmmName,
           swDrvCntWlanWmmTx,
           swDrvCntWlanWmmRx,
           swDrvCntWlanWmmShortRetries,
           swDrvCntWlanWmmLongRetries,
           swDrvCntWlanWmmExceededRetries
           }
        STATUS  current
        DESCRIPTION
            "Software Driver WMM Statistics"
        ::= { groupSoftware 8 }

    groupSwDrvConStat OBJECT-GROUP
        OBJECTS {
           swDrvConStatWlanName,
           swDrvConStatMacName,
           swDrvConStatRxBrExtra,
           swDrvConStatRxBrType,
           swDrvConStatRxBrValue,
           swDrvConStatRxBytes,
           swDrvConStatRxPackets,
           swDrvConStatTxBrExtra,
           swDrvConStatTxBrType,
           swDrvConStatTxBrValue,
           swDrvConStatTxBytes,
           swDrvConStatTxPackets,
           swDrvConStatSigChain0,
           swDrvConStatSigChain1,
           swDrvConStatSigChain2,
           swDrvConStatSigAvgChain0,
           swDrvConStatSigAvgChain1,
           swDrvConStatSigAvgChain2,
           swDrvConStatTxRetries,
           swDrvConStatTxFailed,
           swDrvConStatCacheNo,
           swDrvConStatSigCombined,
           swDrvConStatSigAvgCombined,
           swDrvConStatWlanIf
           }
        STATUS  current
        DESCRIPTION
            "Software Driver Connection Status"
        ::= { groupSoftware 9 }

    groupSwDrvCntWlanTable OBJECT-GROUP
        OBJECTS {
           swDrvCntWlanName,
           swDrvCntWlanAssocSuccess,
           swDrvCntWlanAssocFailure,
           swDrvCntWlanAssocFailureMaxSta,
           swDrvCntWlanNumAssocSta,
           swDrvCntWlanEapAuthStarted,
           swDrvCntWlanEapAuthFailed,
           swDrvCntWlanChannelActive,
           swDrvCntWlanChannelBusy,
           swDrvCntWlanChannelTransmit,
           swDrvCntWlanChannelReceive,
           swDrvCntWlanChannelNoise,
           swDrvCntWlanEapAuthStartedFT,
           swDrvCntWlanEapAuthStartedFILS,
           swDrvCntWlanEapAuthStartedPKMSA
           }
        STATUS  current
        DESCRIPTION
            "Software Driver Wlan Counters"
        ::= { groupSoftware 10 }

    groupSwRdm OBJECT-GROUP
        OBJECTS {
           swRdmMaxEirp,
           swRdmMaxApp
           }
        STATUS  current
        DESCRIPTION
            "Software RDM"
        ::= { groupSoftware 11 }

    groupSwBootloader OBJECT-GROUP
        OBJECTS {
           swBootName,
           swBootVersion,
           swBootBuildDate
           }
        STATUS  current
        DESCRIPTION
            "Bootloader Informations"
        ::= { groupSoftware 20 }

    groupSwConfiguration OBJECT-GROUP
        OBJECTS {
            swCfgChangesCount
            }
        STATUS  current
        DESCRIPTION
            "Device Configuration Information"
        ::= { groupSoftware 30 }


-- * * * * * * * * * * * * * * * * * * * * * * * * * * * * * * * * * * *
-- *  End GROUPS
-- **********************************************************************

-- **********************************************************************
-- *  Begin COMPLIANCE STATEMENTS
-- * * * * * * * * * * * * * * * * * * * * * * * * * * * * * * * * * * *

    compliance MODULE-COMPLIANCE
    STATUS current
    DESCRIPTION
        "Implementation requirements for DT50 bindings"
    MODULE  -- this module
        MANDATORY-GROUPS {
            groupCfgSystem,
            groupCfgNetEthernet,
            groupCfgNetWlan,
            groupCfgNetVlan,
            groupCfgNetIp,
            groupCfgNetCarp,
            groupCfgNetMacVLan,
            groupCfgNetWwan,
            groupCfgWlanDevice,
            groupCfgWlanInterface,
            groupCfgWlanHandoff,
            groupCfgWlanScanFreq,
            groupCfgWlanWme,
            groupCfgWlanDbg,
            groupCfgWlanAclBlack,
            groupCfgWlanAclWhite,
            groupCfgWlanGlobal,
            groupCfgWlan802dot1x,
            groupCfgWlan802dot1xAuth,
            groupCfgWlan802dot1xAcct,
            groupCfgWlan802dot11r,
            groupCfgWlanNeighbour,
            groupCfgRouteDefault,
            groupCfgRouteTable,
            groupCfgMRouteTable,
            groupCfgLogging,
            groupCfgSnmpd,
            groupCfgSnmpTrap,
            groupCfgDhcpGlobal,
            groupCfgDhcpDnsmasq,
            groupCfgDhcpScope,
            groupCfgNtp,
            groupCfgHttp,
            groupCfgLldp,
            groupCfgMdns,
            groupCfgQos,
            groupCfgQosGlobal,
            groupCfgQosDscpToTidMapTable,
            groupCfgQosVlanToTidMapTable,
            groupCfgQosIpToTidMapTable,
            groupCfgNlm,
            groupCfgCli,
            groupCfgCellSim,

            groupRpcConfiguration,
            groupRpcFirmware,
            groupRpcSystem,
            groupRpcCertificate,
            groupRpcDriver,

            groupSetConfigurationFile,
            groupSetWireless,
            groupSetWlanDbg,
            groupSetConfmgmtd,
            groupSetFirmware,
            groupSetCertificate,
            groupSetSystem,

            groupHwSystem,
            groupHwNetwork,
            groupHwWireless,
            groupHwBaseBoard,
            groupHwIfaceBoard,
            groupHwSensor,

            groupSwFirmware,
            groupSwSystem,
            groupSwOperatingSystem,
            groupSwDrvDfs,
            groupSwDrvCntWlanMac,
            groupSwDrvCntWlanWmm,
            groupSwDrvConStat,
            groupSwDrvCntWlanTable,
            groupSwRdm,
            groupSwBootloader,
            groupSwConfiguration
        }
    ::= { compliances 1 }

-- * * * * * * * * * * * * * * * * * * * * * * * * * * * * * * * * * * *
-- *  End COMPLIANCE STATEMENTS
-- **********************************************************************

-- * * * * * * * * * * * * * * * * * * * * * * * * * * * * * * * * * * *
-- *  End of MIB DEFINITION
-- **********************************************************************
END


-- **********************************************************************
-- **********************************************************************

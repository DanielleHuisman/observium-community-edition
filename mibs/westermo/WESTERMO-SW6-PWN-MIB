-- *****************************************************************
-- WESTERMO-SW6-PWN-MIB :
-- SNMP feature configuration of Westermo devices with SW6.
--
-- Copyright (c) 2019 by Westermo Teleindustri AB
-- All rights reserved.
-- *****************************************************************

-- *****************************************************************
-- This script has been tested using the SMI checker smilint
-- the tool can be downloaded at
-- http://www.ibr.cs.tu-bs.de/projects/libsmi/smilint.html
-- or use alternatively the online version at:
-- http://www.simpleweb.org/ietf/mibs/validate/
--
-- smilint -m -s -l 6 -i nameLength-32 ./WESTERMO-SW6-PWN-MIB
-- Ensure that all needed MIBS are located in the SMIPATH.
-- *****************************************************************

-- **********************************************************************
-- * PWN MIB
-- **********************************************************************

WESTERMO-SW6-PWN-MIB DEFINITIONS ::= BEGIN

IMPORTS
    MODULE-IDENTITY, OBJECT-TYPE           FROM SNMPv2-SMI
    DisplayString                          FROM SNMPv2-TC
    MODULE-COMPLIANCE, OBJECT-GROUP        FROM SNMPv2-CONF;

-- **********************************************************************
-- *  MODULE IDENTITY
-- **********************************************************************
pwn MODULE-IDENTITY
    LAST-UPDATED "201909060000Z"
    ORGANIZATION "Westermo Teleindustri AB"
    CONTACT-INFO "E-mail: info@westermo.com"
    DESCRIPTION
            "MIB Module for the Westermo RT-300 Radio Modem Device - PWN
            definitions"

    REVISION     "201909060000Z"
    DESCRIPTION  "Release 6.9.0-RC0"

    ::= { iso(1) org(3) dod(6) internet(1) private(4) enterprises(1)
          westermo(16177) products(1) rt(400) feature(2) 9 }

-- *********************************************************************
-- *  Begin Major sections
-- * * * * * * * * * * * * * * * * * * * * * * * * * * * * * * * * * * *

--  Configuration
--  =============

configuration                   OBJECT IDENTIFIER ::= { pwn 1 }
    cfgWireless                 OBJECT IDENTIFIER ::= { configuration 1 }

--  Conformance Information
--  =======================

conformance                     OBJECT IDENTIFIER ::= { pwn 10000 }
    groups                      OBJECT IDENTIFIER ::= { conformance 1 }
        groupConfiguration      OBJECT IDENTIFIER ::= { groups 1 }
    compliances                 OBJECT IDENTIFIER ::= { conformance 2 }

-- * * * * * * * * * * * * * * * * * * * * * * * * * * * * * * * * * * *
-- *  End Major Sections
-- *********************************************************************

-- *********************************************************************
-- *  Begin Object Types
-- * * * * * * * * * * * * * * * * * * * * * * * * * * * * * * * * * * *

-- Band Steering

cfgWlanBandsteering OBJECT IDENTIFIER ::= { cfgWireless 1 }

cfgWlanBsteerEnabled OBJECT-TYPE
    SYNTAX INTEGER { disabled(0), enabled(1) }
    MAX-ACCESS read-write
    STATUS     current
    DESCRIPTION
        "Enable Band Steering.

        Band steering is a technique used in dual-band (2G4 and 5G) wireless
        setups to encourage dual-band STAs to use the less-congested band.

        Applies to AP. 802.11ac products only."
    ::= { cfgWlanBandsteering 1 }

cfgWlanBsteerMatchingSsid OBJECT-TYPE
    SYNTAX DisplayString (SIZE(1..255))
    MAX-ACCESS read-write
    STATUS     current
    DESCRIPTION
        "List of Matching SSIDs.

        This is a comma and/or space separated list of SSIDs. For each SSID,
        there shall be a matching SSID in the 2G4 and 5G band so that the band
        steering process is able to work and decide which STA shall be connected
        in which band.

        Applies to AP. 802.11ac products only."
    ::= { cfgWlanBandsteering 2 }

-- * * * * * * * * * * * * * * * * * * * * * * * * * * * * * * * * * * *
-- *  End of   Object Types
-- *********************************************************************

-- *********************************************************************
-- *  Begin GROUPS
-- * * * * * * * * * * * * * * * * * * * * * * * * * * * * * * * * * * *

groupCfgWlanBandsteering OBJECT-GROUP
    OBJECTS {
        cfgWlanBsteerEnabled,
        cfgWlanBsteerMatchingSsid
    }
    STATUS  current
    DESCRIPTION
        "Wireless Band Steering Configuration."
    ::= { groupConfiguration 1 }

-- * * * * * * * * * * * * * * * * * * * * * * * * * * * * * * * * * * *
-- *  End GROUPS
-- *********************************************************************

-- *********************************************************************
-- *  Begin COMPLIANCE STATEMENTS
-- * * * * * * * * * * * * * * * * * * * * * * * * * * * * * * * * * * *

compliance MODULE-COMPLIANCE
    STATUS current
    DESCRIPTION
        "Implementation Requirements for DT50 bindings"
    MODULE  -- this module
        MANDATORY-GROUPS {
            groupCfgWlanBandsteering
        }
    ::= { compliances 1 }

-- * * * * * * * * * * * * * * * * * * * * * * * * * * * * * * * * * * *
-- *  End COMPLIANCE STATEMENTS
-- *********************************************************************

-- * * * * * * * * * * * * * * * * * * * * * * * * * * * * * * * * * * *
-- *  End of MIB DEFINITION
-- *********************************************************************
END

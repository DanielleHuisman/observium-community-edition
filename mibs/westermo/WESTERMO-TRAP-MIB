-- *****************************************************************
-- WESTERMO-TRAP-MIB :
-- SNMP feature configuration of Westermo devices with SW6.
--
-- Copyright (c) 2018 by Westermo Teleindustri AB
-- All rights reserved.
-- *****************************************************************

-- *****************************************************************
-- This script has been tested using the SMI checker smilint
-- the tool can be downloaded at
-- http://www.ibr.cs.tu-bs.de/projects/libsmi/smilint.html
-- or use alternatively the online version at:
-- http://www.simpleweb.org/ietf/mibs/validate/
--
-- smilint -m -s -l 6 -i nameLength-32 ./WESTERMO-TRAP-MIB
-- Ensure that all needed MIBS are located in the SMIPATH.
-- *****************************************************************

-- **********************************************************************
-- *  Management Information Base - TRAPS
-- **********************************************************************

WESTERMO-TRAP-MIB DEFINITIONS ::= BEGIN

    IMPORTS
        MODULE-IDENTITY,
        OBJECT-TYPE, NOTIFICATION-TYPE          FROM SNMPv2-SMI
        DisplayString                           FROM SNMPv2-TC
        OBJECT-GROUP,
        MODULE-COMPLIANCE, NOTIFICATION-GROUP   FROM SNMPv2-CONF
    ;

-- **********************************************************************
-- *  MODULE IDENTITY
-- **********************************************************************
notification MODULE-IDENTITY
    LAST-UPDATED "201909060000Z"

    ORGANIZATION "Westermo Teleindustri AB"
    CONTACT-INFO "E-mail: info@westermo.com"
    DESCRIPTION  "MIB Module for the Westermo RT-300 Radio Modem Device - Trap definitions"

    REVISION     "201909060000Z"
    DESCRIPTION  "Release 6.9.0-RC0"

    ::= { iso(1) org(3) dod(6) internet(1) private(4) enterprises(1)
          westermo(16177) products(1) rt(400) 200 }

-- **********************************************************************
-- *  Begin Major sections
-- * * * * * * * * * * * * * * * * * * * * * * * * * * * * * * * * * * *

--  Traps (must be 0 to allow reversable mapping)
    rtTraps                OBJECT IDENTIFIER ::= { notification 0 }

--  Trap message types
    rtTrapMsg              OBJECT IDENTIFIER ::= { notification 1 }

--  Conformance Information
    rtTrapConformance      OBJECT IDENTIFIER ::= { notification 3 }
    rtTrapGroups           OBJECT IDENTIFIER ::= { rtTrapConformance 1 }
    rtTrapCompliances      OBJECT IDENTIFIER ::= { rtTrapConformance 2 }

-- * * * * * * * * * * * * * * * * * * * * * * * * * * * * * * * * * * *
-- *  End Major Sections
-- **********************************************************************


-- **********************************************************************
-- *  Begin Object Types
-- * * * * * * * * * * * * * * * * * * * * * * * * * * * * * * * * * * *
    trapMsgString OBJECT-TYPE
        SYNTAX DisplayString (SIZE(64))
        MAX-ACCESS   accessible-for-notify
        STATUS       current
        DESCRIPTION "Generic Error or Warning Message"
        ::= { rtTrapMsg 1 }

-- * * * * * * * * * * * * * * * * * * * * * * * * * * * * * * * * * * *
-- *  End of Object Types
-- **********************************************************************

-- **********************************************************************
-- *  Begin notifications Types
-- * * * * * * * * * * * * * * * * * * * * * * * * * * * * * * * * * * *

    notifyEmergency NOTIFICATION-TYPE
         OBJECTS {trapMsgString
                  }
         STATUS current
         DESCRIPTION "Indicate an EMERGENCY condition to the Manager"
         ::= { rtTraps 1 }

    notifyAlert NOTIFICATION-TYPE
         OBJECTS {trapMsgString
                  }
         STATUS current
         DESCRIPTION "Indicate an ALERT condition to the Manager"
         ::= { rtTraps 2 }

    notifyCritical NOTIFICATION-TYPE
         OBJECTS {trapMsgString
                  }
         STATUS current
         DESCRIPTION "Indicate an CRITICAL condition to the Manager"
         ::= { rtTraps 3 }

    notifyError NOTIFICATION-TYPE
         OBJECTS {trapMsgString
                  }
         STATUS current
         DESCRIPTION "Indicate an ERROR condition to the Manager"
         ::= { rtTraps 4 }

    notifyWarning NOTIFICATION-TYPE
          OBJECTS {trapMsgString
                  }
         STATUS current
         DESCRIPTION "Warning condition indicated to the Manager"
         ::= { rtTraps 5 }

    notifyNotice  NOTIFICATION-TYPE
         OBJECTS {trapMsgString
                  }
         STATUS current
         DESCRIPTION "Notifications sent to to the Manager"
         ::= { rtTraps 6 }

    notifyInfo  NOTIFICATION-TYPE
         OBJECTS {trapMsgString
                  }
         STATUS current
         DESCRIPTION "Notifications sent to to the Manager"
         ::= { rtTraps 7 }


-- * * * * * * * * * * * * * * * * * * * * * * * * * * * * * * * * * * *
-- *  End of notification Types
-- **********************************************************************



-- **********************************************************************
-- *  Begin GROUPS
-- * * * * * * * * * * * * * * * * * * * * * * * * * * * * * * * * * * *

    rtTrapMsgGroup OBJECT-GROUP
        OBJECTS {
           trapMsgString
        }
        STATUS  current
        DESCRIPTION "
            System Trap Message Group"
        ::= { rtTrapGroups 1 }


    rtTrapGroup NOTIFICATION-GROUP
        NOTIFICATIONS {
            notifyEmergency,
            notifyAlert,
            notifyCritical,
            notifyError,
            notifyWarning,
            notifyNotice,
            notifyInfo
        }
        STATUS  current
        DESCRIPTION "
            System Trap Group"
        ::= { rtTrapGroups 2 }

-- * * * * * * * * * * * * * * * * * * * * * * * * * * * * * * * * * * *
-- *  End GROUPS
-- **********************************************************************


-- **********************************************************************
-- *  Begin COMPLIANCE STATEMENTS
-- * * * * * * * * * * * * * * * * * * * * * * * * * * * * * * * * * * *

    rttrapCompliance MODULE-COMPLIANCE
    STATUS current
    DESCRIPTION
        "Implementation Requirements for a DT50 Radio Modem"
    MODULE  -- this module
        MANDATORY-GROUPS {
            rtTrapMsgGroup,
            rtTrapGroup
        }
    ::= { rtTrapCompliances 1 }

-- * * * * * * * * * * * * * * * * * * * * * * * * * * * * * * * * * * *
-- *  End COMPLIANCE STATEMENTS
-- **********************************************************************

-- * * * * * * * * * * * * * * * * * * * * * * * * * * * * * * * * * * *
-- *  End of MIB DEFINITION
-- **********************************************************************
END


-- **********************************************************************
-- **********************************************************************

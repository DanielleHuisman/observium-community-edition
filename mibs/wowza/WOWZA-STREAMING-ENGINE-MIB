-- __          __                    
-- \ \        / /                    
--  \ \  /\  / /____      ________ _ 
--   \ \/  \/ / _ \ \ /\ / /_  / _` |
--    \  /\  / |_| \ V  V / / / |_| |
--     \/  \/ \___/ \_/\_/ /___\__,_|
--                                   
--  __  __          _ _          _____           _                     
-- |  \/  |        | (_)        / ____|         | |                    
-- | \  / | ___  __| |_  __ _  | (___  _   _ ___| |_ ___ _ __ ___  ___ 
-- | |\/| |/ _ \/ _` | |/ _` |  \___ \| | | / __| __/ _ \ '_ | _ \/ __|
-- | |  | |  __/ |_| | | |_| |  ____) | |_| \__ \ ||  __/ | | | | \__ \
-- |_|  |_|\___|\__,_|_|\__,_| |_____/ \___ |___/\__\___|_| |_| |_|___/
--                                      __/ |                          
--                                     |___/                           
--   _____ _                            _               ______             _            
--  / ____| |                          |_|             |  ____|           |_|           
-- | (___ | |_ _ __ ___  __ _ _ __ ___  _ _ __   __ _  | |__   _ __   __ _ _ _ __   ___ 
--  \___ \| __| '__/ _ \/ _` | '_ | _ \| | '_ \ / _| | |  __| | '_ \ / _' | | |_ \ / _ \
--  ____) | |_| | |  __/ |_| | | | | | | | | | | |_| | | |____| | | | |_| | | | | |  __/
-- |_____/ \__|_|  \___|\__,_|_| |_| |_|_|_| |_|\___ | |______|_| |_|\___ |_|_| |_|\___|
--                                               __/ |                __/ |             
--                                              |___/                |___/             
--
WOWZA-STREAMING-ENGINE-MIB DEFINITIONS ::= BEGIN

IMPORTS
   MODULE-IDENTITY				FROM SNMPv2-SMI
   MODULE-COMPLIANCE				FROM SNMPv2-CONF
   enterprises					FROM SNMPv2-SMI
   DisplayString				FROM SNMPv2-TC
   OBJECT-TYPE					FROM RFC-1212
   OBJECT-GROUP					FROM SNMPv2-CONF
   Counter32					FROM SNMPv2-SMI
   Counter64				 	FROM SNMPv2-SMI
   Integer32				 	FROM SNMPv2-SMI
   TruthValue					FROM SNMPv2-TC;

wowzaStreamingEngineMIB MODULE-IDENTITY
    LAST-UPDATED "201603210000Z"
    ORGANIZATION "Wowza Media Systems LLC"
    CONTACT-INFO
        "

         postal:   Wowza Media Systems, LLC
                   523 Park Point Drive, Suite 300
                   Golden, CO 80401 USA

         email:    legalnotices&wowza.com
        "
    DESCRIPTION
        "First Production SNMP MIB for Wowza Streaming Engine."
    REVISION     "201603210000Z"
    DESCRIPTION
        "First Draft SNMP MIB Wowza Streaming Engine."
    REVISION     "201603090000Z"
    DESCRIPTION
        "First Draft SNMP MIB Wowza Streaming Engine."
    ::= { wowzamediasystems 100 }

wowzamediasystems	OBJECT IDENTIFIER ::=  { enterprises 46706 }
conformance		OBJECT IDENTIFIER ::=  { wowzaStreamingEngineMIB 1 }
servers			OBJECT IDENTIFIER ::=  { wowzaStreamingEngineMIB 10 }
vhosts			OBJECT IDENTIFIER ::=  { wowzaStreamingEngineMIB 20 }
applications		OBJECT IDENTIFIER ::=  { wowzaStreamingEngineMIB 30 }
applicationInstances	OBJECT IDENTIFIER ::=  { wowzaStreamingEngineMIB 40 }
streams			OBJECT IDENTIFIER ::=  { wowzaStreamingEngineMIB 50 }
rtmpclients		OBJECT IDENTIFIER ::=  { wowzaStreamingEngineMIB 60 }
httpclients		OBJECT IDENTIFIER ::=  { wowzaStreamingEngineMIB 70 }
rtspclients		OBJECT IDENTIFIER ::=  { wowzaStreamingEngineMIB 80 }

serverInfo		OBJECT IDENTIFIER ::=  { servers 1 }
vhostInfo		OBJECT IDENTIFIER ::=  { vhosts 1 }
applicationInfo		OBJECT IDENTIFIER ::=  { applications 1 }
applicationInstanceInfo	OBJECT IDENTIFIER ::=  { applicationInstances 1 }
streamInfo		OBJECT IDENTIFIER ::=  { streams 1 }
rtmpclientInfo		OBJECT IDENTIFIER ::=  { rtmpclients 1 }
httpclientInfo		OBJECT IDENTIFIER ::=  { httpclients 1 }
rtspclientInfo		OBJECT IDENTIFIER ::=  { rtspclients 1 }

groups			OBJECT IDENTIFIER ::= { conformance 1 }
groupObject		OBJECT IDENTIFIER ::= { conformance 2 }
compliances		OBJECT IDENTIFIER ::= { conformance 3 }

-- group

groupServer		OBJECT IDENTIFIER ::=  { groups 10 }
groupServerInfo		OBJECT IDENTIFIER ::=  { groupServer 1 }

-- groupObject

serverGroupObject	OBJECT IDENTIFIER ::= { groupObject 10 }
vhostGroupObject	OBJECT IDENTIFIER ::= { groupObject 20 }
applicationGroupObject	OBJECT IDENTIFIER ::= { groupObject 30 }
applicationInstanceGroupObject	OBJECT IDENTIFIER ::= { groupObject 40 }
streamGroupObject	OBJECT IDENTIFIER ::= { groupObject 50 }
clientGroupObject		OBJECT IDENTIFIER ::= { groupObject 60 }

-- compliances

complianceServer	OBJECT IDENTIFIER ::=  { compliances 10 }
complianceVhost		OBJECT IDENTIFIER ::=  { compliances 20 }
complianceApplication	OBJECT IDENTIFIER ::=  { compliances 30 }
complianceApplicationInstance	OBJECT IDENTIFIER ::=  { compliances 40 } 
complianceStream	OBJECT IDENTIFIER ::=  { compliances 50 }
complianceClient	OBJECT IDENTIFIER ::=  { compliances 60 }

-- serverIndex description - start

serverGroupTable OBJECT-TYPE
	  SYNTAX	SEQUENCE OF ServerGroupEntry
	  MAX-ACCESS not-accessible
	  STATUS	current
	  DESCRIPTION
			"Description Yet To Be Added"
	  ::= { groupServerInfo 1 }

serverGroupEntry OBJECT-TYPE
	  SYNTAX	ServerGroupEntry
	  MAX-ACCESS not-accessible
	  STATUS	current
	  DESCRIPTION
			"An index table"
	  INDEX {
		serverIndex,
		vhostIndex,
		applicationIndex,
		applicationInstanceIndex,
		streamIndex,
		clientIndex
		}
	  ::= { serverGroupTable 1 }

ServerGroupEntry ::=
	  SEQUENCE {
		serverIndex			Integer32,
		vhostIndex			Integer32,
		applicationIndex		Integer32,
		applicationInstanceIndex	Integer32,
		streamIndex			Integer32,
		clientIndex			Counter32
	  }

serverIndex OBJECT-TYPE
	SYNTAX	Integer32 (1..2147483647)
	MAX-ACCESS read-only
	STATUS	current
	DESCRIPTION
		"serverIndex"
	::= { serverGroupEntry 1 }

vhostIndex OBJECT-TYPE
	SYNTAX	Integer32 (1..2147483647)
	MAX-ACCESS read-only
	STATUS	current
	DESCRIPTION
			 "vhostIndex"
	::= { serverGroupEntry 2 }

applicationIndex OBJECT-TYPE
	SYNTAX	Integer32 (1..2147483647)
	MAX-ACCESS read-only
	STATUS	current
	DESCRIPTION
			 "applicationIndex"
	::= { serverGroupEntry 3 }

applicationInstanceIndex OBJECT-TYPE
	SYNTAX	Integer32 (1..2147483647)
	MAX-ACCESS read-only
	STATUS	current
	DESCRIPTION
			 "applicationInstanceIndex"
	::= { serverGroupEntry 4 }

streamIndex OBJECT-TYPE
	SYNTAX	Integer32 (1..2147483647)
	MAX-ACCESS read-only
	STATUS	current
	DESCRIPTION
			 "streamIndex"
	::= { serverGroupEntry 5 }

clientIndex OBJECT-TYPE
	SYNTAX	Counter32
	MAX-ACCESS read-only
	STATUS	current
	DESCRIPTION
			 "clientIndex"
	::= { serverGroupEntry 6 }

-- vhostIndex description - end

-- ServerCounterTable - Start

serverCounterTable	OBJECT-TYPE
	SYNTAX	 SEQUENCE OF ServerCounterTable
	MAX-ACCESS  not-accessible
	STATUS	 current
	DESCRIPTION
		"Description Yet To Be Added"
	::= { serverInfo 1 }

serverCounterEntry	OBJECT-TYPE
	SYNTAX 	ServerCounterTable
	MAX-ACCESS  not-accessible
	STATUS	 current
	DESCRIPTION
		"Description Yet To Be Added"
	INDEX { serverIndex }
	::= { serverCounterTable 1 }
	
ServerCounterTable ::=
	SEQUENCE {
		serverCounterCreationTime					Counter64,
		serverCounterGetAdminGUID					DisplayString,
		serverCounterGetClientIdGeneratorRecycleDelaySize		Integer32,
		serverCounterGetClientIdGeneratorRecycleSize			Integer32,
		serverCounterGetClientIdGeneratorTimeout			Counter64,
		serverCounterGetCommittedVirtuallMemory				Counter64,
		serverCounterGetConnectionsMaximum				Counter64, 
		serverCounterGetCoreHandlerPoolSize				Integer32,
		serverCounterGetCoreTransportPoolSize				Integer32,
		serverCounterGetCryptoPoolActiveCount				Integer32,
		serverCounterGetCryptoPoolMaxSize				Integer32,
		serverCounterGetCurrentHeapSize					Counter64,
		serverCounterGetDateStarted 					DisplayString,
		serverCounterGetDefaultStreamPrefix 				DisplayString,
		serverCounterGetGUID 						DisplayString,
		serverCounterGetHTTPHeaderServer 				DisplayString,
		serverCounterGetLiveStreamTranscoderSessionCount 		Counter64,
		serverCounterGetLiveThreads 					Counter64,
		serverCounterGetMaxHeapSize					Counter64,
		serverCounterGetPeakThreads					Counter64,
		serverCounterGetPublishersMaximum 				Counter64,
		serverCounterGetRTMPTHeaderServer				DisplayString,
		serverCounterGetServerGUID 					DisplayString,
		serverCounterGetSessionGUID 					DisplayString,
		serverCounterGetTimeRunning 					DisplayString,
		serverCounterGetTranscoderLicenseInUse				Counter64,
		serverCounterGetTranscoderLicenseTotal 				Counter64,
		serverCounterGetVersion  					DisplayString
		}

serverCounterCreationTime    OBJECT-TYPE
   SYNTAX Counter64
   MAX-ACCESS read-only
   STATUS current
   DESCRIPTION
	 "Description Yet To Be Added"
   ::= { serverCounterEntry 1 }

serverCounterGetAdminGUID    OBJECT-TYPE
   SYNTAX DisplayString
   MAX-ACCESS read-only
   STATUS current
   DESCRIPTION
	 "Description Yet To Be Added"
   ::= { serverCounterEntry 2 }

serverCounterGetClientIdGeneratorRecycleDelaySize	OBJECT-TYPE
	SYNTAX Integer32
	MAX-ACCESS read-only
	STATUS current
	DESCRIPTION
	 "Description Yet To Be Added"
	::= { serverCounterEntry 3 }

serverCounterGetClientIdGeneratorRecycleSize 	OBJECT-TYPE
	SYNTAX Integer32
	MAX-ACCESS read-only
	STATUS current
	DESCRIPTION
	 "Description Yet To Be Added"
	::= { serverCounterEntry 4 }

serverCounterGetClientIdGeneratorTimeout   OBJECT-TYPE
	SYNTAX Counter64
	MAX-ACCESS read-only
	STATUS current
	DESCRIPTION
	 "Description Yet To Be Added"
	::= { serverCounterEntry 5 }

serverCounterGetCommittedVirtuallMemory    OBJECT-TYPE
	SYNTAX Counter64
	MAX-ACCESS read-only
	STATUS current
	DESCRIPTION
	 "Description Yet To Be Added"
	::= { serverCounterEntry 6 }

serverCounterGetConnectionsMaximum	OBJECT-TYPE
	SYNTAX Counter64
	MAX-ACCESS read-only
	STATUS current
	DESCRIPTION
	 "Description Yet To Be Added"
	::= { serverCounterEntry 7 }

serverCounterGetCoreHandlerPoolSize  	OBJECT-TYPE
	SYNTAX Integer32
	MAX-ACCESS read-only
	STATUS current
	DESCRIPTION
	 "Description Yet To Be Added"
	::= { serverCounterEntry 8 }

serverCounterGetCoreTransportPoolSize  	OBJECT-TYPE
	SYNTAX Integer32
	MAX-ACCESS read-only
	STATUS current
	DESCRIPTION
	 "Description Yet To Be Added"
	::= { serverCounterEntry 9 }

serverCounterGetCryptoPoolActiveCount	OBJECT-TYPE
	SYNTAX Integer32
	MAX-ACCESS read-only
	STATUS current
	DESCRIPTION
	 "Description Yet To Be Added"
	::= { serverCounterEntry 10 }

serverCounterGetCryptoPoolMaxSize	OBJECT-TYPE
	SYNTAX Integer32
	MAX-ACCESS read-only
	STATUS current
	DESCRIPTION
	 "Description Yet To Be Added"
	::= { serverCounterEntry 11 }


serverCounterGetCurrentHeapSize    OBJECT-TYPE
	SYNTAX Counter64
	MAX-ACCESS read-only
	STATUS current
	DESCRIPTION
	 "Description Yet To Be Added"
	::= { serverCounterEntry 12 }

serverCounterGetDateStarted    OBJECT-TYPE
	SYNTAX DisplayString
	MAX-ACCESS read-only
	STATUS current
	DESCRIPTION
	 "Description Yet To Be Added"
	::= { serverCounterEntry 13 }

serverCounterGetDefaultStreamPrefix	OBJECT-TYPE
	SYNTAX DisplayString
	MAX-ACCESS read-only
	STATUS current
	DESCRIPTION
	 "Description Yet To Be Added"
	::= { serverCounterEntry 14 }

serverCounterGetGUID	  OBJECT-TYPE
	SYNTAX DisplayString
	MAX-ACCESS read-only
	STATUS current
	DESCRIPTION
	 "Description Yet To Be Added"
	::= { serverCounterEntry 15 }

serverCounterGetHTTPHeaderServer   OBJECT-TYPE
	SYNTAX DisplayString
	MAX-ACCESS read-only
	STATUS current
	DESCRIPTION
	 "Description Yet To Be Added"
	::= { serverCounterEntry 16 }

serverCounterGetLiveStreamTranscoderSessionCount   OBJECT-TYPE
	SYNTAX Counter64
	MAX-ACCESS read-only
	STATUS current
	DESCRIPTION
	 "Description Yet To Be Added"
	::= { serverCounterEntry 17 }

serverCounterGetLiveThreads	OBJECT-TYPE
	SYNTAX Counter64
	MAX-ACCESS read-only
	STATUS current
	DESCRIPTION
	 "Description Yet To Be Added"
	::= { serverCounterEntry 18 }

serverCounterGetMaxHeapSize	OBJECT-TYPE
	SYNTAX Counter64
	MAX-ACCESS read-only
	STATUS current
	DESCRIPTION
	 "Description Yet To Be Added"
	::= { serverCounterEntry 19 }

serverCounterGetPeakThreads	OBJECT-TYPE
	SYNTAX Counter64
	MAX-ACCESS read-only
	STATUS current
	DESCRIPTION
	 "Description Yet To Be Added"
	::= { serverCounterEntry 20 }

serverCounterGetPublishersMaximum  OBJECT-TYPE
	SYNTAX Counter64
	MAX-ACCESS read-only
	STATUS current
	DESCRIPTION
	 "Description Yet To Be Added"
	::= { serverCounterEntry 21 }

serverCounterGetRTMPTHeaderServer  OBJECT-TYPE
	SYNTAX DisplayString
	MAX-ACCESS read-only
	STATUS current
	DESCRIPTION
	 "Description Yet To Be Added"
	::= { serverCounterEntry 22 }

serverCounterGetServerGUID OBJECT-TYPE
	SYNTAX DisplayString
	MAX-ACCESS read-only
	STATUS current
	DESCRIPTION
	 "Description Yet To Be Added"
	::= { serverCounterEntry 23 }

serverCounterGetSessionGUID	OBJECT-TYPE
	SYNTAX DisplayString
	MAX-ACCESS read-only
	STATUS current
	DESCRIPTION
	 "Description Yet To Be Added"
	::= { serverCounterEntry 24 }

serverCounterGetTimeRunning	OBJECT-TYPE
	SYNTAX DisplayString
	MAX-ACCESS read-only
	STATUS current
	DESCRIPTION
	 "Description Yet To Be Added"
	::= { serverCounterEntry 25 }

serverCounterGetTranscoderLicenseInUse	OBJECT-TYPE
	SYNTAX Counter64
	MAX-ACCESS read-only
	STATUS current
	DESCRIPTION
	 "Description Yet To Be Added"
	::= { serverCounterEntry 26 }

serverCounterGetTranscoderLicenseTotal	OBJECT-TYPE
	SYNTAX Counter64
	MAX-ACCESS read-only
	STATUS current
	DESCRIPTION
	 "Description Yet To Be Added"
	::= { serverCounterEntry 27 }

serverCounterGetVersion    OBJECT-TYPE
	SYNTAX DisplayString
	MAX-ACCESS read-only
	STATUS current
	DESCRIPTION
	 "Description Yet To Be Added"
	::= { serverCounterEntry 28 }

-- ServerCounterTable - End

-- ServerConnectTable - Start

serverConnectTable	 OBJECT-TYPE
	SYNTAX	 SEQUENCE OF ServerConnectEntry
	MAX-ACCESS  not-accessible
	STATUS	 current
	DESCRIPTION
		"Description Yet To Be Added"
	::= { serverInfo 2 }

serverConnectEntry	 OBJECT-TYPE
	SYNTAX	ServerConnectEntry
	MAX-ACCESS  not-accessible
	STATUS	 current
	DESCRIPTION
		"Description Yet To Be Added"
	INDEX { serverIndex }
	::= { serverConnectTable 1 }

ServerConnectEntry ::=
	SEQUENCE 
		{
		serverConnectCreationTime			Counter64,
		serverConnectGetCurrent				Counter64,
		serverConnectGetLastConnectAcceptedStamp	Counter64,
		serverConnectGetLastConnectAcceptedStampString  DisplayString,
		serverConnectGetLastConnectAcceptedTimeString	DisplayString,
		serverConnectGetLastConnectRejectedStamp	Counter64,
		serverConnectGetLastConnectRejectedStampString  DisplayString,
		serverConnectGetLastConnectRejectedTimeString	DisplayString,
		serverConnectGetLastDisconnectStamp		Counter64,
		serverConnectGetLastDisconnectStampString	DisplayString,
		serverConnectGetLastDisconnectTimeString	DisplayString,
		serverConnectGetTotal				Counter64,
		serverConnectGetTotalAccepted			Counter64,
		serverConnectGetTotalRejected			Counter64
		}

serverConnectCreationTime    OBJECT-TYPE
   SYNTAX Counter64
   MAX-ACCESS read-only
   STATUS current
   DESCRIPTION
	 "Description Yet To Be Added"
   ::= { serverConnectEntry 1 }

serverConnectGetCurrent    OBJECT-TYPE
   SYNTAX Counter64
   MAX-ACCESS read-only
   STATUS current
   DESCRIPTION
	 "Description Yet To Be Added"
   ::= { serverConnectEntry 2 }

serverConnectGetLastConnectAcceptedStamp    OBJECT-TYPE
   SYNTAX Counter64
   MAX-ACCESS read-only
   STATUS current
   DESCRIPTION
	 "Description Yet To Be Added"
   ::= { serverConnectEntry 3 }

serverConnectGetLastConnectAcceptedStampString    OBJECT-TYPE
   SYNTAX DisplayString
   MAX-ACCESS read-only
   STATUS current
   DESCRIPTION
	 "Description Yet To Be Added"
   ::= { serverConnectEntry 4 }

serverConnectGetLastConnectAcceptedTimeString    OBJECT-TYPE
   SYNTAX DisplayString
   MAX-ACCESS read-only
   STATUS current
   DESCRIPTION
	 "Description Yet To Be Added"
   ::= { serverConnectEntry 5 }

serverConnectGetLastConnectRejectedStamp    OBJECT-TYPE
   SYNTAX Counter64
   MAX-ACCESS read-only
   STATUS current
   DESCRIPTION
	 "Description Yet To Be Added"
   ::= { serverConnectEntry 6 }

serverConnectGetLastConnectRejectedStampString    OBJECT-TYPE
   SYNTAX DisplayString
   MAX-ACCESS read-only
   STATUS current
   DESCRIPTION
	 "Description Yet To Be Added"
   ::= { serverConnectEntry 7 }

serverConnectGetLastConnectRejectedTimeString    OBJECT-TYPE
   SYNTAX DisplayString
   MAX-ACCESS read-only
   STATUS current
   DESCRIPTION
	 "Description Yet To Be Added"
   ::= { serverConnectEntry 8 }

serverConnectGetLastDisconnectStamp    OBJECT-TYPE
   SYNTAX Counter64
   MAX-ACCESS read-only
   STATUS current
   DESCRIPTION
	 "Description Yet To Be Added"
   ::= { serverConnectEntry 9 }

serverConnectGetLastDisconnectStampString    OBJECT-TYPE
   SYNTAX DisplayString
   MAX-ACCESS read-only
   STATUS current
   DESCRIPTION
	 "Description Yet To Be Added"
   ::= { serverConnectEntry 10 }

serverConnectGetLastDisconnectTimeString    OBJECT-TYPE
   SYNTAX DisplayString
   MAX-ACCESS read-only
   STATUS current
   DESCRIPTION
	 "Description Yet To Be Added"
   ::= { serverConnectEntry 11 }

serverConnectGetTotal    OBJECT-TYPE
   SYNTAX Counter64
   MAX-ACCESS read-only
   STATUS current
   DESCRIPTION
	 "Description Yet To Be Added"
   ::= { serverConnectEntry 12 }

serverConnectGetTotalAccepted    OBJECT-TYPE
   SYNTAX Counter64
   MAX-ACCESS read-only
   STATUS current
   DESCRIPTION
	 "Description Yet To Be Added"
   ::= { serverConnectEntry 13 }

serverConnectGetTotalRejected    OBJECT-TYPE
   SYNTAX Counter64
   MAX-ACCESS read-only
   STATUS current
   DESCRIPTION
	 "Description Yet To Be Added"
   ::= { serverConnectEntry 14 }

-- ServerConnectTable - End

-- ServerPerformTable - Start

serverPerformTable OBJECT-TYPE
	SYNTAX	 SEQUENCE OF ServerPerformanceEntry
	MAX-ACCESS  not-accessible
	STATUS	 current
	DESCRIPTION
		"Description Yet To Be Added"
	::= { serverInfo 3 }

serverPerformEntry OBJECT-TYPE
	SYNTAX	 ServerPerformanceEntry
	MAX-ACCESS  not-accessible
	STATUS	 current
	DESCRIPTION
		"Description Yet To Be Added"
	INDEX { serverIndex }
	::= { serverPerformTable 1 }

ServerPerformanceEntry ::=
	SEQUENCE 
		{
		serverPerformCreationTime		Counter64,
		serverPerformGetFileInBytes		Counter64,
		serverPerformGetFileOutBytes		Counter64,
		serverPerformGetMessagesInBytes		Counter64,
		serverPerformGetMessagesInCount		Counter64,
		serverPerformGetMessagesInCountRate	Counter64,
		serverPerformGetMessagesLossBytes	Counter64,
		serverPerformGetMessagesLossCount	Counter64,
		serverPerformGetMessagesLossCountRate	Counter64,
		serverPerformGetMessagesOutBytes	Counter64,
		serverPerformGetMessagesOutCount	Counter64,
		serverPerformGetMessagesOutCountRate	Counter64
		}

serverPerformCreationTime    OBJECT-TYPE
   SYNTAX Counter64
   MAX-ACCESS read-only
   STATUS current
   DESCRIPTION
	 "Description Yet To Be Added"
   ::= { serverPerformEntry 1 }

serverPerformGetFileInBytes    OBJECT-TYPE
   SYNTAX Counter64
   MAX-ACCESS read-only
   STATUS current
   DESCRIPTION
	 "Description Yet To Be Added"
   ::= { serverPerformEntry 2 }

serverPerformGetFileOutBytes    OBJECT-TYPE
   SYNTAX Counter64
   MAX-ACCESS read-only
   STATUS current
   DESCRIPTION
	 "Description Yet To Be Added"
   ::= { serverPerformEntry 3 }

serverPerformGetMessagesInBytes    OBJECT-TYPE
   SYNTAX Counter64
   MAX-ACCESS read-only
   STATUS current
   DESCRIPTION
	 "Description Yet To Be Added"
   ::= { serverPerformEntry 4 }

serverPerformGetMessagesInCount    OBJECT-TYPE
   SYNTAX Counter64
   MAX-ACCESS read-only
   STATUS current
   DESCRIPTION
	 "Description Yet To Be Added"
   ::= { serverPerformEntry 5 }

serverPerformGetMessagesInCountRate    OBJECT-TYPE
   SYNTAX Counter64
   MAX-ACCESS read-only
   STATUS current
   DESCRIPTION
	 "Description Yet To Be Added"
   ::= { serverPerformEntry 6 }

serverPerformGetMessagesLossBytes    OBJECT-TYPE
   SYNTAX Counter64
   MAX-ACCESS read-only
   STATUS current
   DESCRIPTION
	 "Description Yet To Be Added"
   ::= { serverPerformEntry 7 }

serverPerformGetMessagesLossCount    OBJECT-TYPE
   SYNTAX Counter64
   MAX-ACCESS read-only
   STATUS current
   DESCRIPTION
	 "Description Yet To Be Added"
   ::= { serverPerformEntry 8 }

serverPerformGetMessagesLossCountRate    OBJECT-TYPE
   SYNTAX Counter64
   MAX-ACCESS read-only
   STATUS current
   DESCRIPTION
	 "Description Yet To Be Added"
   ::= { serverPerformEntry 9 }

serverPerformGetMessagesOutBytes    OBJECT-TYPE
   SYNTAX Counter64
   MAX-ACCESS read-only
   STATUS current
   DESCRIPTION
	 "Description Yet To Be Added"
   ::= { serverPerformEntry 10 }

serverPerformGetMessagesOutCount    OBJECT-TYPE
   SYNTAX Counter64
   MAX-ACCESS read-only
   STATUS current
   DESCRIPTION
	 "Description Yet To Be Added"
   ::= { serverPerformEntry 11 }

serverPerformGetMessagesOutCountRate    OBJECT-TYPE
   SYNTAX Counter64
   MAX-ACCESS read-only
   STATUS current
   DESCRIPTION
	 "Description Yet To Be Added"
   ::= { serverPerformEntry 12 }

-- ServerPerformTable - End

-- vhostCounterTable - Start

vhostCounterTable	 OBJECT-TYPE
	SYNTAX	 SEQUENCE OF VhostCounterTable
	MAX-ACCESS  not-accessible
	STATUS	 current
	DESCRIPTION
		"Description Yet To Be Added"
	::= { vhostInfo 1 }

vhostCounterEntry	 OBJECT-TYPE
	SYNTAX	VhostCounterTable
	MAX-ACCESS  not-accessible
	STATUS	 current
	DESCRIPTION
		"Description Yet To Be Added"
	INDEX { serverIndex, vhostIndex }
	::= { vhostCounterTable 1 }


VhostCounterTable ::=
	SEQUENCE 
		{
		vhostCounterCreationTime			Counter64,
		vhostCounterGetApplicationTimeout		Integer32,
		vhostCounterGetByteArrayOutputStreamBaseClassPath	DisplayString,
		vhostCounterGetClientCount			Integer32,
		vhostCounterGetClientIdleFrequency		Integer32,
		vhostCounterGetClientTimeout			Integer32,
		vhostCounterGetConnectionLimit			Integer32,
		vhostCounterGetCoreHandlerPoolSize		Integer32,
		vhostCounterGetCoreTransportPoolSize		Integer32,
		vhostCounterGetDateStarted			DisplayString,
		vhostCounterGetFileIOPoolSize			Integer32,
		vhostCounterGetHTTPStreamerMaxPathLen		Integer32,
		vhostCounterGetHomePath				DisplayString,
		vhostCounterGetIdleCheckFrequency		Integer32,
		vhostCounterGetIdleMinimumWaitTime		Integer32,
		vhostCounterGetIdleWorkerCount			Integer32,
		vhostCounterGetKeepAliveTimeout			Integer32,
		vhostCounterGetLiveStreamTranscoderSessionCount	Counter64,
		vhostCounterGetMaximumPendingReadBytes		Integer32,
		vhostCounterGetMaximumPendingWriteBytes		Integer32,
		vhostCounterGetMaximumSetBufferTime		Integer32,
		vhostCounterGetName				DisplayString,
		vhostCounterGetNetConnectionIdleFrequency	Integer32,
		vhostCounterGetNetConnectionProcessorCount	Integer32,
		vhostCounterGetNextMediaCasterId		Integer32,
		vhostCounterGetNextNetConnectionId		Integer32,
		vhostCounterGetPingTimeout			Integer32,
		vhostCounterGetRTPIdleFrequency			Integer32,
		vhostCounterGetRTSPMaxPathLen			Integer32,
		vhostCounterGetScheduledReadMaxSessionBytes	Counter64,
		vhostCounterGetScheduledWriteBytes		Counter64,
		vhostCounterGetScheduledWriteMaxSessionBytes	Counter64,
		vhostCounterGetScheduledWriteMaxSessionClientId	Integer32,
		vhostCounterGetScheduledWriteRequests		Counter64,
		vhostCounterGetScheduledWriteSessions		Counter64,
		vhostCounterGetStartupStreamsDelayTime		Integer32,
		vhostCounterGetTimeRunning			DisplayString,
		vhostCounterGetUnidentifiedSessionTimeout	Integer32,
		vhostCounterGetValidationFrequency		Integer32,
		vhostCounterGetWaitingReadBytes			Counter64,
		vhostCounterGetWebRTCIdleFrequency		Integer32
		}

vhostCounterCreationTime	OBJECT-TYPE
	SYNTAX Counter64
	MAX-ACCESS read-only
	STATUS current
	DESCRIPTION
	"Description Yet To Be Added"
	::= { vhostCounterEntry 1 }

vhostCounterGetApplicationTimeout	  OBJECT-TYPE
	SYNTAX Integer32
	MAX-ACCESS read-only
	STATUS current
	DESCRIPTION
	"Description Yet To Be Added"
	::= { vhostCounterEntry 2 }

vhostCounterGetByteArrayOutputStreamBaseClassPath	  OBJECT-TYPE
	SYNTAX DisplayString
	MAX-ACCESS read-only
	STATUS current
	DESCRIPTION
	"Description Yet To Be Added"
	::= { vhostCounterEntry 3 }

vhostCounterGetClientCount	 OBJECT-TYPE
	SYNTAX Integer32
	MAX-ACCESS read-only
	STATUS current
	DESCRIPTION
	"Description Yet To Be Added"
	::= { vhostCounterEntry 4 }

vhostCounterGetClientIdleFrequency	 OBJECT-TYPE
	SYNTAX Integer32
	MAX-ACCESS read-only
	STATUS current
	DESCRIPTION
	"Description Yet To Be Added"
	::= { vhostCounterEntry 5 }

vhostCounterGetClientTimeout    OBJECT-TYPE
	SYNTAX Integer32
	MAX-ACCESS read-only
	STATUS current
	DESCRIPTION
	"Description Yet To Be Added"
	::= { vhostCounterEntry 6 }

vhostCounterGetConnectionLimit  OBJECT-TYPE
	SYNTAX Integer32
	MAX-ACCESS read-only
	STATUS current
	DESCRIPTION
	"Description Yet To Be Added"
	::= { vhostCounterEntry 7 }

vhostCounterGetCoreHandlerPoolSize	 OBJECT-TYPE
	SYNTAX Integer32
	MAX-ACCESS read-only
	STATUS current
	DESCRIPTION
	"Description Yet To Be Added"
	::= { vhostCounterEntry 8 }

vhostCounterGetCoreTransportPoolSize    OBJECT-TYPE
	SYNTAX Integer32
	MAX-ACCESS read-only
	STATUS current
	DESCRIPTION
	"Description Yet To Be Added"
	::= { vhostCounterEntry 9 }

vhostCounterGetDateStarted	 OBJECT-TYPE
	SYNTAX DisplayString
	MAX-ACCESS read-only
	STATUS current
	DESCRIPTION
	"Description Yet To Be Added"
	::= { vhostCounterEntry 10 }

vhostCounterGetFileIOPoolSize   OBJECT-TYPE
	SYNTAX Integer32
	MAX-ACCESS read-only
	STATUS current
	DESCRIPTION
	"Description Yet To Be Added"
	::= { vhostCounterEntry 11 }

vhostCounterGetHTTPStreamerMaxPathLen   OBJECT-TYPE
	SYNTAX Integer32
	MAX-ACCESS read-only
	STATUS current
	DESCRIPTION
	"Description Yet To Be Added"
	::= { vhostCounterEntry 12 }

vhostCounterGetHomePath		OBJECT-TYPE
	SYNTAX DisplayString
	MAX-ACCESS read-only
	STATUS current
	DESCRIPTION
	"Description Yet To Be Added"
	::= { vhostCounterEntry 13 }

vhostCounterGetIdleCheckFrequency	  OBJECT-TYPE
	SYNTAX Integer32
	MAX-ACCESS read-only
	STATUS current
	DESCRIPTION
	"Description Yet To Be Added"
	::= { vhostCounterEntry 14 }

vhostCounterGetIdleMinimumWaitTime	 OBJECT-TYPE
	SYNTAX Integer32
	MAX-ACCESS read-only
	STATUS current
	DESCRIPTION
	"Description Yet To Be Added"
	::= { vhostCounterEntry 15 }

vhostCounterGetIdleWorkerCount  OBJECT-TYPE
	SYNTAX Integer32
	MAX-ACCESS read-only
	STATUS current
	DESCRIPTION
	"Description Yet To Be Added"
	::= { vhostCounterEntry 16 }

vhostCounterGetKeepAliveTimeout OBJECT-TYPE
	SYNTAX Integer32
	MAX-ACCESS read-only
	STATUS current
	DESCRIPTION
	"Description Yet To Be Added"
	::= { vhostCounterEntry 17 }

vhostCounterGetLiveStreamTranscoderSessionCount OBJECT-TYPE
	SYNTAX Counter64
	MAX-ACCESS read-only
	STATUS current
	DESCRIPTION
	"Description Yet To Be Added"
	::= { vhostCounterEntry 18 }

vhostCounterGetMaximumPendingReadBytes  OBJECT-TYPE
	SYNTAX Integer32
	MAX-ACCESS read-only
	STATUS current
	DESCRIPTION
	"Description Yet To Be Added"
	::= { vhostCounterEntry 19 }

vhostCounterGetMaximumPendingWriteBytes OBJECT-TYPE
	SYNTAX Integer32
	MAX-ACCESS read-only
	STATUS current
	DESCRIPTION
	"Description Yet To Be Added"
	::= { vhostCounterEntry 20 }

vhostCounterGetMaximumSetBufferTime	OBJECT-TYPE
	SYNTAX Integer32
	MAX-ACCESS read-only
	STATUS current
	DESCRIPTION
	"Description Yet To Be Added"
	::= { vhostCounterEntry 21 }

vhostCounterGetName	OBJECT-TYPE
	SYNTAX DisplayString
	MAX-ACCESS read-only
	STATUS current
	DESCRIPTION
	"Description Yet To Be Added"
	::= { vhostCounterEntry 22 }

vhostCounterGetNetConnectionIdleFrequency	  OBJECT-TYPE
	SYNTAX Integer32
	MAX-ACCESS read-only
	STATUS current
	DESCRIPTION
	"Description Yet To Be Added"
	::= { vhostCounterEntry 23 }

vhostCounterGetNetConnectionProcessorCount	 OBJECT-TYPE
	SYNTAX Integer32
	MAX-ACCESS read-only
	STATUS current
	DESCRIPTION
	"Description Yet To Be Added"
	::= { vhostCounterEntry 24 }

vhostCounterGetNextMediaCasterId	OBJECT-TYPE
	SYNTAX Integer32
	MAX-ACCESS read-only
	STATUS current
	DESCRIPTION
	"Description Yet To Be Added"
	::= { vhostCounterEntry 25 }

vhostCounterGetNextNetConnectionId	 OBJECT-TYPE
	SYNTAX Integer32
	MAX-ACCESS read-only
	STATUS current
	DESCRIPTION
	"Description Yet To Be Added"
	::= { vhostCounterEntry 26 }

vhostCounterGetPingTimeout	 OBJECT-TYPE
	SYNTAX Integer32
	MAX-ACCESS read-only
	STATUS current
	DESCRIPTION
	"Description Yet To Be Added"
	::= { vhostCounterEntry 27 }

vhostCounterGetRTPIdleFrequency OBJECT-TYPE
	SYNTAX Integer32
	MAX-ACCESS read-only
	STATUS current
	DESCRIPTION
	"Description Yet To Be Added"
	::= { vhostCounterEntry 28 }

vhostCounterGetRTSPMaxPathLen   OBJECT-TYPE
	SYNTAX Integer32
	MAX-ACCESS read-only
	STATUS current
	DESCRIPTION
	"Description Yet To Be Added"
	::= { vhostCounterEntry 29 }

vhostCounterGetScheduledReadMaxSessionBytes	OBJECT-TYPE
	SYNTAX Counter64
	MAX-ACCESS read-only
	STATUS current
	DESCRIPTION
	"Description Yet To Be Added"
	::= { vhostCounterEntry 30 }

vhostCounterGetScheduledWriteBytes	 OBJECT-TYPE
	SYNTAX Counter64
	MAX-ACCESS read-only
	STATUS current
	DESCRIPTION
	"Description Yet To Be Added"
	::= { vhostCounterEntry 31 }

vhostCounterGetScheduledWriteMaxSessionBytes    OBJECT-TYPE
	SYNTAX Counter64
	MAX-ACCESS read-only
	STATUS current
	DESCRIPTION
	"Description Yet To Be Added"
	::= { vhostCounterEntry 32 }

vhostCounterGetScheduledWriteMaxSessionClientId OBJECT-TYPE
	SYNTAX Integer32
	MAX-ACCESS read-only
	STATUS current
	DESCRIPTION
	"Description Yet To Be Added"
	::= { vhostCounterEntry 33 }

vhostCounterGetScheduledWriteRequests   OBJECT-TYPE
	SYNTAX Counter64
	MAX-ACCESS read-only
	STATUS current
	DESCRIPTION
	"Description Yet To Be Added"
	::= { vhostCounterEntry 34 }

vhostCounterGetScheduledWriteSessions   OBJECT-TYPE
	SYNTAX Counter64
	MAX-ACCESS read-only
	STATUS current
	DESCRIPTION
	"Description Yet To Be Added"
	::= { vhostCounterEntry 35 }

vhostCounterGetStartupStreamsDelayTime  OBJECT-TYPE
	SYNTAX Integer32
	MAX-ACCESS read-only
	STATUS current
	DESCRIPTION
	"Description Yet To Be Added"
	::= { vhostCounterEntry 36 }

vhostCounterGetTimeRunning	 OBJECT-TYPE
	SYNTAX DisplayString
	MAX-ACCESS read-only
	STATUS current
	DESCRIPTION
	"Description Yet To Be Added"
	::= { vhostCounterEntry 37 }

vhostCounterGetUnidentifiedSessionTimeout	  OBJECT-TYPE
	SYNTAX Integer32
	MAX-ACCESS read-only
	STATUS current
	DESCRIPTION
	"Description Yet To Be Added"
	::= { vhostCounterEntry 38 }

vhostCounterGetValidationFrequency	 OBJECT-TYPE
	SYNTAX Integer32
	MAX-ACCESS read-only
	STATUS current
	DESCRIPTION
	"Description Yet To Be Added"
	::= { vhostCounterEntry 39 }

vhostCounterGetWaitingReadBytes OBJECT-TYPE
	SYNTAX Counter64
	MAX-ACCESS read-only
	STATUS current
	DESCRIPTION
	"Description Yet To Be Added"
	::= { vhostCounterEntry 40 }

vhostCounterGetWebRTCIdleFrequency	 OBJECT-TYPE
	SYNTAX Integer32
	MAX-ACCESS read-only
	STATUS current
	DESCRIPTION
	"Description Yet To Be Added"
	::= { vhostCounterEntry 41 }

-- vhostCounterTable - End

-- vhostConnectTable - Start

vhostConnectTable	 OBJECT-TYPE
	SYNTAX	 SEQUENCE OF VhostConnectTable
	MAX-ACCESS  not-accessible
	STATUS	 current
	DESCRIPTION
		"Description Yet To Be Added"
	::= { vhostInfo 2 }

vhostConnectEntry	 OBJECT-TYPE
	SYNTAX	VhostConnectTable
	MAX-ACCESS  not-accessible
	STATUS	 current
	DESCRIPTION
		"An entry in the table, containing initial speed and"
	INDEX { serverIndex, vhostIndex }
	::= { vhostConnectTable 1 }

VhostConnectTable ::=
	SEQUENCE 
		{
		vhostConnectCreationTime			Counter64,
		vhostConnectGetCurrent				Counter64,		
		vhostConnectGetLastConnectAcceptedStamp		Counter64,
		vhostConnectGetLastConnectAcceptedStampString	DisplayString,
		vhostConnectGetLastConnectAcceptedTimeString	DisplayString,
		vhostConnectGetLastConnectRejectedStamp		Counter64,
		vhostConnectGetLastConnectRejectedStampString	DisplayString,
		vhostConnectGetLastConnectRejectedTimeString	DisplayString,
		vhostConnectGetLastDisconnectStamp		Counter64,
		vhostConnectGetLastDisconnectStampString	DisplayString,
		vhostConnectGetLastDisconnectTimeString		DisplayString,
		vhostConnectGetTotal				Counter64,
		vhostConnectGetTotalAccepted			Counter64,
		vhostConnectGetTotalRejected			Counter64
		}

vhostConnectCreationTime	 OBJECT-TYPE
	SYNTAX Counter64
	MAX-ACCESS read-only
	STATUS current
	DESCRIPTION
	"Description Yet To Be Added"
	::= { vhostConnectEntry 1 }

vhostConnectGetCurrent	 OBJECT-TYPE
	SYNTAX Counter64
	MAX-ACCESS read-only
	STATUS current
	DESCRIPTION
	"Description Yet To Be Added"
	::= { vhostConnectEntry 2 }

vhostConnectGetLastConnectAcceptedStamp	 OBJECT-TYPE
	SYNTAX Counter64
	MAX-ACCESS read-only
	STATUS current
	DESCRIPTION
	"Description Yet To Be Added"
	::= { vhostConnectEntry 3 }

vhostConnectGetLastConnectAcceptedStampString	 OBJECT-TYPE
	SYNTAX DisplayString
	MAX-ACCESS read-only
	STATUS current
	DESCRIPTION
	"Description Yet To Be Added"
	::= { vhostConnectEntry 4 }

vhostConnectGetLastConnectAcceptedTimeString	 OBJECT-TYPE
	SYNTAX DisplayString
	MAX-ACCESS read-only
	STATUS current
	DESCRIPTION
	"Description Yet To Be Added"
	::= { vhostConnectEntry 5 }

vhostConnectGetLastConnectRejectedStamp	 OBJECT-TYPE
	SYNTAX Counter64
	MAX-ACCESS read-only
	STATUS current
	DESCRIPTION
	"Description Yet To Be Added"
	::= { vhostConnectEntry 6 }

vhostConnectGetLastConnectRejectedStampString	 OBJECT-TYPE
	SYNTAX DisplayString
	MAX-ACCESS read-only
	STATUS current
	DESCRIPTION
	"Description Yet To Be Added"
	::= { vhostConnectEntry 7 }

vhostConnectGetLastConnectRejectedTimeString	 OBJECT-TYPE
	SYNTAX DisplayString
	MAX-ACCESS read-only
	STATUS current
	DESCRIPTION
	"Description Yet To Be Added"
	::= { vhostConnectEntry 8 }

vhostConnectGetLastDisconnectStamp	 OBJECT-TYPE
	SYNTAX Counter64
	MAX-ACCESS read-only
	STATUS current
	DESCRIPTION
	"Description Yet To Be Added"
	::= { vhostConnectEntry 9 }

vhostConnectGetLastDisconnectStampString	 OBJECT-TYPE
	SYNTAX DisplayString
	MAX-ACCESS read-only
	STATUS current
	DESCRIPTION
	"Description Yet To Be Added"
	::= { vhostConnectEntry 10 }

vhostConnectGetLastDisconnectTimeString	 OBJECT-TYPE
	SYNTAX DisplayString
	MAX-ACCESS read-only
	STATUS current
	DESCRIPTION
	"Description Yet To Be Added"
	::= { vhostConnectEntry 11 }

vhostConnectGetTotal	 OBJECT-TYPE
	SYNTAX Counter64
	MAX-ACCESS read-only
	STATUS current
	DESCRIPTION
	"Description Yet To Be Added"
	::= { vhostConnectEntry 12 }

vhostConnectGetTotalAccepted	 OBJECT-TYPE
	SYNTAX Counter64
	MAX-ACCESS read-only
	STATUS current
	DESCRIPTION
	"Description Yet To Be Added"
	::= { vhostConnectEntry 13 }

vhostConnectGetTotalRejected	 OBJECT-TYPE
	SYNTAX Counter64
	MAX-ACCESS read-only
	STATUS current
	DESCRIPTION
	"Description Yet To Be Added"
	::= { vhostConnectEntry 14 }

-- vhostConnectTable - End

-- vhostPerformTable - Start

vhostPerformTable	 OBJECT-TYPE
	SYNTAX	 SEQUENCE OF VhostPerformTable
	MAX-ACCESS  not-accessible
	STATUS	 current
	DESCRIPTION
		"Description Yet To Be Added"
	::= { vhostInfo 3 }

vhostPerformEntry	 OBJECT-TYPE
	SYNTAX	VhostPerformTable
	MAX-ACCESS  not-accessible
	STATUS	 current
	DESCRIPTION
		"Description Yet To Be Added"
	INDEX { serverIndex, vhostIndex }
	::= { vhostPerformTable 1 }

VhostPerformTable	::=
	SEQUENCE 
		{
		vhostPerformCreationTime		Counter64,
		vhostPerformGetFileInBytes		Counter64,
		vhostPerformGetFileOutBytes		Counter64,
		vhostPerformGetMessagesInBytes		Counter64,
		vhostPerformGetMessagesInCount		Counter64,
		vhostPerformGetMessagesInCountRate	Counter64,
		vhostPerformGetMessagesLossBytes	Counter64,
		vhostPerformGetMessagesLossCount	Counter64,
		vhostPerformGetMessagesLossCountRate	Counter64,
		vhostPerformGetMessagesOutBytes		Counter64,
		vhostPerformGetMessagesOutCount		Counter64,
		vhostPerformGetMessagesOutCountRate	Counter64
		}

vhostPerformCreationTime	 OBJECT-TYPE
	SYNTAX Counter64
	MAX-ACCESS read-only
	STATUS current
	DESCRIPTION
	"Description Yet To Be Added"
	::= { vhostPerformEntry 1 }

vhostPerformGetFileInBytes	 OBJECT-TYPE
	SYNTAX Counter64
	MAX-ACCESS read-only
	STATUS current
	DESCRIPTION
	"Description Yet To Be Added"
	::= { vhostPerformEntry 2 }

vhostPerformGetFileOutBytes	 OBJECT-TYPE
	SYNTAX Counter64
	MAX-ACCESS read-only
	STATUS current
	DESCRIPTION
	"Description Yet To Be Added"
	::= { vhostPerformEntry 3 }

vhostPerformGetMessagesInBytes	 OBJECT-TYPE
	SYNTAX Counter64
	MAX-ACCESS read-only
	STATUS current
	DESCRIPTION
	"Description Yet To Be Added"
	::= { vhostPerformEntry 4 }

vhostPerformGetMessagesInCount	 OBJECT-TYPE
	SYNTAX Counter64
	MAX-ACCESS read-only
	STATUS current
	DESCRIPTION
	"Description Yet To Be Added"
	::= { vhostPerformEntry 5 }

vhostPerformGetMessagesInCountRate	 OBJECT-TYPE
	SYNTAX Counter64
	MAX-ACCESS read-only
	STATUS current
	DESCRIPTION
	"Description Yet To Be Added"
	::= { vhostPerformEntry 6 }

vhostPerformGetMessagesLossBytes	 OBJECT-TYPE
	SYNTAX Counter64
	MAX-ACCESS read-only
	STATUS current
	DESCRIPTION
	"Description Yet To Be Added"
	::= { vhostPerformEntry 7 }

vhostPerformGetMessagesLossCount	 OBJECT-TYPE
	SYNTAX Counter64
	MAX-ACCESS read-only
	STATUS current
	DESCRIPTION
	"Description Yet To Be Added"
	::= { vhostPerformEntry 8 }

vhostPerformGetMessagesLossCountRate	 OBJECT-TYPE
	SYNTAX Counter64
	MAX-ACCESS read-only
	STATUS current
	DESCRIPTION
	"Description Yet To Be Added"
	::= { vhostPerformEntry 9 }

vhostPerformGetMessagesOutBytes	 OBJECT-TYPE
	SYNTAX Counter64
	MAX-ACCESS read-only
	STATUS current
	DESCRIPTION
	"Description Yet To Be Added"
	::= { vhostPerformEntry 10 }

vhostPerformGetMessagesOutCount	 OBJECT-TYPE
	SYNTAX Counter64
	MAX-ACCESS read-only
	STATUS current
	DESCRIPTION
	"Description Yet To Be Added"
	::= { vhostPerformEntry 11 }

vhostPerformGetMessagesOutCountRate	 OBJECT-TYPE
	SYNTAX Counter64
	MAX-ACCESS read-only
	STATUS current
	DESCRIPTION
	"Description Yet To Be Added"
	::= { vhostPerformEntry 12 }

-- vhostPerformTable - End

-- applicationCounterTable - Start

applicationCounterTable	 OBJECT-TYPE
	SYNTAX	 SEQUENCE OF ApplicationCounterTable
	MAX-ACCESS  not-accessible
	STATUS	 current
	DESCRIPTION
		"Description Yet To Be Added"
	::= { applicationInfo 1 }

applicationCounterEntry	 OBJECT-TYPE
	SYNTAX	ApplicationCounterTable
	MAX-ACCESS  not-accessible
	STATUS	 current
	DESCRIPTION
		"Description Yet To Be Added"
	INDEX { serverIndex, vhostIndex, applicationIndex }
	::= { applicationCounterTable 1 }

ApplicationCounterTable   ::=
	SEQUENCE 
		{
		applicationCounterCreationTime			Counter64,
		applicationCounterGetApplicationPath		DisplayString,
		applicationCounterGetConfigPath			DisplayString,
		applicationCounterGetDateStarted		DisplayString,
		applicationCounterGetInstanceCount		Integer32,
		applicationCounterGetMessagesInBytes		Counter64,
		applicationCounterGetMessagesInCount		Counter64,
		applicationCounterGetMessagesInCountRate	Counter64,
		applicationCounterGetMessagesOutBytes		Counter64,
		applicationCounterGetMessagesOutCount		Counter64,
		applicationCounterGetMessagesOutCountRate	Counter64,
		applicationCounterGetName			DisplayString,
		applicationCounterGetTimeRunning		DisplayString
		}

applicationCounterCreationTime	 OBJECT-TYPE
	SYNTAX Counter64
	MAX-ACCESS read-only
	STATUS current
	DESCRIPTION
	"Description Yet To Be Added"
	::= { applicationCounterEntry 1 }

applicationCounterGetApplicationPath	 OBJECT-TYPE
	SYNTAX DisplayString
	MAX-ACCESS read-only
	STATUS current
	DESCRIPTION
	"Description Yet To Be Added"
	::= { applicationCounterEntry 2 }

applicationCounterGetConfigPath	 OBJECT-TYPE
	SYNTAX DisplayString
	MAX-ACCESS read-only
	STATUS current
	DESCRIPTION
	"Description Yet To Be Added"
	::= { applicationCounterEntry 3 }

applicationCounterGetDateStarted	 OBJECT-TYPE
	SYNTAX DisplayString
	MAX-ACCESS read-only
	STATUS current
	DESCRIPTION
	"Description Yet To Be Added"
	::= { applicationCounterEntry 4 }

applicationCounterGetInstanceCount	 OBJECT-TYPE
	SYNTAX Integer32
	MAX-ACCESS read-only
	STATUS current
	DESCRIPTION
	"Description Yet To Be Added"
	::= { applicationCounterEntry 5 }

applicationCounterGetMessagesInBytes	 OBJECT-TYPE
	SYNTAX Counter64
	MAX-ACCESS read-only
	STATUS current
	DESCRIPTION
	"Description Yet To Be Added"
	::= { applicationCounterEntry 6 }

applicationCounterGetMessagesInCount	 OBJECT-TYPE
	SYNTAX Counter64
	MAX-ACCESS read-only
	STATUS current
	DESCRIPTION
	"Description Yet To Be Added"
	::= { applicationCounterEntry 7 }

applicationCounterGetMessagesInCountRate	 OBJECT-TYPE
	SYNTAX Counter64
	MAX-ACCESS read-only
	STATUS current
	DESCRIPTION
	"Description Yet To Be Added"
	::= { applicationCounterEntry 8 }

applicationCounterGetMessagesOutBytes	 OBJECT-TYPE
	SYNTAX Counter64
	MAX-ACCESS read-only
	STATUS current
	DESCRIPTION
	"Description Yet To Be Added"
	::= { applicationCounterEntry 9 }

applicationCounterGetMessagesOutCount	 OBJECT-TYPE
	SYNTAX Counter64
	MAX-ACCESS read-only
	STATUS current
	DESCRIPTION
	"Description Yet To Be Added"
	::= { applicationCounterEntry 10 }

applicationCounterGetMessagesOutCountRate	 OBJECT-TYPE
	SYNTAX Counter64
	MAX-ACCESS read-only
	STATUS current
	DESCRIPTION
	"Description Yet To Be Added"
	::= { applicationCounterEntry 11 }

applicationCounterGetName	 OBJECT-TYPE
	SYNTAX DisplayString
	MAX-ACCESS read-only
	STATUS current
	DESCRIPTION
	"Description Yet To Be Added"
	::= { applicationCounterEntry 12 }

applicationCounterGetTimeRunning	 OBJECT-TYPE
	SYNTAX DisplayString
	MAX-ACCESS read-only
	STATUS current
	DESCRIPTION
	"Description Yet To Be Added"
	::= { applicationCounterEntry 13 }

-- applicationCounterTable - End

-- applicationConnectTable - Start

applicationConnectTable	 OBJECT-TYPE
	SYNTAX	 SEQUENCE OF ApplicationConnectTable
	MAX-ACCESS  not-accessible
	STATUS	 current
	DESCRIPTION
		"Description Yet To Be Added"
	::= { applicationInfo 2 }

applicationConnectEntry	 OBJECT-TYPE
	SYNTAX	ApplicationConnectTable
	MAX-ACCESS  not-accessible
	STATUS	 current
	DESCRIPTION
		"Description Yet To Be Added"
	INDEX { serverIndex, vhostIndex, applicationIndex }
	::= { applicationConnectTable 1 }

ApplicationConnectTable   ::=
	SEQUENCE 
		{
		applicationConnectCreationTime				Counter64,
		applicationConnectGetCurrent				Counter64,
		applicationConnectGetLastConnectAcceptedStamp		Counter64,
		applicationConnectGetLastConnectAcceptedStampString	DisplayString,
		applicationConnectGetLastConnectAcceptedTimeString	DisplayString,
		applicationConnectGetLastConnectRejectedStamp		Counter64,
		applicationConnectGetLastConnectRejectedStampString	DisplayString,
		applicationConnectGetLastConnectRejectedTimeString	DisplayString,
		applicationConnectGetLastDisconnectStamp		Counter64,
		applicationConnectGetLastDisconnectStampString		DisplayString,
		applicationConnectGetLastDisconnectTimeString		DisplayString,
		applicationConnectGetTotal				Counter64,
		applicationConnectGetTotalAccepted			Counter64,
		applicationConnectGetTotalRejected			Counter64
		}

applicationConnectCreationTime	 OBJECT-TYPE
	SYNTAX Counter64
	MAX-ACCESS read-only
	STATUS current
	DESCRIPTION
	"Description Yet To Be Added"
	::= { applicationConnectEntry 1 }

applicationConnectGetCurrent	 OBJECT-TYPE
	SYNTAX Counter64
	MAX-ACCESS read-only
	STATUS current
	DESCRIPTION
	"Description Yet To Be Added"
	::= { applicationConnectEntry 2 }

applicationConnectGetLastConnectAcceptedStamp	 OBJECT-TYPE
	SYNTAX Counter64
	MAX-ACCESS read-only
	STATUS current
	DESCRIPTION
	"Description Yet To Be Added"
	::= { applicationConnectEntry 3 }

applicationConnectGetLastConnectAcceptedStampString	 OBJECT-TYPE
	SYNTAX DisplayString
	MAX-ACCESS read-only
	STATUS current
	DESCRIPTION
	"Description Yet To Be Added"
	::= { applicationConnectEntry 4 }

applicationConnectGetLastConnectAcceptedTimeString	 OBJECT-TYPE
	SYNTAX DisplayString
	MAX-ACCESS read-only
	STATUS current
	DESCRIPTION
	"Description Yet To Be Added"
	::= { applicationConnectEntry 5 }

applicationConnectGetLastConnectRejectedStamp	 OBJECT-TYPE
	SYNTAX Counter64
	MAX-ACCESS read-only
	STATUS current
	DESCRIPTION
	"Description Yet To Be Added"
	::= { applicationConnectEntry 6 }

applicationConnectGetLastConnectRejectedStampString	 OBJECT-TYPE
	SYNTAX DisplayString
	MAX-ACCESS read-only
	STATUS current
	DESCRIPTION
	"Description Yet To Be Added"
	::= { applicationConnectEntry 7 }

applicationConnectGetLastConnectRejectedTimeString	 OBJECT-TYPE
	SYNTAX DisplayString
	MAX-ACCESS read-only
	STATUS current
	DESCRIPTION
	"Description Yet To Be Added"
	::= { applicationConnectEntry 8 }

applicationConnectGetLastDisconnectStamp	 OBJECT-TYPE
	SYNTAX Counter64
	MAX-ACCESS read-only
	STATUS current
	DESCRIPTION
	"Description Yet To Be Added"
	::= { applicationConnectEntry 9 }

applicationConnectGetLastDisconnectStampString	 OBJECT-TYPE
	SYNTAX DisplayString
	MAX-ACCESS read-only
	STATUS current
	DESCRIPTION
	"Description Yet To Be Added"
	::= { applicationConnectEntry 10 }

applicationConnectGetLastDisconnectTimeString	 OBJECT-TYPE
	SYNTAX DisplayString
	MAX-ACCESS read-only
	STATUS current
	DESCRIPTION
	"Description Yet To Be Added"
	::= { applicationConnectEntry 11 }

applicationConnectGetTotal	 OBJECT-TYPE
	SYNTAX Counter64
	MAX-ACCESS read-only
	STATUS current
	DESCRIPTION
	"Description Yet To Be Added"
	::= { applicationConnectEntry 12 }

applicationConnectGetTotalAccepted	 OBJECT-TYPE
	SYNTAX Counter64
	MAX-ACCESS read-only
	STATUS current
	DESCRIPTION
	"Description Yet To Be Added"
	::= { applicationConnectEntry 13 }

applicationConnectGetTotalRejected	 OBJECT-TYPE
	SYNTAX Counter64
	MAX-ACCESS read-only
	STATUS current
	DESCRIPTION
	"Description Yet To Be Added"
	::= { applicationConnectEntry 14 }

-- applicationConnectTable - End

-- applicationPerformTable - Start

applicationPerformTable	 OBJECT-TYPE
	SYNTAX	 SEQUENCE OF ApplicationPerformTable
	MAX-ACCESS  not-accessible
	STATUS	 current
	DESCRIPTION
		"Description Yet To Be Added"
	::= { applicationInfo 3 }

applicationPerformEntry	 OBJECT-TYPE
	SYNTAX	ApplicationPerformTable
	MAX-ACCESS  not-accessible
	STATUS	 current
	DESCRIPTION
		"Description Yet To Be Added"
	INDEX { serverIndex, vhostIndex, applicationIndex }
	::= { applicationPerformTable 1 }

ApplicationPerformTable   ::=
	SEQUENCE 
		{
		applicationPerformCreationTime			Counter64,
		applicationPerformGetFileInBytes		Counter64,
		applicationPerformGetFileOutBytes		Counter64,
		applicationPerformGetMessagesInBytes		Counter64,
		applicationPerformGetMessagesInCount		Counter64,
		applicationPerformGetMessagesInCountRate	Counter64,
		applicationPerformGetMessagesLossBytes		Counter64,
		applicationPerformGetMessagesLossCount		Counter64,
		applicationPerformGetMessagesLossCountRate	Counter64,
		applicationPerformGetMessagesOutBytes		Counter64,
		applicationPerformGetMessagesOutCount		Counter64,
		applicationPerformGetMessagesOutCountRate	Counter64
		}

applicationPerformCreationTime	 OBJECT-TYPE
	SYNTAX Counter64
	MAX-ACCESS read-only
	STATUS current
	DESCRIPTION
	"Description Yet To Be Added"
	::= { applicationPerformEntry 1 }

applicationPerformGetFileInBytes	 OBJECT-TYPE
	SYNTAX Counter64
	MAX-ACCESS read-only
	STATUS current
	DESCRIPTION
	"Description Yet To Be Added"
	::= { applicationPerformEntry 2 }

applicationPerformGetFileOutBytes	 OBJECT-TYPE
	SYNTAX Counter64
	MAX-ACCESS read-only
	STATUS current
	DESCRIPTION
	"Description Yet To Be Added"
	::= { applicationPerformEntry 3 }

applicationPerformGetMessagesInBytes	 OBJECT-TYPE
	SYNTAX Counter64
	MAX-ACCESS read-only
	STATUS current
	DESCRIPTION
	"Description Yet To Be Added"
	::= { applicationPerformEntry 4 }

applicationPerformGetMessagesInCount	 OBJECT-TYPE
	SYNTAX Counter64
	MAX-ACCESS read-only
	STATUS current
	DESCRIPTION
	"Description Yet To Be Added"
	::= { applicationPerformEntry 5 }

applicationPerformGetMessagesInCountRate	 OBJECT-TYPE
	SYNTAX Counter64
	MAX-ACCESS read-only
	STATUS current
	DESCRIPTION
	"Description Yet To Be Added"
	::= { applicationPerformEntry 6 }

applicationPerformGetMessagesLossBytes	 OBJECT-TYPE
	SYNTAX Counter64
	MAX-ACCESS read-only
	STATUS current
	DESCRIPTION
	"Description Yet To Be Added"
	::= { applicationPerformEntry 7 }

applicationPerformGetMessagesLossCount	 OBJECT-TYPE
	SYNTAX Counter64
	MAX-ACCESS read-only
	STATUS current
	DESCRIPTION
	"Description Yet To Be Added"
	::= { applicationPerformEntry 8 }

applicationPerformGetMessagesLossCountRate	 OBJECT-TYPE
	SYNTAX Counter64
	MAX-ACCESS read-only
	STATUS current
	DESCRIPTION
	"Description Yet To Be Added"
	::= { applicationPerformEntry 9 }

applicationPerformGetMessagesOutBytes	 OBJECT-TYPE
	SYNTAX Counter64
	MAX-ACCESS read-only
	STATUS current
	DESCRIPTION
	"Description Yet To Be Added"
	::= { applicationPerformEntry 10 }

applicationPerformGetMessagesOutCount	 OBJECT-TYPE
	SYNTAX Counter64
	MAX-ACCESS read-only
	STATUS current
	DESCRIPTION
	"Description Yet To Be Added"
	::= { applicationPerformEntry 11 }

applicationPerformGetMessagesOutCountRate	 OBJECT-TYPE
	SYNTAX Counter64
	MAX-ACCESS read-only
	STATUS current
	DESCRIPTION
	"Description Yet To Be Added"
	::= { applicationPerformEntry 12 }

-- applicationPerformTable - End

-- applicationInstanceCounter - Start

applicationInstanceCounterTable	 OBJECT-TYPE
	SYNTAX	 SEQUENCE OF ApplicationInstanceCounterTable
	MAX-ACCESS  not-accessible
	STATUS	 current
	DESCRIPTION
		"Description Yet To Be Added"
	::= { applicationInstanceInfo 1 }

applicationInstanceCounterEntry	 OBJECT-TYPE
	SYNTAX	ApplicationInstanceCounterTable
	MAX-ACCESS  not-accessible
	STATUS	 current
	DESCRIPTION
		"aDescription Yet To Be Added"
	INDEX { serverIndex, vhostIndex, applicationIndex, applicationInstanceIndex }
	::= { applicationInstanceCounterTable 1 }

ApplicationInstanceCounterTable   ::=
	SEQUENCE 
		{
		applicationInstanceCounterCreationTime				Counter64,
		applicationInstanceCounterGetApplicationInstanceTouchTimeout	Integer32,
		applicationInstanceCounterGetApplicationTimeout			Integer32,
		applicationInstanceCounterGetClientCount			Integer32,
		applicationInstanceCounterGetClientCountTotal			Integer32,
		applicationInstanceCounterGetClientIdleFrequency		Integer32,
		applicationInstanceCounterGetClientRemoveTime			Counter64,
		applicationInstanceCounterGetContextStr				DisplayString,
		applicationInstanceCounterGetDateStarted			DisplayString,
		applicationInstanceCounterGetDvrRecorderList			DisplayString,
		applicationInstanceCounterGetHTTPStreamerList			DisplayString,
		applicationInstanceCounterGetHTTPStreamerSessionCount		Integer32,
		applicationInstanceCounterGetLastTouchTime			Counter64,
		applicationInstanceCounterGetLiveStreamPacketizerList		DisplayString,
		applicationInstanceCounterGetLiveStreamTranscoderList		DisplayString,
		applicationInstanceCounterGetMaxStorageDirDepth			Integer32,
		applicationInstanceCounterGetMaximumPendingReadBytes		Integer32,
		applicationInstanceCounterGetMaximumPendingWriteBytes		Integer32,
		applicationInstanceCounterGetMaximumSetBufferTime		Integer32,
		applicationInstanceCounterGetMediacasterRTPRTSPRTPTransportMode	Integer32,
		applicationInstanceCounterGetMessagesInBytes			Counter64,
		applicationInstanceCounterGetMessagesInCount			Counter64,
		applicationInstanceCounterGetMessagesInCountRate		Counter64,
		applicationInstanceCounterGetMessagesOutBytes			Counter64,
		applicationInstanceCounterGetMessagesOutCount			Counter64,
		applicationInstanceCounterGetMessagesOutCountRate		Counter64,
		applicationInstanceCounterGetName				DisplayString,
		applicationInstanceCounterGetPingTimeout			Integer32,
		applicationInstanceCounterGetPublisherCount			Integer32,
		applicationInstanceCounterGetPushPublishSessionCount		Integer32,
		applicationInstanceCounterGetRTPAVSyncMethod			Integer32,
		applicationInstanceCounterGetRTPIdleFrequency			Integer32,
		applicationInstanceCounterGetRTPMaxRTCPWaitTime			Integer32,
		applicationInstanceCounterGetRTPPlayAuthenticationMethod	DisplayString,
		applicationInstanceCounterGetRTPPublishAuthenticationMethod	DisplayString,
		applicationInstanceCounterGetRTPSessionCount			Integer32,
		applicationInstanceCounterGetRTSPBindIpAddress			DisplayString,
		applicationInstanceCounterGetRTSPConnectionAddressType		DisplayString,
		applicationInstanceCounterGetRTSPConnectionIpAddress		DisplayString,
		applicationInstanceCounterGetRTSPMaximumPendingWriteBytes	Integer32,
		applicationInstanceCounterGetRTSPOriginAddressType		DisplayString,
		applicationInstanceCounterGetRTSPOriginIpAddress		DisplayString,
		applicationInstanceCounterGetRTSPSessionTimeout			Integer32,
		applicationInstanceCounterGetRepeaterOriginUrl			DisplayString,
		applicationInstanceCounterGetRepeaterQueryString		DisplayString,
		applicationInstanceCounterGetRsoStorageDir			DisplayString,
		applicationInstanceCounterGetRsoStoragePath			DisplayString,
		applicationInstanceCounterGetSharedObjectReadAccess		DisplayString,
		applicationInstanceCounterGetSharedObjectWriteAccess		DisplayString,
		applicationInstanceCounterGetSourceControlSessionCount		Integer32,
		applicationInstanceCounterGetStreamAudioSampleAccess		DisplayString,
		applicationInstanceCounterGetStreamCount			Integer32,
		applicationInstanceCounterGetStreamKeyDir			DisplayString,
		applicationInstanceCounterGetStreamKeyPath			DisplayString,
		applicationInstanceCounterGetStreamReadAccess			DisplayString,
		applicationInstanceCounterGetStreamStorageDir			DisplayString,
		applicationInstanceCounterGetStreamStoragePath			DisplayString,
		applicationInstanceCounterGetStreamType				DisplayString,
		applicationInstanceCounterGetStreamVideoSampleAccess		DisplayString,
		applicationInstanceCounterGetStreamWriteAccess			DisplayString,
		applicationInstanceCounterGetTimeRunning			DisplayString,
		applicationInstanceCounterGetVODTimedTextProviderList		DisplayString,
		applicationInstanceCounterGetValidationFrequency		Integer32
		}

applicationInstanceCounterCreationTime	 OBJECT-TYPE
	SYNTAX Counter64
	MAX-ACCESS read-only
	STATUS current
	DESCRIPTION
	"Description Yet To Be Added"
	::= { applicationInstanceCounterEntry 1 }

applicationInstanceCounterGetApplicationInstanceTouchTimeout	 OBJECT-TYPE
	SYNTAX Integer32
	MAX-ACCESS read-only
	STATUS current
	DESCRIPTION
	"Description Yet To Be Added"
	::= { applicationInstanceCounterEntry 2 }

applicationInstanceCounterGetApplicationTimeout	 OBJECT-TYPE
	SYNTAX Integer32
	MAX-ACCESS read-only
	STATUS current
	DESCRIPTION
	"Description Yet To Be Added"
	::= { applicationInstanceCounterEntry 3 }

applicationInstanceCounterGetClientCount	 OBJECT-TYPE
	SYNTAX Integer32
	MAX-ACCESS read-only
	STATUS current
	DESCRIPTION
	"Description Yet To Be Added"
	::= { applicationInstanceCounterEntry 4 }

applicationInstanceCounterGetClientCountTotal	 OBJECT-TYPE
	SYNTAX Integer32
	MAX-ACCESS read-only
	STATUS current
	DESCRIPTION
	"Description Yet To Be Added"
	::= { applicationInstanceCounterEntry 5 }

applicationInstanceCounterGetClientIdleFrequency	 OBJECT-TYPE
	SYNTAX Integer32
	MAX-ACCESS read-only
	STATUS current
	DESCRIPTION
	"Description Yet To Be Added"
	::= { applicationInstanceCounterEntry 6 }

applicationInstanceCounterGetClientRemoveTime	 OBJECT-TYPE
	SYNTAX Counter64
	MAX-ACCESS read-only
	STATUS current
	DESCRIPTION
	"Description Yet To Be Added"
	::= { applicationInstanceCounterEntry 7 }

applicationInstanceCounterGetContextStr	 OBJECT-TYPE
	SYNTAX DisplayString
	MAX-ACCESS read-only
	STATUS current
	DESCRIPTION
	"Description Yet To Be Added"
	::= { applicationInstanceCounterEntry 8 }

applicationInstanceCounterGetDateStarted	 OBJECT-TYPE
	SYNTAX DisplayString
	MAX-ACCESS read-only
	STATUS current
	DESCRIPTION
	"Description Yet To Be Added"
	::= { applicationInstanceCounterEntry 9 }

applicationInstanceCounterGetDvrRecorderList	 OBJECT-TYPE
	SYNTAX DisplayString
	MAX-ACCESS read-only
	STATUS current
	DESCRIPTION
	"Description Yet To Be Added"
	::= { applicationInstanceCounterEntry 10 }

applicationInstanceCounterGetHTTPStreamerList	 OBJECT-TYPE
	SYNTAX DisplayString
	MAX-ACCESS read-only
	STATUS current
	DESCRIPTION
	"Description Yet To Be Added"
	::= { applicationInstanceCounterEntry 11 }

applicationInstanceCounterGetHTTPStreamerSessionCount	 OBJECT-TYPE
	SYNTAX Integer32
	MAX-ACCESS read-only
	STATUS current
	DESCRIPTION
	"Description Yet To Be Added"
	::= { applicationInstanceCounterEntry 12 }

applicationInstanceCounterGetLastTouchTime	 OBJECT-TYPE
	SYNTAX Counter64
	MAX-ACCESS read-only
	STATUS current
	DESCRIPTION
	"Description Yet To Be Added"
	::= { applicationInstanceCounterEntry 13 }

applicationInstanceCounterGetLiveStreamPacketizerList	 OBJECT-TYPE
	SYNTAX DisplayString
	MAX-ACCESS read-only
	STATUS current
	DESCRIPTION
	"Description Yet To Be Added"
	::= { applicationInstanceCounterEntry 14 }

applicationInstanceCounterGetLiveStreamTranscoderList	 OBJECT-TYPE
	SYNTAX DisplayString
	MAX-ACCESS read-only
	STATUS current
	DESCRIPTION
	"Description Yet To Be Added"
	::= { applicationInstanceCounterEntry 15 }

applicationInstanceCounterGetMaxStorageDirDepth	 OBJECT-TYPE
	SYNTAX Integer32
	MAX-ACCESS read-only
	STATUS current
	DESCRIPTION
	"Description Yet To Be Added"
	::= { applicationInstanceCounterEntry 16 }

applicationInstanceCounterGetMaximumPendingReadBytes	 OBJECT-TYPE
	SYNTAX Integer32
	MAX-ACCESS read-only
	STATUS current
	DESCRIPTION
	"Description Yet To Be Added"
	::= { applicationInstanceCounterEntry 17 }

applicationInstanceCounterGetMaximumPendingWriteBytes	 OBJECT-TYPE
	SYNTAX Integer32
	MAX-ACCESS read-only
	STATUS current
	DESCRIPTION
	"Description Yet To Be Added"
	::= { applicationInstanceCounterEntry 18 }

applicationInstanceCounterGetMaximumSetBufferTime	 OBJECT-TYPE
	SYNTAX Integer32
	MAX-ACCESS read-only
	STATUS current
	DESCRIPTION
	"Description Yet To Be Added"
	::= { applicationInstanceCounterEntry 19 }

applicationInstanceCounterGetMediacasterRTPRTSPRTPTransportMode	 OBJECT-TYPE
	SYNTAX Integer32
	MAX-ACCESS read-only
	STATUS current
	DESCRIPTION
	"Description Yet To Be Added"
	::= { applicationInstanceCounterEntry 20 }

applicationInstanceCounterGetMessagesInBytes	 OBJECT-TYPE
	SYNTAX Counter64
	MAX-ACCESS read-only
	STATUS current
	DESCRIPTION
	"Description Yet To Be Added"
	::= { applicationInstanceCounterEntry 21 }

applicationInstanceCounterGetMessagesInCount	 OBJECT-TYPE
	SYNTAX Counter64
	MAX-ACCESS read-only
	STATUS current
	DESCRIPTION
	"Description Yet To Be Added"
	::= { applicationInstanceCounterEntry 22 }

applicationInstanceCounterGetMessagesInCountRate	 OBJECT-TYPE
	SYNTAX Counter64
	MAX-ACCESS read-only
	STATUS current
	DESCRIPTION
	"Description Yet To Be Added"
	::= { applicationInstanceCounterEntry 23 }

applicationInstanceCounterGetMessagesOutBytes	 OBJECT-TYPE
	SYNTAX Counter64
	MAX-ACCESS read-only
	STATUS current
	DESCRIPTION
	"Description Yet To Be Added"
	::= { applicationInstanceCounterEntry 24 }

applicationInstanceCounterGetMessagesOutCount	 OBJECT-TYPE
	SYNTAX Counter64
	MAX-ACCESS read-only
	STATUS current
	DESCRIPTION
	"Description Yet To Be Added"
	::= { applicationInstanceCounterEntry 25 }

applicationInstanceCounterGetMessagesOutCountRate	 OBJECT-TYPE
	SYNTAX Counter64
	MAX-ACCESS read-only
	STATUS current
	DESCRIPTION
	"Description Yet To Be Added"
	::= { applicationInstanceCounterEntry 26 }

applicationInstanceCounterGetName	 OBJECT-TYPE
	SYNTAX DisplayString
	MAX-ACCESS read-only
	STATUS current
	DESCRIPTION
	"Description Yet To Be Added"
	::= { applicationInstanceCounterEntry 27 }

applicationInstanceCounterGetPingTimeout	 OBJECT-TYPE
	SYNTAX	Integer32 
	MAX-ACCESS read-only
	STATUS current
	DESCRIPTION
	"Description Yet To Be Added"
	::= { applicationInstanceCounterEntry 28 }

applicationInstanceCounterGetPublisherCount	 OBJECT-TYPE
	SYNTAX	Integer32 
	MAX-ACCESS read-only
	STATUS current
	DESCRIPTION
	"Description Yet To Be Added"
	::= { applicationInstanceCounterEntry 29 }

applicationInstanceCounterGetPushPublishSessionCount	 OBJECT-TYPE
	SYNTAX	Integer32 
	MAX-ACCESS read-only
	STATUS current
	DESCRIPTION
	"Description Yet To Be Added"
	::= { applicationInstanceCounterEntry 30 }

applicationInstanceCounterGetRTPAVSyncMethod	 OBJECT-TYPE
	SYNTAX	Integer32 
	MAX-ACCESS read-only
	STATUS current
	DESCRIPTION
	"Description Yet To Be Added"
	::= { applicationInstanceCounterEntry 31 }

applicationInstanceCounterGetRTPIdleFrequency	 OBJECT-TYPE
	SYNTAX	Integer32 
	MAX-ACCESS read-only
	STATUS current
	DESCRIPTION
	"Description Yet To Be Added"
	::= { applicationInstanceCounterEntry 32 }

applicationInstanceCounterGetRTPMaxRTCPWaitTime	 OBJECT-TYPE
	SYNTAX	Integer32 
	MAX-ACCESS read-only
	STATUS current
	DESCRIPTION
	"Description Yet To Be Added"
	::= { applicationInstanceCounterEntry 33 }

applicationInstanceCounterGetRTPPlayAuthenticationMethod	 OBJECT-TYPE
	SYNTAX	DisplayString 
	MAX-ACCESS read-only
	STATUS current
	DESCRIPTION
	"Description Yet To Be Added"
	::= { applicationInstanceCounterEntry 34 }

applicationInstanceCounterGetRTPPublishAuthenticationMethod	 OBJECT-TYPE
	SYNTAX	DisplayString 
	MAX-ACCESS read-only
	STATUS current
	DESCRIPTION
	"Description Yet To Be Added"
	::= { applicationInstanceCounterEntry 35 }

applicationInstanceCounterGetRTPSessionCount	 OBJECT-TYPE
	SYNTAX	Integer32 
	MAX-ACCESS read-only
	STATUS current
	DESCRIPTION
	"Description Yet To Be Added"
	::= { applicationInstanceCounterEntry 36 }

applicationInstanceCounterGetRTSPBindIpAddress	 OBJECT-TYPE
	SYNTAX	DisplayString 
	MAX-ACCESS read-only
	STATUS current
	DESCRIPTION
	"Description Yet To Be Added"
	::= { applicationInstanceCounterEntry 37 }

applicationInstanceCounterGetRTSPConnectionAddressType	 OBJECT-TYPE
	SYNTAX	DisplayString 
	MAX-ACCESS read-only
	STATUS current
	DESCRIPTION
	"Description Yet To Be Added"
	::= { applicationInstanceCounterEntry 38 }

applicationInstanceCounterGetRTSPConnectionIpAddress	 OBJECT-TYPE
	SYNTAX	DisplayString 
	MAX-ACCESS read-only
	STATUS current
	DESCRIPTION
	"Description Yet To Be Added"
	::= { applicationInstanceCounterEntry 39 }

applicationInstanceCounterGetRTSPMaximumPendingWriteBytes	 OBJECT-TYPE
	SYNTAX	Integer32 
	MAX-ACCESS read-only
	STATUS current
	DESCRIPTION
	"Description Yet To Be Added"
	::= { applicationInstanceCounterEntry 40 }

applicationInstanceCounterGetRTSPOriginAddressType	 OBJECT-TYPE
	SYNTAX	DisplayString 
	MAX-ACCESS read-only
	STATUS current
	DESCRIPTION
	"Description Yet To Be Added"
	::= { applicationInstanceCounterEntry 41 }

applicationInstanceCounterGetRTSPOriginIpAddress	 OBJECT-TYPE
	SYNTAX	DisplayString 
	MAX-ACCESS read-only
	STATUS current
	DESCRIPTION
	"Description Yet To Be Added"
	::= { applicationInstanceCounterEntry 42 }

applicationInstanceCounterGetRTSPSessionTimeout	 OBJECT-TYPE
	SYNTAX	Integer32 
	MAX-ACCESS read-only
	STATUS current
	DESCRIPTION
	"Description Yet To Be Added"
	::= { applicationInstanceCounterEntry 43 }

applicationInstanceCounterGetRepeaterOriginUrl	 OBJECT-TYPE
	SYNTAX	DisplayString 
	MAX-ACCESS read-only
	STATUS current
	DESCRIPTION
	"Description Yet To Be Added"
	::= { applicationInstanceCounterEntry 44 }

applicationInstanceCounterGetRepeaterQueryString	 OBJECT-TYPE
	SYNTAX	DisplayString 
	MAX-ACCESS read-only
	STATUS current
	DESCRIPTION
	"Description Yet To Be Added"
	::= { applicationInstanceCounterEntry 45 }

applicationInstanceCounterGetRsoStorageDir	 OBJECT-TYPE
	SYNTAX	DisplayString 
	MAX-ACCESS read-only
	STATUS current
	DESCRIPTION
	"Description Yet To Be Added"
	::= { applicationInstanceCounterEntry 46 }

applicationInstanceCounterGetRsoStoragePath	 OBJECT-TYPE
	SYNTAX	DisplayString 
	MAX-ACCESS read-only
	STATUS current
	DESCRIPTION
	"Description Yet To Be Added"
	::= { applicationInstanceCounterEntry 47 }

applicationInstanceCounterGetSharedObjectReadAccess	 OBJECT-TYPE
	SYNTAX	DisplayString 
	MAX-ACCESS read-only
	STATUS current
	DESCRIPTION
	"Description Yet To Be Added"
	::= { applicationInstanceCounterEntry 48 }

applicationInstanceCounterGetSharedObjectWriteAccess	 OBJECT-TYPE
	SYNTAX	DisplayString 
	MAX-ACCESS read-only
	STATUS current
	DESCRIPTION
	"Description Yet To Be Added"
	::= { applicationInstanceCounterEntry 49 }

applicationInstanceCounterGetSourceControlSessionCount	 OBJECT-TYPE
	SYNTAX	Integer32 
	MAX-ACCESS read-only
	STATUS current
	DESCRIPTION
	"Description Yet To Be Added"
	::= { applicationInstanceCounterEntry 50 }

applicationInstanceCounterGetStreamAudioSampleAccess	 OBJECT-TYPE
	SYNTAX	DisplayString 
	MAX-ACCESS read-only
	STATUS current
	DESCRIPTION
	"Description Yet To Be Added"
	::= { applicationInstanceCounterEntry 51 }

applicationInstanceCounterGetStreamCount	 OBJECT-TYPE
	SYNTAX	Integer32 
	MAX-ACCESS read-only
	STATUS current
	DESCRIPTION
	"Description Yet To Be Added"
	::= { applicationInstanceCounterEntry 52 }

applicationInstanceCounterGetStreamKeyDir	 OBJECT-TYPE
	SYNTAX	DisplayString 
	MAX-ACCESS read-only
	STATUS current
	DESCRIPTION
	"Description Yet To Be Added"
	::= { applicationInstanceCounterEntry 53 }

applicationInstanceCounterGetStreamKeyPath	 OBJECT-TYPE
	SYNTAX	DisplayString 
	MAX-ACCESS read-only
	STATUS current
	DESCRIPTION
	"Description Yet To Be Added"
	::= { applicationInstanceCounterEntry 54 }

applicationInstanceCounterGetStreamReadAccess	 OBJECT-TYPE
	SYNTAX	DisplayString 
	MAX-ACCESS read-only
	STATUS current
	DESCRIPTION
	"Description Yet To Be Added"
	::= { applicationInstanceCounterEntry 55 }

applicationInstanceCounterGetStreamStorageDir	 OBJECT-TYPE
	SYNTAX	DisplayString 
	MAX-ACCESS read-only
	STATUS current
	DESCRIPTION
	"Description Yet To Be Added"
	::= { applicationInstanceCounterEntry 56 }

applicationInstanceCounterGetStreamStoragePath	 OBJECT-TYPE
	SYNTAX	DisplayString 
	MAX-ACCESS read-only
	STATUS current
	DESCRIPTION
	"Description Yet To Be Added"
	::= { applicationInstanceCounterEntry 57 }

applicationInstanceCounterGetStreamType	 OBJECT-TYPE
	SYNTAX	DisplayString 
	MAX-ACCESS read-only
	STATUS current
	DESCRIPTION
	"Description Yet To Be Added"
	::= { applicationInstanceCounterEntry 58 }

applicationInstanceCounterGetStreamVideoSampleAccess	 OBJECT-TYPE
	SYNTAX	DisplayString 
	MAX-ACCESS read-only
	STATUS current
	DESCRIPTION
	"Description Yet To Be Added"
	::= { applicationInstanceCounterEntry 59 }

applicationInstanceCounterGetStreamWriteAccess	 OBJECT-TYPE
	SYNTAX	DisplayString 
	MAX-ACCESS read-only
	STATUS current
	DESCRIPTION
	"Description Yet To Be Added"
	::= { applicationInstanceCounterEntry 60 }

applicationInstanceCounterGetTimeRunning	 OBJECT-TYPE
	SYNTAX	DisplayString 
	MAX-ACCESS read-only
	STATUS current
	DESCRIPTION
	"Description Yet To Be Added"
	::= { applicationInstanceCounterEntry 61 }

applicationInstanceCounterGetVODTimedTextProviderList	 OBJECT-TYPE
	SYNTAX	DisplayString 
	MAX-ACCESS read-only
	STATUS current
	DESCRIPTION
	"Description Yet To Be Added"
	::= { applicationInstanceCounterEntry 62 }

applicationInstanceCounterGetValidationFrequency	OBJECT-TYPE
	SYNTAX	Integer32 
	MAX-ACCESS read-only
	STATUS current
	DESCRIPTION
	"Description Yet To Be Added"
	::= { applicationInstanceCounterEntry 63 }

-- applicationInstanceCounter - End

-- applicationInstanceConnect - Start

applicationInstanceConnectTable	 OBJECT-TYPE
	SYNTAX	 SEQUENCE OF ApplicationInstanceConnectTable
	MAX-ACCESS  not-accessible
	STATUS	 current
	DESCRIPTION
		"Description Yet To Be Added"
	::= { applicationInstanceInfo 2 }

applicationInstanceConnectEntry	 OBJECT-TYPE
	SYNTAX	ApplicationInstanceConnectTable
	MAX-ACCESS  not-accessible
	STATUS	 current
	DESCRIPTION
		"Description Yet To Be Added"
	INDEX { serverIndex, vhostIndex, applicationIndex, applicationInstanceIndex }
	::= { applicationInstanceConnectTable 1 }

ApplicationInstanceConnectTable ::=
	SEQUENCE 
		{
		applicationInstanceConnectCreationTime				Counter64,
		applicationInstanceConnectGetCurrent				Counter64,
		applicationInstanceConnectGetLastConnectAcceptedStamp		Counter64,
		applicationInstanceConnectGetLastConnectAcceptedStampString	DisplayString,
		applicationInstanceConnectGetLastConnectAcceptedTimeString	DisplayString,
		applicationInstanceConnectGetLastConnectRejectedStamp		Counter64,
		applicationInstanceConnectGetLastConnectRejectedStampString	DisplayString,
		applicationInstanceConnectGetLastConnectRejectedTimeString	DisplayString,
		applicationInstanceConnectGetLastDisconnectStamp		Counter64,
		applicationInstanceConnectGetLastDisconnectStampString		DisplayString,
		applicationInstanceConnectGetLastDisconnectTimeString		DisplayString,
		applicationInstanceConnectGetTotal				Counter64,
		applicationInstanceConnectGetTotalAccepted			Counter64,
		applicationInstanceConnectGetTotalRejected			Counter64
		}

applicationInstanceConnectCreationTime	OBJECT-TYPE
	SYNTAX	Counter64 
	MAX-ACCESS read-only
	STATUS current
	DESCRIPTION
	"Description Yet To Be Added"
	::= { applicationInstanceConnectEntry 1 }

applicationInstanceConnectGetCurrent	OBJECT-TYPE
	SYNTAX	Counter64 
	MAX-ACCESS read-only
	STATUS current
	DESCRIPTION
	"Description Yet To Be Added"
	::= { applicationInstanceConnectEntry 2 }

applicationInstanceConnectGetLastConnectAcceptedStamp	OBJECT-TYPE
	SYNTAX	Counter64 
	MAX-ACCESS read-only
	STATUS current
	DESCRIPTION
	"Description Yet To Be Added"
	::= { applicationInstanceConnectEntry 3 }

applicationInstanceConnectGetLastConnectAcceptedStampString	OBJECT-TYPE
	SYNTAX	DisplayString 
	MAX-ACCESS read-only
	STATUS current
	DESCRIPTION
	"Description Yet To Be Added"
	::= { applicationInstanceConnectEntry 4 }

applicationInstanceConnectGetLastConnectAcceptedTimeString	OBJECT-TYPE
	SYNTAX	DisplayString 
	MAX-ACCESS read-only
	STATUS current
	DESCRIPTION
	"Description Yet To Be Added"
	::= { applicationInstanceConnectEntry 5 }

applicationInstanceConnectGetLastConnectRejectedStamp	OBJECT-TYPE
	SYNTAX	Counter64 
	MAX-ACCESS read-only
	STATUS current
	DESCRIPTION
	"Description Yet To Be Added"
	::= { applicationInstanceConnectEntry 6 }

applicationInstanceConnectGetLastConnectRejectedStampString	OBJECT-TYPE
	SYNTAX	DisplayString 
	MAX-ACCESS read-only
	STATUS current
	DESCRIPTION
	"Description Yet To Be Added"
	::= { applicationInstanceConnectEntry 7 }

applicationInstanceConnectGetLastConnectRejectedTimeString	OBJECT-TYPE
	SYNTAX	DisplayString 
	MAX-ACCESS read-only
	STATUS current
	DESCRIPTION
	"Description Yet To Be Added"
	::= { applicationInstanceConnectEntry 8 }

applicationInstanceConnectGetLastDisconnectStamp	OBJECT-TYPE
	SYNTAX	Counter64 
	MAX-ACCESS read-only
	STATUS current
	DESCRIPTION
	"Description Yet To Be Added"
	::= { applicationInstanceConnectEntry 9 }

applicationInstanceConnectGetLastDisconnectStampString	OBJECT-TYPE
	SYNTAX	DisplayString 
	MAX-ACCESS read-only
	STATUS current
	DESCRIPTION
	"Description Yet To Be Added"
	::= { applicationInstanceConnectEntry 10 }

applicationInstanceConnectGetLastDisconnectTimeString	OBJECT-TYPE
	SYNTAX	DisplayString 
	MAX-ACCESS read-only
	STATUS current
	DESCRIPTION
	"Description Yet To Be Added"
	::= { applicationInstanceConnectEntry 11 }

applicationInstanceConnectGetTotal	OBJECT-TYPE
	SYNTAX	Counter64 
	MAX-ACCESS read-only
	STATUS current
	DESCRIPTION
	"Description Yet To Be Added"
	::= { applicationInstanceConnectEntry 12 }

applicationInstanceConnectGetTotalAccepted	OBJECT-TYPE
	SYNTAX	Counter64 
	MAX-ACCESS read-only
	STATUS current
	DESCRIPTION
	"Description Yet To Be Added"
	::= { applicationInstanceConnectEntry 13 }

applicationInstanceConnectGetTotalRejected	OBJECT-TYPE
	SYNTAX	Counter64 
	MAX-ACCESS read-only
	STATUS current
	DESCRIPTION
	"Description Yet To Be Added"
	::= { applicationInstanceConnectEntry 14 }

-- applicationInstanceConnect - End

-- applicationInstancePerform - Start

applicationInstancePerformTable	 OBJECT-TYPE
	SYNTAX	 SEQUENCE OF ApplicationInstancePerformTable
	MAX-ACCESS  not-accessible
	STATUS	 current
	DESCRIPTION
		"Description Yet To Be Added"
	::= { applicationInstanceInfo 3 }

applicationInstancePerformEntry	 OBJECT-TYPE
	SYNTAX	ApplicationInstancePerformTable
	MAX-ACCESS  not-accessible
	STATUS	 current
	DESCRIPTION
		"Description Yet To Be Added"
	INDEX { serverIndex, vhostIndex, applicationIndex, applicationInstanceIndex }
	::= { applicationInstancePerformTable 1 }

ApplicationInstancePerformTable ::=
	SEQUENCE 
		{
		applicationInstancePerformCreationTime			Counter64,
		applicationInstancePerformGetFileInBytes		Counter64,
		applicationInstancePerformGetFileOutBytes		Counter64,
		applicationInstancePerformGetMessagesInBytes		Counter64,
		applicationInstancePerformGetMessagesInCount		Counter64,
		applicationInstancePerformGetMessagesInCountRate	Counter64,
		applicationInstancePerformGetMessagesLossBytes		Counter64,
		applicationInstancePerformGetMessagesLossCount		Counter64,
		applicationInstancePerformGetMessagesLossCountRate	Counter64,
		applicationInstancePerformGetMessagesOutBytes		Counter64,
		applicationInstancePerformGetMessagesOutCount		Counter64,
		applicationInstancePerformGetMessagesOutCountRate	Counter64
		}

applicationInstancePerformCreationTime	OBJECT-TYPE
	SYNTAX	Counter64 
	MAX-ACCESS read-only
	STATUS current
	DESCRIPTION
	"Description Yet To Be Added"
	::= { applicationInstancePerformEntry 1 }

applicationInstancePerformGetFileInBytes	OBJECT-TYPE
	SYNTAX	Counter64 
	MAX-ACCESS read-only
	STATUS current
	DESCRIPTION
	"Description Yet To Be Added"
	::= { applicationInstancePerformEntry 2 }

applicationInstancePerformGetFileOutBytes	OBJECT-TYPE
	SYNTAX	Counter64 
	MAX-ACCESS read-only
	STATUS current
	DESCRIPTION
	"Description Yet To Be Added"
	::= { applicationInstancePerformEntry 3 }

applicationInstancePerformGetMessagesInBytes	OBJECT-TYPE
	SYNTAX	Counter64 
	MAX-ACCESS read-only
	STATUS current
	DESCRIPTION
	"Description Yet To Be Added"
	::= { applicationInstancePerformEntry 4 }

applicationInstancePerformGetMessagesInCount	OBJECT-TYPE
	SYNTAX	Counter64 
	MAX-ACCESS read-only
	STATUS current
	DESCRIPTION
	"Description Yet To Be Added"
	::= { applicationInstancePerformEntry 5 }

applicationInstancePerformGetMessagesInCountRate	OBJECT-TYPE
	SYNTAX	Counter64 
	MAX-ACCESS read-only
	STATUS current
	DESCRIPTION
	"Description Yet To Be Added"
	::= { applicationInstancePerformEntry 6 }

applicationInstancePerformGetMessagesLossBytes	OBJECT-TYPE
	SYNTAX	Counter64 
	MAX-ACCESS read-only
	STATUS current
	DESCRIPTION
	"Description Yet To Be Added"
	::= { applicationInstancePerformEntry 7 }

applicationInstancePerformGetMessagesLossCount	OBJECT-TYPE
	SYNTAX	Counter64 
	MAX-ACCESS read-only
	STATUS current
	DESCRIPTION
	"Description Yet To Be Added"
	::= { applicationInstancePerformEntry 8 }

applicationInstancePerformGetMessagesLossCountRate	OBJECT-TYPE
	SYNTAX	Counter64 
	MAX-ACCESS read-only
	STATUS current
	DESCRIPTION
	"Description Yet To Be Added"
	::= { applicationInstancePerformEntry 9 }

applicationInstancePerformGetMessagesOutBytes	OBJECT-TYPE
	SYNTAX	Counter64 
	MAX-ACCESS read-only
	STATUS current
	DESCRIPTION
	"Description Yet To Be Added"
	::= { applicationInstancePerformEntry 10 }

applicationInstancePerformGetMessagesOutCount	OBJECT-TYPE
	SYNTAX	Counter64 
	MAX-ACCESS read-only
	STATUS current
	DESCRIPTION
	"Description Yet To Be Added"
	::= { applicationInstancePerformEntry 11 }

applicationInstancePerformGetMessagesOutCountRate	OBJECT-TYPE
	SYNTAX	Counter64 
	MAX-ACCESS read-only
	STATUS current
	DESCRIPTION
	"Description Yet To Be Added"
	::= { applicationInstancePerformEntry 12 }

-- applicationInstancePerform - End

-- streamCount - Start

streamCountTable	 OBJECT-TYPE
	SYNTAX	 SEQUENCE OF StreamCountTable
	MAX-ACCESS  not-accessible
	STATUS	 current
	DESCRIPTION
		"Description Yet To Be Added"
	::= { streamInfo 1 }

streamCountEntry	 OBJECT-TYPE
	SYNTAX	StreamCountTable
	MAX-ACCESS  not-accessible
	STATUS	 current
	DESCRIPTION
		"Description Yet To Be Added"
	INDEX { serverIndex, vhostIndex, applicationIndex, applicationInstanceIndex, streamIndex }
	::= { streamCountTable 1 }

StreamCountTable ::=
	SEQUENCE 
		{
		streamCountCreationTime			Counter64,
		streamCountGetAudioMissing		Integer32,
		streamCountGetAudioSize			Integer32,
		streamCountGetAudioTC			Counter64,
		streamCountGetBufferTime		Integer32,
		streamCountGetCacheName			DisplayString,
		streamCountGetClientId			Integer32,
		streamCountGetContextStr		DisplayString,
		streamCountGetDataMissing		Integer32,
		streamCountGetDataSize			Integer32,
		streamCountGetDataTC			Counter64,
		streamCountGetDataType			Integer32,
		streamCountGetDvrRecorder		DisplayString,
		streamCountGetDvrRecorderList		DisplayString,
		streamCountGetDvrRepeater		DisplayString,
		streamCountGetExt			DisplayString,
		streamCountGetFirstPacketTC		Counter64,
		streamCountGetHeaderSize		Integer32,
		streamCountGetLastFlushAudioTC		Counter64,
		streamCountGetLastFlushDataTC		Counter64,
		streamCountGetLastFlushRTTimecode	Counter64,
		streamCountGetLastFlushTime		Counter64,
		streamCountGetLastFlushTimecode		Counter64,
		streamCountGetLastFlushVideoTC		Counter64,
		streamCountGetLastPacketTC		Counter64,
		streamCountGetLastReceivedAudioTC	Counter64,
		streamCountGetLastReceivedDataTC	Counter64,
		streamCountGetLastReceivedVideoTC	Counter64,
		streamCountGetLastSentAudioTC		Counter64,
		streamCountGetLastSentDataTC		Counter64,
		streamCountGetLastSentVideoTC		Counter64,
		streamCountGetLiveStreamPacketizer	DisplayString,
		streamCountGetLiveStreamPacketizerList	DisplayString,
		streamCountGetLiveStreamRepeater	DisplayString,
		streamCountGetLiveStreamTranscoderList	DisplayString,
		streamCountGetMaxTimecode		Counter64,
		streamCountGetName			DisplayString,
		streamCountGetPacketCount		Integer32,
		streamCountGetPublishAudioCodecId	Integer32,
		streamCountGetPublishBitrateAudio	Integer32,
		streamCountGetPublishBitrateVideo	Integer32,
		streamCountGetPublishFrameCountAudio	Counter64,
		streamCountGetPublishFrameCountData	Counter64,
		streamCountGetPublishFrameCountVideo	Counter64,
		streamCountGetPublishVideoCodecId	Integer32,
		streamCountGetQueryStr			DisplayString,
		streamCountGetReceiveVideoFPS		Integer32,
		streamCountGetSrc			Integer32,
		streamCountGetStreamType		DisplayString,
		streamCountGetTimecodeOffset		Counter64,
		streamCountGetTss			Counter64,
		streamCountGetUniqueStreamIdStr		DisplayString,
		streamCountGetVideoMissing		Integer32,
		streamCountGetVideoSize			Integer32,
		streamCountGetVideoTC			Counter64
		}

streamCountCreationTime	OBJECT-TYPE
	SYNTAX	Counter64 
	MAX-ACCESS read-only
	STATUS current
	DESCRIPTION
	"Description Yet To Be Added"
	::= { streamCountEntry 1 }

streamCountGetAudioMissing	OBJECT-TYPE
	SYNTAX	Integer32 
	MAX-ACCESS read-only
	STATUS current
	DESCRIPTION
	"Description Yet To Be Added"
	::= { streamCountEntry 2 }

streamCountGetAudioSize	OBJECT-TYPE
	SYNTAX	Integer32 
	MAX-ACCESS read-only
	STATUS current
	DESCRIPTION
	"Description Yet To Be Added"
	::= { streamCountEntry 3 }

streamCountGetAudioTC	OBJECT-TYPE
	SYNTAX	Counter64 
	MAX-ACCESS read-only
	STATUS current
	DESCRIPTION
	"Description Yet To Be Added"
	::= { streamCountEntry 4 }

streamCountGetBufferTime	OBJECT-TYPE
	SYNTAX	Integer32 
	MAX-ACCESS read-only
	STATUS current
	DESCRIPTION
	"Description Yet To Be Added"
	::= { streamCountEntry 5 }

streamCountGetCacheName	OBJECT-TYPE
	SYNTAX	DisplayString 
	MAX-ACCESS read-only
	STATUS current
	DESCRIPTION
	"Description Yet To Be Added"
	::= { streamCountEntry 6 }

streamCountGetClientId	OBJECT-TYPE
	SYNTAX	Integer32 
	MAX-ACCESS read-only
	STATUS current
	DESCRIPTION
	"Description Yet To Be Added"
	::= { streamCountEntry 7 }

streamCountGetContextStr	OBJECT-TYPE
	SYNTAX	DisplayString 
	MAX-ACCESS read-only
	STATUS current
	DESCRIPTION
	"Description Yet To Be Added"
	::= { streamCountEntry 8 }

streamCountGetDataMissing	OBJECT-TYPE
	SYNTAX	Integer32 
	MAX-ACCESS read-only
	STATUS current
	DESCRIPTION
	"Description Yet To Be Added"
	::= { streamCountEntry 9 }

streamCountGetDataSize	OBJECT-TYPE
	SYNTAX	Integer32 
	MAX-ACCESS read-only
	STATUS current
	DESCRIPTION
	"Description Yet To Be Added"
	::= { streamCountEntry 10 }

streamCountGetDataTC	OBJECT-TYPE
	SYNTAX	Counter64 
	MAX-ACCESS read-only
	STATUS current
	DESCRIPTION
	"Description Yet To Be Added"
	::= { streamCountEntry 11 }

streamCountGetDataType	OBJECT-TYPE
	SYNTAX	Integer32 
	MAX-ACCESS read-only
	STATUS current
	DESCRIPTION
	"Description Yet To Be Added"
	::= { streamCountEntry 12 }

streamCountGetDvrRecorder	OBJECT-TYPE
	SYNTAX	DisplayString 
	MAX-ACCESS read-only
	STATUS current
	DESCRIPTION
	"Description Yet To Be Added"
	::= { streamCountEntry 13 }

streamCountGetDvrRecorderList	OBJECT-TYPE
	SYNTAX	DisplayString 
	MAX-ACCESS read-only
	STATUS current
	DESCRIPTION
	"Description Yet To Be Added"
	::= { streamCountEntry 14 }

streamCountGetDvrRepeater	OBJECT-TYPE
	SYNTAX	DisplayString 
	MAX-ACCESS read-only
	STATUS current
	DESCRIPTION
	"Description Yet To Be Added"
	::= { streamCountEntry 15 }

streamCountGetExt	OBJECT-TYPE
	SYNTAX	DisplayString 
	MAX-ACCESS read-only
	STATUS current
	DESCRIPTION
	"Description Yet To Be Added"
	::= { streamCountEntry 16 }

streamCountGetFirstPacketTC	OBJECT-TYPE
	SYNTAX	Counter64 
	MAX-ACCESS read-only
	STATUS current
	DESCRIPTION
	"Description Yet To Be Added"
	::= { streamCountEntry 17 }

streamCountGetHeaderSize	OBJECT-TYPE
	SYNTAX	Integer32 
	MAX-ACCESS read-only
	STATUS current
	DESCRIPTION
	"Description Yet To Be Added"
	::= { streamCountEntry 18 }

streamCountGetLastFlushAudioTC	OBJECT-TYPE
	SYNTAX	Counter64 
	MAX-ACCESS read-only
	STATUS current
	DESCRIPTION
	"Description Yet To Be Added"
	::= { streamCountEntry 19 }

streamCountGetLastFlushDataTC	OBJECT-TYPE
	SYNTAX	Counter64 
	MAX-ACCESS read-only
	STATUS current
	DESCRIPTION
	"Description Yet To Be Added"
	::= { streamCountEntry 20 }

streamCountGetLastFlushRTTimecode	OBJECT-TYPE
	SYNTAX	Counter64 
	MAX-ACCESS read-only
	STATUS current
	DESCRIPTION
	"Description Yet To Be Added"
	::= { streamCountEntry 21 }

streamCountGetLastFlushTime	OBJECT-TYPE
	SYNTAX	Counter64 
	MAX-ACCESS read-only
	STATUS current
	DESCRIPTION
	"Description Yet To Be Added"
	::= { streamCountEntry 22 }

streamCountGetLastFlushTimecode	OBJECT-TYPE
	SYNTAX	Counter64 
	MAX-ACCESS read-only
	STATUS current
	DESCRIPTION
	"Description Yet To Be Added"
	::= { streamCountEntry 23 }

streamCountGetLastFlushVideoTC	OBJECT-TYPE
	SYNTAX	Counter64 
	MAX-ACCESS read-only
	STATUS current
	DESCRIPTION
	"Description Yet To Be Added"
	::= { streamCountEntry 24 }

streamCountGetLastPacketTC	OBJECT-TYPE
	SYNTAX	Counter64 
	MAX-ACCESS read-only
	STATUS current
	DESCRIPTION
	"Description Yet To Be Added"
	::= { streamCountEntry 25 }

streamCountGetLastReceivedAudioTC	OBJECT-TYPE
	SYNTAX	Counter64 
	MAX-ACCESS read-only
	STATUS current
	DESCRIPTION
	"Description Yet To Be Added"
	::= { streamCountEntry 26 }

streamCountGetLastReceivedDataTC	OBJECT-TYPE
	SYNTAX	Counter64 
	MAX-ACCESS read-only
	STATUS current
	DESCRIPTION
	"Description Yet To Be Added"
	::= { streamCountEntry 27 }

streamCountGetLastReceivedVideoTC	OBJECT-TYPE
	SYNTAX	Counter64 
	MAX-ACCESS read-only
	STATUS current
	DESCRIPTION
	"Description Yet To Be Added"
	::= { streamCountEntry 28 }

streamCountGetLastSentAudioTC	OBJECT-TYPE
	SYNTAX	Counter64 
	MAX-ACCESS read-only
	STATUS current
	DESCRIPTION
	"Description Yet To Be Added"
	::= { streamCountEntry 29 }

streamCountGetLastSentDataTC	OBJECT-TYPE
	SYNTAX	Counter64 
	MAX-ACCESS read-only
	STATUS current
	DESCRIPTION
	"Description Yet To Be Added"
	::= { streamCountEntry 30 }

streamCountGetLastSentVideoTC	OBJECT-TYPE
	SYNTAX	Counter64 
	MAX-ACCESS read-only
	STATUS current
	DESCRIPTION
	"Description Yet To Be Added"
	::= { streamCountEntry 31 }

streamCountGetLiveStreamPacketizer	OBJECT-TYPE
	SYNTAX	DisplayString 
	MAX-ACCESS read-only
	STATUS current
	DESCRIPTION
	"Description Yet To Be Added"
	::= { streamCountEntry 32 }

streamCountGetLiveStreamPacketizerList	OBJECT-TYPE
	SYNTAX	DisplayString 
	MAX-ACCESS read-only
	STATUS current
	DESCRIPTION
	"Description Yet To Be Added"
	::= { streamCountEntry 33 }

streamCountGetLiveStreamRepeater	OBJECT-TYPE
	SYNTAX	DisplayString 
	MAX-ACCESS read-only
	STATUS current
	DESCRIPTION
	"Description Yet To Be Added"
	::= { streamCountEntry 34 }

streamCountGetLiveStreamTranscoderList	OBJECT-TYPE
	SYNTAX	DisplayString 
	MAX-ACCESS read-only
	STATUS current
	DESCRIPTION
	"Description Yet To Be Added"
	::= { streamCountEntry 35 }

streamCountGetMaxTimecode	OBJECT-TYPE
	SYNTAX	Counter64 
	MAX-ACCESS read-only
	STATUS current
	DESCRIPTION
	"Description Yet To Be Added"
	::= { streamCountEntry 36 }

streamCountGetName	OBJECT-TYPE
	SYNTAX	DisplayString 
	MAX-ACCESS read-only
	STATUS current
	DESCRIPTION
	"Description Yet To Be Added"
	::= { streamCountEntry 37 }

streamCountGetPacketCount	OBJECT-TYPE
	SYNTAX	Integer32 
	MAX-ACCESS read-only
	STATUS current
	DESCRIPTION
	"Description Yet To Be Added"
	::= { streamCountEntry 38 }

streamCountGetPublishAudioCodecId	OBJECT-TYPE
	SYNTAX	Integer32 
	MAX-ACCESS read-only
	STATUS current
	DESCRIPTION
	"Description Yet To Be Added"
	::= { streamCountEntry 39 }

streamCountGetPublishBitrateAudio	OBJECT-TYPE
	SYNTAX	Integer32 
	MAX-ACCESS read-only
	STATUS current
	DESCRIPTION
	"Description Yet To Be Added"
	::= { streamCountEntry 40 }

streamCountGetPublishBitrateVideo	OBJECT-TYPE
	SYNTAX	Integer32 
	MAX-ACCESS read-only
	STATUS current
	DESCRIPTION
	"Description Yet To Be Added"
	::= { streamCountEntry 41 }

streamCountGetPublishFrameCountAudio	OBJECT-TYPE
	SYNTAX	Counter64 
	MAX-ACCESS read-only
	STATUS current
	DESCRIPTION
	"Description Yet To Be Added"
	::= { streamCountEntry 42 }

streamCountGetPublishFrameCountData	OBJECT-TYPE
	SYNTAX	Counter64 
	MAX-ACCESS read-only
	STATUS current
	DESCRIPTION
	"Description Yet To Be Added"
	::= { streamCountEntry 43 }

streamCountGetPublishFrameCountVideo	OBJECT-TYPE
	SYNTAX	Counter64 
	MAX-ACCESS read-only
	STATUS current
	DESCRIPTION
	"Description Yet To Be Added"
	::= { streamCountEntry 44 }

streamCountGetPublishVideoCodecId	OBJECT-TYPE
	SYNTAX	Integer32 
	MAX-ACCESS read-only
	STATUS current
	DESCRIPTION
	"Description Yet To Be Added"
	::= { streamCountEntry 45 }

streamCountGetQueryStr	OBJECT-TYPE
	SYNTAX	DisplayString 
	MAX-ACCESS read-only
	STATUS current
	DESCRIPTION
	"Description Yet To Be Added"
	::= { streamCountEntry 46 }

streamCountGetReceiveVideoFPS	OBJECT-TYPE
	SYNTAX	Integer32 
	MAX-ACCESS read-only
	STATUS current
	DESCRIPTION
	"Description Yet To Be Added"
	::= { streamCountEntry 47 }

streamCountGetSrc	OBJECT-TYPE
	SYNTAX	Integer32 
	MAX-ACCESS read-only
	STATUS current
	DESCRIPTION
	"Description Yet To Be Added"
	::= { streamCountEntry 48 }

streamCountGetStreamType	OBJECT-TYPE
	SYNTAX	DisplayString 
	MAX-ACCESS read-only
	STATUS current
	DESCRIPTION
	"Description Yet To Be Added"
	::= { streamCountEntry 49 }

streamCountGetTimecodeOffset	OBJECT-TYPE
	SYNTAX	Counter64 
	MAX-ACCESS read-only
	STATUS current
	DESCRIPTION
	"Description Yet To Be Added"
	::= { streamCountEntry 50 }

streamCountGetTss	OBJECT-TYPE
	SYNTAX	Counter64 
	MAX-ACCESS read-only
	STATUS current
	DESCRIPTION
	"Description Yet To Be Added"
	::= { streamCountEntry 51 }

streamCountGetUniqueStreamIdStr	OBJECT-TYPE
	SYNTAX	DisplayString 
	MAX-ACCESS read-only
	STATUS current
	DESCRIPTION
	"Description Yet To Be Added"
	::= { streamCountEntry 52 }

streamCountGetVideoMissing	OBJECT-TYPE
	SYNTAX	Integer32 
	MAX-ACCESS read-only
	STATUS current
	DESCRIPTION
	"Description Yet To Be Added"
	::= { streamCountEntry 53 }

streamCountGetVideoSize	OBJECT-TYPE
	SYNTAX	Integer32 
	MAX-ACCESS read-only
	STATUS current
	DESCRIPTION
	"Description Yet To Be Added"
	::= { streamCountEntry 54 }

streamCountGetVideoTC	OBJECT-TYPE
	SYNTAX	Counter64 
	MAX-ACCESS read-only
	STATUS current
	DESCRIPTION
	"Description Yet To Be Added"
	::= { streamCountEntry 55 }

-- streamCount - End

-- streamPerform - Start

streamPerformTable	 OBJECT-TYPE
	SYNTAX	 SEQUENCE OF StreamPerformTable
	MAX-ACCESS  not-accessible
	STATUS	 current
	DESCRIPTION
		"Description Yet To Be Added"
	::= { streamInfo 3 }

streamPerformEntry	 OBJECT-TYPE
	SYNTAX	StreamPerformTable
	MAX-ACCESS  not-accessible
	STATUS	 current
	DESCRIPTION
		"Description Yet To Be Added"
	INDEX { serverIndex, vhostIndex, applicationIndex, applicationInstanceIndex, streamIndex }
	::= { streamPerformTable 1 }

StreamPerformTable ::=
	SEQUENCE 
		{
		streamPerformCreationTime		Counter64,
		streamPerformGetFileInBytes		Counter64,
		streamPerformGetFileOutBytes		Counter64,
		streamPerformGetMessagesInBytes		Counter64,
		streamPerformGetMessagesInCount		Counter64,
		streamPerformGetMessagesInCountRate	Counter64,
		streamPerformGetMessagesLossBytes	Counter64,
		streamPerformGetMessagesLossCount	Counter64,
		streamPerformGetMessagesLossCountRate	Counter64,
		streamPerformGetMessagesOutBytes	Counter64,
		streamPerformGetMessagesOutCount	Counter64,
		streamPerformGetMessagesOutCountRate	Counter64
		}

streamPerformCreationTime	OBJECT-TYPE
	SYNTAX	Counter64 
	MAX-ACCESS read-only
	STATUS current
	DESCRIPTION
	"Description Yet To Be Added"
	::= { streamPerformEntry 1 }

streamPerformGetFileInBytes	OBJECT-TYPE
	SYNTAX	Counter64 
	MAX-ACCESS read-only
	STATUS current
	DESCRIPTION
	"Description Yet To Be Added"
	::= { streamPerformEntry 2 }

streamPerformGetFileOutBytes	OBJECT-TYPE
	SYNTAX	Counter64 
	MAX-ACCESS read-only
	STATUS current
	DESCRIPTION
	"Description Yet To Be Added"
	::= { streamPerformEntry 3 }

streamPerformGetMessagesInBytes	OBJECT-TYPE
	SYNTAX	Counter64 
	MAX-ACCESS read-only
	STATUS current
	DESCRIPTION
	"Description Yet To Be Added"
	::= { streamPerformEntry 4 }

streamPerformGetMessagesInCount	OBJECT-TYPE
	SYNTAX	Counter64 
	MAX-ACCESS read-only
	STATUS current
	DESCRIPTION
	"Description Yet To Be Added"
	::= { streamPerformEntry 5 }

streamPerformGetMessagesInCountRate	OBJECT-TYPE
	SYNTAX	Counter64 
	MAX-ACCESS read-only
	STATUS current
	DESCRIPTION
	"Description Yet To Be Added"
	::= { streamPerformEntry 6 }

streamPerformGetMessagesLossBytes	OBJECT-TYPE
	SYNTAX	Counter64 
	MAX-ACCESS read-only
	STATUS current
	DESCRIPTION
	"Description Yet To Be Added"
	::= { streamPerformEntry 7 }

streamPerformGetMessagesLossCount	OBJECT-TYPE
	SYNTAX	Counter64 
	MAX-ACCESS read-only
	STATUS current
	DESCRIPTION
	"Description Yet To Be Added"
	::= { streamPerformEntry 8 }

streamPerformGetMessagesLossCountRate	OBJECT-TYPE
	SYNTAX	Counter64 
	MAX-ACCESS read-only
	STATUS current
	DESCRIPTION
	"Description Yet To Be Added"
	::= { streamPerformEntry 9 }

streamPerformGetMessagesOutBytes	OBJECT-TYPE
	SYNTAX	Counter64 
	MAX-ACCESS read-only
	STATUS current
	DESCRIPTION
	"Description Yet To Be Added"
	::= { streamPerformEntry 10 }

streamPerformGetMessagesOutCount	OBJECT-TYPE
	SYNTAX	Counter64 
	MAX-ACCESS read-only
	STATUS current
	DESCRIPTION
	"Description Yet To Be Added"
	::= { streamPerformEntry 11 }

streamPerformGetMessagesOutCountRate	OBJECT-TYPE
	SYNTAX	Counter64 
	MAX-ACCESS read-only
	STATUS current
	DESCRIPTION
	"Description Yet To Be Added"
	::= { streamPerformEntry 12 }

-- streamPerform - End

-- rtmpClientCount - End

rtmpClientCountTable	 OBJECT-TYPE
	SYNTAX	 SEQUENCE OF RTMPClientCountTable
	MAX-ACCESS  not-accessible
	STATUS	 current
	DESCRIPTION
		"Description Yet To Be Added"
	::= { rtmpclientInfo 1 }

rtmpClientCountEntry	 OBJECT-TYPE
	SYNTAX	RTMPClientCountTable
	MAX-ACCESS  not-accessible
	STATUS	 current
	DESCRIPTION
		"Description Yet To Be Added"
	INDEX { serverIndex, vhostIndex, applicationIndex, applicationInstanceIndex, clientIndex }
	::= { rtmpClientCountTable 1 }

RTMPClientCountTable ::=
	SEQUENCE 
		{
		rtmpClientCountCreationTime			Counter64,
		rtmpClientCountGetAcceptConnectionDescription	DisplayString,
		rtmpClientCountGetBufferTime			Integer32,
		rtmpClientCountGetClientId			Integer32,
		rtmpClientCountGetConnectTime			Counter64,
		rtmpClientCountGetDateStarted			DisplayString,
		rtmpClientCountGetDebugDumpData			Integer32,
		rtmpClientCountGetFlashVer			DisplayString,
		rtmpClientCountGetHandshake			Integer32,
		rtmpClientCountGetIdleFrequency			Integer32,
		rtmpClientCountGetIp				DisplayString,
		rtmpClientCountGetLastPingWriteId		Counter64,
		rtmpClientCountGetLastReqChunkCounter		Counter64,
		rtmpClientCountGetLastRequestType		Integer32,
		rtmpClientCountGetLastStreamId			Integer32,
		rtmpClientCountGetLastValidateTime		Counter64,
		rtmpClientCountGetLeftOverCID			Integer32,
		rtmpClientCountGetLeftOverMissing		Integer32,
		rtmpClientCountGetLiveRepeaterCapabilities	Integer32,
		rtmpClientCountGetLiveStreamPacketizerList	DisplayString,
		rtmpClientCountGetLiveStreamTranscoderList	DisplayString,
		rtmpClientCountGetMaximumPendingReadBytes	Integer32,
		rtmpClientCountGetMaximumPendingWriteBytes	Integer32,
		rtmpClientCountGetMaximumSetBufferTime		Integer32,
		rtmpClientCountGetNextConfirmBytesReceived	Counter64,
		rtmpClientCountGetObjectEncoding		Integer32,
		rtmpClientCountGetPageUrl			DisplayString,
		rtmpClientCountGetPingRoundTripTime		Counter64,
		rtmpClientCountGetPingTimeout			Integer32,
		rtmpClientCountGetPlayResponse			Integer32,
		rtmpClientCountGetPlayStreamCount		Integer32,
		rtmpClientCountGetProtocol			Integer32,
		rtmpClientCountGetPublishStreamCount		Integer32,
		rtmpClientCountGetQueryStr			DisplayString,
		rtmpClientCountGetReceiveChunkSize		Integer32,
		rtmpClientCountGetReferrer			DisplayString,
		rtmpClientCountGetRepeaterOriginUrl		DisplayString,
		rtmpClientCountGetRequestDataSize		Integer32,
		rtmpClientCountGetRequestRTMPTSequence		Counter64,
		rtmpClientCountGetResponseIndex			Integer32,
		rtmpClientCountGetSendChunkSize			Integer32,
		rtmpClientCountGetSharedObjectReadAccess	DisplayString,
		rtmpClientCountGetSharedObjectWriteAccess	DisplayString,
		rtmpClientCountGetStreamAudioSampleAccess	DisplayString,
		rtmpClientCountGetStreamReadAccess		DisplayString,
		rtmpClientCountGetStreamType			DisplayString,
		rtmpClientCountGetStreamVideoSampleAccess	DisplayString,
		rtmpClientCountGetStreamWriteAccess		DisplayString,
		rtmpClientCountGetTimeRunning			DisplayString,
		rtmpClientCountGetTimebase			Counter64,
		rtmpClientCountGetTotalInBytes			Counter64,
		rtmpClientCountGetTouch				Counter64,
		rtmpClientCountGetUri				DisplayString,
		rtmpClientCountGetValidationFrequency		Integer32
		}

rtmpClientCountCreationTime	OBJECT-TYPE
	SYNTAX	Counter64 
	MAX-ACCESS read-only
	STATUS current
	DESCRIPTION
	"Description Yet To Be Added"
	::= { rtmpClientCountEntry 1 }

rtmpClientCountGetAcceptConnectionDescription	OBJECT-TYPE
	SYNTAX	DisplayString 
	MAX-ACCESS read-only
	STATUS current
	DESCRIPTION
	"Description Yet To Be Added"
	::= { rtmpClientCountEntry 2 }

rtmpClientCountGetBufferTime	OBJECT-TYPE
	SYNTAX	Integer32 
	MAX-ACCESS read-only
	STATUS current
	DESCRIPTION
	"Description Yet To Be Added"
	::= { rtmpClientCountEntry 3 }

rtmpClientCountGetClientId	OBJECT-TYPE
	SYNTAX	Integer32 
	MAX-ACCESS read-only
	STATUS current
	DESCRIPTION
	"Description Yet To Be Added"
	::= { rtmpClientCountEntry 4 }

rtmpClientCountGetConnectTime	OBJECT-TYPE
	SYNTAX	Counter64 
	MAX-ACCESS read-only
	STATUS current
	DESCRIPTION
	"Description Yet To Be Added"
	::= { rtmpClientCountEntry 5 }

rtmpClientCountGetDateStarted	OBJECT-TYPE
	SYNTAX	DisplayString 
	MAX-ACCESS read-only
	STATUS current
	DESCRIPTION
	"Description Yet To Be Added"
	::= { rtmpClientCountEntry 6 }

rtmpClientCountGetDebugDumpData	OBJECT-TYPE
	SYNTAX	Integer32 
	MAX-ACCESS read-only
	STATUS current
	DESCRIPTION
	"Description Yet To Be Added"
	::= { rtmpClientCountEntry 7 }

rtmpClientCountGetFlashVer	OBJECT-TYPE
	SYNTAX	DisplayString 
	MAX-ACCESS read-only
	STATUS current
	DESCRIPTION
	"Description Yet To Be Added"
	::= { rtmpClientCountEntry 8 }

rtmpClientCountGetHandshake	OBJECT-TYPE
	SYNTAX	Integer32 
	MAX-ACCESS read-only
	STATUS current
	DESCRIPTION
	"Description Yet To Be Added"
	::= { rtmpClientCountEntry 9 }

rtmpClientCountGetIdleFrequency	OBJECT-TYPE
	SYNTAX	Integer32 
	MAX-ACCESS read-only
	STATUS current
	DESCRIPTION
	"Description Yet To Be Added"
	::= { rtmpClientCountEntry 10 }

rtmpClientCountGetIp	OBJECT-TYPE
	SYNTAX	DisplayString 
	MAX-ACCESS read-only
	STATUS current
	DESCRIPTION
	"Description Yet To Be Added"
	::= { rtmpClientCountEntry 11 }

rtmpClientCountGetLastPingWriteId	OBJECT-TYPE
	SYNTAX	Counter64 
	MAX-ACCESS read-only
	STATUS current
	DESCRIPTION
	"Description Yet To Be Added"
	::= { rtmpClientCountEntry 12 }

rtmpClientCountGetLastReqChunkCounter	OBJECT-TYPE
	SYNTAX	Counter64 
	MAX-ACCESS read-only
	STATUS current
	DESCRIPTION
	"Description Yet To Be Added"
	::= { rtmpClientCountEntry 13 }

rtmpClientCountGetLastRequestType	OBJECT-TYPE
	SYNTAX	Integer32 
	MAX-ACCESS read-only
	STATUS current
	DESCRIPTION
	"Description Yet To Be Added"
	::= { rtmpClientCountEntry 14 }

rtmpClientCountGetLastStreamId	OBJECT-TYPE
	SYNTAX	Integer32 
	MAX-ACCESS read-only
	STATUS current
	DESCRIPTION
	"Description Yet To Be Added"
	::= { rtmpClientCountEntry 15 }

rtmpClientCountGetLastValidateTime	OBJECT-TYPE
	SYNTAX	Counter64 
	MAX-ACCESS read-only
	STATUS current
	DESCRIPTION
	"Description Yet To Be Added"
	::= { rtmpClientCountEntry 16 }

rtmpClientCountGetLeftOverCID	OBJECT-TYPE
	SYNTAX	Integer32 
	MAX-ACCESS read-only
	STATUS current
	DESCRIPTION
	"Description Yet To Be Added"
	::= { rtmpClientCountEntry 17 }

rtmpClientCountGetLeftOverMissing	OBJECT-TYPE
	SYNTAX	Integer32 
	MAX-ACCESS read-only
	STATUS current
	DESCRIPTION
	"Description Yet To Be Added"
	::= { rtmpClientCountEntry 18 }

rtmpClientCountGetLiveRepeaterCapabilities	OBJECT-TYPE
	SYNTAX	Integer32 
	MAX-ACCESS read-only
	STATUS current
	DESCRIPTION
	"Description Yet To Be Added"
	::= { rtmpClientCountEntry 19 }

rtmpClientCountGetLiveStreamPacketizerList	OBJECT-TYPE
	SYNTAX	DisplayString 
	MAX-ACCESS read-only
	STATUS current
	DESCRIPTION
	"Description Yet To Be Added"
	::= { rtmpClientCountEntry 20 }

rtmpClientCountGetLiveStreamTranscoderList	OBJECT-TYPE
	SYNTAX	DisplayString 
	MAX-ACCESS read-only
	STATUS current
	DESCRIPTION
	"Description Yet To Be Added"
	::= { rtmpClientCountEntry 21 }

rtmpClientCountGetMaximumPendingReadBytes	OBJECT-TYPE
	SYNTAX	Integer32 
	MAX-ACCESS read-only
	STATUS current
	DESCRIPTION
	"Description Yet To Be Added"
	::= { rtmpClientCountEntry 22 }

rtmpClientCountGetMaximumPendingWriteBytes	OBJECT-TYPE
	SYNTAX	Integer32 
	MAX-ACCESS read-only
	STATUS current
	DESCRIPTION
	"Description Yet To Be Added"
	::= { rtmpClientCountEntry 23 }

rtmpClientCountGetMaximumSetBufferTime	OBJECT-TYPE
	SYNTAX	Integer32 
	MAX-ACCESS read-only
	STATUS current
	DESCRIPTION
	"Description Yet To Be Added"
	::= { rtmpClientCountEntry 24 }

rtmpClientCountGetNextConfirmBytesReceived	OBJECT-TYPE
	SYNTAX	Counter64 
	MAX-ACCESS read-only
	STATUS current
	DESCRIPTION
	"Description Yet To Be Added"
	::= { rtmpClientCountEntry 25 }

rtmpClientCountGetObjectEncoding	OBJECT-TYPE
	SYNTAX	Integer32 
	MAX-ACCESS read-only
	STATUS current
	DESCRIPTION
	"Description Yet To Be Added"
	::= { rtmpClientCountEntry 26 }

rtmpClientCountGetPageUrl	OBJECT-TYPE
	SYNTAX	DisplayString 
	MAX-ACCESS read-only
	STATUS current
	DESCRIPTION
	"Description Yet To Be Added"
	::= { rtmpClientCountEntry 27 }

rtmpClientCountGetPingRoundTripTime	OBJECT-TYPE
	SYNTAX	Counter64 
	MAX-ACCESS read-only
	STATUS current
	DESCRIPTION
	"Description Yet To Be Added"
	::= { rtmpClientCountEntry 28 }

rtmpClientCountGetPingTimeout	OBJECT-TYPE
	SYNTAX	Integer32 
	MAX-ACCESS read-only
	STATUS current
	DESCRIPTION
	"Description Yet To Be Added"
	::= { rtmpClientCountEntry 29 }

rtmpClientCountGetPlayResponse	OBJECT-TYPE
	SYNTAX	Integer32 
	MAX-ACCESS read-only
	STATUS current
	DESCRIPTION
	"Description Yet To Be Added"
	::= { rtmpClientCountEntry 30 }

rtmpClientCountGetPlayStreamCount	OBJECT-TYPE
	SYNTAX	Integer32 
	MAX-ACCESS read-only
	STATUS current
	DESCRIPTION
	"Description Yet To Be Added"
	::= { rtmpClientCountEntry 31 }

rtmpClientCountGetProtocol	OBJECT-TYPE
	SYNTAX	Integer32 
	MAX-ACCESS read-only
	STATUS current
	DESCRIPTION
	"Description Yet To Be Added"
	::= { rtmpClientCountEntry 32 }

rtmpClientCountGetPublishStreamCount	OBJECT-TYPE
	SYNTAX	Integer32 
	MAX-ACCESS read-only
	STATUS current
	DESCRIPTION
	"Description Yet To Be Added"
	::= { rtmpClientCountEntry 33 }

rtmpClientCountGetQueryStr	OBJECT-TYPE
	SYNTAX	DisplayString 
	MAX-ACCESS read-only
	STATUS current
	DESCRIPTION
	"Description Yet To Be Added"
	::= { rtmpClientCountEntry 34 }

rtmpClientCountGetReceiveChunkSize	OBJECT-TYPE
	SYNTAX	Integer32 
	MAX-ACCESS read-only
	STATUS current
	DESCRIPTION
	"Description Yet To Be Added"
	::= { rtmpClientCountEntry 35 }

rtmpClientCountGetReferrer	OBJECT-TYPE
	SYNTAX	DisplayString 
	MAX-ACCESS read-only
	STATUS current
	DESCRIPTION
	"Description Yet To Be Added"
	::= { rtmpClientCountEntry 36 }

rtmpClientCountGetRepeaterOriginUrl	OBJECT-TYPE
	SYNTAX	DisplayString 
	MAX-ACCESS read-only
	STATUS current
	DESCRIPTION
	"Description Yet To Be Added"
	::= { rtmpClientCountEntry 37 }

rtmpClientCountGetRequestDataSize	OBJECT-TYPE
	SYNTAX	Integer32 
	MAX-ACCESS read-only
	STATUS current
	DESCRIPTION
	"Description Yet To Be Added"
	::= { rtmpClientCountEntry 38 }

rtmpClientCountGetRequestRTMPTSequence	OBJECT-TYPE
	SYNTAX	Counter64 
	MAX-ACCESS read-only
	STATUS current
	DESCRIPTION
	"Description Yet To Be Added"
	::= { rtmpClientCountEntry 39 }

rtmpClientCountGetResponseIndex	OBJECT-TYPE
	SYNTAX	Integer32 
	MAX-ACCESS read-only
	STATUS current
	DESCRIPTION
	"Description Yet To Be Added"
	::= { rtmpClientCountEntry 40 }

rtmpClientCountGetSendChunkSize	OBJECT-TYPE
	SYNTAX	Integer32 
	MAX-ACCESS read-only
	STATUS current
	DESCRIPTION
	"Description Yet To Be Added"
	::= { rtmpClientCountEntry 41 }

rtmpClientCountGetSharedObjectReadAccess	OBJECT-TYPE
	SYNTAX	DisplayString 
	MAX-ACCESS read-only
	STATUS current
	DESCRIPTION
	"Description Yet To Be Added"
	::= { rtmpClientCountEntry 42 }

rtmpClientCountGetSharedObjectWriteAccess	OBJECT-TYPE
	SYNTAX	DisplayString 
	MAX-ACCESS read-only
	STATUS current
	DESCRIPTION
	"Description Yet To Be Added"
	::= { rtmpClientCountEntry 43 }

rtmpClientCountGetStreamAudioSampleAccess	OBJECT-TYPE
	SYNTAX	DisplayString 
	MAX-ACCESS read-only
	STATUS current
	DESCRIPTION
	"Description Yet To Be Added"
	::= { rtmpClientCountEntry 44 }

rtmpClientCountGetStreamReadAccess	OBJECT-TYPE
	SYNTAX	DisplayString 
	MAX-ACCESS read-only
	STATUS current
	DESCRIPTION
	"Description Yet To Be Added"
	::= { rtmpClientCountEntry 45 }

rtmpClientCountGetStreamType	OBJECT-TYPE
	SYNTAX	DisplayString 
	MAX-ACCESS read-only
	STATUS current
	DESCRIPTION
	"Description Yet To Be Added"
	::= { rtmpClientCountEntry 46 }

rtmpClientCountGetStreamVideoSampleAccess	OBJECT-TYPE
	SYNTAX	DisplayString 
	MAX-ACCESS read-only
	STATUS current
	DESCRIPTION
	"Description Yet To Be Added"
	::= { rtmpClientCountEntry 47 }

rtmpClientCountGetStreamWriteAccess	OBJECT-TYPE
	SYNTAX	DisplayString 
	MAX-ACCESS read-only
	STATUS current
	DESCRIPTION
	"Description Yet To Be Added"
	::= { rtmpClientCountEntry 48 }

rtmpClientCountGetTimeRunning	OBJECT-TYPE
	SYNTAX	DisplayString 
	MAX-ACCESS read-only
	STATUS current
	DESCRIPTION
	"Description Yet To Be Added"
	::= { rtmpClientCountEntry 49 }

rtmpClientCountGetTimebase	OBJECT-TYPE
	SYNTAX	Counter64 
	MAX-ACCESS read-only
	STATUS current
	DESCRIPTION
	"Description Yet To Be Added"
	::= { rtmpClientCountEntry 50 }

rtmpClientCountGetTotalInBytes	OBJECT-TYPE
	SYNTAX	Counter64 
	MAX-ACCESS read-only
	STATUS current
	DESCRIPTION
	"Description Yet To Be Added"
	::= { rtmpClientCountEntry 51 }

rtmpClientCountGetTouch	OBJECT-TYPE
	SYNTAX	Counter64 
	MAX-ACCESS read-only
	STATUS current
	DESCRIPTION
	"Description Yet To Be Added"
	::= { rtmpClientCountEntry 52 }

rtmpClientCountGetUri	OBJECT-TYPE
	SYNTAX	DisplayString 
	MAX-ACCESS read-only
	STATUS current
	DESCRIPTION
	"Description Yet To Be Added"
	::= { rtmpClientCountEntry 53 }

rtmpClientCountGetValidationFrequency	OBJECT-TYPE
	SYNTAX	Integer32 
	MAX-ACCESS read-only
	STATUS current
	DESCRIPTION
	"Description Yet To Be Added"
	::= { rtmpClientCountEntry 54 }

-- rtmpClientCount - End

-- rtmpClientPerform - Start

rtmpClientPerformTable	 OBJECT-TYPE
	SYNTAX	 SEQUENCE OF RTMPClientPerformTable
	MAX-ACCESS  not-accessible
	STATUS	 current
	DESCRIPTION
		"Description Yet To Be Added"
	::= { rtmpclientInfo 3 }

rtmpClientPerformEntry	 OBJECT-TYPE
	SYNTAX	RTMPClientPerformTable
	MAX-ACCESS  not-accessible
	STATUS	 current
	DESCRIPTION
		"Description Yet To Be Added"
	INDEX { serverIndex, vhostIndex, applicationIndex, applicationInstanceIndex, clientIndex }
	::= { rtmpClientPerformTable 1 }

RTMPClientPerformTable ::=
	SEQUENCE 
		{
		rtmpClientPerformCreationTime			Counter64,
		rtmpClientPerformGetFileInBytes			Counter64,
		rtmpClientPerformGetFileOutBytes		Counter64,
		rtmpClientPerformGetMessagesInBytes		Counter64,
		rtmpClientPerformGetMessagesInCount		Counter64,
		rtmpClientPerformGetMessagesInCountRate		Counter64,
		rtmpClientPerformGetMessagesLossBytes		Counter64,
		rtmpClientPerformGetMessagesLossCount		Counter64,
		rtmpClientPerformGetMessagesLossCountRate	Counter64,
		rtmpClientPerformGetMessagesOutBytes		Counter64,
		rtmpClientPerformGetMessagesOutCount		Counter64,
		rtmpClientPerformGetMessagesOutCountRate	Counter64
		}

rtmpClientPerformCreationTime	OBJECT-TYPE
	SYNTAX	Counter64 
	MAX-ACCESS read-only
	STATUS current
	DESCRIPTION
	"Description Yet To Be Added"
	::= { rtmpClientPerformEntry 1 }

rtmpClientPerformGetFileInBytes	OBJECT-TYPE
	SYNTAX	Counter64 
	MAX-ACCESS read-only
	STATUS current
	DESCRIPTION
	"Description Yet To Be Added"
	::= { rtmpClientPerformEntry 2 }

rtmpClientPerformGetFileOutBytes	OBJECT-TYPE
	SYNTAX	Counter64 
	MAX-ACCESS read-only
	STATUS current
	DESCRIPTION
	"Description Yet To Be Added"
	::= { rtmpClientPerformEntry 3 }

rtmpClientPerformGetMessagesInBytes	OBJECT-TYPE
	SYNTAX	Counter64 
	MAX-ACCESS read-only
	STATUS current
	DESCRIPTION
	"Description Yet To Be Added"
	::= { rtmpClientPerformEntry 4 }

rtmpClientPerformGetMessagesInCount	OBJECT-TYPE
	SYNTAX	Counter64 
	MAX-ACCESS read-only
	STATUS current
	DESCRIPTION
	"Description Yet To Be Added"
	::= { rtmpClientPerformEntry 5 }

rtmpClientPerformGetMessagesInCountRate	OBJECT-TYPE
	SYNTAX	Counter64 
	MAX-ACCESS read-only
	STATUS current
	DESCRIPTION
	"Description Yet To Be Added"
	::= { rtmpClientPerformEntry 6 }

rtmpClientPerformGetMessagesLossBytes	OBJECT-TYPE
	SYNTAX	Counter64 
	MAX-ACCESS read-only
	STATUS current
	DESCRIPTION
	"Description Yet To Be Added"
	::= { rtmpClientPerformEntry 7 }

rtmpClientPerformGetMessagesLossCount	OBJECT-TYPE
	SYNTAX	Counter64 
	MAX-ACCESS read-only
	STATUS current
	DESCRIPTION
	"Description Yet To Be Added"
	::= { rtmpClientPerformEntry 8 }

rtmpClientPerformGetMessagesLossCountRate	OBJECT-TYPE
	SYNTAX	Counter64 
	MAX-ACCESS read-only
	STATUS current
	DESCRIPTION
	"Description Yet To Be Added"
	::= { rtmpClientPerformEntry 9 }

rtmpClientPerformGetMessagesOutBytes	OBJECT-TYPE
	SYNTAX	Counter64 
	MAX-ACCESS read-only
	STATUS current
	DESCRIPTION
	"Description Yet To Be Added"
	::= { rtmpClientPerformEntry 10 }

rtmpClientPerformGetMessagesOutCount	OBJECT-TYPE
	SYNTAX	Counter64 
	MAX-ACCESS read-only
	STATUS current
	DESCRIPTION
	"Description Yet To Be Added"
	::= { rtmpClientPerformEntry 11 }

rtmpClientPerformGetMessagesOutCountRate	OBJECT-TYPE
	SYNTAX	Counter64 
	MAX-ACCESS read-only
	STATUS current
	DESCRIPTION
	"Description Yet To Be Added"
	::= { rtmpClientPerformEntry 12 }

-- rtmpClientPerform - Start

-- rtspClientCount - Start

rtspClientCountTable	 OBJECT-TYPE
	SYNTAX	 SEQUENCE OF RTSPClientCountTable
	MAX-ACCESS  not-accessible
	STATUS	 current
	DESCRIPTION
		"Description Yet To Be Added"
	::= { rtspclientInfo 1 }

rtspClientCountEntry	 OBJECT-TYPE
	SYNTAX	RTSPClientCountTable
	MAX-ACCESS  not-accessible
	STATUS	 current
	DESCRIPTION
		"Description Yet To Be Added"
	INDEX { serverIndex, vhostIndex, applicationIndex, applicationInstanceIndex, clientIndex }
	::= { rtspClientCountTable 1 }

RTSPClientCountTable ::=
	SEQUENCE 
		{
		rtspClientCountCreationTime			Counter64,
		rtspClientCountGetCookieStr			DisplayString,
		rtspClientCountGetIdleFrequency			Integer32,
		rtspClientCountGetIp				DisplayString,
		rtspClientCountGetLastAuthenticateMethod	Integer32,
		rtspClientCountGetQueryStr			DisplayString,
		rtspClientCountGetRTSPTunnelingSessionId	DisplayString,
		rtspClientCountGetRedirectSessionCode		Integer32,
		rtspClientCountGetRedirectSessionMessage	DisplayString,
		rtspClientCountGetRedirectSessionURL		DisplayString,
		rtspClientCountGetReferrer			DisplayString,
		rtspClientCountGetServerIp			DisplayString,
		rtspClientCountGetServerPort			Integer32,
		rtspClientCountGetSessionId			DisplayString,
		rtspClientCountGetTimeRunning			DisplayString,
		rtspClientCountGetUri				DisplayString,
		rtspClientCountGetUserAgent			DisplayString
		}

rtspClientCountCreationTime	OBJECT-TYPE
	SYNTAX	Counter64 
	MAX-ACCESS read-only
	STATUS current
	DESCRIPTION
	"Description Yet To Be Added"
	::= { rtspClientCountEntry 1 }

rtspClientCountGetCookieStr	OBJECT-TYPE
	SYNTAX	DisplayString 
	MAX-ACCESS read-only
	STATUS current
	DESCRIPTION
	"Description Yet To Be Added"
	::= { rtspClientCountEntry 2 }

rtspClientCountGetIdleFrequency	OBJECT-TYPE
	SYNTAX	Integer32 
	MAX-ACCESS read-only
	STATUS current
	DESCRIPTION
	"Description Yet To Be Added"
	::= { rtspClientCountEntry 3 }

rtspClientCountGetIp	OBJECT-TYPE
	SYNTAX	DisplayString 
	MAX-ACCESS read-only
	STATUS current
	DESCRIPTION
	"Description Yet To Be Added"
	::= { rtspClientCountEntry 4 }

rtspClientCountGetLastAuthenticateMethod	OBJECT-TYPE
	SYNTAX	Integer32 
	MAX-ACCESS read-only
	STATUS current
	DESCRIPTION
	"Description Yet To Be Added"
	::= { rtspClientCountEntry 5 }

rtspClientCountGetQueryStr	OBJECT-TYPE
	SYNTAX	DisplayString 
	MAX-ACCESS read-only
	STATUS current
	DESCRIPTION
	"Description Yet To Be Added"
	::= { rtspClientCountEntry 6 }

rtspClientCountGetRTSPTunnelingSessionId	OBJECT-TYPE
	SYNTAX	DisplayString 
	MAX-ACCESS read-only
	STATUS current
	DESCRIPTION
	"Description Yet To Be Added"
	::= { rtspClientCountEntry 7 }

rtspClientCountGetRedirectSessionCode	OBJECT-TYPE
	SYNTAX	Integer32 
	MAX-ACCESS read-only
	STATUS current
	DESCRIPTION
	"Description Yet To Be Added"
	::= { rtspClientCountEntry 8 }

rtspClientCountGetRedirectSessionMessage	OBJECT-TYPE
	SYNTAX	DisplayString 
	MAX-ACCESS read-only
	STATUS current
	DESCRIPTION
	"Description Yet To Be Added"
	::= { rtspClientCountEntry 9 }

rtspClientCountGetRedirectSessionURL	OBJECT-TYPE
	SYNTAX	DisplayString 
	MAX-ACCESS read-only
	STATUS current
	DESCRIPTION
	"Description Yet To Be Added"
	::= { rtspClientCountEntry 10 }

rtspClientCountGetReferrer	OBJECT-TYPE
	SYNTAX	DisplayString 
	MAX-ACCESS read-only
	STATUS current
	DESCRIPTION
	"Description Yet To Be Added"
	::= { rtspClientCountEntry 11 }

rtspClientCountGetServerIp	OBJECT-TYPE
	SYNTAX	DisplayString 
	MAX-ACCESS read-only
	STATUS current
	DESCRIPTION
	"Description Yet To Be Added"
	::= { rtspClientCountEntry 12 }

rtspClientCountGetServerPort	OBJECT-TYPE
	SYNTAX	Integer32 
	MAX-ACCESS read-only
	STATUS current
	DESCRIPTION
	"Description Yet To Be Added"
	::= { rtspClientCountEntry 13 }

rtspClientCountGetSessionId	OBJECT-TYPE
	SYNTAX	DisplayString 
	MAX-ACCESS read-only
	STATUS current
	DESCRIPTION
	"Description Yet To Be Added"
	::= { rtspClientCountEntry 14 }

rtspClientCountGetTimeRunning	OBJECT-TYPE
	SYNTAX	DisplayString 
	MAX-ACCESS read-only
	STATUS current
	DESCRIPTION
	"Description Yet To Be Added"
	::= { rtspClientCountEntry 15 }

rtspClientCountGetUri	OBJECT-TYPE
	SYNTAX	DisplayString 
	MAX-ACCESS read-only
	STATUS current
	DESCRIPTION
	"Description Yet To Be Added"
	::= { rtspClientCountEntry 16 }

rtspClientCountGetUserAgent	OBJECT-TYPE
	SYNTAX	DisplayString 
	MAX-ACCESS read-only
	STATUS current
	DESCRIPTION
	"Description Yet To Be Added"
	::= { rtspClientCountEntry 17 }

-- rtspClientCount - End

-- rtspClientPerform - Start

rtspClientPerformTable	 OBJECT-TYPE
	SYNTAX	 SEQUENCE OF RTSPClientPerformTable
	MAX-ACCESS  not-accessible
	STATUS	 current
	DESCRIPTION
		"Description Yet To Be Added"
	::= { rtspclientInfo 3 }

rtspClientPerformEntry	 OBJECT-TYPE
	SYNTAX	RTSPClientPerformTable
	MAX-ACCESS  not-accessible
	STATUS	 current
	DESCRIPTION
		"Description Yet To Be Added"
	INDEX { serverIndex, vhostIndex, applicationIndex, applicationInstanceIndex, clientIndex }
	::= { rtspClientPerformTable 1 }

RTSPClientPerformTable ::=
	SEQUENCE 
		{
		rtspClientPerformCreationTime			Counter64,
		rtspClientPerformGetFileInBytes			Counter64,
		rtspClientPerformGetFileOutBytes		Counter64,
		rtspClientPerformGetMessagesInBytes		Counter64,
		rtspClientPerformGetMessagesInCount		Counter64,
		rtspClientPerformGetMessagesInCountRate		Counter64,
		rtspClientPerformGetMessagesLossBytes		Counter64,
		rtspClientPerformGetMessagesLossCount		Counter64,
		rtspClientPerformGetMessagesLossCountRate	Counter64,
		rtspClientPerformGetMessagesOutBytes		Counter64,
		rtspClientPerformGetMessagesOutCount		Counter64,
		rtspClientPerformGetMessagesOutCountRate	Counter64
		}

rtspClientPerformCreationTime	OBJECT-TYPE
	SYNTAX	Counter64 
	MAX-ACCESS read-only
	STATUS current
	DESCRIPTION
	"Description Yet To Be Added"
	::= { rtspClientPerformEntry 1 }

rtspClientPerformGetFileInBytes	OBJECT-TYPE
	SYNTAX	Counter64 
	MAX-ACCESS read-only
	STATUS current
	DESCRIPTION
	"Description Yet To Be Added"
	::= { rtspClientPerformEntry 2 }

rtspClientPerformGetFileOutBytes	OBJECT-TYPE
	SYNTAX	Counter64 
	MAX-ACCESS read-only
	STATUS current
	DESCRIPTION
	"Description Yet To Be Added"
	::= { rtspClientPerformEntry 3 }

rtspClientPerformGetMessagesInBytes	OBJECT-TYPE
	SYNTAX	Counter64 
	MAX-ACCESS read-only
	STATUS current
	DESCRIPTION
	"Description Yet To Be Added"
	::= { rtspClientPerformEntry 4 }

rtspClientPerformGetMessagesInCount	OBJECT-TYPE
	SYNTAX	Counter64 
	MAX-ACCESS read-only
	STATUS current
	DESCRIPTION
	"Description Yet To Be Added"
	::= { rtspClientPerformEntry 5 }

rtspClientPerformGetMessagesInCountRate	OBJECT-TYPE
	SYNTAX	Counter64 
	MAX-ACCESS read-only
	STATUS current
	DESCRIPTION
	"Description Yet To Be Added"
	::= { rtspClientPerformEntry 6 }

rtspClientPerformGetMessagesLossBytes	OBJECT-TYPE
	SYNTAX	Counter64 
	MAX-ACCESS read-only
	STATUS current
	DESCRIPTION
	"Description Yet To Be Added"
	::= { rtspClientPerformEntry 7 }

rtspClientPerformGetMessagesLossCount	OBJECT-TYPE
	SYNTAX	Counter64 
	MAX-ACCESS read-only
	STATUS current
	DESCRIPTION
	"Description Yet To Be Added"
	::= { rtspClientPerformEntry 8 }

rtspClientPerformGetMessagesLossCountRate	OBJECT-TYPE
	SYNTAX	Counter64 
	MAX-ACCESS read-only
	STATUS current
	DESCRIPTION
	"Description Yet To Be Added"
	::= { rtspClientPerformEntry 9 }

rtspClientPerformGetMessagesOutBytes	OBJECT-TYPE
	SYNTAX	Counter64 
	MAX-ACCESS read-only
	STATUS current
	DESCRIPTION
	"Description Yet To Be Added"
	::= { rtspClientPerformEntry 10 }

rtspClientPerformGetMessagesOutCount	OBJECT-TYPE
	SYNTAX	Counter64 
	MAX-ACCESS read-only
	STATUS current
	DESCRIPTION
	"Description Yet To Be Added"
	::= { rtspClientPerformEntry 11 }

rtspClientPerformGetMessagesOutCountRate	OBJECT-TYPE
	SYNTAX	Counter64 
	MAX-ACCESS read-only
	STATUS current
	DESCRIPTION
	"Description Yet To Be Added"
	::= { rtspClientPerformEntry 12 }

-- rtspClientPerform - End

-- httpClientCount - Start

httpClientCountTable	 OBJECT-TYPE
	SYNTAX	 SEQUENCE OF HTTPClientCountTable
	MAX-ACCESS  not-accessible
	STATUS	 current
	DESCRIPTION
		"Description Yet To Be Added"
	::= { httpclientInfo 1 }

httpClientCountEntry	 OBJECT-TYPE
	SYNTAX	HTTPClientCountTable
	MAX-ACCESS  not-accessible
	STATUS	 current
	DESCRIPTION
		"Description Yet To Be Added"
	INDEX { serverIndex, vhostIndex, applicationIndex, applicationInstanceIndex, clientIndex }
	::= { httpClientCountTable 1 }

HTTPClientCountTable ::=
	SEQUENCE 
		{
		httpClientCountCreationTime 			Counter64,
		httpClientCountGetCookieStr			DisplayString,
		httpClientCountGetHTTPDate			DisplayString,
		httpClientCountGetIpAddress			DisplayString,
		httpClientCountGetIsFirstChunk			TruthValue,
		httpClientCountGetLastRequest			Counter64,
		httpClientCountGetLiveStreamingPacketizer	DisplayString,
		httpClientCountGetPlayDuration			Counter64,
		httpClientCountGetPlaySeek			Counter64,
		httpClientCountGetPlayStart			Counter64,
		httpClientCountGetQueryStr			DisplayString,
		httpClientCountGetRedirectSessionCode		Integer32,
		httpClientCountGetRedirectSessionContentType	DisplayString,
		httpClientCountGetRedirectSessionURL		DisplayString,
		httpClientCountGetReferrer			DisplayString,
		httpClientCountGetServerIp			DisplayString,
		httpClientCountGetServerPort			Integer32,
		httpClientCountGetSessionId			DisplayString,
		httpClientCountGetSessionProtocol		Integer32,
		httpClientCountGetSessionTimeout		Integer32,
		httpClientCountGetSessionType			Integer32,
		httpClientCountGetStreamExt			DisplayString,
		httpClientCountGetStreamName			DisplayString,
		httpClientCountGetStreamPosition		Counter64,
		httpClientCountGetTimeRunning			DisplayString,
		httpClientCountGetUri				DisplayString,
		httpClientCountGetUserAgent			DisplayString,
		httpClientCountGetUserQueryStr			DisplayString,
		httpClientCountGetVODTranscodeNGRP		DisplayString
		}

httpClientCountCreationTime	OBJECT-TYPE
	SYNTAX	Counter64 
	MAX-ACCESS read-only
	STATUS current
	DESCRIPTION
	"Description Yet To Be Added"
	::= { httpClientCountEntry 1 }

httpClientCountGetCookieStr	OBJECT-TYPE
	SYNTAX	DisplayString 
	MAX-ACCESS read-only
	STATUS current
	DESCRIPTION
	"Description Yet To Be Added"
	::= { httpClientCountEntry 2 }

httpClientCountGetHTTPDate	OBJECT-TYPE
	SYNTAX	DisplayString 
	MAX-ACCESS read-only
	STATUS current
	DESCRIPTION
	"Description Yet To Be Added"
	::= { httpClientCountEntry 3 }

httpClientCountGetIpAddress	OBJECT-TYPE
	SYNTAX	DisplayString 
	MAX-ACCESS read-only
	STATUS current
	DESCRIPTION
	"Description Yet To Be Added"
	::= { httpClientCountEntry 4 }

httpClientCountGetIsFirstChunk	OBJECT-TYPE
	SYNTAX	TruthValue 
	MAX-ACCESS read-only
	STATUS current
	DESCRIPTION
	"Description Yet To Be Added"
	::= { httpClientCountEntry 5 }

httpClientCountGetLastRequest	OBJECT-TYPE
	SYNTAX	Counter64 
	MAX-ACCESS read-only
	STATUS current
	DESCRIPTION
	"Description Yet To Be Added"
	::= { httpClientCountEntry 6 }

httpClientCountGetLiveStreamingPacketizer	OBJECT-TYPE
	SYNTAX	DisplayString 
	MAX-ACCESS read-only
	STATUS current
	DESCRIPTION
	"Description Yet To Be Added"
	::= { httpClientCountEntry 7 }

httpClientCountGetPlayDuration	OBJECT-TYPE
	SYNTAX	Counter64 
	MAX-ACCESS read-only
	STATUS current
	DESCRIPTION
	"Description Yet To Be Added"
	::= { httpClientCountEntry 8 }

httpClientCountGetPlaySeek	OBJECT-TYPE
	SYNTAX	Counter64 
	MAX-ACCESS read-only
	STATUS current
	DESCRIPTION
	"Description Yet To Be Added"
	::= { httpClientCountEntry 9 }

httpClientCountGetPlayStart	OBJECT-TYPE
	SYNTAX	Counter64 
	MAX-ACCESS read-only
	STATUS current
	DESCRIPTION
	"Description Yet To Be Added"
	::= { httpClientCountEntry 10 }

httpClientCountGetQueryStr	OBJECT-TYPE
	SYNTAX	DisplayString 
	MAX-ACCESS read-only
	STATUS current
	DESCRIPTION
	"Description Yet To Be Added"
	::= { httpClientCountEntry 11 }

httpClientCountGetRedirectSessionCode	OBJECT-TYPE
	SYNTAX	Integer32 
	MAX-ACCESS read-only
	STATUS current
	DESCRIPTION
	"Description Yet To Be Added"
	::= { httpClientCountEntry 12 }

httpClientCountGetRedirectSessionContentType	OBJECT-TYPE
	SYNTAX	DisplayString 
	MAX-ACCESS read-only
	STATUS current
	DESCRIPTION
	"Description Yet To Be Added"
	::= { httpClientCountEntry 13 }

httpClientCountGetRedirectSessionURL	OBJECT-TYPE
	SYNTAX	DisplayString 
	MAX-ACCESS read-only
	STATUS current
	DESCRIPTION
	"Description Yet To Be Added"
	::= { httpClientCountEntry 14 }

httpClientCountGetReferrer	OBJECT-TYPE
	SYNTAX	DisplayString 
	MAX-ACCESS read-only
	STATUS current
	DESCRIPTION
	"Description Yet To Be Added"
	::= { httpClientCountEntry 15 }

httpClientCountGetServerIp	OBJECT-TYPE
	SYNTAX	DisplayString 
	MAX-ACCESS read-only
	STATUS current
	DESCRIPTION
	"Description Yet To Be Added"
	::= { httpClientCountEntry 16 }

httpClientCountGetServerPort	OBJECT-TYPE
	SYNTAX	Integer32 
	MAX-ACCESS read-only
	STATUS current
	DESCRIPTION
	"Description Yet To Be Added"
	::= { httpClientCountEntry 17 }

httpClientCountGetSessionId	OBJECT-TYPE
	SYNTAX	DisplayString 
	MAX-ACCESS read-only
	STATUS current
	DESCRIPTION
	"Description Yet To Be Added"
	::= { httpClientCountEntry 18 }

httpClientCountGetSessionProtocol	OBJECT-TYPE
	SYNTAX	Integer32 
	MAX-ACCESS read-only
	STATUS current
	DESCRIPTION
	"Description Yet To Be Added"
	::= { httpClientCountEntry 19 }

httpClientCountGetSessionTimeout	OBJECT-TYPE
	SYNTAX	Integer32 
	MAX-ACCESS read-only
	STATUS current
	DESCRIPTION
	"Description Yet To Be Added"
	::= { httpClientCountEntry 20 }

httpClientCountGetSessionType	OBJECT-TYPE
	SYNTAX	Integer32 
	MAX-ACCESS read-only
	STATUS current
	DESCRIPTION
	"Description Yet To Be Added"
	::= { httpClientCountEntry 21 }

httpClientCountGetStreamExt	OBJECT-TYPE
	SYNTAX	DisplayString 
	MAX-ACCESS read-only
	STATUS current
	DESCRIPTION
	"Description Yet To Be Added"
	::= { httpClientCountEntry 22 }

httpClientCountGetStreamName	OBJECT-TYPE
	SYNTAX	DisplayString 
	MAX-ACCESS read-only
	STATUS current
	DESCRIPTION
	"Description Yet To Be Added"
	::= { httpClientCountEntry 23 }

httpClientCountGetStreamPosition	OBJECT-TYPE
	SYNTAX	Counter64 
	MAX-ACCESS read-only
	STATUS current
	DESCRIPTION
	"Description Yet To Be Added"
	::= { httpClientCountEntry 24 }

httpClientCountGetTimeRunning	OBJECT-TYPE
	SYNTAX	DisplayString 
	MAX-ACCESS read-only
	STATUS current
	DESCRIPTION
	"Description Yet To Be Added"
	::= { httpClientCountEntry 25 }

httpClientCountGetUri	OBJECT-TYPE
	SYNTAX	DisplayString 
	MAX-ACCESS read-only
	STATUS current
	DESCRIPTION
	"Description Yet To Be Added"
	::= { httpClientCountEntry 26 }

httpClientCountGetUserAgent	OBJECT-TYPE
	SYNTAX	DisplayString 
	MAX-ACCESS read-only
	STATUS current
	DESCRIPTION
	"Description Yet To Be Added"
	::= { httpClientCountEntry 27 }

httpClientCountGetUserQueryStr	OBJECT-TYPE
	SYNTAX	DisplayString 
	MAX-ACCESS read-only
	STATUS current
	DESCRIPTION
	"Description Yet To Be Added"
	::= { httpClientCountEntry 28 }

httpClientCountGetVODTranscodeNGRP	OBJECT-TYPE
	SYNTAX	DisplayString 
	MAX-ACCESS read-only
	STATUS current
	DESCRIPTION
	"Description Yet To Be Added"
	::= { httpClientCountEntry 29 }

-- httpClientCount - End

-- httpClientPerform - Start

httpClientPerformTable	 OBJECT-TYPE
	SYNTAX	 SEQUENCE OF HTTPClientPerformTable
	MAX-ACCESS  not-accessible
	STATUS	 current
	DESCRIPTION
		"Description Yet To Be Added"
	::= { httpclientInfo 3 }

httpClientPerformEntry	 OBJECT-TYPE
	SYNTAX	HTTPClientPerformTable
	MAX-ACCESS  not-accessible
	STATUS	 current
	DESCRIPTION
		"Description Yet To Be Added"
	INDEX { serverIndex, vhostIndex, applicationIndex, applicationInstanceIndex, clientIndex }
	::= { httpClientPerformTable 1 }

HTTPClientPerformTable ::=
	SEQUENCE 
		{
		httpClientPerformCreationTime			Counter64,
		httpClientPerformGetFileInBytes			Counter64,
		httpClientPerformGetFileOutBytes		Counter64,
		httpClientPerformGetMessagesInBytes		Counter64,
		httpClientPerformGetMessagesInCount		Counter64,
		httpClientPerformGetMessagesInCountRate		Counter64,
		httpClientPerformGetMessagesLossBytes		Counter64,
		httpClientPerformGetMessagesLossCount		Counter64,
		httpClientPerformGetMessagesLossCountRate	Counter64,
		httpClientPerformGetMessagesOutBytes		Counter64,
		httpClientPerformGetMessagesOutCount		Counter64,
		httpClientPerformGetMessagesOutCountRate	Counter64
		}

httpClientPerformCreationTime	OBJECT-TYPE
	SYNTAX	Counter64 
	MAX-ACCESS read-only
	STATUS current
	DESCRIPTION
	"Description Yet To Be Added"
	::= { httpClientPerformEntry 1 }

httpClientPerformGetFileInBytes	OBJECT-TYPE
	SYNTAX	Counter64 
	MAX-ACCESS read-only
	STATUS current
	DESCRIPTION
	"Description Yet To Be Added"
	::= { httpClientPerformEntry 2 }

httpClientPerformGetFileOutBytes	OBJECT-TYPE
	SYNTAX	Counter64 
	MAX-ACCESS read-only
	STATUS current
	DESCRIPTION
	"Description Yet To Be Added"
	::= { httpClientPerformEntry 3 }

httpClientPerformGetMessagesInBytes	OBJECT-TYPE
	SYNTAX	Counter64 
	MAX-ACCESS read-only
	STATUS current
	DESCRIPTION
	"Description Yet To Be Added"
	::= { httpClientPerformEntry 4 }

httpClientPerformGetMessagesInCount	OBJECT-TYPE
	SYNTAX	Counter64 
	MAX-ACCESS read-only
	STATUS current
	DESCRIPTION
	"Description Yet To Be Added"
	::= { httpClientPerformEntry 5 }

httpClientPerformGetMessagesInCountRate	OBJECT-TYPE
	SYNTAX	Counter64 
	MAX-ACCESS read-only
	STATUS current
	DESCRIPTION
	"Description Yet To Be Added"
	::= { httpClientPerformEntry 6 }

httpClientPerformGetMessagesLossBytes	OBJECT-TYPE
	SYNTAX	Counter64 
	MAX-ACCESS read-only
	STATUS current
	DESCRIPTION
	"Description Yet To Be Added"
	::= { httpClientPerformEntry 7 }

httpClientPerformGetMessagesLossCount	OBJECT-TYPE
	SYNTAX	Counter64 
	MAX-ACCESS read-only
	STATUS current
	DESCRIPTION
	"Description Yet To Be Added"
	::= { httpClientPerformEntry 8 }

httpClientPerformGetMessagesLossCountRate	OBJECT-TYPE
	SYNTAX	Counter64 
	MAX-ACCESS read-only
	STATUS current
	DESCRIPTION
	"Description Yet To Be Added"
	::= { httpClientPerformEntry 9 }

httpClientPerformGetMessagesOutBytes	OBJECT-TYPE
	SYNTAX	Counter64 
	MAX-ACCESS read-only
	STATUS current
	DESCRIPTION
	"Description Yet To Be Added"
	::= { httpClientPerformEntry 10 }

httpClientPerformGetMessagesOutCount	OBJECT-TYPE
	SYNTAX	Counter64 
	MAX-ACCESS read-only
	STATUS current
	DESCRIPTION
	"Description Yet To Be Added"
	::= { httpClientPerformEntry 11 }

httpClientPerformGetMessagesOutCountRate	OBJECT-TYPE
	SYNTAX	Counter64 
	MAX-ACCESS read-only
	STATUS current
	DESCRIPTION
	"Description Yet To Be Added"
	::= { httpClientPerformEntry 12 }

-- httpClientPerform - End

-- serverGroupConformanceObjectTable - start

serverGroupEntryConformanceTable	OBJECT-GROUP
	OBJECTS { serverIndex } 
	STATUS  current
	DESCRIPTION
			"A collection of objects providing information"
	  ::= { serverGroupObject 1 }

serverCounterGroupEntryConformanceTable	OBJECT-GROUP
	OBJECTS
		{
		serverCounterCreationTime, 
		serverCounterGetAdminGUID, 
		serverCounterGetClientIdGeneratorRecycleDelaySize,
		serverCounterGetClientIdGeneratorRecycleSize, 
		serverCounterGetClientIdGeneratorTimeout, 
		serverCounterGetCommittedVirtuallMemory,
		serverCounterGetConnectionsMaximum, 
		serverCounterGetCoreHandlerPoolSize, 
		serverCounterGetCoreTransportPoolSize,
		serverCounterGetCryptoPoolActiveCount, 
		serverCounterGetCryptoPoolMaxSize, 
		serverCounterGetCurrentHeapSize,
		serverCounterGetDateStarted, 
		serverCounterGetDefaultStreamPrefix, 
		serverCounterGetGUID,
		serverCounterGetHTTPHeaderServer, 
		serverCounterGetLiveStreamTranscoderSessionCount, 
		serverCounterGetLiveThreads,
		serverCounterGetMaxHeapSize, 
		serverCounterGetPeakThreads, 
		serverCounterGetPublishersMaximum,
		serverCounterGetRTMPTHeaderServer, 
		serverCounterGetServerGUID, 
		serverCounterGetSessionGUID,
		serverCounterGetTimeRunning, 
		serverCounterGetTranscoderLicenseInUse, 
		serverCounterGetTranscoderLicenseTotal,
		serverCounterGetVersion
		}
	STATUS  current
	DESCRIPTION
		"A collection of objects providing information"
	::= { serverGroupObject 2 }

serverConnectGroupEntryConformanceTable OBJECT-GROUP
	OBJECTS
		{
		serverConnectCreationTime, 
		serverConnectGetCurrent, 
		serverConnectGetLastConnectAcceptedStamp,
		serverConnectGetLastConnectAcceptedStampString,
		serverConnectGetLastConnectAcceptedTimeString,
		serverConnectGetLastConnectRejectedStamp, 
		serverConnectGetLastConnectRejectedStampString,
		serverConnectGetLastConnectRejectedTimeString, 
		serverConnectGetLastDisconnectStamp,
		serverConnectGetLastDisconnectStampString, 
		serverConnectGetLastDisconnectTimeString,
		serverConnectGetTotal, 
		serverConnectGetTotalAccepted, 
		serverConnectGetTotalRejected
		}
	STATUS  current
	DESCRIPTION
		"A collection of objects providing information"
	::= { serverGroupObject 3 }

serverPerformGroupEntryConformanceTable OBJECT-GROUP
	OBJECTS
		{
		serverPerformCreationTime, 
		serverPerformGetFileInBytes, 
		serverPerformGetFileOutBytes,
		serverPerformGetMessagesInBytes, 
		serverPerformGetMessagesInCount, 
		serverPerformGetMessagesInCountRate,
		serverPerformGetMessagesLossBytes, 
		serverPerformGetMessagesLossCount, 
		serverPerformGetMessagesLossCountRate,
		serverPerformGetMessagesOutBytes, 
		serverPerformGetMessagesOutCount, 
		serverPerformGetMessagesOutCountRate
		}
	STATUS  current
	DESCRIPTION
		"A collection of objects providing information"
	::= { serverGroupObject 4 }

vhostGroupEntryConformanceTable	OBJECT-GROUP
	OBJECTS { vhostIndex }
	STATUS  current
	DESCRIPTION
			"A collection of objects providing information"
	  ::= { vhostGroupObject 1 }

vhostCounterGroupEntryConformanceTable OBJECT-GROUP
	OBJECTS
		{
		vhostCounterCreationTime, 
		vhostCounterGetApplicationTimeout, 
		vhostCounterGetByteArrayOutputStreamBaseClassPath,
		vhostCounterGetClientCount, 
		vhostCounterGetClientIdleFrequency, 
		vhostCounterGetClientTimeout,
		vhostCounterGetConnectionLimit, 
		vhostCounterGetCoreHandlerPoolSize, 
		vhostCounterGetCoreTransportPoolSize,
		vhostCounterGetDateStarted, 
		vhostCounterGetFileIOPoolSize, 
		vhostCounterGetHTTPStreamerMaxPathLen,
		vhostCounterGetHomePath, 
		vhostCounterGetIdleCheckFrequency, 
		vhostCounterGetIdleMinimumWaitTime, 
		vhostCounterGetIdleWorkerCount,
		vhostCounterGetKeepAliveTimeout, 
		vhostCounterGetLiveStreamTranscoderSessionCount, 
		vhostCounterGetMaximumPendingReadBytes,
		vhostCounterGetMaximumPendingWriteBytes, 
		vhostCounterGetMaximumSetBufferTime, 
		vhostCounterGetName,
		vhostCounterGetNetConnectionIdleFrequency, 
		vhostCounterGetNetConnectionProcessorCount, 
		vhostCounterGetNextMediaCasterId,
		vhostCounterGetNextNetConnectionId, 
		vhostCounterGetPingTimeout, 
		vhostCounterGetRTPIdleFrequency,
		vhostCounterGetRTSPMaxPathLen, 
		vhostCounterGetScheduledReadMaxSessionBytes, 
		vhostCounterGetScheduledWriteBytes,
		vhostCounterGetScheduledWriteMaxSessionBytes, 
		vhostCounterGetScheduledWriteMaxSessionClientId, 
		vhostCounterGetScheduledWriteRequests,
		vhostCounterGetScheduledWriteSessions, 
		vhostCounterGetStartupStreamsDelayTime, 
		vhostCounterGetTimeRunning,
		vhostCounterGetUnidentifiedSessionTimeout, 
		vhostCounterGetValidationFrequency, 
		vhostCounterGetWaitingReadBytes,
		vhostCounterGetWebRTCIdleFrequency
		}
	STATUS  current
	DESCRIPTION
			 "A collection of objects providing information"
	::= { vhostGroupObject 2 }

vhostConnectGroupEntryConformanceTable OBJECT-GROUP
	OBJECTS
		{
		vhostConnectCreationTime,vhostConnectGetCurrent, 
		vhostConnectGetLastConnectAcceptedStamp, 
		vhostConnectGetLastConnectAcceptedStampString,
		vhostConnectGetLastConnectAcceptedTimeString, 
		vhostConnectGetLastConnectRejectedStamp, 
		vhostConnectGetLastConnectRejectedStampString,
		vhostConnectGetLastConnectRejectedTimeString, 
		vhostConnectGetLastDisconnectStamp, 
		vhostConnectGetLastDisconnectStampString,
		vhostConnectGetLastDisconnectTimeString, 
		vhostConnectGetTotal, 
		vhostConnectGetTotalAccepted,
		vhostConnectGetTotalRejected
		}
	STATUS  current
	DESCRIPTION
			 "A collection of objects providing information"
	::= { vhostGroupObject 3 }


vhostPerformGroupEntryConformanceTable OBJECT-GROUP
	OBJECTS
		{
		vhostPerformCreationTime,
		vhostPerformGetFileInBytes, 
		vhostPerformGetFileOutBytes, 
		vhostPerformGetMessagesInBytes,
		vhostPerformGetMessagesInCount, 
		vhostPerformGetMessagesInCountRate, 
		vhostPerformGetMessagesLossBytes,
		vhostPerformGetMessagesLossCount, 
		vhostPerformGetMessagesLossCountRate, 
		vhostPerformGetMessagesOutBytes,
		vhostPerformGetMessagesOutCount, 
		vhostPerformGetMessagesOutCountRate
		}
	STATUS  current
	DESCRIPTION
			 "A collection of objects providing information"
	::= { vhostGroupObject 4 }

applicationGroupEntryConformanceTable	OBJECT-GROUP
	OBJECTS { applicationIndex }
	STATUS  current
	DESCRIPTION
			"A collection of objects providing information"
	  ::= { applicationGroupObject 1 }


applicationCounterGroupEntryConformanceTable OBJECT-GROUP
	OBJECTS
		{
		applicationCounterCreationTime, 
		applicationCounterGetApplicationPath, 
		applicationCounterGetConfigPath,
		applicationCounterGetDateStarted, 
		applicationCounterGetInstanceCount, 
		applicationCounterGetMessagesInBytes,
		applicationCounterGetMessagesInCount, 
		applicationCounterGetMessagesInCountRate, 
		applicationCounterGetMessagesOutBytes,
		applicationCounterGetMessagesOutCount, 
		applicationCounterGetMessagesOutCountRate, 
		applicationCounterGetName,
		applicationCounterGetTimeRunning
		}

	STATUS  current
	DESCRIPTION
			 "A collection of objects providing information"
	::= { applicationGroupObject 2 }

applicationConnectGroupEntryConformanceTable OBJECT-GROUP
	OBJECTS
		{
		applicationConnectCreationTime, 
		applicationConnectGetCurrent,
		applicationConnectGetLastConnectAcceptedStamp, 
		applicationConnectGetLastConnectAcceptedStampString,
		applicationConnectGetLastConnectAcceptedTimeString, 
		applicationConnectGetLastConnectRejectedStamp,
		applicationConnectGetLastConnectRejectedStampString, 
		applicationConnectGetLastConnectRejectedTimeString,
		applicationConnectGetLastDisconnectStamp, 
		applicationConnectGetLastDisconnectStampString,
		applicationConnectGetLastDisconnectTimeString, 
		applicationConnectGetTotal,
		applicationConnectGetTotalAccepted, 
		applicationConnectGetTotalRejected
		}

	STATUS  current
	DESCRIPTION
			 "A collection of objects providing information"
	::= { applicationGroupObject 3 }

applicationPerformGroupEntryConformanceTable OBJECT-GROUP
	OBJECTS
		{
		applicationPerformCreationTime, 
		applicationPerformGetFileInBytes,
		applicationPerformGetFileOutBytes, 
		applicationPerformGetMessagesInBytes,
		applicationPerformGetMessagesInCount, 
		applicationPerformGetMessagesInCountRate,
		applicationPerformGetMessagesLossBytes, 
		applicationPerformGetMessagesLossCount,
		applicationPerformGetMessagesLossCountRate, 
		applicationPerformGetMessagesOutBytes,
		applicationPerformGetMessagesOutCount, 
		applicationPerformGetMessagesOutCountRate
		}

	STATUS  current
	DESCRIPTION
			 "A collection of objects providing information"
	::= { applicationGroupObject 4 }


applicationInstanceGroupEntryConformanceTable	OBJECT-GROUP
	OBJECTS { applicationInstanceIndex }
	STATUS  current
	DESCRIPTION
			"A collection of objects providing information"
	  ::= { applicationInstanceGroupObject 1 }

applicationInstanceCounterGroupEntryConformanceTable	OBJECT-GROUP
	OBJECTS { 
		applicationInstanceCounterCreationTime, 
		applicationInstanceCounterGetApplicationInstanceTouchTimeout,
		applicationInstanceCounterGetApplicationTimeout, 
		applicationInstanceCounterGetClientCount,
		applicationInstanceCounterGetClientCountTotal, 
		applicationInstanceCounterGetClientIdleFrequency,
		applicationInstanceCounterGetClientRemoveTime, 
		applicationInstanceCounterGetContextStr,
		applicationInstanceCounterGetDateStarted, 
		applicationInstanceCounterGetDvrRecorderList,
		applicationInstanceCounterGetHTTPStreamerList, 
		applicationInstanceCounterGetHTTPStreamerSessionCount,
		applicationInstanceCounterGetLastTouchTime, 
		applicationInstanceCounterGetLiveStreamPacketizerList,
		applicationInstanceCounterGetLiveStreamTranscoderList, 
		applicationInstanceCounterGetMaxStorageDirDepth,
		applicationInstanceCounterGetMaximumPendingReadBytes, 
		applicationInstanceCounterGetMaximumPendingWriteBytes,
		applicationInstanceCounterGetMaximumSetBufferTime, 
		applicationInstanceCounterGetMediacasterRTPRTSPRTPTransportMode,
		applicationInstanceCounterGetMessagesInBytes, 
		applicationInstanceCounterGetMessagesInCount,
		applicationInstanceCounterGetMessagesInCountRate, 
		applicationInstanceCounterGetMessagesOutBytes,
		applicationInstanceCounterGetMessagesOutCount, 
		applicationInstanceCounterGetMessagesOutCountRate,
		applicationInstanceCounterGetName, 
		applicationInstanceCounterGetPingTimeout,
		applicationInstanceCounterGetPublisherCount, 
		applicationInstanceCounterGetPushPublishSessionCount,
		applicationInstanceCounterGetRTPAVSyncMethod, 
		applicationInstanceCounterGetRTPIdleFrequency,
		applicationInstanceCounterGetRTPMaxRTCPWaitTime, 
		applicationInstanceCounterGetRTPPlayAuthenticationMethod,
		applicationInstanceCounterGetRTPPublishAuthenticationMethod, 
		applicationInstanceCounterGetRTPSessionCount,
		applicationInstanceCounterGetRTSPBindIpAddress, 
		applicationInstanceCounterGetRTSPConnectionAddressType,
		applicationInstanceCounterGetRTSPConnectionIpAddress, 
		applicationInstanceCounterGetRTSPMaximumPendingWriteBytes,
		applicationInstanceCounterGetRTSPOriginAddressType, 
		applicationInstanceCounterGetRTSPOriginIpAddress,
		applicationInstanceCounterGetRTSPSessionTimeout, 
		applicationInstanceCounterGetRepeaterOriginUrl,
		applicationInstanceCounterGetRepeaterQueryString, 
		applicationInstanceCounterGetRsoStorageDir,
		applicationInstanceCounterGetRsoStoragePath, 
		applicationInstanceCounterGetSharedObjectReadAccess,
		applicationInstanceCounterGetSharedObjectWriteAccess, 
		applicationInstanceCounterGetSourceControlSessionCount,
		applicationInstanceCounterGetStreamAudioSampleAccess, 
		applicationInstanceCounterGetStreamCount,
		applicationInstanceCounterGetStreamKeyDir, 
		applicationInstanceCounterGetStreamKeyPath,
		applicationInstanceCounterGetStreamReadAccess, 
		applicationInstanceCounterGetStreamStorageDir,
		applicationInstanceCounterGetStreamStoragePath, 
		applicationInstanceCounterGetStreamType,
		applicationInstanceCounterGetStreamVideoSampleAccess, 
		applicationInstanceCounterGetStreamWriteAccess,
		applicationInstanceCounterGetTimeRunning, 
		applicationInstanceCounterGetVODTimedTextProviderList,
		applicationInstanceCounterGetValidationFrequency
		}
	STATUS  current
	DESCRIPTION
			"A collection of objects providing information"
	  ::= { applicationInstanceGroupObject 2 }

applicationInstanceConnectGroupEntryConformanceTable	OBJECT-GROUP
	OBJECTS { 
		applicationInstanceConnectCreationTime, 
		applicationInstanceConnectGetCurrent,
		applicationInstanceConnectGetLastConnectAcceptedStamp, 
		applicationInstanceConnectGetLastConnectAcceptedStampString,
		applicationInstanceConnectGetLastConnectAcceptedTimeString, 
		applicationInstanceConnectGetLastConnectRejectedStamp,
		applicationInstanceConnectGetLastConnectRejectedStampString, 
		applicationInstanceConnectGetLastConnectRejectedTimeString,
		applicationInstanceConnectGetLastDisconnectStamp, 
		applicationInstanceConnectGetLastDisconnectStampString,
		applicationInstanceConnectGetLastDisconnectTimeString, 
		applicationInstanceConnectGetTotal,
		applicationInstanceConnectGetTotalAccepted, 
		applicationInstanceConnectGetTotalRejected
		}
	STATUS  current
	DESCRIPTION
			"A collection of objects providing information"
	  ::= { applicationInstanceGroupObject 3 }


applicationInstancePerformGroupEntryConformanceTable	OBJECT-GROUP
	OBJECTS { 
		applicationInstancePerformCreationTime, 
		applicationInstancePerformGetFileInBytes,
		applicationInstancePerformGetFileOutBytes, 
		applicationInstancePerformGetMessagesInBytes, 
		applicationInstancePerformGetMessagesInCount, 
		applicationInstancePerformGetMessagesInCountRate, 
		applicationInstancePerformGetMessagesLossBytes, 
		applicationInstancePerformGetMessagesLossCount,
		applicationInstancePerformGetMessagesLossCountRate, 
		applicationInstancePerformGetMessagesOutBytes,
		applicationInstancePerformGetMessagesOutCount, 
		applicationInstancePerformGetMessagesOutCountRate
		}
	STATUS  current
	DESCRIPTION
			"A collection of objects providing information"
	  ::= { applicationInstanceGroupObject 4 }

streamGroupEntryConformanceTable	OBJECT-GROUP
	OBJECTS { streamIndex }
	STATUS  current
	DESCRIPTION
			"A collection of objects providing information"
	  ::= { streamGroupObject 1 }

streamCounterGroupEntryConformanceTable	OBJECT-GROUP
	OBJECTS { 
		streamCountCreationTime, 
		streamCountGetAudioMissing, 
		streamCountGetAudioSize,
		streamCountGetAudioTC, 
		streamCountGetBufferTime, 
		streamCountGetCacheName,
		streamCountGetClientId, 
		streamCountGetContextStr, 
		streamCountGetDataMissing,
		streamCountGetDataSize, 
		streamCountGetDataTC, 
		streamCountGetDataType,
		streamCountGetDvrRecorder, 
		streamCountGetDvrRecorderList, 
		streamCountGetDvrRepeater,
		streamCountGetExt, 
		streamCountGetFirstPacketTC, 
		streamCountGetHeaderSize,
		streamCountGetLastFlushAudioTC, 
		streamCountGetLastFlushDataTC, 
		streamCountGetLastFlushRTTimecode,
		streamCountGetLastFlushTime, 
		streamCountGetLastFlushTimecode, 
		streamCountGetLastFlushVideoTC,
		streamCountGetLastPacketTC, 
		streamCountGetLastReceivedAudioTC, 
		streamCountGetLastReceivedDataTC,
		streamCountGetLastReceivedVideoTC, 
		streamCountGetLastSentAudioTC, 
		streamCountGetLastSentDataTC,
		streamCountGetLastSentVideoTC, 
		streamCountGetLiveStreamPacketizer, 
		streamCountGetLiveStreamPacketizerList,
		streamCountGetLiveStreamRepeater, 
		streamCountGetLiveStreamTranscoderList, 
		streamCountGetMaxTimecode,
		streamCountGetName, 
		streamCountGetPacketCount, 
		streamCountGetPublishAudioCodecId,
		streamCountGetPublishBitrateAudio, 
		streamCountGetPublishBitrateVideo, 
		streamCountGetPublishFrameCountAudio,
		streamCountGetPublishFrameCountData, 
		streamCountGetPublishFrameCountVideo, 
		streamCountGetPublishVideoCodecId,
		streamCountGetQueryStr, 
		streamCountGetReceiveVideoFPS, 
		streamCountGetSrc, 
		streamCountGetStreamType,
		streamCountGetTimecodeOffset, 
		streamCountGetTss, 
		streamCountGetUniqueStreamIdStr,
		streamCountGetVideoMissing, 
		streamCountGetVideoSize, 
		streamCountGetVideoTC
		}
	STATUS  current
	DESCRIPTION
			"A collection of objects providing information"
	  ::= { streamGroupObject 2 }

streamPerformGroupEntryConformanceTable	OBJECT-GROUP
	OBJECTS { 
		streamPerformCreationTime, 
		streamPerformGetFileInBytes, 
		streamPerformGetFileOutBytes,
		streamPerformGetMessagesInBytes, 
		streamPerformGetMessagesInCount, 
		streamPerformGetMessagesInCountRate,
		streamPerformGetMessagesLossBytes, 
		streamPerformGetMessagesLossCount, 
		streamPerformGetMessagesLossCountRate,
		streamPerformGetMessagesOutBytes, 
		streamPerformGetMessagesOutCount, 
		streamPerformGetMessagesOutCountRate
		}
	STATUS  current
	DESCRIPTION
			"A collection of objects providing information"
	  ::= { streamGroupObject 3 }


clientGroupEntryConformanceTable	OBJECT-GROUP
	OBJECTS { clientIndex }
	STATUS  current
	DESCRIPTION
			"A collection of objects providing information"
	  ::= { clientGroupObject 1 }

rtmpClientCountGroupEntryConformanceTable	OBJECT-GROUP
	OBJECTS { 
		rtmpClientCountCreationTime, 
		rtmpClientCountGetAcceptConnectionDescription,
		rtmpClientCountGetBufferTime, 
		rtmpClientCountGetClientId, 
		rtmpClientCountGetConnectTime,
		rtmpClientCountGetDateStarted, 
		rtmpClientCountGetDebugDumpData, 
		rtmpClientCountGetFlashVer,
		rtmpClientCountGetHandshake, 
		rtmpClientCountGetIdleFrequency, 
		rtmpClientCountGetIp,
		rtmpClientCountGetLastPingWriteId, 
		rtmpClientCountGetLastReqChunkCounter, 
		rtmpClientCountGetLastRequestType,
		rtmpClientCountGetLastStreamId, 
		rtmpClientCountGetLastValidateTime, 
		rtmpClientCountGetLeftOverCID,
		rtmpClientCountGetLeftOverMissing, 
		rtmpClientCountGetLiveRepeaterCapabilities,
		rtmpClientCountGetLiveStreamPacketizerList,
		rtmpClientCountGetLiveStreamTranscoderList,
		rtmpClientCountGetMaximumPendingReadBytes, 
		rtmpClientCountGetMaximumPendingWriteBytes,
		rtmpClientCountGetMaximumSetBufferTime, 
		rtmpClientCountGetNextConfirmBytesReceived,
		rtmpClientCountGetObjectEncoding, 
		rtmpClientCountGetPageUrl, 
		rtmpClientCountGetPingRoundTripTime,
		rtmpClientCountGetPingTimeout, 
		rtmpClientCountGetPlayResponse, 
		rtmpClientCountGetPlayStreamCount,
		rtmpClientCountGetProtocol, 
		rtmpClientCountGetPublishStreamCount, 
		rtmpClientCountGetQueryStr,
		rtmpClientCountGetReceiveChunkSize, 
		rtmpClientCountGetReferrer, 
		rtmpClientCountGetRepeaterOriginUrl,
		rtmpClientCountGetRequestDataSize, 
		rtmpClientCountGetRequestRTMPTSequence, 
		rtmpClientCountGetResponseIndex,
		rtmpClientCountGetSendChunkSize, 
		rtmpClientCountGetSharedObjectReadAccess, 
		rtmpClientCountGetSharedObjectWriteAccess,
		rtmpClientCountGetStreamAudioSampleAccess, 
		rtmpClientCountGetStreamReadAccess, 
		rtmpClientCountGetStreamType,
		rtmpClientCountGetStreamVideoSampleAccess, 
		rtmpClientCountGetStreamWriteAccess, 
		rtmpClientCountGetTimeRunning,
		rtmpClientCountGetTimebase, 
		rtmpClientCountGetTotalInBytes, 
		rtmpClientCountGetTouch, 
		rtmpClientCountGetUri,
		rtmpClientCountGetValidationFrequency
		}
	STATUS  current
	DESCRIPTION
			"A collection of objects providing information"
	  ::= { clientGroupObject 2 }

rtmpClientPerformGroupEntryConformanceTable	OBJECT-GROUP
	OBJECTS { 
		rtmpClientPerformCreationTime, 
		rtmpClientPerformGetFileInBytes, 
		rtmpClientPerformGetFileOutBytes,
		rtmpClientPerformGetMessagesInBytes, 
		rtmpClientPerformGetMessagesInCount,
		rtmpClientPerformGetMessagesInCountRate, 
		rtmpClientPerformGetMessagesLossBytes,
		rtmpClientPerformGetMessagesLossCount, 
		rtmpClientPerformGetMessagesLossCountRate,
		rtmpClientPerformGetMessagesOutBytes, 
		rtmpClientPerformGetMessagesOutCount,
		rtmpClientPerformGetMessagesOutCountRate
		}
	STATUS  current
	DESCRIPTION
			"A collection of objects providing information"
	  ::= { clientGroupObject 3 }

rtspClientCountGroupEntryConformanceTable	OBJECT-GROUP
	OBJECTS { 
		rtspClientCountCreationTime, 
		rtspClientCountGetCookieStr, 
		rtspClientCountGetIdleFrequency,
		rtspClientCountGetIp, 
		rtspClientCountGetLastAuthenticateMethod, 
		rtspClientCountGetQueryStr,
		rtspClientCountGetRTSPTunnelingSessionId, 
		rtspClientCountGetRedirectSessionCode,
		rtspClientCountGetRedirectSessionMessage, 
		rtspClientCountGetRedirectSessionURL,
		rtspClientCountGetReferrer, 
		rtspClientCountGetServerIp, 
		rtspClientCountGetServerPort,
		rtspClientCountGetSessionId, 
		rtspClientCountGetTimeRunning, 
		rtspClientCountGetUri,
		rtspClientCountGetUserAgent
		}
	STATUS  current
	DESCRIPTION
			"A collection of objects providing information"
	  ::= { clientGroupObject 4 }

rtspClientPerformGroupEntryConformanceTable	OBJECT-GROUP
	OBJECTS { 
		rtspClientPerformCreationTime, 
		rtspClientPerformGetFileInBytes, 
		rtspClientPerformGetFileOutBytes,
		rtspClientPerformGetMessagesInBytes, 
		rtspClientPerformGetMessagesInCount,
		rtspClientPerformGetMessagesInCountRate, 
		rtspClientPerformGetMessagesLossBytes,
		rtspClientPerformGetMessagesLossCount, 
		rtspClientPerformGetMessagesLossCountRate,
		rtspClientPerformGetMessagesOutBytes, 
		rtspClientPerformGetMessagesOutCount,
		rtspClientPerformGetMessagesOutCountRate
		}
	STATUS  current
	DESCRIPTION
			"A collection of objects providing information"
	  ::= { clientGroupObject 5 }

httpClientCountGroupEntryConformanceTable	OBJECT-GROUP
	OBJECTS { 
		httpClientCountCreationTime,
		httpClientCountGetCookieStr,
		httpClientCountGetHTTPDate,
		httpClientCountGetIpAddress,
		httpClientCountGetIsFirstChunk,
		httpClientCountGetLastRequest,
		httpClientCountGetLiveStreamingPacketizer,
		httpClientCountGetPlayDuration,
		httpClientCountGetPlaySeek,
		httpClientCountGetPlayStart,
		httpClientCountGetQueryStr,
		httpClientCountGetRedirectSessionCode,
		httpClientCountGetRedirectSessionContentType,
		httpClientCountGetRedirectSessionURL,
		httpClientCountGetReferrer,
		httpClientCountGetServerIp,
		httpClientCountGetServerPort,
		httpClientCountGetSessionId,
		httpClientCountGetSessionProtocol,
		httpClientCountGetSessionTimeout,
		httpClientCountGetSessionType,
		httpClientCountGetStreamExt,
		httpClientCountGetStreamName,
		httpClientCountGetStreamPosition,
		httpClientCountGetTimeRunning,
		httpClientCountGetUri,
		httpClientCountGetUserAgent,
		httpClientCountGetUserQueryStr,
		httpClientCountGetVODTranscodeNGRP
		}
	STATUS  current
	DESCRIPTION
			"A collection of objects providing information"
	  ::= { clientGroupObject 6 }

httpClientPerformGroupEntryConformanceTable	OBJECT-GROUP
	OBJECTS { 
		httpClientPerformCreationTime,
		httpClientPerformGetFileInBytes,
		httpClientPerformGetFileOutBytes,
		httpClientPerformGetMessagesInBytes,
		httpClientPerformGetMessagesInCount,
		httpClientPerformGetMessagesInCountRate,
		httpClientPerformGetMessagesLossBytes,
		httpClientPerformGetMessagesLossCount,
		httpClientPerformGetMessagesLossCountRate,
		httpClientPerformGetMessagesOutBytes,
		httpClientPerformGetMessagesOutCount,
		httpClientPerformGetMessagesOutCountRate
		}
	STATUS  current
	DESCRIPTION
			"A collection of objects providing information"
	  ::= { clientGroupObject 7 }

-- serverGroupConformanceObjectTable - end

-- compliance here

wowzaEngineMIBComplianceServer	MODULE-COMPLIANCE
	STATUS  current
	DESCRIPTION
			"The compliance statement for entities which implement
			 the Wowza Engine Management MIB"
	MODULE
			MANDATORY-GROUPS {
			serverGroupEntryConformanceTable,
			serverCounterGroupEntryConformanceTable,
			serverConnectGroupEntryConformanceTable,
			serverPerformGroupEntryConformanceTable
				}
	  ::= { complianceServer 1 }

wowzaEngineMIBComplianceVhost  MODULE-COMPLIANCE
	STATUS  current
	DESCRIPTION
			"The compliance statement for entities which implement
			 the Wowza Engine Management MIB"
	MODULE
			 MANDATORY-GROUPS {
			vhostGroupEntryConformanceTable,
			vhostCounterGroupEntryConformanceTable,
			vhostConnectGroupEntryConformanceTable,	
			vhostPerformGroupEntryConformanceTable
						  }
	  ::= { complianceVhost 1 }

wowzaEngineMIBComplianceApplication	MODULE-COMPLIANCE
	STATUS  current
	DESCRIPTION
			"The compliance statement for entities which implement
			 the Wowza Engine Management MIB"
	MODULE
			 MANDATORY-GROUPS {
			applicationGroupEntryConformanceTable,
			applicationCounterGroupEntryConformanceTable,
			applicationConnectGroupEntryConformanceTable,
			applicationPerformGroupEntryConformanceTable
		}
	::= { complianceApplication 1 }

wowzaEngineMIBComplianceApplicationInstance	MODULE-COMPLIANCE
	STATUS  current
	DESCRIPTION
			"The compliance statement for entities which implement
			 the Wowza Engine Management MIB"
	MODULE
			 MANDATORY-GROUPS {
			applicationInstanceGroupEntryConformanceTable,
			applicationInstanceCounterGroupEntryConformanceTable,
			applicationInstanceConnectGroupEntryConformanceTable,
			applicationInstancePerformGroupEntryConformanceTable
		}
	::= { complianceApplicationInstance 1 }

wowzaEngineMIBComplianceStream	MODULE-COMPLIANCE
	STATUS  current
	DESCRIPTION
			"The compliance statement for entities which implement
			 the Wowza Engine Management MIB"
	MODULE
			 MANDATORY-GROUPS {
			streamGroupEntryConformanceTable,
			streamCounterGroupEntryConformanceTable,
			streamPerformGroupEntryConformanceTable
		}
	::= { complianceStream 1 }

wowzaEngineMIBComplianceRTMPClient	MODULE-COMPLIANCE
	STATUS  current
	DESCRIPTION
			"The compliance statement for entities which implement
			 the Wowza Engine Management MIB"
	MODULE 
			 MANDATORY-GROUPS {
			clientGroupEntryConformanceTable,
			rtmpClientCountGroupEntryConformanceTable,
			rtmpClientPerformGroupEntryConformanceTable
		}
	::= { complianceClient 1 }

wowzaEngineMIBComplianceRTSPClient	MODULE-COMPLIANCE
	STATUS  current
	DESCRIPTION
			"The compliance statement for entities which implement
			 the Wowza Engine Management MIB"
	MODULE  
			MANDATORY-GROUPS {
			clientGroupEntryConformanceTable,
			rtspClientCountGroupEntryConformanceTable,
			rtspClientPerformGroupEntryConformanceTable
		}
	::= { complianceClient 2 }

wowzaEngineMIBComplianceHTTPClient	MODULE-COMPLIANCE
	STATUS  current
	DESCRIPTION
			"The compliance statement for entities which implement
			 the Wowza Engine Management MIB"
	MODULE 
			MANDATORY-GROUPS {
			clientGroupEntryConformanceTable,
			httpClientCountGroupEntryConformanceTable,
			httpClientPerformGroupEntryConformanceTable
		}
	::= { complianceClient 3 }

END

--
 -- Copyright(C) 2013 Western Telematic, Inc.
 --

 WTI-RSM-TSM-MIB DEFINITIONS ::= BEGIN
 IMPORTS
 MODULE-IDENTITY, NOTIFICATION-TYPE,
 OBJECT-TYPE, enterprises FROM SNMPv2-SMI
 DisplayString FROM SNMPv2-TC;
 westernTelematic OBJECT IDENTIFIER ::= { enterprises 2634 }
 rsm-tsm MODULE-IDENTITY
  LAST-UPDATED "201401081600Z" -- 08 Jan 2014
  ORGANIZATION "Western Telematic, Inc."
  CONTACT-INFO
  "Western Telematic, Inc.
  5 Sterling
  Irvine, Ca 92618
  Email: anthonyb@wti.com"
  DESCRIPTION
   "This is the MIB module for the RSM/TSM"
  REVISION "201401081600Z" -- 08 Jan 2014
  DESCRIPTION
   "V5.10 for the RSM/TSM "
 ::= { westernTelematic 1 }
 --
 -- System Tables
 --
 systemTables OBJECT IDENTIFIER ::= { rsm-tsm 100 }
 --
 -- Port Table
 --
 portTable OBJECT-TYPE
  SYNTAX SEQUENCE OF PortEntry
  MAX-ACCESS not-accessible
  STATUS current
  DESCRIPTION
   "A table of ports."
 ::= { systemTables 100 }
 portEntry OBJECT-TYPE
  SYNTAX PortEntry
  MAX-ACCESS not-accessible
  STATUS current
  DESCRIPTION
   "Row definition for the port table."
  INDEX {portIndex}
 ::= { portTable 1 }
 PortEntry ::= SEQUENCE {
  portIndex INTEGER,
  portID DisplayString,
  portName DisplayString,
  portBufferThreshold INTEGER,
  portUserName DisplayString,
  portStatus DisplayString,
  portBufferCt INTEGER
 }
 portIndex OBJECT-TYPE
  SYNTAX INTEGER (0..41)
  MAX-ACCESS not-accessible
  STATUS current
  DESCRIPTION
   "Index for the port table."
 ::= { portEntry 1 }
 portID OBJECT-TYPE
  SYNTAX DisplayString(SIZE(6..7))
  MAX-ACCESS read-only
  STATUS current
  DESCRIPTION
   "The ID of the port."
 ::= { portEntry 2 }
 portName OBJECT-TYPE
  SYNTAX DisplayString
  MAX-ACCESS read-only
  STATUS current
  DESCRIPTION
   "The name of the port."
 ::= { portEntry 3 }
 portBufferThreshold OBJECT-TYPE
  SYNTAX INTEGER (1..262144)
  MAX-ACCESS read-only
  STATUS current
  DESCRIPTION
   "Port buffer threshold"
 ::= { portEntry 4 }
 portUserName OBJECT-TYPE
  SYNTAX DisplayString
  MAX-ACCESS read-only
  STATUS current
  DESCRIPTION
   "The name of the user logged in to port"
 ::= { portEntry 5 }
 portStatus OBJECT-TYPE
  SYNTAX DisplayString
  MAX-ACCESS read-write
  STATUS current
  DESCRIPTION
   "The status of the port."
 ::= { portEntry 6 }
 portBufferCt OBJECT-TYPE
  SYNTAX INTEGER
  MAX-ACCESS read-only
  STATUS current
  DESCRIPTION
   "Port byte threshold"
 ::= { portEntry 7 }
 --
 -- Plug Table
 --
 plugTable OBJECT-TYPE
  SYNTAX SEQUENCE OF PlugEntry
  MAX-ACCESS not-accessible
  STATUS current
  DESCRIPTION
   "A table of plugs."
 ::= { systemTables 200 }
 plugEntry OBJECT-TYPE
  SYNTAX PlugEntry
  MAX-ACCESS not-accessible
  STATUS current
  DESCRIPTION
   "Row definition for the plug table."
  INDEX { plugIndex }
 ::= { plugTable 1 }
 PlugEntry ::= SEQUENCE {
  plugIndex INTEGER,
  plugID DisplayString,
  plugStatus INTEGER,
  plugAction INTEGER,
  plugName DisplayString,
  plugCurrent INTEGER,
  plugPower INTEGER
 }
 plugIndex OBJECT-TYPE
  SYNTAX INTEGER (0..80)
  MAX-ACCESS not-accessible
  STATUS current
  DESCRIPTION
   "Index for the plug table."
 ::= { plugEntry 1 }
 plugID OBJECT-TYPE
  SYNTAX DisplayString(SIZE(9..11))
  MAX-ACCESS read-only
  STATUS current
  DESCRIPTION
   "The ID of the plug."
 ::= { plugEntry 2 }
 plugStatus OBJECT-TYPE
  SYNTAX INTEGER (0..1)
  MAX-ACCESS read-only
  STATUS current
  DESCRIPTION
   "Plug status"
 ::= { plugEntry 3 }
 plugAction OBJECT-TYPE
  SYNTAX INTEGER (0..8)
  MAX-ACCESS read-write
  STATUS current
  DESCRIPTION
   "Plug action"
 ::= { plugEntry 4 }
 plugName OBJECT-TYPE
  SYNTAX DisplayString
  MAX-ACCESS read-only
  STATUS current
  DESCRIPTION
   "The Name of the plug."
 ::= { plugEntry 5 }
 plugCurrent OBJECT-TYPE
  SYNTAX INTEGER
  MAX-ACCESS read-only
  STATUS current
  DESCRIPTION
   "Plug current (In tenths of amps, divide by 10 for value in amps)"
 ::= { plugEntry 7 }
 plugPower OBJECT-TYPE
  SYNTAX INTEGER
  MAX-ACCESS read-only
  STATUS current
  DESCRIPTION
   "Plug power (Watts)"
 ::= { plugEntry 8 }
 --
 -- Plug Group Table
 --
 plugGroupTable OBJECT-TYPE
  SYNTAX SEQUENCE OF PlugGroupEntry
  MAX-ACCESS not-accessible
  STATUS current
  DESCRIPTION
   "A table of plug groups."
 ::= { systemTables 300 }
 plugGroupEntry OBJECT-TYPE
  SYNTAX PlugGroupEntry
  MAX-ACCESS not-accessible
  STATUS current
  DESCRIPTION
   "Row definition for the plug group table."
  INDEX { plugGroupIndex }
 ::= { plugGroupTable 1 }
 PlugGroupEntry ::= SEQUENCE {
  plugGroupIndex INTEGER,
  plugGroupName DisplayString,
  plugGroupAction INTEGER,
  plugGroupCurrent INTEGER,
  plugGroupPower INTEGER
 }
 plugGroupIndex OBJECT-TYPE
  SYNTAX INTEGER (0..54)
  MAX-ACCESS not-accessible
  STATUS current
  DESCRIPTION
   "Index for the plug group table."
 ::= { plugGroupEntry 1 }
 plugGroupName OBJECT-TYPE
  SYNTAX DisplayString(SIZE(1..24))
  MAX-ACCESS read-only
  STATUS current
  DESCRIPTION
   "The name of the plug group."
 ::= { plugGroupEntry 2 }
 plugGroupAction OBJECT-TYPE
  SYNTAX INTEGER (0..8)
  MAX-ACCESS read-write
  STATUS current
  DESCRIPTION
   "Plug group action"
 ::= { plugGroupEntry 3 }
 plugGroupCurrent OBJECT-TYPE
  SYNTAX INTEGER
  MAX-ACCESS read-only
  STATUS current
  DESCRIPTION
   "Plug group current (In tenths of amps, divide by 10 for value in amps)"
 ::= { plugGroupEntry 4 }
 plugGroupPower OBJECT-TYPE
  SYNTAX INTEGER
  MAX-ACCESS read-only
  STATUS current
  DESCRIPTION
   "Plug group power (Watts)"
 ::= { plugGroupEntry 5 }
 --
 -- User Table
 --
 userTable OBJECT-TYPE
  SYNTAX SEQUENCE OF UserEntry
  MAX-ACCESS not-accessible
  STATUS current
  DESCRIPTION
   "A table of users."
 ::= { systemTables 400 }
 userEntry OBJECT-TYPE
  SYNTAX UserEntry
  MAX-ACCESS not-accessible
  STATUS current
  DESCRIPTION
   "Row definition for the user table."
  INDEX { userIndex }
 ::= { userTable 1 }
 UserEntry ::= SEQUENCE {
  userIndex INTEGER,
  userName DisplayString,
  userPasswd DisplayString,
  userAccessLevel INTEGER,
  userPortAccess DisplayString,
  userPlugAccess DisplayString,
  userGroupAccess DisplayString,
  userSerialAccess INTEGER,
  userTelnetSshAccess INTEGER,
  userWebAccess INTEGER,
  userOutboundTelAccess INTEGER,
  userCallbackNum DisplayString,
  userSubmit INTEGER
 }
 userIndex OBJECT-TYPE
  SYNTAX INTEGER (0..128)
  MAX-ACCESS not-accessible
  STATUS current
  DESCRIPTION
   "Index for the user table."
 ::= { userEntry 1 }
 userName OBJECT-TYPE
  SYNTAX DisplayString(SIZE(0..32))
  MAX-ACCESS read-write
  STATUS current
  DESCRIPTION
   "The name of the user."
 ::= { userEntry 2 }
 userPasswd OBJECT-TYPE
  SYNTAX DisplayString(SIZE(1..16))
  MAX-ACCESS read-write
  STATUS current
  DESCRIPTION
   "The password of the user."
 ::= { userEntry 3 }
 userAccessLevel OBJECT-TYPE
  SYNTAX INTEGER (0..3)
  MAX-ACCESS read-write
  STATUS current
  DESCRIPTION
   "Users access level"
 ::= { userEntry 4 }
 userPortAccess OBJECT-TYPE
  SYNTAX DisplayString(SIZE(1..41))
  MAX-ACCESS read-write
  STATUS current
  DESCRIPTION
   "Access to ports."
 ::= { userEntry 5 }
 userPlugAccess OBJECT-TYPE
  SYNTAX DisplayString(SIZE(1..20))
  MAX-ACCESS read-write
  STATUS current
  DESCRIPTION
   "Access to plugs."
 ::= { userEntry 6 }
 userGroupAccess OBJECT-TYPE
  SYNTAX DisplayString(SIZE(1..54))
  MAX-ACCESS read-write
  STATUS current
  DESCRIPTION
   "Access to plug groups."
 ::= { userEntry 10 }
 userSerialAccess OBJECT-TYPE
  SYNTAX INTEGER (0..1)
  MAX-ACCESS read-write
  STATUS current
  DESCRIPTION
   "Access to serial interface."
 ::= { userEntry 11 }
 userTelnetSshAccess OBJECT-TYPE
  SYNTAX INTEGER (0..1)
  MAX-ACCESS read-write
  STATUS current
  DESCRIPTION
   "Access to Telnet/SSH interface."
 ::= { userEntry 12 }
 userWebAccess OBJECT-TYPE
  SYNTAX INTEGER (0..1)
  MAX-ACCESS read-write
  STATUS current
  DESCRIPTION
   "Access to web interface."
 ::= { userEntry 13 }
 userOutboundTelAccess OBJECT-TYPE
  SYNTAX INTEGER (0..1)
  MAX-ACCESS read-write
  STATUS current
  DESCRIPTION
   "Access to outbound telnet."
 ::= { userEntry 14 }
 userCallbackNum OBJECT-TYPE
  SYNTAX DisplayString(SIZE(0..32))
  MAX-ACCESS read-write
  STATUS current
  DESCRIPTION
   "Callback number."
 ::= { userEntry 16 }
 userSubmit OBJECT-TYPE
  SYNTAX INTEGER (0..1)
  MAX-ACCESS read-write
  STATUS current
  DESCRIPTION
   "Submit changes to user."
 ::= { userEntry 31 }
 --
 -- Environment Tables
 --
 environmentTables OBJECT IDENTIFIER ::= { rsm-tsm 200 }
 environmentUnitTable OBJECT-TYPE
  SYNTAX SEQUENCE OF EnvironmentUnitEntry
  MAX-ACCESS not-accessible
  STATUS current
  DESCRIPTION
   "A table of environment status for units."
 ::= { environmentTables 10 }
 environmentUnitEntry OBJECT-TYPE
  SYNTAX EnvironmentUnitEntry
  MAX-ACCESS not-accessible
  STATUS current
  DESCRIPTION
   "Row definition for the environment unit table."
  INDEX { environmentUnitIndex }
 ::= { environmentUnitTable 1 }
 EnvironmentUnitEntry ::= SEQUENCE {
  environmentUnitIndex INTEGER,
  environmentUnitName DisplayString,
  environmentUnitTemperature INTEGER,
  environmentSysRAM INTEGER,
  environmentSysFlash INTEGER,
  environmentMacEth0 DisplayString,
  environmentMacEth1 DisplayString
 }
 environmentUnitIndex OBJECT-TYPE
  SYNTAX INTEGER (0..3)
  MAX-ACCESS not-accessible
  STATUS current
  DESCRIPTION
   "Index for the environment unit table."
 ::= { environmentUnitEntry 1 }
 environmentUnitName OBJECT-TYPE
  SYNTAX DisplayString
  MAX-ACCESS read-only
  STATUS current
  DESCRIPTION
   "The name of the unit."
 ::= { environmentUnitEntry 2 }
 environmentUnitTemperature OBJECT-TYPE
  SYNTAX INTEGER
  MAX-ACCESS read-only
  STATUS current
  DESCRIPTION
   "The temperature of the unit."
 ::= { environmentUnitEntry 3 }
 environmentSysRAM OBJECT-TYPE
  SYNTAX INTEGER
  MAX-ACCESS read-only
  STATUS current
  DESCRIPTION
   "Total system RAM."
 ::= { environmentUnitEntry 18 }
 environmentSysFlash OBJECT-TYPE
  SYNTAX INTEGER
  MAX-ACCESS read-only
  STATUS current
  DESCRIPTION
   "Total system Flash."
 ::= { environmentUnitEntry 19 }
 environmentMacEth0 OBJECT-TYPE
  SYNTAX DisplayString
  MAX-ACCESS read-only
  STATUS current
  DESCRIPTION
   "MAC Address Eth0"
 ::= { environmentUnitEntry 20 }
 environmentMacEth1 OBJECT-TYPE
  SYNTAX DisplayString
  MAX-ACCESS read-only
  STATUS current
  DESCRIPTION
   "MAC Address Eth1"
 ::= { environmentUnitEntry 21 }
 --
 -- Alarm Tables
 --
 alarmTables OBJECT IDENTIFIER ::= { rsm-tsm 280 }
 alarmOverCurrentInitial OBJECT-TYPE
  SYNTAX INTEGER
  MAX-ACCESS read-only
  STATUS current
  DESCRIPTION
   "State of the Over Current Initial Alarm (0 = Inactive, 1 = Active)"
 ::= { alarmTables 1 }
 alarmOverCurrentCritical OBJECT-TYPE
  SYNTAX INTEGER
  MAX-ACCESS read-only
  STATUS current
  DESCRIPTION
   "State of the Over Current Critical Alarm (0 = Inactive, 1 = Active)"
 ::= { alarmTables 2 }
 alarmOverTemperatureInitial OBJECT-TYPE
  SYNTAX INTEGER
  MAX-ACCESS read-only
  STATUS current
  DESCRIPTION
   "State of the Over Temperature Initial Alarm (0 = Inactive, 1 = Active)"
 ::= { alarmTables 3 }
 alarmOverTemperatureCritical OBJECT-TYPE
  SYNTAX INTEGER
  MAX-ACCESS read-only
  STATUS current
  DESCRIPTION
   "State of the Over Temperature Critical Alarm (0 = Inactive, 1 = Active)"
 ::= { alarmTables 4 }
 alarmCircuitBreakerOpen OBJECT-TYPE
  SYNTAX INTEGER
  MAX-ACCESS read-only
  STATUS current
  DESCRIPTION
   "State of the Circuit Breaker Open Alarm (0 = Inactive, 1 = Active)"
 ::= { alarmTables 5 }
 alarmCommLoss OBJECT-TYPE
  SYNTAX INTEGER
  MAX-ACCESS read-only
  STATUS current
  DESCRIPTION
   "State of the Communication Loss Alarm (0 = Inactive, 1 = Active)"
 ::= { alarmTables 6 }
 alarmPingNoAnswer OBJECT-TYPE
  SYNTAX INTEGER
  MAX-ACCESS read-only
  STATUS current
  DESCRIPTION
   "State of the Ping No Answer Alarm (0 = Inactive, 1 = Active)"
 ::= { alarmTables 8 }
 alarmInvalidAccessLockout OBJECT-TYPE
  SYNTAX INTEGER
  MAX-ACCESS read-only
  STATUS current
  DESCRIPTION
   "State of the Invalid Access Lockout Alarm (0 = Inactive, 1 = Active)"
 ::= { alarmTables 9 }
 alarmPowerCycle OBJECT-TYPE
  SYNTAX INTEGER
  MAX-ACCESS read-only
  STATUS current
  DESCRIPTION
   "State of the Power Cycle Alarm (0 = Inactive, 1 = Active)"
 ::= { alarmTables 10 }
 alarmBufferThreshold OBJECT-TYPE
  SYNTAX INTEGER
  MAX-ACCESS read-only
  STATUS current
  DESCRIPTION
   "State of the Buffer Threshold Alarm (0 = Inactive, 1 = Active)"
 ::= { alarmTables 11 }
 alarmPlugCurrent OBJECT-TYPE
  SYNTAX INTEGER
  MAX-ACCESS read-only
  STATUS current
  DESCRIPTION
   "State of the Plug Current Alarm (0 = Inactive, 1 = Active)"
 ::= { alarmTables 13 }
 alarmLostOptoVoltage OBJECT-TYPE
  SYNTAX INTEGER
  MAX-ACCESS read-only
  STATUS current
  DESCRIPTION
   "State of the Lost Voltage (Line Input) Alarm (0 = Inactive, 1 = Active)"
 ::= { alarmTables 14 }
 alarmEmergencyShutoff OBJECT-TYPE
  SYNTAX INTEGER
  MAX-ACCESS read-only
  STATUS current
  DESCRIPTION
   "State of the Emergency Shutoff Alarm (0 = Inactive, 1 = Active)"
 ::= { alarmTables 15 }
 alarmNoDialtone OBJECT-TYPE
  SYNTAX INTEGER
  MAX-ACCESS read-only
  STATUS current
  DESCRIPTION
   "State of the No Dialtone Alarm (0 = Inactive, 1 = Active)"
 ::= { alarmTables 16 }
 --
 -- Traps
 --
 wtiTraps OBJECT IDENTIFIER ::= { rsm-tsm 300 }
 -- Trap Info
 trapInfo OBJECT-TYPE
  SYNTAX DisplayString
  MAX-ACCESS read-only
  STATUS current
  DESCRIPTION
   "Alarm information"
 ::= { wtiTraps 1 }
 -- Test Traps
 testTraps OBJECT IDENTIFIER ::= { wtiTraps 2}
 testTrap TRAP-TYPE
  ENTERPRISE testTraps
  VARIABLES {
  trapInfo
  }
  DESCRIPTION
   "A test trap"
 ::= 1
 -- Alarm Traps
 bufferThresholdTraps OBJECT IDENTIFIER ::= { wtiTraps 3}
 bufferThresholdCrossedSetTrap TRAP-TYPE
  ENTERPRISE bufferThresholdTraps
  VARIABLES {
  trapInfo
  }
  DESCRIPTION
   "Buffer Threshold Crossed Alarm"
 ::= 1
 bufferThresholdCrossedClearTrap TRAP-TYPE
  ENTERPRISE bufferThresholdTraps
  VARIABLES {
  trapInfo
  }
  DESCRIPTION
   "Buffer Threshold Crossed Alarm (Clear)"
 ::= 2
 overCurrentInitialTraps OBJECT IDENTIFIER ::= { wtiTraps 4}
 overCurrentInitialSetTrap TRAP-TYPE
  ENTERPRISE overCurrentInitialTraps
  VARIABLES {
  trapInfo
  }
  DESCRIPTION
   "Over Current Initial Alarm"
 ::= 1
 overCurrentInitialClearTrap TRAP-TYPE
  ENTERPRISE overCurrentInitialTraps
  VARIABLES {
  trapInfo
  }
  DESCRIPTION
   "Over Current Initial Alarm (Clear)"
 ::= 2
 overCurrentCriticalTraps OBJECT IDENTIFIER ::= { wtiTraps 5}
 overCurrentCriticalSetTrap TRAP-TYPE
  ENTERPRISE overCurrentCriticalTraps
  VARIABLES {
  trapInfo
  }
  DESCRIPTION
   "Over Current Critical Alarm"
 ::= 1
 overCurrentCriticalClearTrap TRAP-TYPE
  ENTERPRISE overCurrentCriticalTraps
  VARIABLES {
  trapInfo
  }
  DESCRIPTION
   "Over Current Critical Alarm (Clear)"
 ::= 2
 overTemperatureInitialTraps OBJECT IDENTIFIER ::= { wtiTraps 6}
 overTemperatureInitialSetTrap TRAP-TYPE
  ENTERPRISE overTemperatureInitialTraps
  VARIABLES {
  trapInfo
  }
  DESCRIPTION
   "Over Temperature Initial Alarm"
 ::= 1
 overTemperatureInitialClearTrap TRAP-TYPE
  ENTERPRISE overTemperatureInitialTraps
  VARIABLES {
  trapInfo
  }
  DESCRIPTION
   "Over Temperature Initial Alarm (Clear)"
 ::= 2
 overTemperatureCriticalTraps OBJECT IDENTIFIER ::= { wtiTraps 7}
 overTemperatureCriticalSetTrap TRAP-TYPE
  ENTERPRISE overTemperatureCriticalTraps
  VARIABLES {
  trapInfo
  }
  DESCRIPTION
   "Over Temperature Critical Alarm"
 ::= 1
 overTemperatureCriticalClearTrap TRAP-TYPE
  ENTERPRISE overTemperatureCriticalTraps
  VARIABLES {
  trapInfo
  }
  DESCRIPTION
   "Over Temperature Critical Alarm (Clear)"
 ::= 2
 circuitBreakerOpenTraps OBJECT IDENTIFIER ::= { wtiTraps 8}
 circuitBreakerOpenSetTrap TRAP-TYPE
  ENTERPRISE circuitBreakerOpenTraps
  VARIABLES {
  trapInfo
  }
  DESCRIPTION
   "Circuit Breaker Open Alarm"
 ::= 1
 circuitBreakerOpenClearTrap TRAP-TYPE
  ENTERPRISE circuitBreakerOpenTraps
  VARIABLES {
  trapInfo
  }
  DESCRIPTION
   "Circuit Breaker Open Alarm (Clear)"
 ::= 2
 lostCommTraps OBJECT IDENTIFIER ::= { wtiTraps 9}
 lostCommSetTrap TRAP-TYPE
  ENTERPRISE lostCommTraps
  VARIABLES {
  trapInfo
  }
  DESCRIPTION
   "Lost Communication with AUX Unit"
 ::= 1
 lostCommClearTrap TRAP-TYPE
  ENTERPRISE lostCommTraps
  VARIABLES {
  trapInfo
  }
  DESCRIPTION
   "Lost Communication with AUX Unit (Clear)"
 ::= 2
 pingNoAnswerTraps OBJECT IDENTIFIER ::= { wtiTraps 11}
 pingNoAnswerSetTrap TRAP-TYPE
  ENTERPRISE pingNoAnswerTraps
  VARIABLES {
  trapInfo
  }
  DESCRIPTION
   "Ping No Answer"
 ::= 1
 pingNoAnswerClearTrap TRAP-TYPE
  ENTERPRISE pingNoAnswerTraps
  VARIABLES {
  trapInfo
  }
  DESCRIPTION
   "Ping No Answer (Clear)"
 ::= 2
 lockoutTraps OBJECT IDENTIFIER ::= { wtiTraps 12}
 lockoutSetTrap TRAP-TYPE
  ENTERPRISE lockoutTraps
  VARIABLES {
  trapInfo
  }
  DESCRIPTION
   "Invalid Access Lockout"
 ::= 1
 lockoutClearTrap TRAP-TYPE
  ENTERPRISE lockoutTraps
  VARIABLES {
  trapInfo
  }
  DESCRIPTION
   "Invalid Access Lockout (Clear)"
 ::= 2
 powercycleTraps OBJECT IDENTIFIER ::= { wtiTraps 13}
 powercycleSetTrap TRAP-TYPE
  ENTERPRISE powercycleTraps
  VARIABLES {
  trapInfo
  }
  DESCRIPTION
   "Power Cycle"
 ::= 1
 plugCurrentTraps OBJECT IDENTIFIER ::= { wtiTraps 15}
 plugCurrentSetTrap TRAP-TYPE
  ENTERPRISE plugCurrentTraps
  VARIABLES {
  trapInfo
  }
  DESCRIPTION
   "Plug Current"
 ::= 1
 plugCurrentClearTrap TRAP-TYPE
  ENTERPRISE plugCurrentTraps
  VARIABLES {
  trapInfo
  }
  DESCRIPTION
   "Plug Current (Clear)"
 ::= 2
 lostOptoVoltageTraps OBJECT IDENTIFIER ::= { wtiTraps 16}
 lostOptoVoltageSetTrap TRAP-TYPE
  ENTERPRISE lostOptoVoltageTraps
  VARIABLES {
  trapInfo
  }
  DESCRIPTION
   "Lost Voltage"
 ::= 1
 lostOptoVoltageClearTrap TRAP-TYPE
  ENTERPRISE lostOptoVoltageTraps
  VARIABLES {
  trapInfo
  }
  DESCRIPTION
   "Lost Voltage (Clear)"
 ::= 2
 emergencyShutoffTraps OBJECT IDENTIFIER ::= { wtiTraps 17}
 emergencyShutoffSetTrap TRAP-TYPE
  ENTERPRISE emergencyShutoffTraps
  VARIABLES {
  trapInfo
  }
  DESCRIPTION
   "Emergency Shutoff"
 ::= 1
 emergencyShutoffClearTrap TRAP-TYPE
  ENTERPRISE emergencyShutoffTraps
  VARIABLES {
  trapInfo
  }
  DESCRIPTION
   "Emergency Shutoff (Clear)"
 ::= 2
 noDialtoneTraps OBJECT IDENTIFIER ::= { wtiTraps 18}
 noDialtoneSetTrap TRAP-TYPE
  ENTERPRISE noDialtoneTraps
  VARIABLES {
  trapInfo
  }
  DESCRIPTION
   "No Dialtone"
 ::= 1
 noDialtoneClearTrap TRAP-TYPE
  ENTERPRISE noDialtoneTraps
  VARIABLES {
  trapInfo
  }
  DESCRIPTION
   "No Dialtone (Clear)"
 ::= 2
 END

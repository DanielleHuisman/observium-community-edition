XEROX-COMMON-MIB DEFINITIONS ::= BEGIN

-- Module:  Common
-- Editors: coherence@crt.xerox.com
-- File:    02common.txt
-- Date:    September 17, 2002
-- Version: 5.10.pub

IMPORTS
    enterprises, OBJECT-IDENTITY, MODULE-IDENTITY
    FROM SNMPv2-SMI;                            -- IETF RFC 1442

xerox MODULE-IDENTITY
    LAST-UPDATED "0209170000Z"
    ORGANIZATION "Xerox Corporation -
                  Xerox Common Management Interface Working Group"
    CONTACT-INFO "
                     XCMI Editors
        E-Mail       coherence@crt.xerox.com

    "
    DESCRIPTION
        "Xerox Common MIB Root Module, Version 5.10.pub.

        Copyright (C) 1997-2002 Xerox Corporation. All Rights Reserved."
    ::= { enterprises 253 }

xeroxCommonMIB OBJECT-IDENTITY
    STATUS      current
    DESCRIPTION
        "The root of the Xerox Common MIB module.

         xeroxCommonMIB ::= { iso(1) org(3) dod(6) internet(1)
                              private(4) enterprises(1) Xerox(253) 8 }"
    ::= { xerox 8 }

END

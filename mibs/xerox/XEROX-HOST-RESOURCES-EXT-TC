XEROX-HOST-RESOURCES-EXT-TC DEFINITIONS ::= BEGIN

--  Module: XCMI Extensions to IETF Host Resources TC
--  File:   10hosttc.mib
--  Date:   12 October 2011 - Version 6.001.pub   VersionUpdate

--  Textual Conventions companion to the Host Resources Extensions MIB
--  Contains the REGISTRY of XCMI Standard Device Types,
--  the REGISTRY of XCMI Standard CRU Types,
--  the REGISTRY of XCMI HRX Admin Service Types, and
--  the REGISTRY of XCMI HRX Admin Device Operation Types.

IMPORTS
    MODULE-IDENTITY, OBJECT-IDENTITY,
        OBJECT-TYPE
            FROM SNMPv2-SMI             -- IETF RFC 1442/1902/2578
    TEXTUAL-CONVENTION
            FROM SNMPv2-TC              -- IETF RFC 1443/1903/2579
    xeroxCommonMIB
            FROM XEROX-COMMON-MIB;

xcmHrTC MODULE-IDENTITY
    LAST-UPDATED "1110120000Z" -- 12 October 2011
    ORGANIZATION "Xerox Corporation - XCMI Working Group"
    CONTACT-INFO
        "           XCMI Editors
        Email:      coherence@crt.xerox.com
        "
    DESCRIPTION
        "Version:    6.001.pub

        The TC module for textual conventions, enumerated types, OIDs,
        and other volatile elements of the companion Host Resources
        Extensions MIB ('xcmHrMIB'), which supports extended
        configuration and management of various host resources for
        network accessible host systems.  These modules augment and
        extend the original IETF Host Resources MIB (RFC 2790).

        Usage:  This MIB module introduces support for the 'realization'
        of both 'physical' and 'logical' devices, consistent with ISO
        DPA (Document Printing Application), ISO/IEC 10175, as reflected
        in the object 'xcmHrDevInfoRealization'.

        Note:   Conforming implementations SHALL NOT 'bubble up' status
        from 'physical' devices to associated 'logical' devices.  All


        devices SHALL report their own status ONLY.

        See:    Section 9 'Supplement' in XCMI Extensions to IETF Host
        Resources TC, for implementation guidance for this TC module.

        Copyright (C) 1995-2009 Xerox Corporation. All Rights Reserved."
    ::= { xeroxCommonMIB 52 }

--
--          XCMI Extensions to IETF Host Resources (HRX) TC
--

--          REGISTRY of XCMI Standard Device Types
--          (used with 'hrDeviceType' in Device Group
--          of the IETF Host Resources MIB, RFC 2790).
--
--  Usage:  Developers SHOULD request registration of appropriate
--  XCMI standard device types when they design or integrate a device
--  (with some physical, and NOT merely logical, realization)
--  which is network manageable on a host system.
--
--  Usage:  Logical devices (ie, services of some sort) SHOULD
--  be represented by: a) their own fully free-standing MIBs; and/or
--  b) elaboration of an existing IETF or XCMI standard device type into
--  a 'logical' sibling.
--
--  The final arc of IETF standard device types is within the
--  range '1..49'.
--  The final arc of XCMI standard device types is within the
--  range '101..149'.
--
--  In the future, XCMI MAY add types for 'marker', 'input tray', etc,
--  to enable support of managed host systems which do NOT have printer
--  capabilities (and therefore do NOT implement the Printer MIB),
--  and to support installation and configuration information for
--  their component physical subunits.

xcmHrDeviceTypes OBJECT-IDENTITY
    STATUS      current
    DESCRIPTION
        "The root of all additional device types defined in HRX TC."
    ::= { xcmHrTC 2 }

xcmHrDeviceHostSystem OBJECT-IDENTITY
    STATUS      current
    DESCRIPTION
        "Host system device type - manufacturer independent.
        For host systems which instrument multiple devices and
        support MIBs with tables INDEXed by 'hrDeviceIndex', the single
        'xcmHrDeviceHostSystem' device represents the 'root' device
        which MAY be used to manage overall host system defaults,
        configuration, status, etc."
    REFERENCE
        "See:   'xcmHrDeviceHostSystemHistory' in this XCMI HRX TC."


    ::= { xcmHrDeviceTypes 101 }

xcmHrDeviceScanner OBJECT-IDENTITY
    STATUS      current
    DESCRIPTION
        "Scanner device type - manufacturer independent.
        An 'xcmHrDeviceScanner' device with 'xcmHrDevInfoRealization' of
        'physical' is a 'real' input device (eg, a 'scan channel' on a
        multifunction printer).
        An 'xcmHrDeviceScanner' device with 'xcmHrDevInfoRealization' of
        'logical' is a 'virtual' input device (eg, a 'personality' of a
        'scan channel' on a multifunction printer)."
    REFERENCE
        "See:   'xcmHrDeviceScannerHistory' in this XCMI HRX TC."
    ::= { xcmHrDeviceTypes 102 }

xcmHrDeviceCopier OBJECT-IDENTITY
    STATUS      current
    DESCRIPTION
        "Copier device type - manufacturer independent.
        An 'xcmHrDeviceCopier' device with 'xcmHrDevInfoRealization' of
        'physical' is a 'real' I/O device (eg, a 'copier' on a
        multifunction printer).
        An 'xcmHrDeviceCopier' device with 'xcmHrDevInfoRealization' of
        'logical' is a 'virtual' I/O device (eg, a 'personality' of a
        'copier' on a multifunction printer)."
    REFERENCE
        "See:   'xcmHrDeviceCopierHistory' in this XCMI HRX TC."
    ::= { xcmHrDeviceTypes 103 }

xcmHrDeviceFax OBJECT-IDENTITY
    STATUS      current
    DESCRIPTION
        "Fax device type - manufacturer independent.
         xcmHrDeviceFax is maintained for legacy products.  It is 
         recommended that the hrDeviceType is explicitly defined using
         xcmHrDeviceEmbeddedFax, xcmHrDeviceServerFax or
         xcmHrDeviceInternetFax.
        An 'xcmHrDeviceFax' device with 'xcmHrDevInfoRealization' of
        'physical' is a 'real' I/O device (eg, a 'fax channel' on a
        multifunction printer).
        An 'xcmHrDeviceFax' device with 'xcmHrDevInfoRealization' of
        'logical' is a 'virtual' I/O device (eg, a 'personality' of a
        'fax channel' on a multifunction printer)."
    REFERENCE
        "See:   'xcmHrDeviceFaxHistory' in this XCMI HRX TC."
    ::= { xcmHrDeviceTypes 104 }

xcmHrDeviceMailbox OBJECT-IDENTITY
    STATUS      current
    DESCRIPTION
        "Mailbox device type - manufacturer independent.
        An 'xcmHrDeviceMailbox' device is a 'multi-bin' output device,


        with each 'bin' assigned to a user, group, account, etc, and
        (optionally) physical security associated with each 'bin'.
        An 'xcmHrDeviceMailbox' device with 'xcmHrDevInfoRealization' of
        'physical' is a 'real' output device (eg, a 'tower mailbox' on
        a high-end printer).
        An 'xcmHrDeviceMailbox' device with 'xcmHrDevInfoRealization' of
        'logical' is a 'virtual' output device (eg, a 'personality' of a
        'tower mailbox' on a high-end printer).

        An 'xcmHrDeviceMailbox' device with 'xcmHrDevInfoRealization' of
        'logical' MAY also indicate the current configuration of a
        'physical' device of type 'xcmHrDeviceMailboxSorter'."
    REFERENCE
        "See:   'xcmHrDeviceMailboxSorter' and 'xcmHrDeviceSorter'."
    ::= { xcmHrDeviceTypes 105 }

xcmHrDeviceFinisher OBJECT-IDENTITY
    STATUS      current
    DESCRIPTION
        "Finisher device type - manufacturer independent.
        An 'xcmHrDeviceFinisher' device is an output finishing device.
        An 'xcmHrDeviceFinisher' device with 'xcmHrDevInfoRealization'
        of 'physical' is a 'real' output device (eg, a 'stapler'
        on a high-end printer).
        An 'xcmHrDeviceFinisher' device with 'xcmHrDevInfoRealization'
        of 'logical' is a 'virtual' output device (eg, a 'personality'
        of a 'stapler' on a high-end printer)."
    ::= { xcmHrDeviceTypes 106 }

xcmHrDeviceFeeder OBJECT-IDENTITY
    STATUS      current
    DESCRIPTION
        "Feeder device type - manufacturer independent.
        An 'xcmHrDeviceFeeder' device is an input device.
        An 'xcmHrDeviceFeeder' device with 'xcmHrDevInfoRealization'
        of 'physical' is a 'real' output device (eg, a 'high-capacity
        feeder' on a high-end printer).
        An 'xcmHrDeviceFeeder' device with 'xcmHrDevInfoRealization'
        of 'logical' is a 'virtual' output device (eg, a 'personality'
        of a 'high-capacity feeder' on a high-end printer)."
    ::= { xcmHrDeviceTypes 107 }

xcmHrDeviceSorter OBJECT-IDENTITY
    STATUS      current
    DESCRIPTION
        "Sorter device type - manufacturer independent.
        An 'xcmHrDeviceSorter' device is a 'multi-bin' output device,
        with each 'bin' assigned to a copy of the current job, and
        NO physical security associated with each 'bin'.
        An 'xcmHrDeviceSorter' device with 'xcmHrDevInfoRealization' of
        'physical' is a 'real' output device (eg, a '10-bin sorter' on
        a mid-range printer).
        An 'xcmHrDeviceSorter' device with 'xcmHrDevInfoRealization' of
        'logical' is a 'virtual' output device (eg, a 'personality' of a


        '10-bin sorter' on a mid-range printer).

        An 'xcmHrDeviceSorter' device with 'xcmHrDevInfoRealization' of
        'logical' MAY also indicate the current configuration of a
        'physical' device of type 'xcmHrDeviceMailboxSorter'."
    REFERENCE
        "See:   'xcmHrDeviceMailboxSorter' and 'xcmHrDeviceMailbox'."
    ::= { xcmHrDeviceTypes 108 }

xcmHrDeviceMailboxSorter OBJECT-IDENTITY
    STATUS      current
    DESCRIPTION
        "MailboxSorter device type - manufacturer independent.
        An 'xcmHrDeviceMailboxSorter' is a 'multi-bin' output device,
        which MAY be configured as either a 'mailbox' or a 'sorter',
        by a system adminstrator or by default product configuration.
        An 'xcmHrDeviceMailboxSorter' with 'xcmHrDevInfoRealization' of
        'physical' is a 'real' output device and associated with
        associated with exactly two 'logical' output devices of types
        'xcmHrDeviceMailbox' and 'xcmHrDeviceSorter' - one of these
        'logical' devices MAY be 'running' (currently configured) - at
        least one SHALL be 'down' (NOT currently configured)."
    ::= { xcmHrDeviceTypes 109 }

xcmHrDevicePrintAppliance OBJECT-IDENTITY
    STATUS      current
    DESCRIPTION
        "Print appliance device type - manufacturer independent.
        An 'xcmHrDevicePrintAppliance' is a network printing appliance
        with 'xcmHrDevInfoRealization' of 'physical'.
        An 'xcmHrDevicePrintAppliance' SHALL statically and/or actively
        discover available network printers and SHOULD advertise them
        as supported output devices, using rows in 'hrDeviceTable' of
        IETF HR MIB (RFC 2790) and 'prtGeneralTable' of the Printer MIB
        (RFC 1759 or successor), with 'hrDeviceType' set to
        'hrDevicePrinter'.
        An 'xcmHrDevicePrintAppliance' SHALL NOT use 'hrDeviceIndex' of
        '1' (first row) for an 'hrDevicePrinter' row, because a network
        printing appliance is an enhanced spooler and NOT a printer."
    REFERENCE
        "See:   'hrDevicePrinter' in IETF Host Resources MIB (RFC 2790).
        See:    'xcmHrDevicePrinterHistory' in this XCMI HRX TC."
    ::= { xcmHrDeviceTypes 110 }

xcmHrDeviceMarker OBJECT-IDENTITY
    STATUS      current
    DESCRIPTION
        "Marker Engine device type - manufacturer independent.
        An 'xcmHrDeviceMarker' device with 'xcmHrDevInfoRealization' 
        of 'physical' is a 'real' output device (eg, the 
        'marking engine' on a multifunction printer or copier).  The 
        marking engine is the module that accepts a print ready image 
        and physical media as input and outputs physical media with a 
        physical representation of the print ready input image.  The 


        'xcmHrDeviceMarker' is a 
        single module within a group of modules that cumulatively are 
        represented by 'hrDevicePrinter'. The marker shall represent the
        whole marker as a single physical unit and should maintain a 
        single entry in the 'hrDeviceTable' for all products that 
        support a single marking engine regardless of internal engine
        mark points. 
        (e.g. B&W, Highlight Color and Full Color Presses shall have a 
        single entry in 'hrDeviceTable'). Multiple entries of 
        'xcmHrDeviceMarker' may exist in the 'hrDeviceTable' if the 
        system supports multiple print engines whether chained, in     
        parallel or in any other configuration.   
        An 'xcmHrDeviceMarker' SHALL NOT use 'hrDeviceIndex' of
        '1' (first row).  The index 1 is reserved for an 
        'hrDevicePrinter' row." 
    ::= { xcmHrDeviceTypes 111 }

xcmHrDeviceFinisherBFM OBJECT-IDENTITY
    STATUS      current
    DESCRIPTION
        "Basic Finisher Module device type - manufacturer independent.
        An 'xcmHrDeviceFinisherBFM' device is a basic output finishing
        device. An 'xcmHrDeviceFinisherBFM' device with 
        'xcmHrDevInfoRealization' of 'physical' is a 'real' output 
        device (eg, a 'stapler' on a high-end printer).
        An 'xcmHrDeviceFinisherBFM' device with 
        'xcmHrDevInfoRealization' of 'logical' is a 'virtual' output 
        device (eg, a 'personality' of a 'stapler' on a high-end 
        printer)."
    ::= { xcmHrDeviceTypes 112 }

xcmHrDeviceFinisherMFF OBJECT-IDENTITY
    STATUS      current
    DESCRIPTION
        "Multi-Function Finisher device type - manufacturer 
         independent.
        An 'xcmHrDeviceFinisherMFF' device is a multi-function output 
         finishing device. An 'xcmHrDeviceFinisherMFF' device with 
         'xcmHrDevInfoRealization' of 'physical' is a 'real' output 
         device (eg, a 'saddle stitcher', 'C-Folder', 'Z-Folder', 
         'Hole Puncher' on a high-end printer).
        An 'xcmHrDeviceFinisherMFF' device with 
         'xcmHrDevInfoRealization' of 'logical' is a 'virtual' output 
         device (eg, a 'personality' of a 'saddle stitcher', 
         'C-Folder', 'Z-Folder', 'Hole Puncher' on a 
        high-end printer)."
    ::= { xcmHrDeviceTypes 113 }

xcmHrDeviceFinisherXIM OBJECT-IDENTITY
    STATUS      current
    DESCRIPTION
         "eXternal Interface Module Finisher device type.
        An 'xcmHrDeviceFinisherXIM' device is a hardware interface 
        used to pass media from a Xerox printing device to a 3rd party


        finishing devices. The 'xcmHrDeviceFinihserXIM' may or may not 
        contain its own output trays or finishing capabilities.
        An 'xcmHrDeviceFinisherXIM' device with 
        'xcmHrDevInfoRealization' of 'physical' is a 'real' output 
        device (e.g., an 'output bridge' on a high-end printer)."
    ::= { xcmHrDeviceTypes 114 }

xcmHrDeviceFinisher3rdParty OBJECT-IDENTITY
    STATUS      current
    DESCRIPTION
         "3rd Party Finisher device type - manufacturer independent.
        An 'xcmHrDeviceFinisher3rdParty' device is an output finishing 
        device. An 'xcmHrDeviceFinisher3rdParty' device with 
        'xcmHrDevInfoRealization'
        of 'physical' is a 'real' output device (eg, a 'stapler' on 
        a high-end printer). An 'xcmHrDeviceFinisher3rdParty' device 
        with 'xcmHrDevInfoRealization' of 'logical' is a 'virtual' 
        output device (eg, a 'personality' of a 'stapler' on a high-end
        printer)."
    ::= { xcmHrDeviceTypes 115 }

xcmHrDevicePaymentInterface OBJECT-IDENTITY
    STATUS      current
    DESCRIPTION
        "Payment Interface device type - manufacturer independent.
        An 'xcmHrDevicePaymentInterface' device is an payment 
        authorization device.
        An 'xcmHrDevicePaymentInterface' device with 
        'xcmHrDevInfoRealization' of 'physical' is a 'real' point of 
        purchase validation device (eg, a 'coin operated', 'smart card' 
        or other form of point of purchase payment for services 
        rendered on a multi-function printer or copier).
        An 'xcmHrDevicePaymentInterface' device with 
        'xcmHrDevInfoRealization' of 'logical' is a 'virtual' point 
        of purchase validation device (eg, a software service that 
        accepts payment through the Web or some other form of remote 
        point of purchase payment for services rendered on a 
        multi-function printer or copier)."
    ::= { xcmHrDeviceTypes 116 }

xcmHrDeviceInterposer OBJECT-IDENTITY
    STATUS      current
    DESCRIPTION
        "Interposer device type - manufacturer independent.
        An 'xcmHrDeviceInterposer' device is an input device which 
        physically resides downstream of the print engine amongst 
        finishing modules.
        An 'xcmHrDeviceInterposer' device with 
        'xcmHrDevInfoRealization' of 'physical' is a 'real' input 
        device (eg, a 'high-capacity Interposing feeder' that 
        physically resides amongst finishing modules
        on a high-end printer).
        An 'xcmHrDeviceInterposer' device with 
        'xcmHrDevInfoRealization' of 'logical' is a 'virtual' 


        input device (eg, a 'personality' of a 
        'high-capacity Interposing feeder' that physically resides 
        amongst finishing modules on a high-end printer). 
        Interposers are essentially feeders that are placed 
        downstream of the print engine paper path and upstream of 
        finishing devices.  Interposer fed media is not marked by the
        print engine; instead media fed from an interposer is inserted 
        before, between or after marked pages.  The media constitutes 
        covers, separators etc."  
    ::= { xcmHrDeviceTypes 117 }

xcmHrDeviceInternetFax OBJECT-IDENTITY
    STATUS      current
    DESCRIPTION
        "Internet Fax device type - manufacturer independent.
 A local Fax service which sends and/or receives faxes
 over the internet"
    REFERENCE
        "See:   'xcmHrDeviceFax' in this XCMI HRX TC."
    ::= { xcmHrDeviceTypes 118 }

xcmHrDeviceServerFax OBJECT-IDENTITY
    STATUS      current
    DESCRIPTION
        "Server Fax device type - manufacturer independent.
 A Fax service which works with a server on the network
 to send and/or receive faxes over a remote modem and
 phone lines"
    REFERENCE
        "See:   'xcmHrDeviceFax' in this XCMI HRX TC."
    ::= { xcmHrDeviceTypes 119 }

xcmHrDeviceEmbeddedFax OBJECT-IDENTITY
    STATUS      current
    DESCRIPTION
        "Embedded Fax device type - manufacturer independent. 
         A local fax service which sends and/or receives fax 
         directly over a modem and phone lines."
    REFERENCE
        "See:   'xcmHrDeviceFax' in this XCMI HRX TC."
    ::= { xcmHrDeviceTypes 120 }

xcmHrDeviceForeignInterface OBJECT-IDENTITY 
    STATUS      current 
    DESCRIPTION 
        "Foreign Interface device type - manufacturer independent. 
         A physical connection provided by a device for the purpose 
         of connecting an external accessory. This accessory may 
         be capable of tracking data (e.g. Auditron) or may enable/ 
         disable device operation (e.g. card reader, coin operator, 
         etc.). This device type shall only be used when the device 
         cannot detect the type of external accessory that is 
         physically connected. If the device can detect the type of 
         external accessory which can be physically connected, 


         then the appropriate device type for that interface should 
         be used instead. (e.g. xcmHrDevicePaymentInterface, 
         xcmHrDeviceSecurityInterface, or 
         xcmHrDeviceAccountingInterface" 
    ::= { xcmHrDeviceTypes 121 } 

xcmHrDeviceSecurityInterface OBJECT-IDENTITY 
    STATUS      current 
    DESCRIPTION 
        "Security device type - manufacturer independent. 
         A physical connection provided by a device for the purpose 
         of connecting an external security-related accessory. This 
         accessory may consist of a card reader or biometric device 
         which would restrict access to a machine to only authorized 
         users." 
    ::= { xcmHrDeviceTypes 122 } 

xcmHrDeviceAccountingInterface OBJECT-IDENTITY 
    STATUS      current 
    DESCRIPTION 
        "Accounting device type - manufacturer independent. 
         A physical connection provided by a device for the purpose 
         of connecting an external accounting-related accessory. This 
         accessory would provide the capability to track machine 
         usage but would not restrict access to the machine as would 
         an accessory defined by type xcmHrDevicePaymentInterface." 
    ::= { xcmHrDeviceTypes 123 } 

xcmHrDeviceFeederSFM OBJECT-IDENTITY 
    STATUS      current 
    DESCRIPTION 
        "Feeder device type - Xerox Substraite Feeding Module 
        An 'xcmHrDeviceFeederSFM' device is an input device. 
        An 'xcmHrDeviceFeederSFM' device with 
        'xcmHrDevInfoRealization' of 'physical' is a 'real' output 
        device (eg, a 'high-capacity feeder' on a high-end printer). 
        An 'xcmHrDeviceFeeder' device with 'xcmHrDevInfoRealization' 
        of 'logical' is a 'virtual' output device (eg, a 'personality' 
        of a 'high-capacity feeder' on a high-end printer)." 
    ::= { xcmHrDeviceTypes 124 } 

xcmHrDeviceFeederLFF OBJECT-IDENTITY 
    STATUS      current 
    DESCRIPTION 
        "Feeder device type - Xerox Large Format Feeder. 
        An 'xcmHrDeviceFeederLFF' device is an input device. 
        An 'xcmHrDeviceFeeder' device with 'xcmHrDevInfoRealization' 
        of 'physical' is a 'real' output device (eg, a 'high-capacity 
        large format feeder' on a high-end printer). 
        An 'xcmHrDeviceFeeder' device with 'xcmHrDevInfoRealization' 
        of 'logical' is a 'virtual' output device (eg, a 'personality' 
        of a 'high-capacity large format feeder' 
        on a high-end printer)." 
    ::= { xcmHrDeviceTypes 125 } 


xcmHrDeviceScannerADF OBJECT-IDENTITY 
    STATUS      current 
    DESCRIPTION 
        "Scanner device type - manufacturer independent automatic 
         document feeding scanner.  An 'xcmHrDeviceScannerADF' device 
         with 'xcmHrDevInfoRealization' of 'physical' is a 'real' input 
         device (eg, a 'scan channel' on a multifunction printer). 
         An 'xcmHrDeviceScannerADF' device with 
         'xcmHrDevInfoRealization' of 'logical' is a 'virtual' input 
         device (eg, a 'personality' of a 'scan channel' on a 
         multifunction printer)." 
    REFERENCE 
        "See:   'xcmHrDeviceScannerHistory' in this XCMI HRX TC." 
    ::= { xcmHrDeviceTypes 126 } 

xcmHrDeviceScannerPlaten OBJECT-IDENTITY 
    STATUS      current 
    DESCRIPTION 
        "Scanner device type -  manufacturer independent platen glass 
         scanner. An 'xcmHrDeviceScannerPlaten' device with 
         'xcmHrDevInfoRealization' of 'physical' is a 'real' input 
         device (eg, a 'scan channel' on a multifunction printer). 
        An 'xcmHrDeviceScannerPlaten' device with 
        'xcmHrDevInfoRealization' of 'logical' is a 'virtual' input 
        device (eg, a 'personality' of a 'scan channel' on a 
        multifunction printer)." 
    REFERENCE 
        "See:   'xcmHrDeviceScannerHistory' in this XCMI HRX TC." 
    ::= { xcmHrDeviceTypes 127 } 

xcmHrDeviceColorScanningCard OBJECT-IDENTITY 
    STATUS      current 
    DESCRIPTION 
        "An xcmHrDeviceColorScanningCard is a physical card that allows 
         for scanning of color, or monochrome, images from the printer
         to a remote device."
    ::= { xcmHrDeviceTypes 128 } 

--          REGISTRY of XCMI Standard History Device Types
--          (used with 'hrDeviceType' in Device Group
--          of the IETF Host Resources MIB, RFC 2790).
--
--  Usage:  May be used to segregate historical information for any
--  standard device type in any MIB table indexed by 'hrDeviceIndex'.
--
--  Eg, the 'xcmJobGenBasicTable' in the XCMI Job Monitoring MIB and/or
--  the 'jm[Job|Attribute]Table' in the PWG Job Monitoring MIB could
--  have a segment for an 'hrDevicePrinter' device type (current and
--  very recent jobs) and a segment for an 'xcmHrDevicePrinterHistory'
--  device type (longer-term job history of completed jobs).
--  Entries in the 'xcmHrDevDetailTable' SHOULD cross-link these related
--  devices (using 'deviceJob[Service|History]DeviceIndex').
--


--  Algorithm:  The final arc of each standard job history device type
--  is derived by adding decimal '50' to the final arc of the companion
--  standard job service device type.

xcmHrDeviceHostSystemHistory OBJECT-IDENTITY
    STATUS      current
    DESCRIPTION
        "Host system history device type - manufacturer independent."
    REFERENCE
        "See:   'xcmHrDeviceHostSystem' in this XCMI HRX TC."
    ::= { xcmHrDeviceTypes 151 }

xcmHrDeviceScannerHistory OBJECT-IDENTITY
    STATUS      current
    DESCRIPTION
        "Scanner history device type - manufacturer independent."
    REFERENCE
        "See:   'xcmHrDeviceScanner' in this XCMI HRX TC."
    ::= { xcmHrDeviceTypes 152 }

xcmHrDeviceCopierHistory OBJECT-IDENTITY
    STATUS      current
    DESCRIPTION
        "Copier history device type - manufacturer independent."
    REFERENCE
        "See:   'xcmHrDeviceCopier' in this XCMI HRX TC."
    ::= { xcmHrDeviceTypes 153 }

xcmHrDeviceFaxHistory OBJECT-IDENTITY
    STATUS      current
    DESCRIPTION
        "Fax history device type - manufacturer independent."
    REFERENCE
        "See:   'xcmHrDeviceFax' in this XCMI HRX TC."
    ::= { xcmHrDeviceTypes 154 }

xcmHrDevicePrinterHistory OBJECT-IDENTITY
    STATUS      current
    DESCRIPTION
        "Printer history device type - manufacturer independent."
    REFERENCE
        "See:   'hrDevicePrinter' in the IETF HR MIB."
    ::= { xcmHrDeviceTypes 55 }         -- 'hrDevicePrinter' + 50

--          REGISTRY of XCMI Standard CRU Types
--          (used with 'hrDeviceType' in Device Group
--          of the IETF Host Resources MIB, RFC 2790).

xcmHrCruXerographicModule OBJECT-IDENTITY
    STATUS      current
    DESCRIPTION
        "CRU xerographic module - manufacturer independent.
        An 'xcmHrCruXerographicModule' device is a customer
        replaceable unit, with 'xcmHrDevInfoRealization' of 'physical'."


    ::= { xcmHrDeviceTypes 201 }

xcmHrCruFuserModule OBJECT-IDENTITY
    STATUS      current
    DESCRIPTION
        "CRU fuser module - manufacturer independent.
        An 'xcmHrCruFuserModule' device is a customer
        replaceable unit, with 'xcmHrDevInfoRealization' of 'physical'."
    ::= { xcmHrDeviceTypes 202 }

xcmHrCruTonerBottleModule OBJECT-IDENTITY
    STATUS      current
    DESCRIPTION
        "CRU toner bottle module - manufacturer independent.
        An 'xcmHrCruTonerBottleModule' device is a customer
        replaceable unit, with 'xcmHrDevInfoRealization' of 'physical'."
    ::= { xcmHrDeviceTypes 203 }

xcmHrCruCollectorBottleModule OBJECT-IDENTITY
    STATUS      current
    DESCRIPTION
        "CRU (developer) collector bottle - manufacturer independent.
        An 'xcmHrCruCollectorBottleModule' device is a customer
        replaceable unit, with 'xcmHrDevInfoRealization' of 'physical'."
    ::= { xcmHrDeviceTypes 204 }

xcmHrCruTrayFeedHeadModule OBJECT-IDENTITY
    STATUS      current
    DESCRIPTION
        "CRU tray feed head module - manufacturer independent.
        An 'xcmHrCruTrayFeedHeadModule' device is a customer
        replaceable unit, with 'xcmHrDevInfoRealization' of 'physical'."
    ::= { xcmHrDeviceTypes 205 }

xcmHrCruAdfFeedHeadModule OBJECT-IDENTITY
    STATUS      current
    DESCRIPTION
        "CRU ADF feed head module - manufacturer independent.
        An 'xcmHrCruAdfFeedHeadModule' device is a customer
        replaceable unit, with 'xcmHrDevInfoRealization' of 'physical'.
        Note:   ADF is an acronym for 'automatic document feeder'."
    ::= { xcmHrDeviceTypes 206 }

xcmHrCruFuserWebModule OBJECT-IDENTITY
    STATUS      current
    DESCRIPTION
        "CRU fuser web module - manufacturer independent.
        An 'xcmHrCruFuserWebModule' device is a customer
        replaceable unit, with 'xcmHrDevInfoRealization' of 'physical'.
        Note:   A 'fuser web' is an oil-soaked fiber roll in a fuser,
        which prevents toner from getting on the fuser roll.  The 'fuser
        web' device would normally be replaced several times before the
        actual fuser device ('xcmHrCRUFuserModule') is replaced."
    ::= { xcmHrDeviceTypes 207 }


xcmHrCruFilterModule OBJECT-IDENTITY
    STATUS      current
    DESCRIPTION
        "CRU filter module - manufacturer independent.
        An 'xcmHrCruFilterModule' device is a customer replaceable 
        filter or filter unit, with 'xcmHrDevInfoRealization' of
        'physical'."
    ::= { xcmHrDeviceTypes 208 }

xcmHrCruCleanerUnitModule OBJECT-IDENTITY
    STATUS      current
    DESCRIPTION
        "CRU cleaner unit module - manufacturer independent.
        An 'xcmHrCruCleanerUnitModule' device is a customer
        replaceable cleaner unit, with 'xcmHrDevInfoRealization' of
        'physical' (eg, a belt cleaner or a photoreceptor cleaner)."
    REFERENCE
        "See:   'cleanerUnit' in 'PrtMarkerSuppliesTypeTC' in
                the Printer MIB v2."
    ::= { xcmHrDeviceTypes 209 }

xcmHrCruTransferUnitModule OBJECT-IDENTITY
    STATUS      current
    DESCRIPTION
        "CRU transfer unit module - manufacturer independent.
        An 'xcmHrCruTransferUnitModule' device is a customer
        replaceable transfer unit, with 'xcmHrDevInfoRealization' of
        'physical'."
    REFERENCE
        "See:   'transferUnit' in 'PrtMarkerSuppliesTypeTC' in
                the Printer MIB v2."
    ::= { xcmHrDeviceTypes 210 }

xcmHrCruTransferRollerModule OBJECT-IDENTITY
    STATUS      current
    DESCRIPTION
        "CRU transfer roller module - manufacturer independent.
        An 'xcmHrCruTransferRollerModule' device is a customer
        replaceable transfer roller, with 'xcmHrDevInfoRealization' of
        'physical' (eg, a biased transfer roller)."
    REFERENCE
        "See:   'transferUnit' in 'PrtMarkerSuppliesTypeTC' in
                the Printer MIB v2."
    ::= { xcmHrDeviceTypes 211 }

xcmHrCruPFPFeedRollModule OBJECT-IDENTITY
    STATUS      current
    DESCRIPTION
        "CRU Paper Feed Platform module - manufacturer independent.
        An 'xcmHrCruPaperFeedModule' device is a customer
        replaceable unit, with 'xcmHrDevInfoRealization' of 'physical'."
    ::= { xcmHrDeviceTypes 212 }


xcmHrCruPFPRetardRollModule OBJECT-IDENTITY
    STATUS    current
    DESCRIPTION
        "CRU PFP Retard Roll module - manufacturer independent.
        An 'xcmHrCruPFPRetardRollModule' device is a customer 
        replaceable unit, with 'xcmHrDevInfoRealization' of 'physical'."
    ::= { xcmHrDeviceTypes 213 }

xcmHrDeviceUSBPort  OBJECT-IDENTITY 
 STATUS current 
 DESCRIPTION 
  "The device type identifier used for a
  Universal Serial Bus port." 
 ::= { xcmHrDeviceTypes 250 } 

xcmHrDeviceFlashDIMMFileStore  OBJECT-IDENTITY 
 STATUS current 
 DESCRIPTION 
         "The device type identifier used for a Flash DIMM that contains
          a file system that is used to store files such as font files. 
          opposed to a Flash DIMM that contains a boot loader."
 ::= { xcmHrDeviceTypes 260 } 

xcmHrDeviceFlashDIMMBootLoader  OBJECT-IDENTITY 
 STATUS current 
 DESCRIPTION 
         "The device type identifier used for a Flash DIMM that contains
          the boot loader for a device. Files may or may not be stored o
          this device. As opposed to a Flash DIMM that contains a file 
          store system." 
 ::= { xcmHrDeviceTypes 261 } 

xcmHrDeviceFlashDrive  OBJECT-IDENTITY 
        STATUS current 
        DESCRIPTION 
         "The device type identifier used for a Flash Drive for a device
          Files may or may not be stored on this device. As opposed to a
          Flash DIMM that contains a file store system or a bootloader."
        ::= { xcmHrDeviceTypes 262 } 

--          REGISTRY of XCMI HRX Admin Service Types (Classes)
--          (MAY be used in the 'xcmSec[Service|PolicyService]TypeOID'
--          objects in the closely related XCMI Security MIB, in
--          conforming management agents which do NOT implement the
--          related XCMI System Admin MIB).

xcmHrAdminServiceTypes OBJECT-IDENTITY
    STATUS      current
    DESCRIPTION
        "The root of all host system management service types (classes)
        defined in the Host Resources Extensions TC."
    REFERENCE
        "See:   'XcmSecPosixVerbs' and 'xcmSecServiceTypeOID'


                in XCMI Security TC/MIB."
    ::= { xcmHrTC 3 }

xcmHrAdminObjectService OBJECT-IDENTITY
    STATUS      current
    DESCRIPTION
        "The host system object management service."
    REFERENCE
        "See:   'xcmSysAdminObject...' in XCMI System Admin MIB.
        See:    'XcmSecPosixVerbs' and 'xcmSecServiceTypeOID'
                in XCMI Security TC/MIB."
    ::= { xcmHrAdminServiceTypes 1 }

xcmHrAdminServerService OBJECT-IDENTITY
    STATUS      current
    DESCRIPTION
        "The host system server management service."
    REFERENCE
        "See:   'xcmSysAdminServer...' in XCMI System Admin MIB,
                'hrSW[Running|Installed]Table' in IETF HR MIB, and
                'xcmHrSW[Running|Installed]ExtTable' in XCMI HRX MIB.
        See:    'XcmSecPosixVerbs' and 'xcmSecServiceTypeOID'
                in XCMI Security TC/MIB."
    ::= { xcmHrAdminServiceTypes 2 }

xcmHrAdminDeviceService OBJECT-IDENTITY
    STATUS      current
    DESCRIPTION
        "The host system device management service."
    REFERENCE
        "See:   'xcmSysAdminDevice...' in XCMI System Admin MIB,
                'hrDeviceTable' in IETF HR MIB, and
                'xcmHrDev[Info|Help|Mgmt|Power|Traffic|Calendar]Table'
                in XCMI HRX MIB.
        See:    'XcmSecPosixVerbs' and 'xcmSecServiceTypeOID'
                in XCMI Security TC/MIB."
    ::= { xcmHrAdminServiceTypes 3 }

xcmHrAdminJobService OBJECT-IDENTITY
    STATUS      current
    DESCRIPTION
        "The host system job management service."
    REFERENCE
        "See:   'xcmSysAdminJob...' in XCMI System Admin MIB, and
                'xcmJob[...]Table' in XCMI Job Monitoring MIB.
        See:    'XcmSecPosixVerbs' and 'xcmSecServiceTypeOID'
                in XCMI Security TC/MIB."
    ::= { xcmHrAdminServiceTypes 4 }

xcmHrAdminDocService OBJECT-IDENTITY
    STATUS      current
    DESCRIPTION
        "The host system document management service."
    REFERENCE


        "See:   'xcmSysAdminDoc...' in XCMI System Admin MIB, and
                'xcmDoc[...]Table' in XCMI Job Monitoring MIB.
        See:    'XcmSecPosixVerbs' and 'xcmSecServiceTypeOID'
                in XCMI Security TC/MIB."
    ::= { xcmHrAdminServiceTypes 5 }

xcmHrAdminSecurityService OBJECT-IDENTITY
    STATUS      current
    DESCRIPTION
        "The host system security management service."
    REFERENCE
        "See:   'xcmSysAdminSecurity...' in XCMI System Admin MIB.
        See:    'XcmSecPosixVerbs' and 'xcmSecServiceTypeOID'
                in XCMI Security TC/MIB."
    ::= { xcmHrAdminServiceTypes 6 }

xcmHrAdminCommsService OBJECT-IDENTITY
    STATUS      current
    DESCRIPTION
        "The host system communications management service."
    REFERENCE
        "See:   'xcmSysAdminComms...' in XCMI System Admin MIB and
                XCMI Comms Config and Comms Engine MIBs.
        See:    'XcmSecPosixVerbs' and 'xcmSecServiceTypeOID'
                in XCMI Security TC/MIB."
    ::= { xcmHrAdminServiceTypes 7 }

--          REGISTRY of XCMI HRX Admin Device Operation Types
--          (MAY be used in the 'xcmSecPolicyVerbTypeOID'
--          object in the closely related XCMI Security MIB, for
--          fine-grained access control to device management verbs, in
--          conforming management agents which do NOT implement the
--          related XCMI System Admin MIB).

xcmHrAdminDeviceOperationTypes OBJECT-IDENTITY
    STATUS      current
    DESCRIPTION
        "The root of all host resources admin device operation types
        defined in the Host Resources Extensions TC.

        Usage:  The following OIDs support access control for the simple
        device admin operations defined in 'XcmHrDevMgmtCommandRequest'
        and used in 'xcmHrDevMgmtCommandRequest' in the XCMI HRX MIB,
        via 'xcmSec[Master|Policy]VerbTypeOID' in the XCMI Security MIB,
        WITHOUT requiring implementation of the XCMI System Admin MIB."
    REFERENCE
        "See:   'xcmSec[Master|Policy]VerbTypeOID' in
                XCMI Security MIB."
    ::= { xcmHrTC 4 }

xcmHrAdminDeviceNone            OBJECT IDENTIFIER
    ::= { xcmHrAdminDeviceOperationTypes 1 }
xcmHrAdminDeviceStartup         OBJECT IDENTIFIER
    ::= { xcmHrAdminDeviceOperationTypes 2 }


xcmHrAdminDeviceResetWarning    OBJECT IDENTIFIER
    ::= { xcmHrAdminDeviceOperationTypes 3 }
xcmHrAdminDeviceTest            OBJECT IDENTIFIER
    ::= { xcmHrAdminDeviceOperationTypes 4 }
xcmHrAdminDeviceShutdown        OBJECT IDENTIFIER
    ::= { xcmHrAdminDeviceOperationTypes 5 }
xcmHrAdminDeviceQuiesce         OBJECT IDENTIFIER
    ::= { xcmHrAdminDeviceOperationTypes 6 }
xcmHrAdminDeviceResetCounters   OBJECT IDENTIFIER
    ::= { xcmHrAdminDeviceOperationTypes 7 }
xcmHrAdminDeviceResetWarm       OBJECT IDENTIFIER
    ::= { xcmHrAdminDeviceOperationTypes 8 }
xcmHrAdminDeviceResetCold       OBJECT IDENTIFIER
    ::= { xcmHrAdminDeviceOperationTypes 9 }
xcmHrAdminDeviceResetFactory    OBJECT IDENTIFIER
    ::= { xcmHrAdminDeviceOperationTypes 10 }
xcmHrAdminDeviceFlushInput      OBJECT IDENTIFIER
    ::= { xcmHrAdminDeviceOperationTypes 11 }
xcmHrAdminDeviceFlushOutput     OBJECT IDENTIFIER
    ::= { xcmHrAdminDeviceOperationTypes 12 }
xcmHrAdminDeviceFlushInOut      OBJECT IDENTIFIER
    ::= { xcmHrAdminDeviceOperationTypes 13 }
xcmHrAdminDeviceManage          OBJECT IDENTIFIER
    ::= { xcmHrAdminDeviceOperationTypes 14 }
xcmHrAdminDeviceRefresh         OBJECT IDENTIFIER
    ::= { xcmHrAdminDeviceOperationTypes 15 }
xcmHrAdminDeviceWarmUp          OBJECT IDENTIFIER
    ::= { xcmHrAdminDeviceOperationTypes 16 }
xcmHrAdminDeviceCoolDown        OBJECT IDENTIFIER
    ::= { xcmHrAdminDeviceOperationTypes 17 }
xcmHrAdminDeviceEnergySave      OBJECT IDENTIFIER
    ::= { xcmHrAdminDeviceOperationTypes 18 }
xcmHrAdminDeviceWakeUp          OBJECT IDENTIFIER
    ::= { xcmHrAdminDeviceOperationTypes 19 }
xcmHrAdminDevicePowerToReady    OBJECT IDENTIFIER
    ::= { xcmHrAdminDeviceOperationTypes 20 }
xcmHrAdminDevicePowerToStandby  OBJECT IDENTIFIER
    ::= { xcmHrAdminDeviceOperationTypes 21 }
xcmHrAdminDevicePowerToSleep    OBJECT IDENTIFIER
    ::= { xcmHrAdminDeviceOperationTypes 22 }

--
--          The Host Resources Extensions (HRX) TC
--
--          Textual Conventions

XcmHrDevCalendarDayOfWeek ::= TEXTUAL-CONVENTION
    STATUS      current
    DESCRIPTION
        "The day of week when the command specified in a conceptual
        row in the 'xcmHrDevCalendarTable' SHALL be invoked."
    SYNTAX      INTEGER {
        monday(1),
        tuesday(2),


        wednesday(3),
        thursday(4),
        friday(5),
        saturday(6),
        sunday(7),
        everyDay(8),                    -- monday through sunday
        businessOpenDay(9),             -- site specific
        businessClosedDay(10),          -- site specific
        businessHoliday(11)             -- site specific
    }

XcmHrDevCalendarTimeOfDay ::= TEXTUAL-CONVENTION
    STATUS      current
    DESCRIPTION
        "The time of day when the command specified in a conceptual
        row in the 'xcmHrDevCalendarTable' SHALL be invoked, specified
        as hours (0..23) multiplied by 100, added to minutes (0..59),
        added to a constant bias of 10000 (avoids an index value of zero
        in 'xcmHrDevCalendarTimeOfDay')."
    SYNTAX      INTEGER (10000..12359)

XcmHrDevDetailType ::= TEXTUAL-CONVENTION
    STATUS      current
    DESCRIPTION
        "The type of the device detail information specified
        in this conceptual row in the 'xcmHrDevDetailTable'.

        Usage:  Conforming management stations and management agents
        SHALL implement specified semantics for device detail types."

--      -   Device other/unknown details
--    * 'other'
--    * 'unknown'
--    
--      -   Device general info
--    * 'deviceName'
--      - device administrative name in directory (primary name)
--      - (same usage as 'xcmCOSpecialName' in XCMI Comms Config TC)
--      - type - (XcmFixedLocaleDisplayString)
--      - subtype - '...ValueOID' (directory in XCMI Comms Config TC)
--      - (eg, 'xcmCOInternetDNS')
--      - data - '...ValueString'
--      - (eg, 'showstopper.sample.com')
--      - see - 'xcmCOSpecialName' in XCMI Comms Config TC
--      - see - 'deviceAlias' in XCMI HRX TC
--      - see - 'xcmHrDevInfoName' in XCMI HRX MIB
--      - see - DPA-1 9.4.1 'Printer-name'
--      - see - DPA-1 9.5.1 'Server-name'
--    * 'deviceAlias'
--      - device administrative alias in directory (alternate name)
--      - (same usage as 'xcmCOSpecialName' in XCMI Comms Config TC)
--      - type - (XcmFixedLocaleDisplayString)
--      - subtype - '...ValueOID' (directory in XCMI Comms Config TC)
--      - (eg, 'xcmCOInternetDNS')


--      - data - '...ValueString'
--      - (eg, 'LaserRat')
--      - see - 'xcmCOSpecialName' in XCMI Comms Config TC
--      - see - 'deviceName' in XCMI HRX TC
--      - see - DPA-1 9.4.2 'Printer-name-aliases'
--      - see - DPA-1 9.5.2 'Server-name-aliases'
--    * 'deviceType'
--      - device type
--      - type - (OBJECT IDENTIFIER)
--      - data - '...ValueOID'
--      - (eg, 'hrDevicePrinter')
--      - see - 'hrDeviceType' in IETF HR MIB
--      - see - 'Usage of hrDeviceType and hrDeviceDescr' section of
--      - 'XCMI Supplement to IETF Host Resources MIB' in XCMI HRX TC
--    * 'deviceDescription'
--      - device description
--      - type - (XcmFixedLocaleDisplayString)
--      - data - '...ValueString'
--      - (eg, 'Xerox DocuCentre 230 ST v1.0 - Printer')
--      - see - 'hrDeviceDescr' in IETF HR MIB
--      - see - 'Usage of hrDeviceType and hrDeviceDescr' section of
--      - 'XCMI Supplement to IETF Host Resources MIB' in XCMI HRX TC
--    * 'deviceID'
--      - device (product) ID
--      - type - (ProductID)
--      - data - '...ValueOID'
--      - (eg, 'xcmPidDC230STV1')
--      - see - 'ProductID' and 'hrDeviceID' in IETF HR MIB
--      - see - 'IETF HR DeviceTable' section of
--      - 'XCMI Supplement to IETF Host Resources MIB' in XCMI HRX TC
--    * 'deviceTree'
--      - device tree prefix to name/alias in directory
--      - type - (XcmFixedLocaleDisplayString)
--      - subtype - '...ValueOID' (directory in XCMI Comms Config TC)
--      - (eg, 'xcmCONetwareNDS')
--      - data - '...ValueString'
--      - (MAY also appear in 'deviceName')
--    * 'deviceContext'
--      - device context prefix to name/alias in directory
--      - type - (XcmFixedLocaleDisplayString)
--      - subtype - '...ValueOID' (directory in XCMI Comms Config TC)
--      - (eg, 'xcmCONetwareNDS')
--      - data - '...ValueString'
--      - (MAY also appear in 'deviceName')
--    * 'deviceManufacturer'
--      - device manufacturer (or OEM) name
--      - type - (XcmFixedLocaleDisplayString)
--      - data - '...ValueString'
--      - compare - 'hrDeviceDescr' in IETF HR MIB
--    * 'deviceModel'
--      - device model (alphanumeric)
--      - type - (XcmFixedLocaleDisplayString)
--      - data - '...ValueString'
--      - see - DPA-1 9.4.4 'Printer-model'


--      - compare - 'hrDeviceDescr' in IETF HR MIB
--    * 'deviceSerialNumber'
--      - device serial number
--      - see - 'xcmHrDevInfoSerialNumber' in XCMI HRX MIB
--      - type - (XcmFixedLocaleDisplayString)
--      - data - '...ValueString'
--    * 'deviceVendor'
--      - device vendor (to customer)
--      - type - (XcmFixedLocaleDisplayString)
--      - data - '...ValueString'
--      - compare - 'hrDeviceDescr' in IETF HR MIB
--    * 'deviceVersion'
--      - device version (alphanumeric)
--      - type - (XcmFixedLocaleDisplayString)
--      - data - '...ValueString'
--      - compare - 'hrDeviceDescr' in IETF HR MIB
--
--      -   Device service info
--    * 'deviceServiceByCustomer'
--      - device serviced by customer (rather than vendor)
--      - type - (TruthValue)
--      - data - '...ValueInteger'
--      - 'true' = serviced by customer
--      - 'false' = serviced by vendor
--    * 'deviceReplaceByCustomer'
--      - device replaced by customer (rather than vendor)
--      - type - (TruthValue)
--      - data - '...ValueInteger'
--      - 'true' = replaced by customer
--      - 'false' = replaced by vendor
--    * 'deviceServicePlanName'
--      - device service plan name
--      - type - (XcmFixedLocaleDisplayString)
--      - data - '...ValueString'
--      - (eg, 'Goldspot77')
--    * deviceServicePlanPassword'
--      - device service plan password (protected/encrypted)
--      - type - (XcmFixedLocaleDisplayString)
--      - data - '...ValueString'
--      - (eg, 'EA123456')
--    * 'deviceReplaceByWarranty'
--      - device replaced by warranty (rather than at end-of-life)
--      - type - (TruthValue)
--      - data - '...ValueInteger'
--      - 'true' = replaced by warranty (by some date or usage limit)
--      - 'false' = replaced at end-of-life
--
--      -   Device lifetime usage and limits
--      -   (several usage counters MAY be defined for a single device)
--      -   (several usage limits MAY be defined for a single counter)
--      -   (usage counter and usage limit groups are defined as sharing
--      -   the same value of 'xcmHrDevDetailIndex')
--    * 'deviceLifetimeUsage'
--      - device lifetime usage counter (MAY be multi-valued)


--      - (SHALL NOT be remotely reset, unlike 'deviceAccountingUsage')
--      - type - (Counter32)
--      - subtype - '...ValueString' (XcmGenMessageMapStringLabel)
--      - and (optional) trailing description after whitespace
--      - data - '...ValueInteger'
--      - (eg, monochrome and color page counters)
--      - note - SHOULD be subtyped by well-formed Xerox message
--      - string label of the 'XcmGenMessageMapStringLabel' syntax
--      - defined in the XCMI General TC (06gentc)
--      - for example:
--      - 'xs-iso-101715-mediaSize-na-letter'
--      -   - counts any DPA media size (w/out type/color)
--      - 'xs-ietf-rfc2911-media-iso-a4-...'
--      -   - counts any IETF IPP 'media' (w/ size, type, or color)
--      - 'xs-xcmi-40jobtc-XcmJMImpsCountType-blackAndWhiteCount'
--      -   - counts monochrome impressions
--      - 'xs-xcmi-40jobtc-XcmJMImpsCountType-highlightColorCount'
--      -   - counts highlight color impressions
--    * 'deviceReorderLifetimeLimit'
--      - device reorder at limit (MAY be multi-valued)
--      - type - (Cardinal32)
--      - subtype - see parallel 'deviceLifetimeUsage'
--      - data - '...ValueInteger'
--      - positive integer = limit in 'xcmHrDevDetailUnit' units
--      - zero = no limit specified
--    * 'deviceWarningLifetimeLimit'
--      - warn device user at usage limit (MAY be multi-valued)
--      - type - (Cardinal32)
--      - subtype - see parallel 'deviceLifetimeUsage'
--      - data - '...ValueInteger'
--      - positive integer = limit in 'xcmHrDevDetailUnit' units
--      - zero = no limit specified
--    * 'deviceReplaceLifetimeLimit'
--      - replace device at usage limit (MAY be multi-valued)
--      - type - (Cardinal32)
--      - subtype - see parallel 'deviceLifetimeUsage'
--      - data - '...ValueInteger'
--      - positive integer = limit in 'xcmHrDevDetailUnit' units
--      - zero = no limit specified
--    * 'deviceMaximumLifetimeLimit'
--      - stop device at usage limit (MAY be multi-valued)
--      - type - (Cardinal32)
--      - subtype - see parallel 'deviceLifetimeUsage'
--      - data - '...ValueInteger'
--      - positive integer = limit in 'xcmHrDevDetailUnit' units
--      - zero = no limit specified
--
--      -   Device message to user time remaining
--      -   (estimated dates when messages will be sent to the user)
--      -   (estimated by the device, based on current rate of usage)
--    * 'deviceDaysUntilReorderMsg'
--      - days left until reorder msg (estimated from rate of usage)
--      - type - (Cardinal32) days
--      - data - '...ValueInteger'


--    * 'deviceDaysUntilWarningMsg'
--      - days left until warning msg (estimated from rate of usage)
--      - type - (Cardinal32) days
--      - data - '...ValueInteger'
--    * 'deviceDaysUntilReplaceMsg'
--      - days left until replace msg (estimated from rate of usage)
--      - type - (Cardinal32) days
--      - data - '...ValueInteger'
--    * 'deviceDaysUntilMaximumMsg'
--      - days left until stop msg (estimated from rate of usage)
--      - type - (Cardinal32) days
--      - data - '...ValueInteger'
--    * 'deviceLifetimeMsgDisplay'
--      - where to send lifetime msgs to user
--      - type - (Cardinal32) local enum below
--      - data - '...ValueInteger'
--      - '0' = none (no msg sent)
--      - '1' = local device UI only
--      - '2' = remote clients only
--      - '3' = both (local and remote)
--
--      -   Device accounting usage
--    * 'deviceAccountingUsage'
--      - device accounting usage counter (MAY be multi-valued)
--      - (MAY be remotely reset, unlike 'deviceLifetimeUsage')
--      - type - (Counter32)
--      - subtype - '...ValueString' (XcmGenMessageMapStringLabel)
--      - and (optional) trailing description after whitespace
--      - data - '...ValueInteger'
--      - (eg, monochrome and color page counters)
--      - see - 'deviceLifetimeUsage' (which is NOT reset remotely)
--      - note - SHOULD be subtyped by a well-formed Xerox message
--      - string label of the 'XcmGenMessageMapStringLabel' syntax
--      - defined in the XCMI General TC (06gentc)
--      - for example:
--      - 'xs-iso-101715-mediaSize-na-letter'
--      -   - counts any DPA media size (w/out type/color)
--      - 'xs-ietf-rfc2911-media-iso-a4-...'
--      -   - counts any IETF IPP 'media' (w/ size, type, or color)
--      - 'xs-xcmi-40jobtc-XcmJMImpsCountType-blackAndWhiteCount'
--      -   - counts monochrome impressions
--      - 'xs-xcmi-40jobtc-XcmJMImpsCountType-highlightColorCount'
--      -   - counts highlight color impressions
--
--      -   Device message to user and reorder dates
--      -   (fixed dates when messages will be sent to the user)
--      -   (fixed by system administrator)
--    * 'deviceReorderOnDate'
--      - reorder device on fixed date (and send message to user)
--      - type - (DateAndTime)
--      - data - '...ValueString'
--    * 'deviceWarningOnDate'
--      - warn device user on fixed date
--      - type - (DateAndTime)


--      - data - '...ValueString'
--    * 'deviceReplaceOnDate'
--      - replace device on fixed date (and send message to user)
--      - type - (DateAndTime)
--      - data - '...ValueString'
--    * 'deviceMaximumOnDate'
--      - stop device on fixed date (and send message to user)
--      - type - (DateAndTime)
--      - data - '...ValueString'
--
--      -   Device lifetime errors and warnings
--      -   (several error counters MAY be defined for a single device)
--      -   (one error limit MAY be defined for a single error counter)
--      -   (error counter and error limit pairs are defined as sharing
--      -   the same value of 'xcmHrDevDetailIndex')
--    * 'deviceLifetimeErrorCount'
--      - device lifetime error counter (MAY be multi-valued)
--      - type - (Counter32)
--      - subtype - '...ValueString' (XcmGenMessageMapStringLabel)
--      - and (optional) trailing description after whitespace
--      - data - '...ValueInteger'
--      - note - SHOULD be subtyped by a well-formed Xerox message
--      - string label of the 'XcmGenMessageMapStringLabel' syntax
--      - defined in the XCMI General TC (06gentc)
--      - for example:
--      - 'xs-ietf-rfc1759-prtAlertCode-jam'
--      -   - paper jam - see 'prtAlertCode' in Printer MIB
--    * 'deviceLifetimeErrorLimit'
--      - device lifetime error limit (MAY be multi-valued)
--      - type - (Cardinal32)
--      - subtype - see parallel 'deviceLifetimeErrorCount'
--      - data - '...ValueInteger'
--      - positive integer = limit in 'deviceLifetimeErrorCount' units
--      - zero = no limit specified
--      - note - product-unique error handling at this limit
--    * 'deviceLifetimeWarningCount'
--      - device lifetime warning counter (MAY be multi-valued)
--      - type - (Counter32)
--      - subtype - '...ValueString' (XcmGenMessageMapStringLabel)
--      - and (optional) trailing description after whitespace
--      - data - '...ValueInteger'
--      - note - SHOULD be subtyped by a well-formed Xerox message
--      - string label of the 'XcmGenMessageMapStringLabel' syntax
--      - defined in the XCMI General TC (06gentc)
--      - for example:
--      - 'xs-ietf-rfc1759-prtAlertCode-inputMediaSupplyLow'
--      -   - paper low - see 'prtAlertCode' in Printer MIB
--    * 'deviceLifetimeWarningLimit'
--      - device lifetime warning limit (MAY be multi-valued)
--      - type - (Cardinal32)
--      - subtype - see parallel 'deviceLifetimeWarningCount'
--      - data - '...ValueInteger'
--      - positive integer = limit in 'deviceLifetimeWarningCount' units
--      - zero = no limit specified


--      - note - product-unique warning handling at this limit
--
--      -   Device message to user triggers
--      -   (actual days before an estimated limit date, when messages
--      -   SHALL be sent to users)
--      -   (while the 'triggers' are in terms of actual days, the
--      -   determination of the [future] limit reached date is based
--      -   on estimation by the device from current rate of usage)
--    * 'deviceTriggerDaysForReorder'
--      - days to reorder msg trigger (send before reorder limit)
--      - type - (DateAndTime)
--      - data - '...ValueString'
--    * 'deviceTriggerDaysForWarning'
--      - days to warning msg trigger (send before warning limit)
--      - type - (DateAndTime)
--      - data - '...ValueString'
--    * 'deviceTriggerDaysForReplace'
--      - days to replace msg trigger (send before replace limit)
--      - type - (DateAndTime)
--      - data - '...ValueString'
--    * 'deviceTriggerDaysForMaximum'
--      - days to stop msg trigger (send before stop limit)
--      - type - (DateAndTime)
--      - data - '...ValueString'
--
--      -   Device message to user dates actually sent
--      -   (log of dates when messages were actually sent to user,
--      -   based on estimates, actual limits, actual dates, etc)
--    * 'deviceReorderMsgSentDate'
--      - date of reorder msg to user (MAY be multi-valued)
--      - type - (DateAndTime)
--      - data - '...ValueString'
--    * deviceWarningMsgSentDate'
--      - date of warning msg to user (MAY be multi-valued)
--      - type - (DateAndTime)
--      - data - '...ValueString'
--    * 'deviceReplaceMsgSentDate'
--      - date of replace msg to user (MAY be multi-valued)
--      - type - (DateAndTime)
--      - data - '...ValueString'
--    * 'deviceMaximumMsgSentDate'
--      - date of maximum msg to user (MAY be multi-valued)
--      - type - (DateAndTime)
--      - data - '...ValueString'
--
--      -   Device reorder and replace actual dates
--      -   (log of dates when reorder and replacement were actually
--      -   done for this device)
--    * 'deviceReorderToVendorDate'
--      - date reorder to vendor sent (MAY be multi-valued)
--      - type - (DateAndTime)
--      - data - '...ValueString'
--    * 'deviceReorderConfirmDate'
--      - date reorder confirm received (MAY be multi-valued)


--      - type - (DateAndTime)
--      - data - '...ValueString'
--    * 'deviceReplaceDate'
--      - date of replacement (MAY be multi-valued)
--      - type - (DateAndTime)
--      - data - '...ValueString'
--    * 'deviceReplaceSystemUsage'
--      - system usage at date of replacement (MAY be multi-valued)
--      - type - (Counter32) some usage counter
--      - (eg, 'total marked images')
--      - date - '...ValueInteger'
--    * 'deviceReplaceWithGeneric'
--      - device MAY be replaced with generic (third-party) part
--      - (MAY indicate that a package is installed to support generics)
--      - type - (TruthValue)
--      - data - '...ValueInteger'
--      - 'true' = device MAY be replaced with a generic part
--      - 'false' = device MAY NOT be replaced with a generic part
--
--      -   Device help info (contact info)
--      - NOTE - Device Help group is DEPRECATED (as of XCMI v4.1)
--      - The following device details SHOULD be used instead
--    * 'deviceHelpName'
--      - device help person name and role
--      - type - (XcmFixedLocaleDisplayString)
--      - subtype - '...ValueOID' (directory in XCMI Comms Config TC)
--      - (eg, 'xcmCONetwareBindery')
--      - data - '...ValueString'
--      - (eg, 'Joe Hampton')
--      - role - '...ValueInteger' (XcmSecUserRole in XCMI Security TC)
--      - (eg, 'systemOperator')
--    * 'deviceHelpAddress'
--      - device help person address and role
--      - type - (XcmFixedLocaleDisplayString)
--      - subtype - '...ValueOID' (protocol in XCMI Comms Config TC)
--      - (eg, 'xcmCOOsiwanFax')
--      - data - '...ValueString'
--      - (eg, '1-800-232-7979')
--      - role - '...ValueInteger' (XcmSecUserRole in XCMI Security TC)
--      - (eg, 'systemOperator')
--    * 'deviceHelpDescription'
--      - device help person description
--      - type - (XcmFixedLocaleDisplayString)
--      - data - '...ValueString'
--      - (eg, 'has keys to supplies')
--    * 'deviceHelpLocation'
--      - device help person physical location
--      - type - (XcmFixedLocaleDisplayString)
--      - data - '...ValueString'
--      - (eg, '3rd floor lobby')
--      - see - DPA-1 9.4.3 'Printer-locations'
--    * 'deviceHelpURI'
--      - device help person URI (Uniform Resource Identifier)
--      - (same usage as 'xcmCOInternetHTTPAddressURI' in XCMI CC TC)


--      - type - (XcmFixedLocaleDisplayString)
--      - subtype - '...ValueOID' (protocol in XCMI Comms Config TC)
--      - (eg, 'xcmCOInternetHTTP' (HTTP))
--      - data - '...ValueString'
--      - (eg, 'http://www.foo.com' (HTTP))
--      - see - 'xcmCOInternetHTTPAddressURI' in XCMI Comms Config TC
--      - see - Generic URI Syntax (RFC 2396)
--      - compare - 'system[Protocol|ProtocolDetail' in XCMI Svc Mon TC
--      - compare - 'systemURI' in XCMI Svc Mon TC
--
--      -   Device supported and ready info
--      -   (from ISO 10175 DPA-1 Section 9.4 'Printer Object')
--      -   (see 9.4.74 'Common Printer and Server object attributes')
--    * 'deviceTranslatorSupport'
--      - type - (XcmFixedLocaleDisplayString)
--      - data - '...ValueString'
--      - see - DPA-1 9.4.74.5 'Translators-supported'
--    * 'deviceTranslatorReady'
--      - type - (XcmFixedLocaleDisplayString)
--      - data - '...ValueString'
--      - see - DPA-1 9.4.74.6 'Translators-ready'
--    * 'deviceInitialValueJobSupport'
--      - type - (XcmFixedLocaleDisplayString)
--      - data - '...ValueString'
--      - see - DPA-1 9.4.74.13 'Initial-value-jobs-supported'
--    * 'deviceInitialValueDocSupport'
--      - type - (XcmFixedLocaleDisplayString)
--      - data - '...ValueString'
--      - see - DPA-1 9.4.74.14 'Initial-value-documents-supported'
--    * 'deviceMultipleDocSupport'
--      - type - (TruthValue)
--      - data - '...ValueInteger'
--      - see - DPA-1 9.4.74.3 'Multiple-documents-supported'
--    * 'deviceCancelDocSupport'
--      - type - (TruthValue)
--      - data - '...ValueInteger'
--      - see - DPA-1 9.4.74.4 'Cancel-individual-documents-supported'
--    * 'deviceForeignJobsVisible'
--      - type - (TruthValue)
--      - data - '...ValueInteger'
--      - see - DPA-1 9.4.74.15 'Are-foreign-jobs-visible'
--    * 'deviceInitialValueJobDefault'
--      - type - (XcmFixedLocaleDisplayString)
--      - data - '...ValueString'
--      - see - DPA-1 9.4.12 'Printer-initial-value-job'
--    * 'deviceInitialValueDocDefault'
--      - type - (XcmFixedLocaleDisplayString)
--      - data - '...ValueString'
--      - see - DPA-1 9.4.13 'Printer-initial-value-document'
--    * 'deviceInputMaxSpeedTrafficUnit'
--      - traffic unit of numerator of device input max speed
--      - type - (XcmHrDevTrafficUnit)
--      - data - '...ValueInteger'
--      - see - DPA-1 9.4.7 'Maximum-printer-speed'


--    * 'deviceInputMaxSpeedTimeUnit'
--      - time unit of divisor of device input max speed
--      - type - (XcmHrDevPowerTimeUnit)
--      - data - '...ValueInteger'
--      - see - DPA-1 9.4.7 'Maximum-printer-speed'
--    * 'deviceInputMaxSpeed'
--      - device input max speed
--      - type - (Cardinal32)
--      - data - '...ValueInteger'
--      - see - DPA-1 9.4.7 'Maximum-printer-speed'
--    * 'deviceOutputMaxSpeedTrafficUnit'
--      - traffic unit of numerator of device output max speed
--      - type - (XcmHrDevTrafficUnit)
--      - data - '...ValueInteger'
--      - see - DPA-1 9.4.7 'Maximum-printer-speed'
--    * 'deviceOutputMaxSpeedTimeUnit'
--      - time unit of divisor of device output max speed
--      - type - (XcmHrDevPowerTimeUnit)
--      - data - '...ValueInteger'
--      - see - DPA-1 9.4.7 'Maximum-printer-speed'
--    * 'deviceOutputMaxSpeed'
--      - device output max speed
--      - type - (Cardinal32)
--      - data - '...ValueInteger'
--      - see - DPA-1 9.4.7 'Maximum-printer-speed'
--    * 'deviceFeedResolutionSupport'
--      - type - (Cardinal32) DPI (dots per inch)
--      - data - '...ValueInteger'
--      - see - DPA-1 9.4.8 'Printer-resolutions-supported'
--    * 'deviceXFeedResolutionSupport'
--      - type - (Cardinal32) DPI (dots per inch)
--      - data - '...ValueInteger'
--      - see - DPA-1 9.4.8 'Printer-resolutions-supported'
--    * 'deviceSchedulerSupport'
--      - type - (XcmFixedLocaleDisplayString)
--      - data - '...ValueString'
--      - see - DPA-1 9.4.63 'Schedulers-supported'
--    * 'deviceSchedulerReady'
--      - type - (XcmFixedLocaleDisplayString)
--      - data - '...ValueString'
--      - see - DPA-1 9.4.64 'Scheduler-ready'
--
--      -   Device supported and ready device name info (list)
--    * 'devicePhysicalNameSupport'
--      - type - (XcmFixedLocaleDisplayString)
--      - data - '...ValueString'
--      - see - DPA-1 9.4.10 'Printer-associated-printers'
--      - see - DPA-1 9.5.6 'Physical-printers-supported' (servers)
--    * 'devicePhysicalNameReady'
--      - type - (XcmFixedLocaleDisplayString)
--      - data - '...ValueString'
--      - see - DPA-1 9.4.11 'Printers-ready'
--      - see - DPA-1 9.5.7 'Physical-printers-ready' (servers)
--    * 'deviceLogicalNameSupport'


--      - type - (XcmFixedLocaleDisplayString)
--      - data - '...ValueString'
--      - see - DPA-1 9.4.10 'Printer-associated-printers'
--      - see - DPA-1 9.5.8 'Logical-printers-supported' (servers)
--    * 'deviceLogicalNameReady'
--      - type - (XcmFixedLocaleDisplayString)
--      - data - '...ValueString'
--      - see - DPA-1 9.4.11 'Printers-ready'
--      - see - DPA-1 9.5.9 'Logical-printers-ready' (servers)
--
--      -   Device supported and ready device index info (list)
--    * 'devicePhysicalIndexSupport'
--      - type - (Cardinal32) 'hrDeviceIndex'
--      - data - '...ValueInteger'
--      - see - DPA-1 9.4.10 'Printer-associated-printers'
--      - see - DPA-1 9.5.6 'Physical-printers-supported' (servers)
--    * 'devicePhysicalIndexReady'
--      - type - (Cardinal32) 'hrDeviceIndex'
--      - data - '...ValueInteger'
--      - see - DPA-1 9.4.11 'Printers-ready'
--      - see - DPA-1 9.5.7 'Physical-printers-ready' (servers)
--    * 'deviceLogicalIndexSupport'
--      - type - (Cardinal32) 'hrDeviceIndex'
--      - data - '...ValueInteger'
--      - see - DPA-1 9.4.10 'Printer-associated-printers'
--      - see - DPA-1 9.5.8 'Logical-printers-supported' (servers)
--    * 'deviceLogicalIndexReady'
--      - type - (Cardinal32) 'hrDeviceIndex'
--      - data - '...ValueInteger'
--      - see - DPA-1 9.4.11 'Printers-ready'
--      - see - DPA-1 9.5.9 'Logical-printers-ready' (servers)
--
--      -   Device job service and job history device index info
--    * 'deviceJobServiceDeviceIndex'
--      - device service device index (reference from history device)
--      - type - (Cardinal32) 'hrDeviceIndex'
--      - data - '...ValueInteger'
--      - see - 'xcmHrDevice...' types in XCMI HRX TC
--    * 'deviceJobHistoryDeviceIndex'
--      - device history device index (reference from service device)
--      - type - (Cardinal32) 'hrDeviceIndex'
--      - data - '...ValueInteger'
--      - see - 'xcmHrDevice...History' types in XCMI HRX TC
--
--      -   Device supported and ready font/resource index info (list)
--    * 'deviceFontIndexSupport'
--      - type - (Cardinal32) 'xcmFontIndex' in XCMI Resources MIB
--      - data - '...ValueInteger'
--      - see - DPA-1 9.4.19 'Fonts-supported'
--    * 'deviceFontIndexReady'
--      - type - (Cardinal32) 'xcmFontIndex' in XCMI Resources MIB
--      - data - '...ValueInteger'
--      - see - DPA-1 9.4.20 'Fonts-ready'
--    * 'deviceResourceIndexSupport'


--      - type - (Cardinal32) 'xcmRsrcIndex' in XCMI Resources MIB
--      - data - '...ValueInteger'
--      - see - DPA-1 9.4.21 'Resources-supported'
--    * 'deviceResourceIndexReady'
--      - type - (Cardinal32) 'xcmRsrcIndex' in XCMI Resources MIB
--      - data - '...ValueInteger'
--      - see - DPA-1 9.4.22 'Resources-ready'
--
--      -   Device power management
--    * 'devicePowerModeName'
--      - device power mode administrative name (locale dependent)
--      - type - (XcmFixedLocaleDisplayString)
--      - data - '...ValueString'
--    * 'devicePowerModeType'
--      - device power mode type (locale independent)
--      - type - (XcmHrDevPowerModeType)
--      - data - '...ValueInteger'
--    * 'devicePowerModeDescription'
--      - device power mode description (locale dependent)
--      - type - (XcmFixedLocaleDisplayString)
--      - data - '...ValueString'
--    * 'devicePowerModeSupport'
--      - device power mode support (MAY be used to disable a mode)
--      - type - (PresentOnOff)
--      - data - '...ValueInteger'
--    * 'devicePowerTimeUnit'
--      - device power mode transition time unit (defaults to seconds)
--      - type - (XcmHrDevPowerTimeUnit)
--      - data - '...ValueString'
--    * 'devicePowerWarmerSupport'
--      - device power mode to warmer mode transition support
--      - type - (PresentOnOff)
--      - data - '...ValueInteger'
--    * 'devicePowerCoolerSupport'
--      - device power mode to cooler mode transition support
--      - type - (PresentOnOff)
--      - data - '...ValueInteger'
--    * 'devicePowerWarmerDelay'
--      - device power mode to warmer mode transition delay
--      - (delay after trigger event until transition begins)
--      - type - (XcmHrDevPowerTimeUnit)
--      - data - '...ValueInteger'
--    * 'devicePowerWarmerDuration'
--      - device power mode to warmer mode transition duration
--      - (duration after transition begins until transition completes)
--      - type - (XcmHrDevPowerTimeUnit)
--      - data - '...ValueInteger'
--    * 'devicePowerCoolerDelay'
--      - device power mode to cooler mode transition delay
--      - (delay after trigger event until transition begins)
--      - type - (XcmHrDevPowerTimeUnit)
--      - data - '...ValueInteger'
--    * 'devicePowerCoolerDuration'
--      - device power mode to cooler mode transition duration


--      - (duration after transition begins until transition completes)
--      - type - (XcmHrDevPowerTimeUnit)
--      - data - '...ValueInteger'
--    * 'devicePowerWarmerTrigger'
--      - device warmer mode trigger description
--      - type - (XcmFixedLocaleDisplayString)
--      - data - '...ValueString'
--    * 'devicePowerCoolerTrigger'
--      - device cooler mode trigger description
--      - type - (XcmFixedLocaleDisplayString)
--      - data - '...ValueString'
--    * 'deviceNextWarmerModeIndex'
--      - device next warmer mode pointer (in device details)
--      - type - (Cardinal32) 'xcmHrDevDetailIndex'
--      - data - '...ValueInteger'
--    * 'deviceNextCoolerModeIndex'
--      - device next cooler mode pointer (in device details)
--      - type - (Cardinal32) 'xcmHrDevDetailIndex'
--      - data - '...ValueInteger'
--    * 'deviceEnergyStarSuspendMode'
--      - device (in device details)
--      - type - (Cardinal32) 'xcmHrDevDetailIndex'
--      - data - '...ValueInteger'
--
--      -   Device 'hrDeviceProcessor' details
--    * 'deviceProcessorFrwID'
--      - device firmware ID
--      - type - (ProductID) 'hrProcessorFrwID'
--      - data - '...ValueOID'
--
--      -   Device 'hrDeviceNetwork' details
--    * 'deviceNetworkIfIndex'
--      - device interface index
--      - type - (Cardinal32) 'hrNetworkIfIndex'
--      - data - '...ValueInteger'
--
--      -   Device 'hrDeviceDiskStorage' details
--    * 'deviceDiskStorageAccess'
--      - device disk access
--      - type - (Cardinal32) 'hrDiskStorageAccess'
--      - data - '...ValueInteger'
--    * 'deviceDiskStorageMedia'
--      - device disk media
--      - type - (Cardinal32) 'hrDiskStorageMedia'
--      - data - '...ValueInteger'
--    * 'deviceDiskStorageRemovable'
--      - device removable
--      - type - (Cardinal32) 'hrDiskStorageRemoveble' ('removable')
--      - data - '...ValueInteger'
--    * 'deviceDiskStorageCapacity'
--      - device capacity
--      - type - (Cardinal32) 'hrDiskStorageCapacity'
--      - data - '...ValueInteger'
--


--    * 'deviceMemorySize'
--      - type - (Integer32)
--      - subtype - '. . .ValueString' 
--      - (used to describe the memory and units, eg. 
--         "Embedded Fax Card Memory (Mb)")
--      - data - '. . .ValueInteger'
--
--    * 'deviceConfigurationSetting' 
--      - (used for configuration settings and device defaults) 
--      - UnitClass = classGenOptionValueSyntax(3) 
--      - DetailUnit = integerNumber(3), integerEnum(5), 
--                     integerTruthValue(8), oidObject (9), 
--                     stringDisplay(12) or stringLocalization(13)
--      - data - '. . .ValueInteger' or 
--               '. . .ValueOID' or 
--               '. . .ValueString' 
--               depending on the DetailUnit 
--      - usage: xcmHrDevDetailType or xcmHrDetailType 
--      - when used with xcmHrDevDetailType subtype - '. . .ValueString'
--        can be used as a description when the value is 
--                '. . .ValueInteger' or 
--                '. . .ValueOID' 
--       - when used with xcmHrDetailType, xcmHrDetailDescription 
--         is used for the description 
-- 
--    * 'deviceTimezone'
--      - device timezone
--      - type - (XcmFixedLocaleDisplayString)
--      - data - '...ValueString'
--      - where ValueString is one of the following:
--      - ValueString            Typical Display String
--      - - - - - - -            - - - - - - - - - - - - 
--      - Pacific/Pago_Pago     (GMT -11:00) Midway Island, Niue, Samoa
--      - America/Adak          (GMT -10:00) Adak
--      - Pacific/Honolulu      (GMT -10:00) Cook Islands, Hawaii, Tahit
--      - Pacific/Marquesas     (GMT -09:30) Marquesas Islands
--      - America/Anchorage     (GMT -09:00) Alaska
--      - Pacific/Gambier       (GMT -09:00) Gambier Islands
--      - America/Dawson        (GMT -08:00) Pacific Time (US & Canada)
--      - Pacific/Pitcairn      (GMT -08:00) Pitcairn Islands
--      - America/Tijuana       (GMT -08:00) Tijuana
--      - America/Hermosillo    (GMT -07:00) Arizona, Dawson Creek, 
--      -                                     Sonora
--      - America/Chihuahua     (GMT -07:00) Chihuahhua, Mazatlan
--      - America/Cambridge_Bay (GMT -07:00) Mountain Time (US & Canada)
--      - America/Cancun        (GMT -06:00) Cancun, Mexico City, 
--      -                                     Monterrey
--      - America/Belize        (GMT -06:00) Central America
--      - America/Rainy_River   (GMT -06:00) Central Time (US & Canada)
--      - Pacific/Easter        (GMT -06:00) Easter Island
--      - Pacific/Galapagos     (GMT -06:00) Galapagos Islands
--      - America/Regina        (GMT -06:00) Saskatchewan
--      - America/Atikokan      (GMT -05:00) Atikokan, Resolute
--      - America/Bogota        (GMT -05:00) Bogota, Lima, Panama, Quito


--      - America/Cayman        (GMT -05:00) Cayman Islands, Jamaica, 
--      -                                     Port-au-Prince
--      - America/Detroit       (GMT -05:00) Eastern Time (US & Canada)
--      - America/Grand_Turk    (GMT -05:00) Grand Turk
--      - America/Havana        (GMT -05:00) Havana
--      - America/Caracas       (GMT -04:30) Caracas
--      - America/Asuncion      (GMT -04:00) Asuncion
--      - America/Glace_Bay     (GMT -04:00) Atlantic Time (Canada)
--      - Atlantic/Bermuda      (GMT -04:00) Bermuda
--      - America/Blanc-Sablon  (GMT -04:00) Blanc-Sablon
--      - America/Anguilla      (GMT -04:00) Caribbean Islands
--      - America/Campo_Grande  (GMT -04:00) Cuiaba
--      - America/Boa_Vista     (GMT -04:00) Georgetown, La Paz, Manaus
--      - Antarctica/Palmer     (GMT -04:00) Palmer Archipelago, Santiag
--      - Atlantic/Stanley      (GMT -04:00) Stanley
--      - America/Thule         (GMT -04:00) Thule
--      - America/St_Johns      (GMT -03:30) St. John's
--      - America/Araguaina     (GMT -03:00) Brasilia, Cayenne, 
--      -                                     Paramaribo
--      - America/Argentina/Catamarca   (GMT -03:00) Buenos Aires
--      - America/Godthab       (GMT -03:00) Greenland
--      - America/Miquelon      (GMT -03:00) Miquelon
--      - America/Montevideo    (GMT -03:00) Montevideo
--      - Antarctica/Rothera    (GMT -03:00) Rothera
--      - America/Noronha       (GMT -02:00) Noronha
--      - Atlantic/South_Georgia(GMT -02:00) South Georgia Island
--      - Atlantic/Azores       (GMT -01:00) Azores, Scoresbysund
--      - Atlantic/Cape_Verde   (GMT -01:00) Cape Verde
--      - GMT+0                 Greenwich Mean Time:  DST disabled
--      - America/Danmarkshavn. (GMT+0)
--      - Africa/Abidjan        (GMT 0:00) Accra, Bamako, Dakar, 
--      -                                     Nouakchott
--      - Africa/Casablanca     (GMT) Casablanca
--      - Europe/Dublin         (GMT) Dublin, Edinburgh, Lisbon, London
--      - Atlantic/Reykjavik    (GMT) Reykjavik
--      - Africa/Algiers        (GMT +01:00) Algiers, Douala, Libreville
--      -                                     Luanda
--      - Europe/Amsterdam      (GMT +01:00) Amsterdam, Berlin, Rome, 
--      -                                     Stockholm, Vienna
--      - Europe/Belgrade       (GMT +01:00) Belgrade, Bratislava, 
--      -                                     Budapest, Prague
--      - Europe/Brussels       (GMT +01:00) Brussels, Copenhagen, Madri
--      -                                     Paris
--      - Europe/Warsaw         (GMT +01:00) Sarajevo, Skopje, Warsaw, 
--      -                                     Zagreb
--      - Africa/Tunis          (GMT +01:00) Tunis
--      - Africa/Windhoek       (GMT +01:00) Windhoek
--      - Asia/Amman            (GMT +02:00) Amman
--      - Europe/Athens         (GMT +02:00) Athens, Bucharest, Istanbul
--      - Asia/Beirut           (GMT +02:00) Beirut
--      - Africa/Cairo          (GMT +02:00) Cairo
--      - Asia/Damascus         (GMT +02:00) Damascus
--      - Africa/Harare         (GMT +02:00) Harare, Johannesburg, 
--      -                                     Kinshasa, Tripoli


--      - Europe/Helsinki       (GMT +02:00) Helsinki, Kiev, Riga, Sofia
--      - Asia/Jerusalem        (GMT +02:00) Jerusalem
--      - Europe/Kaliningrad    (GMT +02:00) Kaliningrad, Minsk
--      - Asia/Nicosia          (GMT +02:00) Nicosia
--      - Asia/Gaza             (GMT +02:00) Palestine
--      - Africa/Addis_Ababa    (GMT +03:00) Addis Ababa, Khartoum, 
--      -                                     Mogadishu, Nairobi
--      - Asia/Baghdad          (GMT +03:00) Aden, Baghdad, Qatar, Riyad
--      - Indian/Antananarivo   (GMT +03:00) Antanarivo, Comoro Islands,
--      -                                     Mayotte
--      - Europe/Moscow         (GMT +03:00) Moscow
--      - Antarctica/Syowa      (GMT +03:00) Syowa
--      - Asia/Tehran           (GMT +03:30) Tehran
--      - Asia/Baku             (GMT +04:00) Baku
--      - Asia/Dubai            (GMT +04:00) Dubai, Muscat, Tbilsi
--      - Indian/Mahe           (GMT +04:00) Mahe, Reunion
--      - Indian/Mauritius      (GMT +04:00) Mauritius
--      - Europe/Samara         (GMT +04:00) Samara
--      - Asia/Yerevan          (GMT +04:00) Yerevan
--      - Asia/Kabul            (GMT +04:30) Kabul
--      - Asia/Aqtau            (GMT +05:00) Aqtau, Aqtobe, Ashgabat, 
--      -                                     Samarkand
--      - Asia/Yekaterinburg    (GMT +05:00) Ekaterinburg
--      - Asia/Karachi          (GMT +05:00) Karachi
--      - Indian/Kerguelen      (GMT +05:00) Kerguelen, Maldives
--      - Asia/Colombo          (GMT +05:30) Colombo, Kolkata
--      - Asia/Katmandu         (GMT +05:45) Kathmandu
--      - Asia/Almaty           (GMT +06:00) Almaty, Bishkek, Dhaka, 
--      -                                     Thimphu
--      - Indian/Chagos         (GMT +06:00) Chagos
--      - Antarctica/Mawson     (GMT +06:00) Mawson, Vostok
--      - Asia/Novosibirsk      (GMT +06:00) Novosibirsk, Omsk
--      - Indian/Cocos          (GMT +06:30) Cocos Islands
--      - Asia/Rangoon          (GMT +06:30) Yangon (Rangoon)
--      - Asia/Bangkok          (GMT +07:00) Bankok, Ho Chi Minh, Hovd, 
--      -                                     Jakarta
--      - Indian/Christmas      (GMT +07:00) Christmas Island
--      - Antarctica/Davis      (GMT +07:00) Davis
--      - Asia/Krasnoyarsk      (GMT +07:00)  Krasnoyarsk
--      - Antarctica/Casey      (GMT +08:00) Casey
--      - Asia/Chongqing        (GMT +08:00) Chongqing, Hong Kong, 
--      -                                     Shanghai
--      - Asia/Irkutsk          (GMT +08:00) Irkutsk
--      - Asia/Kuala_Lumpur     (GMT +08:00) Kuala, Lampur, Makassar, 
--      -                                     Manilla, Singapore
--      - Australia/Perth       (GMT +08:00) Perth
--      - Asia/Taipei           (GMT +08:00) Taipei
--      - Asia/Ulaanbaatar      (GMT +08:00) Ulaan Baatar
--      - Australia/Eucla       (GMT +08:45) Eucla
--      - Asia/Dili             (GMT +09:00) Dili, Jayapura
--      - Pacific/Palau         (GMT +09:00) Palau
--      - Asia/Pyongyang        (GMT +09:00) Pyongyang
--      - Asia/Seoul            (GMT +09:00) Seoul
--      - Asia/Tokyo            (GMT +09:00) Tokyo


--      - Asia/Yakutsk          (GMT +09:00) Yakutsk
--      - Australia/Adelaide    (GMT +09:30) Adelaide
--      - Australia/Darwin      (GMT +09:30) Darwin
--      - Australia/Lindeman    (GMT +10:00) Brisbane, Lindeman
--      - Antarctica/DumontDUrville   (GMT +10:00) Dumont d'Urville
--      - Pacific/Guam          (GMT +10:00) Guam, Port Moresby, Saipan
--      - Australia/Currie      (GMT +10:00) Hobart, Melbourne, Sydney
--      - Asia/Vladivostok      (GMT +10:00) Sakhalin, Vladivostok
--      - Australia/Lord_Howe   (GMT +10:30) Lord Howe Island
--      - Pacific/Efate         (GMT +11:00) Efate, Guadalcanal, Kosrae
--      - Asia/Magadan          (GMT +11:00) Magadan
--      - Pacific/Norfolk       (GMT +11:30) Norfolk Island
--      - Asia/Anadyr           (GMT +12:00) Anadyr, Kamchatka
--      - Pacific/Auckland      (GMT +12:00) Auckland
--      - Pacific/Fiji          (GMT +12:00) Fiji, Marshall Islands
--      - Antarctica/McMurdo    (GMT +12:00) McMurdo
--      - Pacific/Chatham       (GMT +12:45) Chatham
--      - Pacific/Tongatapu     (GMT +13:00) Tongatapu
--      - Pacific/Kiritimati    (GMT +14:00) Kiritimati
--      - Additional strings should be submitted to the XMCI editors as 
--      - needed so they can be added to this list of common strings
--      - reference: http://en.wikipedia.org/wiki/Zoneinfo
--
--      -   Device job service timeouts
--
--    * 'deviceJobIncompleteTimeout'
--      - device job incomplete timeout
--      - (delay until job with incomplete input is deleted)
--      - type - (Cardinal32) seconds
--      - data - '...ValueInteger'
--      - (zero=none or 1..n seconds)
--      - see - 'xcmCOInternetLPRJobTimeout' in XCMI CC TC
--      - compare - 'systemJobIncompleteTimeout' in XCMI Svc Mon TC
--    * 'deviceJobProgrammingTimeout'
--      - device job programming timeout
--      - (delay until job programming settings are deleted)
--      - type - (Cardinal32) seconds
--      - data - '...ValueInteger'
--      - (zero=none or 1..n seconds)
--      - see - 'deviceJobIncompleteTimeout' above
--      - compare - 'systemJobProgrammingTimeout' in XCMI Svc Mon TC
--    * 'deviceJobHoldDeleteTimeout'
--      - device job hold until delete timeout
--      - (delay until held job is automatically deleted)
--      - type - (Cardinal32) seconds
--      - data - '...ValueInteger'
--      - (zero=none or 1..n seconds)
--      - see - 'deviceJobIncompleteTimeout' above
--      - see - 'jobPause' in 'XcmSimpleJobMgmtOperation' in XCMI SJM TC
--      - compare - 'systemJobHoldDeleteTimeout' in XCMI Svc Mon TC
--    * 'deviceJobPauseResumeTimeout'
--      - device job pause until resume timeout
--      - (delay until paused job is automatically resumed)
--      - type - (Cardinal32) seconds


--      - data - '...ValueInteger'
--      - (zero=none or 1..n seconds)
--      - see - 'deviceJobIncompleteTimeout' above
--      - see - 'jobPause' in 'XcmSimpleJobMgmtOperation' in XCMI SJM TC
--      - compare - 'systemJobPauseResumeTimeout' in XCMI Svc Mon TC
--
--      -   Device guest/alien job and log full policies
--    * 'deviceGuestJobPolicy'
--      - device policy for jobs with 'guest' (empty) user/account
--      - type - (XcmSecGuestJobPolicy)
--      - data - '...ValueInteger'
--      - see - 'xcmSecServiceGuestJobPolicy' in XCMI Security MIB
--    * 'deviceAlienJobPolicy'
--      - device policy for jobs with 'alien' (invalid) user/account
--      - type - (XcmSecGuestJobPolicy)
--      - data - '...ValueInteger'
--      - see - 'xcmSecServiceAlienJobPolicy' in XCMI Security MIB
--    * 'deviceEventLogFullPolicy'
--      - device policy for handling event log full conditions
--      - type - (XcmGenLogFullPolicy)
--      - data - '...ValueInteger'
--      - see - 'xcmSecServiceEventLogFullPolicy' in XCMI Security MIB
--      - see - DPA-1 9.1.6.8 'Notification-profile' (events)
--      - see - DPA-1 9.4 'Printer Object attributes' (generic)
--    * 'deviceJobLogFullPolicy'
--      - device policy for handling job log full conditions
--      - type - (XcmGenLogFullPolicy)
--      - data - '...ValueInteger'
--      - see - 'xcmSecServiceJobLogFullPolicy' in XCMI Security MIB
--      - see - DPA-1 9.1.6.9 'Logging-profile' (jobs)
--      - see - DPA-1 9.4 'Printer Object attributes' (generic)
--    * 'deviceRequestLogFullPolicy'
--      - device policy for handling request log full conditions
--      - type - (XcmGenLogFullPolicy)
--      - data - '...ValueInteger'
--      - see - 'xcmSecServiceRequestLogFullPolicy' in XCMI Security MIB
--
--      -   Device model info
--    * 'deviceUniversalProductCode'
--      - device UPC (alphanumeric)
--      - type - (XcmFixedLocaleDisplayString)
--      - data - '...ValueString'
--      - see - 'deviceSerialNumber'
--      - see - 'hrDeviceDescr' in IETF HR MIB (RFC 2790)
--    * 'deviceModelName'
--      - device model name (alphanumeric)
--      - type - (XcmFixedLocaleDisplayString)
--      - data - '...ValueString'
--      - see - 'deviceModel' and 'deviceDescription'
--      - see - 'hrDeviceDescr' in IETF HR MIB (RFC 2790)
--      - see - section 9.1.3.1.1 of XCMI HRX TC for mapping and terms
--    * 'deviceModelDescription'
--      - device model description (alphanumeric)
--      - type - (XcmFixedLocaleDisplayString)


--      - data - '...ValueString'
--      - see - 'deviceModel' and 'deviceDescription'
--      - see - 'hrDeviceDescr' in IETF HR MIB (RFC 2790)
--      - see - section 9.1.3.1.1 of XCMI HRX TC for mapping and terms
--    * 'deviceModelNumber'
--      - device model number (alphanumeric)
--      - type - (XcmFixedLocaleDisplayString)
--      - data - '...ValueString'
--      - see - 'deviceModel' and 'deviceDescription'
--      - see - 'hrDeviceDescr' in IETF HR MIB (RFC 2790)
--      - see - section 9.1.3.1.1 of XCMI HRX TC for mapping and terms
--    * 'deviceManufacturerURI'
--      - device manufacturer URI (per RFC 2396)
--      - type - (XcmFixedLocaleDisplayString)
--      - data - '...ValueString'
--      - (eg, 'http://www.xerox.com')
--      - see - 'deviceManufacturer'
--      - see - 'sysContact' in IETF MIB-II (RFC 1213)
--    * 'deviceModelURI'
--      - device model-specific URI (per RFC 2396)
--      - type - (XcmFixedLocaleDisplayString)
--      - data - '...ValueString'
--      - (eg, 'http://www.xerox.com/docucentre/470')
--      - see - 'deviceModel'
--      - see - 'sysContact' in IETF MIB-II (RFC 1213)
--
--      - Service Usage Counters
--      -   Counters which can be used by a billing system to adjust
--      -   deviceLifetimeUsage counters.  These counters are set by
--      -   service to reflect the usage of the machine during the 
--      -   service call which should not be billed separately to the
--      -   customer.
--      -   (several usage counters MAY be defined for a single device)
--      -   (usage counter and service usage groups are defined as shari
--      -   the same value of 'xcmHrDevDetailIndex')
--    * 'deviceServiceUsage'(230)
--      - device lifetime service usage counter (MAY be multi-valued)
--      - type - (Counter32)
--      - subtype - '...ValueString' counter description 
--      - data - '...ValueInteger'
--      - 
--    * 'deviceDeltaServiceUsage'(231)
--      - Delta for the sevice usage counter (MAY be multi-valued)
--      - A SET to xcmHrDevDetailValueInteger.1.231.X will increase
--      - the counter xcmHrDevDetailValueInteger.1.230.X by the amount
--      - of the SET integer.  A GET on the same value will return the
--      - last value set or 0 if there has been no set since reboot.
--      - type - (Counter32)
--      - data - '...ValueInteger'
--      - (eg, monochrome and color page counters)
--      -
--    * 'deviceRolloverValue' (232)
--      - The maximum value of a usage counter before it rolls over.
--      - For example if the counters are 6 digits, then this value 


--      -    should be 999999
--      - If it is a 32 bit integer then this value should be 
--      -     2,147,483,647   (2^31 - 1)
--      - When the counter reaches 999999 (first example) and 1 
--      -     more print is made, then the counter becomes 1 
--      -     (rolls over to 1)
--      -
--    * 'deviceCPMenuControl'
--      - type - (TruthValue)
--      - subtype - '... ValueString' (DisplayString) 
--      - Control Panel Menu Element Name (NVT ASCII string)
--      - data - '...ValueInteger'
--      - 'true' = Menu element is enabled, i.e. element available 
--      -          to the user
--      - 'false' = Menu element is disabled, i.e. element not 
--      -           available to the user
--    * 'deviceUsageWarningThreshold'
--      - (warning when it is estimated that the device cannot hold 
--         more than x units)
--      - (example: scan disk cannot hold more than 10 images)
--      - type (XcmHrDevTrafficUnit)
--      - subtype - '. . .DetailUnitClass' (classHrDevTrafficUnit(9))
--      - subtype - '. . .DetailUnit' 
--         (value from XcmHrDevTrafficUnit enumeration)
--      - subtype - '. . .ValueString' (XcmGenMessageMapStringLabel)
--      - (used to describe the use of this element)
--      - data - ' . . . ValueInteger'
--
--      - Supplies Details
--
--    * 'deviceLifetimeAvgCoverage'
--      - device lifetime average toner/ink coverage (MAY be
--        multi-valued)
--      - Use the values of xcmHrDevDetailIndex is table 22 to report
--        average coverage for different types of jobs.
--      - deviceLifetimeAvgCoverage is grouped with deviceLifetimeUsage 
--        and deviceMaximumLifetimeLimit based on xcmHrDevDetailIndex.
--      - (SHALL NOT be remotely reset)
--      - type - (Counter32)
--      - subtype - '...ValueString' A US English description of the 
--        value.
--      - Localization of the string may be done using 
--        xcmGenMessageTextTable.
--      - data - '...ValueInteger' in 1/1000's of a percent, 
--        i.e. 1% = 1000
--
--    * 'deviceLifeRemainingPercent'
--      - device life remaining in percent of supply (MAY be 
--        multi-valued)
--      - (SHALL NOT be remotely reset, unlike 'deviceAccountingUsage')
--      - type - (Counter32)
--      - subtype - '...ValueString' (XcmGenMessageMapStringLabel)
--      - and (optional) trailing description after whitespace
--      - data - '...ValueInteger'


--      - note - SHOULD be subtyped by well-formed Xerox message
--      - string label of the 'XcmGenMessageMapStringLabel' syntax
--
--    * 'deviceRemainingImpressions'
--      - estimated number of impressions remaining until the supply 
--      - is empty
--      - (SHALL NOT be remotely reset)
--      - type - (Integer32)
--      - subtype - '...UnitClass' classHrDevTrafficUnit(9)
--      - subtype - '...DetailUnit' mediaImpression(27)
--      - subtype - '...ValueString' A US English description of the 
--        value.
--      - data - '...ValueInteger' 
--
--    * 'deviceSuppliesClass'
--      - used for detail attributes of supplies from xcmHrSuppliesTable
--      - similar to prtMarkerSuppliesClass
--      - syntax PrtMarkerSuppliesClassTC
--      - type - integer
--    * 'deviceSupplyUnit'
--      - used for detail attributes of supplies from xcmHrSuppliesTable
--      - similar to prtMarkerSuppliesSupplyUnit
--      - syntax PrtMarkerSuppliesSupplyUnitTC
--      - type - integer
--    * 'deviceSuppliesMaxCapacity'
--      - used for detail attributes of supplies from xcmHrSuppliesTable
--      - similar to prtMarkerSuppliesMaxCapacity
--      - type - integer
--    * 'deviceSuppliesCurrentLevel'
--      - used for detail attributes of supplies from xcmHrSuppliesTable
--      - similar to prtMarkerSuppliesCurrentLevel
--      - type - integer
--
--    * 'deviceInstallDate'
--      - date the device was installed on
--      - type - (DateAndTime)
-- 
--    * 'deviceStatus'
--      - (current status of the device)
--      - (example: black toner needs to be reordered)
--      - type (XcmHrDeviceStatusType) 
--      - data - ' . . . ValueInteger'
--      - subtype - '. . .DetailUnitClass' (classGenOptionValueSyntax(3)
--      - subtype - '. . .DetailUnit' (integerEnum(5))
--      -  (value from XcmHrDeviceStatusType enumeration)
--      - subtype - '. . .ValueString' (XcmGenMessageMapStringLabel)
--      - (used to describe the use of this element)
--
--    * 'deviceFaxCountry'
--      - Fax modem country setting (for example, US, FR, DE)
--      - ISO/IEC 3166:1993 - Codes for the Representation of
--      - Names of Countries
--      - type - (CodedCountry)
--      - data - '...ValueString'


--
--    * 'deviceFaxDialType'
--      - Fax modem dial type
--      - type - (Cardinal32) local enum below
--      - data - '...ValueInteger'
--      - '0' = Tone Dialing
--      - '1' = Pulse Dialing
--
--    * 'deviceInstallationKeyCSVPrintSubmission'
--      - CSV Print Submission for Feature Key enablement 
--      - enable/disable a device's ability to accept a CSV Print 
--          submission for Installation Key.
--      - type - (enable/disable)
--      - read/write
--      - data - '...IntegerTruthValue'

--    * 'deviceFeatureInstallationKeyAvailablity'
--      - Feature Key Installation
--      - Used to determine if a feature Installation Key has been 
--          installed on device
--      - type - (available/unavailable)
--      - read-only
--      - data - '...IntegerTruthValue'

--    * 'deviceFeatureInstallationKeyDisablement'
--      - Feature Key Disablement
--      - Used to determine if a Feature may or may not be disabled 
--          once installed
--      - type - (may be disabled/may NOT be disabled)
--      - read-only
--      - data - '...IntegerTruthValue'

--    * 'deviceFeatureInstallationKeyDate'
--      - Feature Key installation date
--      - Used to view when a Feature using an Installation Key was 
--          installed on a device.
--      - type - (FORMAT (in network byte order, 0-11) = <year, 0-65536>
--               <month, 1-12> <day, 1-31> <hour, 0-23> <minutes, 0-59> 
--               <seconds, 0-60> <deci-seconds, 0-9> <direction from UTC
--               "+" or "-"> <hours from UTC,  
--               0-13> <minutes from UTC, 0-59>)
--      - read-only
--      - data - '...StringLocalization'

    REFERENCE
        "See:   'xcmHrDevDetailUnitClass' and
                'xcmHrDevDetailUnit' for syntax of device detail."
    SYNTAX      INTEGER {
        --  Device other/unknown details
        other(1),
        unknown(2),
        --  Device general info
        deviceName(3),


        deviceAlias(4),
        deviceType(5),
        deviceDescription(6),
        deviceID(7),
        deviceTree(8),
        deviceContext(9),
        deviceManufacturer(10),
        deviceModel(11),
        deviceSerialNumber(12),
        deviceVendor(13),
        deviceVersion(14),
        --  Device service info
        deviceServiceByCustomer(15),
        deviceReplaceByCustomer(16),
        deviceServicePlanName(17),
        deviceServicePlanPassword(18),
        deviceReplaceByWarranty(19),
        --  Device lifetime usage and limits
        deviceLifetimeUsage(20),
        deviceReorderLifetimeLimit(21),
        deviceWarningLifetimeLimit(22),
        deviceReplaceLifetimeLimit(23),
        deviceMaximumLifetimeLimit(24),
        --  Device message to user time remaining
        deviceDaysUntilReorderMsg(25),
        deviceDaysUntilWarningMsg(26),
        deviceDaysUntilReplaceMsg(27),
        deviceDaysUntilMaximumMsg(28),
        deviceLifetimeMsgDisplay(29),
        --  Device accounting usage
        deviceAccountingUsage(30),
        --  Device message to user and reorder dates
        deviceReorderOnDate(31),
        deviceWarningOnDate(32),
        deviceReplaceOnDate(33),
        deviceMaximumOnDate(34),
        --  Device lifetime errors and warnings
        deviceLifetimeErrorCount(35),
        deviceLifetimeErrorLimit(36),
        deviceLifetimeWarningCount(37),
        deviceLifetimeWarningLimit(38),
        --  Device message to user triggers
        deviceTriggerDaysForReorder(41),
        deviceTriggerDaysForWarning(42),
        deviceTriggerDaysForReplace(43),
        deviceTriggerDaysForMaximum(44),
        --  Device message to user dates actually sent
        deviceReorderMsgSentDate(51),
        deviceWarningMsgSentDate(52),
        deviceReplaceMsgSentDate(53),
        deviceMaximumMsgSentDate(54),
        --  Device reorder and replace actual dates
        deviceReorderToVendorDate(55),
        deviceReorderConfirmDate(56),


        deviceReplaceDate(57),
        deviceReplaceSystemUsage(58),
        deviceReplaceWithGeneric(59),
        --  Device help info (contact info)
        deviceHelpName(60),
        deviceHelpAddress(61),
        deviceHelpDescription(62),
        deviceHelpLocation(63),
        deviceHelpURI(64),
        --  Device supported and ready info
        deviceTranslatorSupport(71),
        deviceTranslatorReady(72),
        deviceInitialValueJobSupport(73),
        deviceInitialValueDocSupport(74),
        deviceMultipleDocSupport(75),
        deviceCancelDocSupport(76),
        deviceForeignJobsVisible(77),
        deviceInitialValueJobDefault(78),
        deviceInitialValueDocDefault(79),
        deviceInputMaxSpeedTrafficUnit(80),
        deviceInputMaxSpeedTimeUnit(81),
        deviceInputMaxSpeed(82),
        deviceOutputMaxSpeedTrafficUnit(83),
        deviceOutputMaxSpeedTimeUnit(84),
        deviceOutputMaxSpeed(85),
        deviceFeedResolutionSupport(86),
        deviceXFeedResolutionSupport(87),
        deviceSchedulerSupport(88),
        deviceSchedulerReady(89),
        --  Device supported and ready device name info (list)
        devicePhysicalNameSupport(90),
        devicePhysicalNameReady(91),
        deviceLogicalNameSupport(92),
        deviceLogicalNameReady(93),
        --  Device supported and ready device index info (list)
        devicePhysicalIndexSupport(94),
        devicePhysicalIndexReady(95),
        deviceLogicalIndexSupport(96),
        deviceLogicalIndexReady(97),
        --  Device job service and job history device index info
        deviceJobServiceDeviceIndex(98),
        deviceJobHistoryDeviceIndex(99),
        --  Device supported and ready font/resource index info (list)
        deviceFontIndexSupport(100),
        deviceFontIndexReady(101),
        deviceResourceIndexSupport(102),
        deviceResourceIndexReady(103),
        --  Device power management
        devicePowerModeName(110),
        devicePowerModeType(111),
        devicePowerModeDescription(112),
        devicePowerModeSupport(113),
        devicePowerTimeUnit(114),
        devicePowerWarmerSupport(115),


        devicePowerCoolerSupport(116),
        devicePowerWarmerDelay(117),
        devicePowerWarmerDuration(118),
        devicePowerCoolerDelay(119),
        devicePowerCoolerDuration(120),
        devicePowerWarmerTrigger(121),
        devicePowerCoolerTrigger(122),
        deviceNextWarmerModeIndex(123),
        deviceNextCoolerModeIndex(124),
        -- per Hao Zou Request 8/12/03
        deviceEnergyStarSuspendMode(125),
        --  Device 'hrDeviceProcessor' details
        deviceProcessorFrwID(130),
        --  Device 'hrDeviceNetwork' details
        deviceNetworkIfIndex(140),
        --  Device 'hrDeviceDiskStorage' details
        deviceDiskStorageAccess(160),
        deviceDiskStorageMedia(161),
        deviceDiskStorageRemovable(162),
        deviceDiskStorageCapacity(163),
        -- Device Embedded Fax Card Mb 
        deviceMemorySize(170),
        --  Device configuration settings and defaults 
        deviceConfigurationSetting(180), 
        deviceTimezone(181),
        --  Device job service timeouts
        deviceJobIncompleteTimeout(191),
        deviceJobProgrammingTimeout(192),
        deviceJobHoldDeleteTimeout(193),
        deviceJobPauseResumeTimeout(194),
        --  Device guest/alien job and log full policies
        deviceGuestJobPolicy(200),
        deviceAlienJobPolicy(201),
        deviceEventLogFullPolicy(202),
        deviceJobLogFullPolicy(203),
        deviceRequestLogFullPolicy(204),
        --  Device model info
        deviceUniversalProductCode(210),
        deviceModelName(211),
        deviceModelDescription(212),
        deviceModelNumber(213),
        deviceManufacturerURI(220),
        deviceModelURI(221),
        --  Service Usage counters for billing.
        deviceServiceUsage(230),
        deviceDeltaServiceUsage(231),
        deviceRolloverValue(232),
        --  Control Panel Menu Control
        deviceCPMenuControl(235),
        -- Service Usage Warning
        deviceUsageWarningThreshold(240),
        --  Supplies Details
        deviceLifetimeAvgCoverage(250),
        deviceLifeRemainingPercent(251),


        deviceRemainingImpressions(252),
        deviceSuppliesClass(253),
        deviceSupplyUnit(254),
        deviceSuppliesMaxCapacity(255),
        deviceSuppliesCurrentLevel(256),
        deviceInstallDate(260),
        deviceStatus(270),

        --  Fax Modem Details
        deviceFaxCountry(280),
        deviceFaxDialType(281),

        --  Feature Installation Key Details
        deviceInstallationKeyCSVPrintSubmission(500),
        deviceFeatureInstallationKeyAvailability(501),
        deviceFeatureInstallationKeyDisablement(502),
        deviceFeatureInstallationKeyDate(503)

    }

XcmHrDevDetailUnitClass ::= TEXTUAL-CONVENTION
    STATUS      current
    DESCRIPTION
        "The value unit class of the device detail information specified
        in this conceptual row in the 'xcmHrDevDetailTable'.

        Usage:  Used to select a textual convention for specifying the
        units of this device detail value.

        Usage:  Some of the value unit class enumerations specify that
        the actual unit is REQUIRED to be selected in '...DetailUnit'
        and REQUIRE '...DetailValueString' contains a value in units
        (and are commented as such below).

        Usage:  Some of the value unit class enumerations specify the
        actual unit DIRECTLY and REQUIRE that '...DetailUnit' be zero
        and REQUIRE '...DetailValueString' contains a value in the
        named textual convention (or a bit-mask derived from it)
        (and are commented as such below).

        Usage:  Some of the value unit class enumerations specify that
        '...DetailValueString' SHALL contain a bit-mask which is
        formed via the bit-wise OR of '2**(n)', where (n) is each
        selected enumerated value in the named textual convention.
        (see 'xcmGenBaseSNMPDomainSupport' object in XCMI General MIB)."
    SYNTAX      INTEGER {
        other(1),
        unknown(2),
        --  The following values specify that the actual unit
        --  is REQUIRED to be selected in the '...DetailUnit' object
        --  and REQUIRE '...DetailValueString' contains a value in units
        classGenOptionValueSyntax(3),   -- XcmGenOptionValueSyntax
        --  The following values specify the actual unit
        --  DIRECTLY and REQUIRE that '...DetailUnit' be zero


        --  and REQUIRE '...DetailValueString' contains a value in the
        --  named textual convention (or a bit-mask derived from it)
        classDateAndTime(4),            -- DateAndTime (from SNMPv2-TC)
        classHrDevCalendarDayOfWeek(5), -- XcmHrDevCalendarDayOfWeek
        classHrDevCalendarTimeOfDay(6), -- XcmHrDevCalendarTimeOfDay
        classHrDevMgmtCommandRequest(7),-- XcmHrDevMgmtCommandRequest
        --  The following values specify that the actual unit
        --  is REQUIRED to be selected in the '...DetailUnit' object
        --  and REQUIRE '...DetailValueString' contains a value in units
        classHrDevPowerTimeUnit(8),     -- XcmHrDevPowerTimeUnit
        classHrDevTrafficUnit(9),       -- XcmHrDevTrafficUnit
        --  The following values specify the actual unit
        --  DIRECTLY and REQUIRE that '...DetailUnit' be zero
        --  and REQUIRE '...DetailValueString' contains a value in the
        --  named textual convention (or a bit-mask derived from it)
        classRowPersistence(10),        -- XcmGenRowPersistence
        classRowPersistenceMask(11),    -- XcmGenRowPersistence -> mask
        classLogFullPolicy(12),         -- XcmGenLogFullPolicy
        classLogFullPolicyMask(13),     -- XcmGenLogFullPolicy -> mask
        classHrDevInfoStatus(14),       -- XcmHrDevInfoStatus
        classHrDevInfoStatusMask(15),   -- XcmHrDevInfoStatus -> mask
        classHrDevInfoXStatus(16),      -- XcmHrDevInfoXStatus
        classHrDpaState(17),            -- XcmHrDpaState
        classHrDpaConditions(18),       -- XcmHrDpaConditions
        classHrDpaAvailability(19),     -- XcmHrDpaAvailability
        classHrDpaObjectClassSupport(20), -- XcmHrDpaObjectClassSupport
                                          -- (is already bit-mask)
        classHrDpaJobValidateSupport(21), -- XcmHrDpaJobValidateSupport
                                          -- (is already bit-mask)
        classJMJobState(22),            -- XcmJMJobState
        classJMJobStateMask(23),        -- XcmJMJobState -> mask
        classSecGuestJobPolicy(24),     -- XcmSecGuestJobPolicy
        classSecGuestJobPolicyMask(25), -- XcmSecGuestJobPolicy -> mask
        classSecPosixRights(26),        -- XcmSecPosixRights
                                        -- (is already bit-mask)
        classSecPosixVerbs(27),         -- XcmSecPosixVerbs
                                        -- (is already bit-mask)
        classSvcMonJobConfirmSupport(28), -- XcmSvcMonJobConfirmSupport
                                          -- (is already bit-mask)

        --  The following values specify the actual unit
        --  DIRECTLY and REQUIRE that '...DetailUnit' be zero
        --  and REQUIRE '...DetailValueString' and 
        --  '...DetailValueInteger' contain a bit-mask in the named
        --  textual convention 
        classSvcMonAttachmentPDLSupport(29) 
                                        -- XcmSvcMonAttachmentPDLSupport
                                        -- (is already a bit-mask)
    }


XcmHrDevInfoRealization ::= TEXTUAL-CONVENTION
    STATUS      current
    DESCRIPTION
        "An extended device type (or device 'realization'),
        used by system administrators and end users of this device.

        Usage:  The use of either 'other' or 'unknown' is uninformative
        and SHOULD be avoided by conforming implementations.

      * 'physical' - 'real' device installed on this managed system;
      * 'logical' - 'virtual' device configured on this managed system;
      * 'logicalAndPhysical' - 'combined' device (from ISO DPA ??)."
    REFERENCE
        "See:   'hrDeviceType' in the basic Device Group of the
        IETF Host Resources MIB (RFC 2790).
        See:    Section 9.4 'Printer Object attributes' of ISO DPA
        (Document Printing Application) ISO/IEC 10175 (Final Text, March
        1996) for a discussion of 'printer realizations' of 'physical',
        'logical', and 'logical-and-physical' types (the latter unique
        to DPA)."
    SYNTAX      INTEGER {
        other(1),                       -- other device       
        unknown(2),                     -- unknown device     
        physical(11),                   -- 'real' device
        logical(12),                    -- 'virtual' device
        logicalAndPhysical(13)          -- 'combined' device
    }

XcmHrDevInfoStatus ::= TEXTUAL-CONVENTION
    STATUS      current
    DESCRIPTION
        "The current operational state of the device
        described by this row of the table.  A value
        'unknown(1)' indicates that the current state of the
        device is unknown.  'running(2)' indicates that the
        device is up and running and that no unusual error
        conditions are known.  The 'warning(3)' state
        indicates that agent has been informed of an
        unusual error condition by the operational software
        (eg, a disk device driver) but that the device is
        still 'operational'.  An example would be a high
        number of soft errors on a disk.  A value of
        'testing(4)', indicates that the device is not
        available for use because it is in the testing
        state.  The state of 'down(5)' is used only when the
        agent has been informed that the device is not
        available for any use.

        Usage:  Conforming implementations SHALL NOT 'bubble up' status
        from 'physical' devices to associated 'logical' devices.  All
        devices SHALL report their own status ONLY.

        Usage:  Devices in the 'down' state SHOULD NOT be accepting new
        work (or still processing old work).  Devices in the 'running'


        state SHOULD be prepared to accept new work.

        Usage:  The use of the state 'unknown' is uninformative
        and SHOULD be avoided by conforming implementations.

        Usage:  This is a textual convention representation of the
        'hrDeviceStatus' enumeration in the IETF Host Resources MIB
        (RFC 2790), rewritten from SMIv1 style (RFCs 1155 and 1212) into
        SMIv2 style (RFCs 1902/2578, 1903/2579, and 1904/2580)."
    REFERENCE
        "See:   'hrDeviceStatus' in the basic Device Group of the
        IETF Host Resources MIB (RFC 2790).
        See:    'xcmHrDevInfoXStatus', 'xcmHrDevInfoConditions', and
        'xcmHrDevInfoXConditions' in the Host Resources Extensions MIB."
    SYNTAX      INTEGER {
        unknown(1),                     -- indeterminate      
        running(2),                     -- normally operational, started
        warning(3),                     -- operational, but alert posted
        testing(4),                     -- NOT operational, testing
        down(5)                         -- NOT operational, shutdown
    }

XcmHrDevInfoXStatus ::= TEXTUAL-CONVENTION
    STATUS      current
    DESCRIPTION
        "An extended device status, used by system administrators
        and end users of this device (here, read 'state' for 'status').

        Usage:  Conforming implementations SHALL NOT 'bubble up' status
        from 'physical' devices to associated 'logical' devices.  All
        devices SHALL report their own status ONLY.

        Usage:  Exactly one enumeration of extended device status
        SHALL be defined, with ranges for each basic device type (eg,
        'hrDevicePrinter').  The legal range for extended device status
        for a given device type (either defined by RFC 2790 or by this
        MIB) is found by multiplying the final arc of the the device
        type OID by 100 - the result is the device specific range base -
        the end of the device specific range is 99 larger.  These device
        specific extended device status values SHALL be reissued
        periodically in the 'XcmHrDevInfoXStatus' textual convention."
    REFERENCE
        "See:   Section 9.4.9 'Printer-state' of ISO DPA
        (Document Printing Application) ISO/IEC 10175 (Final Text,
        18 May 1995) for a discussion of the printer states used here.
        Note that the DPA state 'connecting-to-printer' has no meaning
        in the context of a 'physical' printer device, but only in the
        context of an intermediate DP-Server presenting a 'logical'
        printer device.
        See:    'hrPrinterStatus' and 'hrPrinterDetectedErrorState' in
        the IETF Host Resources MIB (RFC 2790) for related discussion.

        See:    'hrDeviceStatus' in the basic Device Group of the
        IETF Host Resources MIB (RFC 2790).


        See:    'xcmHrDevInfoConditions' and 'xcmHrDevInfoXConditions'
        in the Host Resources Extensions MIB."
    SYNTAX      INTEGER {
        --  Common extended device status
        commonNone(0),
        commonOther(1),
        commonUnknown(2),
        commonLast(99),

        --  'hrDeviceOther'
        otherNone(100),

        --  'hrDeviceUnknown'
        unknownNone(200),

        --  'hrDeviceProcessor'
        processorNone(300),

        --  'hrDeviceNetwork'
        networkNone(400),

        --  'hrDevicePrinter'
        --  See:    Section 9.4.9 'Printer-state' of ISO/IEC 10175
        --          (was on page 185 in earlier text, May 1995)
        --  See:    'id-val-printer-state-...' in Annex A of ISO/IEC
        --          10175 (was on page 307 in earlier text, May 1995)
        --  If 'dpaPrinterStateFinalArc' is truncated from an OID
        --  'id-val-printer-state-...' in Annex A of ISO/IEC 10175
        --  and 'xcmiPrinterStatus' is the corresponding enum value of
        --  'printer...' in 'XcmHrDevInfoXStatus' (below),
        --  then:
        --      xcmiPrinterStatus = (dpaPrinterStateFinalArc + 502)
        printerNone(500),               -- XCMI extension to ISO DPA
        printerOther(501),              -- XCMI extension to ISO DPA
        printerUnknown(502),            -- unknown or indeterminate
        printerIdle(503),               -- ready to accept jobs
        printerPrinting(504),           -- currently printing a job
        printerNeedsAttention(505),     -- needs general human attention
        printerPaused(506),             -- paused by user or operator
        printerShutdown(507),           -- taken out of service
        printerJobStartWait(508),       -- see ISO DPA 'job-start-wait'
        printerJobEndWait(509),         -- see ISO DPA 'job-end-wait'
        printerNeedsKeyOperator(510),   -- needs toner, developer, etc
        printerJobPasswordWait(511),    -- see ISO DPA 'job-password'
        printerTimedOut(512),           -- ISO DPA Servers only
        printerConnectingToPrinter(513),-- ISO DPA Servers only

        --  'hrDeviceDiskStorage'
        diskStorageNone(600),

        --  'hrDeviceVideo'
        videoNone(1000),

        --  'hrDeviceAudio'


        audioNone(1100),

        --  'hrDeviceCoprocessor'
        coprocessorNone(1200),

        --  'hrDeviceKeyboard'
        keyboardNone(1300),

        --  'hrDeviceModem'
        modemNone(1400),

        --  'hrDeviceParallelPort'
        parallelPortNone(1500),

        --  'hrDevicePointing'
        pointingNone(1600),

        --  'hrDeviceSerialPort'
        serialPortNone(1700),

        --  'hrDeviceTape'
        tapeNone(1800),

        --  'hrDeviceClock'
        clockNone(1900),

        --  'hrDeviceVolatileMemory'
        volatileMemoryNone(2000),

        --  'hrDeviceNonVolatileMemory'
        nonVolatileMemoryNone(2100),

        --  'xcmHrDeviceHostSystem'
        hostSystemNone(10100),

        --  'xcmHrDeviceScanner'
        scannerNone(10200),

        --  'xcmHrDeviceCopier'
        copierNone(10300),

        --  'xcmHrDeviceFax'
        faxNone(10400),

        --  'xcmHrDeviceMailbox'
        mailboxNone(10500),

        --  'xcmHrDeviceMarker'
        markerNone(11100),

        --  'xcmHrDeviceFinisherBFM'
        finisherBFMNone(11200),

        --  'xcmHrDeviceFinisherMFF'


        finisherMFFNone(11300),

        --  'xcmHrDeviceFinisherXIM'
        finisherXIMNone(11400),

        --  'xcmHrDeviceFinisher3rdParty'
        finisher3rdPartyNone(11500),

        --  'xcmHrDevicePaymentInterface'
        paymentInterfaceNone(11600),

        --  'xcmHrDeviceInterposer'
        interposerNone(11700),

        --  'xcmHrDeviceInternetFax'
        internetFaxNone(11800),

        --  'xcmHrDeviceServerFax'
        serverFaxNone(11900),

        --  'xcmHrDeviceEmbeddedFax'
        embeddedFaxNone(12000),

 -- 'xcmHrDeviceForeignInterface' 
 foreignInterfaceNone(12100),

        -- 'xcmHrDeviceSecurityInterface' 
        securityInterfaceNone(12200),

        -- 'xcmHrDeviceAccountingInterface' 
        accountingInterfaceNone(12300), 

        --  'xcmHrCru...' - Customer Replaceable Units
        cruNone(20000),                 -- CRU no status
        cruOther(20001),                -- CRU other status
        cruUnknown(20002),              -- CRU unknown status
        cruReady(20003),                -- CRU OK (normal wear)
        cruReorder(20004),              -- CRU should be reordered
        cruReplace(20005),              -- CRU should be replaced
        cruFault(20006),                -- CRU has one or more faults

        reserved(40000)                 -- placeholder
    }

XcmHrDevInfoConditions ::= TEXTUAL-CONVENTION
    STATUS      current
    DESCRIPTION
        "A relatively generic description of the current 'conditions'
        of this device, specified in a bit-mask.

              1 : startupInProgress             -- 2**0
              2 : resetWarningInProgresss       -- 2**1       (optional)
              4 : testInProgress                -- 2**2
              8 : shutdownInProgress            -- 2**3       (optional)


             16 : quiesceInProgress             -- 2**4       (optional)
             32 : resetCountersInProgress       -- 2**5       (optional)
             64 : resetWarmInProgress           -- 2**6
            128 : resetColdInProgress           -- 2**7
            256 : resetFactoryInProgress        -- 2**8
            512 : flushInputInProgress          -- 2**9
           1024 : flushOutputInProgress         -- 2**10
           2048 : flushInOutInProgress          -- 2**11
           4096 : manageInProgress              -- 2**12      (optional)

        The above basic 'conditions' record the original intent of the
        current command, when it results in delayed state transitions
        before arriving at the 'target' state.  They augment the state
        information available from 'hrDeviceStatus'.

           8192 : warmUpDelayInProgress         -- 2**13      (optional)
          16384 : warmUpCycleInProgress         -- 2**14      (optional)
          32768 : readyMode                     -- 2**15      (optional)
          65536 : coolDownDelayInProgress       -- 2**16      (optional)
         131072 : coolDownCycleInProgress       -- 2**17      (optional)
         262144 : standbyMode                   -- 2**18      (optional)
         524288 : energySaveDelayInProgress     -- 2**19      (optional)
        1048576 : energySaveCycleInProgress     -- 2**20      (optional)
        2097152 : sleepMode                     -- 2**21      (optional)
        4194304 : wakeUpDelayInProgress         -- 2**22      (optional)
        8388608 : wakeUpCycleInProgress         -- 2**23      (optional)
       16777216 : powerToReadyInProgress        -- 2**24      (optional)
       33554432 : powerToStandbyInProgress      -- 2**25      (optional)
       67108864 : powerToSleepInProgress        -- 2**26      (optional)

        The above optional 'conditions' record the progress of device
        'warm up', 'cool down', 'energy save', and 'wake up' power mgmt
        cycles and also define the device 'readyMode', 'standbyMode',
        and 'sleepMode' qualifiers to the generic 'hrDeviceStatus' of
        'running(2)', 'warning(3)', or 'testing(4)' (but NOT 'down(5)').
        See the power management cycle feature support and feature time
        objects in the Device Power Group of the Host Resources Ext MIB.

        Usage:  It is desirable that the implementor report 'conditions'
        of all devices corresponding to conceptual rows in the
        'hrDeviceTable' as accurately as feasible.  'Conditions' occur
        within or across 'states' in a finite state machine (FSM)
        implementation of a device.  They represent both short term and
        long term conditions.

        Usage:  A device with 'hrDeviceStatus' of 'running(2)' might
        have 'xcmHrDevInfoConditions' of 'quiesceInProgress', indicating
        that the device will soon transition to 'hrDeviceStatus' of
        'down(5)'.

        Usage:  A multi-bit example of 'xcmHrDevInfoConditions' is
        'quiesceInProgress' concurrently with 'standbyMode', ie, the
        device has previously 'cooled down' and will soon transition
        from 'hrDeviceStatus' of 'running(2)' to 'down(5)'."


    REFERENCE
        "See:   'hrDeviceStatus' in the basic Device Group of the
        IETF Host Resources MIB (RFC 2790).
        See:    'xcmHrDevInfoXStatus' and 'xcmHrDevInfoXConditions'
        in the Host Resources Extensions MIB."
    SYNTAX      INTEGER (0..2147483647)  -- biggest int = 2**31-1

XcmHrDevInfoXConditions ::= TEXTUAL-CONVENTION
    STATUS      current
    DESCRIPTION
        "A device specific description of the extended 'conditions'
        of this device, specified in a bit-mask.

        Usage:  For FUTURE expansion.

        Usage:  Exactly one bit mask of extended device conditions SHALL
        be defined for each basic device type (eg, 'hrDevicePrinter').
        These device specific extended device conditions values SHALL be
        reissued periodically in the 'XcmHrDevInfoXConditions' textual
        convention.  These device specific extended device conditions
        are mutually exclusive and 'overloaded' in the single reporting
        object 'xcmHrDevInfoXConditions'."
    REFERENCE
        "See:   'hrDeviceStatus' in the basic Device Group of the
        IETF Host Resources MIB (RFC 2790).
        See:    'xcmHrDevInfoXStatus' and 'xcmHrDevInfoConditions'
        in the Host Resources Extensions MIB."
    SYNTAX      INTEGER (0..2147483647)  -- biggest int = 2**31-1

XcmHrDeviceStatusType ::= TEXTUAL-CONVENTION
    STATUS      current
    DESCRIPTION
        "Used to describe the device status.

        Usage: used in xcmHrDetailTable for supplies.
        Required because supplies are not in the
        hrDeviceTable and therefore hrDeviceStatus
        cannot be used.

        Modeled after hrDeviceStatus where 2=running, 
        3=warning and 5=down."
    SYNTAX      INTEGER {
        unknown(1),
        ok(2),
        supplyReorder(3), 
        supplyReplace(5),
 supplyMissing(6)
    }  


XcmHrDevMgmtCommandRequest ::= TEXTUAL-CONVENTION
    STATUS      current
    DESCRIPTION
        "A write of this type by an (authorized) management station
        invokes a command for this device.
        A read of this type always returns the command currently in
        progress or last completed.
        It is mandatory that a conforming management agent ensure that
        the contents of this object remain 'in bounds' - an undefined
        value SHALL be replaced by 'none' - ie, although rejected with
        error in the SetResponse PDU, this object SHALL NOT contain any
        such undefined value.  At system initialization, this object
        SHALL contain 'none'.

      * 'none' - NO action(s) SHALL be taken, except to clear
        '...CommandData' and set '...CommandStatus' to 'noError'.
      * 'test' or 'manage' - the associated '...CommandData' object
        SHOULD/SHALL be specified in the same SetRequest PDU.
      * all other commands - the associated '...CommandData' object
        MAY be specified in the same SetRequest PDU.
      * 'startup', 'resetWarm', 'resetCold', or 'resetFactory' - the
        final state SHALL be 'running' (after cycle completes) - the
        sequence of states SHOULD be 'down' -> 'testing' -> 'running' -
        the final power mode SHALL be 'ready'.
      * 'startup' - this device SHALL transition from the 'down' state
        to the 'running' state and 'ready' power mode.
      * 'resetWarning' - this device SHALL transition from the 'warning'
        state to the 'running' state (because a management station has
        acknowledged the management agent's previous warning).
      * 'test' - this device SHALL transition immediately (ie, without
        attempting graceful quiesce) to the 'testing' state; it is a
        local matter (ie, device specific) how this command is
        processed; however, '...CommandData' SHOULD be specified.
      * 'shutdown' - this device SHALL transition immediately (ie,
        without attempting graceful quiesce) to the 'down' state and
        'off' power mode.
      * 'quiesce' - this device MAY transition gracefully to the 'down'
        state, or it MAY choose to treat a 'quiesce' as 'shutdown'.
      * 'resetCounters' - all device counters SHALL be reset to zero and
        the device SHALL remain in the same state and power mode.
      * 'resetWarm' - a device 'warm restart' SHALL be performed (ie,
        without a power cycle reset).
      * 'resetCold' - a device 'cold restart' SHALL be performed (ie,
        with a power cycle reset).
      * 'resetFactory' - all factory defaults SHALL be restored, and a
        device 'cold restart' SHALL be performed (ie, with a power cycle
        reset).
      * 'flushInput' - all device input (in progress or internally
        queued) SHALL be gracefully flushed.
      * 'flushOutput' - all device output (in progress or internally
        queued) SHALL be gracefully flushed.
      * 'flushInOut' - all device input and output output (in progress
        or internally queued) SHALL be gracefully flushed.
      * 'manage' - it is a local matter (ie, device specific) how this


        command is processed; however, '...CommandData' SHALL be
        specified.
      * 'refresh' - the device SHALL promptly read all of its manageable
        configuration parameters, but SHALL NOT perform a reset.
      * 'warmUp' - the device SHALL transition from the 'standby' mode
        to the 'ready' mode - invalid from any other power mode
        (optional command for remote device power management).
      * 'coolDown' - the device SHALL transition from the 'ready' mode
        to the 'standby' mode - invalid from any other power mode
        (optional command for remote device power management).
      * 'energySave' - the device SHALL transition from the 'standby'
        mode to the 'sleep' mode - invalid from any other power mode
        (optional command for remote device power management).
      * 'wakeUp' - the device SHALL transition from the 'sleep'
        mode to the 'standby' mode - invalid from any other power mode
        (optional command for remote device power management).
      * 'powerToReady' - the device SHALL transition from the 'standby'
        mode or the 'sleep' mode to the 'ready' mode
        (optional command for remote device power management).
      * 'powerToStandby' - the device SHALL transition from the 'ready'
        mode or the 'sleep' mode to the 'standby' mode
        (optional command for remote device power management).
      * 'powerToSleep' - the device SHALL transition from the 'ready'
        mode or the 'standby' mode to the 'sleep' mode
        (optional command for remote device power management).

        Note:   All of the POSIX and XCMI device level operations are
        taken from the POSIX System Admin std (IEEE 1387.4) and aligned
        with the high-end XCMI System Admin MIB."
    REFERENCE
        "See:   'dot5Commands' in IEEE 802.5 Token Ring MIB (RFC 1748)
        and 'hrDeviceStatus' in IETF Host Resources MIB (RFC 2790).
        Compare:    'ifOperStatus' (current) and 'ifAdminStatus'
        (desired) in the Interfaces Group of IETF MIB-II (RFC 1213);
        'RowStatus' textual convention in IETF SMIv2 (RFC 1902/2578).

        See:    Section 4 'Print Utilities' (pages 71 to 212) of
                POSIX Sys Admin (IEEE 1387.4 / Draft 8, October 1994).
        See:    OBJECT clause in MODULE-COMPLIANCE macro of
                XCMI Ext to Host Resources MIB, for compliance info.
        See:    Section 3.4 'XCMI Standard Tagged Management Data' and
                Section 3.5 'Simple Device Management Requests' in
                XCMI Ext to Host Resources TC.
        See:    Section 3.5.3 'Secure Simple Device Mgmt Requests' in
                XCMI Security TC."
    SYNTAX      INTEGER {
        none(1),                        -- no operation
        startup(2),                     -- to 'running'
        resetWarning(3),                -- from 'warning' to 'running'
        test(4),                        -- to 'testing' immediately
        shutdown(5),                    -- to 'down' immediately
        quiesce(6),                     -- to 'down' gracefully
        resetCounters(7),               -- reset all device counters
        resetWarm(8),                   -- warm restart to 'running'


        resetCold(9),                   -- cold restart to 'running'
        resetFactory(10),               -- factory defaults cold restart
        flushInput(11),                 -- flush all input
        flushOutput(12),                -- flush all output
        flushInOut(13),                 -- flush all input and output
        manage(14),                     -- manage command, any state
        refresh(15),                    -- refresh device w/out reset
        warmUp(16),                     -- 'standby' to 'ready' ONLY
        coolDown(17),                   -- 'ready' to 'standby' ONLY
        energySave(18),                 -- 'standby' to 'sleep' ONLY
        wakeUp(19),                     -- 'sleep' to 'standby' ONLY
        powerToReady(20),               -- 'standby|sleep' to 'ready'
        powerToStandby(21),             -- 'ready|sleep' to 'standby'
        powerToSleep(22),               -- 'ready|standby' to 'sleep'
        --  POSIX - Device level operations (on host system)
        deviceCreate(1301),             -- 'pdcreate' (create device)
        deviceDelete(1302),             -- 'pddelete' (delete device)
        deviceList(1303),               -- 'pdls' (list attributes)
        deviceSet(1304),                -- 'pdset' (set attributes)
        deviceClean(1305),              -- 'pdclean' (remove all jobs)
        deviceDisable(1306),            -- 'pddisable' (stop new jobs)
        deviceEnable(1307),             -- 'pdenable' (allow new jobs)
        devicePause(1308),              -- 'pdpause' (pause device)
        deviceResume(1309),             -- 'pdresume' (resume device)
        deviceShutdown(1310),           -- 'pdshutdown' (end device)
        deviceQueueList(1311),          -- 'pdq' (list device job queue)
        deviceJobCreate(1312),          -- 'pdpr' (submit job to device)
        --  XCMI - Device level extensions (on host system)
        deviceManage(2301),             -- manage device object(s)
        deviceRestart(2302),            -- restart device
        deviceInstall(2321),            -- install device object(s)
        deviceUpgrade(2322),            -- upgrade device object(s)
        deviceBackup(2323),             -- backup device object(s)
        deviceRestore(2324),            -- restore device object(s)
        deviceConfigure(2325),          -- configure device object(s)
        deviceDiagnose(2326),           -- diagnose device object(s)
        deviceResetCounters(2331),      -- reset device counters
        deviceResetWarm(2332),          -- warm reset (no power cycle)
        deviceResetCold(2333),          -- cold reset (w/ power cycle)
        deviceResetFactory(2334),       -- factory defaults reset
        deviceFormat(2335),             -- format device (storage)
        deviceRefresh(2336),            -- refresh device (comms)
        deviceLogin(2341),              -- login w/ authentication
        deviceLogout(2342),             -- logout w/ authentication
        deviceDiskOverwrite(2343),      -- disk overwrite for security 
        --  POSIX - Entity level operations (on host system)
        entityCreate(1901),             -- 'pdcreate' (create entity)
        entityDelete(1902),             -- 'pddelete' (delete entity)
        entityList(1903),               -- 'pdls' (list attributes)
        entitySet(1904),                -- 'pdset' (set attributes)
        entityClean(1905),              -- 'pdclean' (remove all jobs)
        entityDisable(1906),            -- 'pddisable' (stop new jobs)
        entityEnable(1907),             -- 'pdenable' (allow new jobs)
        entityPause(1908),              -- 'pdpause' (pause entity)


        entityResume(1909),             -- 'pdresume' (resume entity)
        entityShutdown(1910),           -- 'pdshutdown' (end entity)
        entityQueueList(1911),          -- 'pdq' (list entity job queue)
        entityJobCreate(1912),          -- 'pdpr' (submit job to entity)
        --  XCMI - Entity level extensions (on host system)
        entityManage(2901),             -- manage entity object(s)
        entityRestart(2902),            -- restart entity
        entityInstall(2921),            -- install entity object(s)
        entityUpgrade(2922),            -- upgrade entity object(s)
        entityBackup(2923),             -- backup entity object(s)
        entityRestore(2924),            -- restore entity object(s)
        entityConfigure(2925),          -- configure entity object(s)
        entityDiagnose(2926),           -- diagnose entity object(s)
        entityResetCounters(2931),      -- reset entity counters
        entityResetWarm(2932),          -- warm reset (no power cycle)
        entityResetCold(2933),          -- cold reset (w/ power cycle)
        entityResetFactory(2934),       -- factory defaults reset
        entityFormat(2935),             -- format entity (storage)
        entityRefresh(2936),            -- refresh entity (comms)
        entityLogin(2941),              -- login w/ authentication
        entityLogout(2942)              -- logout w/ authentication
    }

XcmHrDevMgmtCommandData ::= TEXTUAL-CONVENTION
    STATUS      current
    DESCRIPTION
        "A write of this type specifies:  a) a 'test' command subtype
        and any accompanying 'test' device specific data; or b) a
        'manage' command subtype and any accompanying 'manage' device
        specific data; or c) device specific data accompanying any
        other command.
        A read of this type always returns the data (if any) which
        accompanied the current or last completed command."
    REFERENCE
        "See:   Section 4 'Print Utilities' (pages 71 to 212) of
                POSIX Sys Admin (IEEE 1387.4 / Draft 8, October 1994).
        See:    'hrDeviceStatus' in the Device group of the
                IETF Host Resources MIB (RFC 2790).
        See:    Section 3.4 'XCMI Standard Tagged Management Data' and
                Section 3.5 'Simple Device Management Requests' in
                XCMI Ext to Host Resources TC.
        See:    Section 3.5.3 'Secure Simple Device Mgmt Requests' in
                XCMI Security TC."
    SYNTAX      OCTET STRING (SIZE (0..255))

XcmHrDevMgmtCommandDataTag ::= TEXTUAL-CONVENTION
    STATUS      current
    DESCRIPTION
        "XCMI device management commands are passed as enumerated types
        in 'xcmHrDevMgmtCommandRequest' in the XCMI HRX MIB.
        Other XCMI management commands are passed as enumerated types in
        'xcmCommsMgmtCommandRequest', 'xcmSimpleJobMgmtOperation', etc,
        in the XCMI Comms Engine, Simple Job Mgmt, and other MIBs.


        XCMI management commands MAY also require one or more arguments
        (in addition to any specific variable bindings of MIB objects).
        Required arguments are passed as 'tagged string arguments' in
        'xcmHrDevMgmtCommandData', 'xcmSimpleJobMgmtData', etc.
        Each 'tagged string argument' substring is of the form:

            'TT=value:'

        where:
            'TT'        two-character 'tag', naming argument type
            '='         literal equal sign, beginning argument value
            'value'     human-readable string, encoding argument value
            ':'         literal colon, terminating argument value

        XCMI conforming management stations SHALL terminate ALL
        'tagged string argument' substrings properly with colon (':').

        XCMI standard 'tagged string arguments' MAY pass colon (':')
        in their 'value' by escaping it with backslash ('\').  XCMI
        conforming management agents SHALL interpret backslash
        followed by ANY other character as the literal value of the
        second character (ie, backslash is permitted, and is NOT
        restricted to certain following characters).

        XCMI standard 'tags' for data in 'tagged string arguments',
        (in 'xcmHrDevMgmtCommandData', 'xcmSimpleJobMgmtData', etc)
        are as follows:

        --  Generic Data (no object mapping to MIBs)
        --  For domain-specific future extensions to operations
      * SC  [Sub-Command - domain-specific, must be FIRST tag present]
        --  syntax 'XcmFixedLocaleDisplayString (SIZE (0..255))'
        --  domain-specific sub-command for management request
        --  passed in fixed locale (see 'xcmGenFixedLocalizationIndex')
        --  passed as character string, NOT as binary value

        --  For generic access to any IETF or XCMI defined objects
      * OI  [Object Identifier - no object mapping]
        --  syntax 'OBJECT IDENTIFIER'
        --  object identifier of object (WITHOUT instance qualifiers)
        --  passed as dotted decimal OID or as object label
        --  (eg, 'hrDeviceID'), NOT as binary object identifier

      * OV  [Object Value - no object mapping]
        --  syntax 'XcmFixedLocaleDisplayString (SIZE (0..255))'
        --  object value of object
        --  passed as character string, NOT as binary value
        --  passed in fixed locale (see 'xcmGenFixedLocalizationIndex')

        --  For protection against 'replay' attacks
      * DT  [Date and Time - no object mapping]
        --  (see 'hrSystemDate' in System group of IETF HR MIB)
        --  syntax 'DateAndTime'


        --  date and time stamp for management request
        --  passed as dotted decimal string (ie, 'yyyy.mm.dd.hh.mm.ss'),
        --  NOT as binary value

      * NI  [Noise Information - no object mapping]
        --  syntax 'XcmFixedLocaleDisplayString (SIZE (0..255))'
        --  arbitrary noise info for management request
        --  passed as hexadecimal string, NOT as binary value

      * SI  [Sequence Identifier - no object mapping]
        --  syntax 'Ordinal32'
        --  sequence ID for management request (for 'secure streams')
        --  passed as decimal string, NOT as binary value

        --  Security Data from XCMI Security MIB (63sec)
        --  For account-based authentication
      * AI  'xcmSecAccountIndex'
        --  syntax 'Ordinal32'
        --  index of account (ie, account ID)
        --  passed as decimal string, NOT as binary value

      * AN  'xcmSecAccountName'
        --  syntax 'XcmFixedLocaleDisplayString (SIZE (0..255))'
        --  human-readable name of account (ie, account label)
        --  passed in fixed locale (see 'xcmGenFixedLocalizationIndex')

      * AC  'xcmSecAccountPasscode'
        --  syntax 'XcmFixedLocaleDisplayString (SIZE (0..255))'
        --  protected numeric password of account
        --  passed as hexadecimal string, NOT as binary value
        --  (protected text form, NOT cleartext password)

      * AW  'xcmSecAccountPassword'
        --  syntax 'XcmFixedLocaleDisplayString (SIZE (0..255))'
        --  protected alphanumeric password of account
        --  passed as hexadecimal string, NOT as binary value
        --  (protected text form, NOT cleartext password)

        --  For user-based authentication
      * UI  'xcmSecUserIndex'
        --  syntax 'Ordinal32'
        --  index of user (ie, user ID)
        --  passed as decimal string, NOT as binary value

      * UN  'xcmSecUserName'
        --  syntax 'XcmFixedLocaleDisplayString (SIZE (0..255))'
        --  human-readable name of user (ie, user label)
        --  passed in fixed locale (see 'xcmGenFixedLocalizationIndex')

      * UC  'xcmSecUserPasscode'
        --  syntax 'XcmFixedLocaleDisplayString (SIZE (0..255))'
        --  protected numeric password of user
        --  passed as hexadecimal string, NOT as binary value
        --  (protected text form, NOT cleartext password)


      * UW  'xcmSecUserPassword'
        --  syntax 'XcmFixedLocaleDisplayString (SIZE (0..255))'
        --  protected alphanumeric password of user
        --  passed as hexadecimal string, NOT as binary value
        --  (protected text form, NOT cleartext password)

        --  System group of IETF MIB-II (RFC 1213)
      * ZD  'sysDescr'
        --  syntax 'DisplayString (SIZE (0..255))'
        --  (NVT ASCII string)
        --  textual description of host system, 
        --  passed as ASCII string, NOT as localized string
        --  (see XCMI MIB Implementer's Guide for the format
        --   of sysDescr).
        --  (see 'hrDeviceDescr' of type 'DisplayString' in IETF HR MIB)

      * ZI  'sysObjectID'
        --  syntax 'OBJECT IDENTIFIER'
        --  product ID of host system
        --  passed as dotted decimal OID or as system product ID label
        --  (eg, 'xcmPidStarship20'), NOT as binary object identifier
        --  (see 'hrDeviceID' of type 'ProductID' in IETF HR MIB)

      * ZS  'sysServices'
        --  syntax 'INTEGER (0..127)'
        --  bit-mask of services host system offers
        --  passed as decimal string, NOT as binary value

        --  Interface group of IETF MIB-II (RFC 1213)
      * IX  'ifIndex'
        --  syntax 'INTEGER (1..2147483647)'
        --  index of host system interface conceptual row
        --  (REQUIRED for 'entityCreate')
        --  passed as decimal string, NOT as binary index

      * ID  'ifDescr'
        --  syntax 'DisplayString (SIZE (0..255))'
        --  (NVT ASCII string)
        --  textual description of host system interface,
        --  including manufacturer, product name, version of hardware

      * IY  'ifType'
        --  syntax 'INTEGER (1..2147483647)' (enumeration)
        --  (see 'IANAifType' textual convention in 'IANAifType-MIB')
        --  type of host system interface
        --  passed as decimal string or as interface type enum label
        --  (eg, 'iso88025-tokenRing'), NOT as binary value

      * IM  'ifMtu'
        --  syntax 'INTEGER (0..2147483647)'
        --  max transmission unit (datagram) on host system interface
        --  passed as decimal string, NOT as binary value


      * IS  'ifSpeed'
        --  syntax 'INTEGER (0..2147483647)'
        --  speed (bits/second) of host system interface
        --  passed as decimal string, NOT as binary value

      * IP  'ifPhysAddress'
        --  syntax 'PhysAddress'
        --  physical address of host system interface
        --  passed as hexadecimal string, NOT as binary value

      * IZ  'ifSpecific'
        --  syntax 'OBJECT IDENTIFIER'
        --  reference to media-specific MIB for host system interface
        --  passed as dotted decimal OID or as media-specific MIB label
        --  (eg, 'EtherLike-MIB'), NOT as binary value

        --  System group of IETF HR MIB (RFC 2790)
      * ZA  'hrSystemDate'
        --  syntax 'DateAndTime'
        --  local date and time on host system
        --  passed as dotted decimal string (ie, 'yyyy.mm.dd.hh.mm.ss'),
        --  NOT as binary value

      * ZL  'hrSystemInitialLoadDevice'
        --  syntax 'INTEGER (1..2147483647)'
        --  (see 'hrDeviceIndex' in IETF HR MIB)
        --  index of 'hrDeviceEntry' for host system boot device
        --  (usually a disk drive or ROM)
        --  passed as decimal string, NOT as binary value

      * ZP  'hrSystemInitialLoadParameters'
        --  syntax 'InternationalDisplayString (SIZE (0..128))'
        --  host system boot parameters (eg, pathname and options)
        --  passed in dynamic locale
        --  (see 'xcmGenCurrentLocalizationIndex')

      * ZM  'hrSystemMaxProcesses'
        --  syntax 'INTEGER (0..2147483647)'
        --  max number of process contexts supported on host system
        --  or zero (if no fixed limit)
        --  passed as decimal string, NOT as binary value

        --  Storage group of IETF HR MIB (RFC 2790)
      * SX  'hrStorageIndex'
        --  syntax 'INTEGER (1..2147483647)'
        --  index of host system storage conceptual row
        --  (REQUIRED for 'entityCreate')
        --  passed as decimal string, NOT as binary index

      * SY  'hrStorageType'
        --  syntax 'OBJECT IDENTIFIER'
        --  (see 'hrStorageTypes' in IETF HR MIB)
        --  type of host system storage


        --  passed as dotted decimal OID or as storage type label

      * SD  'hrStorageDescr'
        --  syntax 'DisplayString (SIZE (0..64))'
        --  (NVT ASCII string)
        --  textual description of host system storage,
        --  including the type and instance of the storage
        --  passed as ASCII string, NOT as localized string

      * SU  'hrStorageAllocationUnits'
        --  syntax 'INTEGER (1..2147483647)'
        --  (size in bytes)
        --  size of allocation units on host system storage
        --  passed as decimal string, NOT as binary value

      * SS  'hrStorageSize'
        --  syntax 'INTEGER (1..2147483647)'
        --  (size in allocation units)
        --  size in 'hrStorageAllocationUnits' of host system storage
        --  passed as decimal string, NOT as binary value

        --  Device table in Device group of IETF HR MIB (RFC 2790)
      * DX  'hrDeviceIndex'
        --  syntax 'INTEGER (1..2147483647)'
        --  index of host system device conceptual row
        --  (REQUIRED for 'deviceCreate')
        --  passed as decimal string, NOT as binary index

      * DY  'hrDeviceType'
        --  syntax 'OBJECT IDENTIFIER'
        --  (see 'hrDeviceTypes' in IETF HR MIB)
        --  type of host system device
        --  (certain device types make related table entries MANDATORY)
        --  passed as dotted decimal OID or as device type label
        --  (eg, 'hrDevicePrinter'), NOT as binary 'OBJECT IDENTIFIER'

      * DD  'hrDeviceDescr'
        --  syntax 'DisplayString' (SIZE (0..64))
        --  (NVT ASCII string)
        --  textual description of host system device,
        --  including manufacturer and revision, and
        --  (optionally) serial number
        --  passed as ASCII string, NOT as localized string

      * DI  'hrDeviceID'
        --  syntax 'ProductID'
        --  (manufacturer defined object identifier)
        --  product ID of host system device
        --  passed as dotted decimal OID or as device product ID label
        --  (eg, 'xcmPidStarship20'), NOT as binary object identifier

        --  Processor table in Device group of IETF HR MIB (RFC 2790)
      * PI  'hrProcessorFrwID'
        --  syntax 'ProductID'


        --  (manufacturer defined object identifier)
        --  product ID of firmware associated with processor device
        --  passed as dotted decimal OID or as firmware product ID label
        --  (for device types 'hrDeviceProcessor' in HR Device table)

        --  Network table in Device group of IETF HR MIB (RFC 2790)
      * NI  'hrNetworkIfIndex'
        --  syntax 'INTEGER (1..2147483647)'
        --  (see 'ifIndex' in IETF MIB-II)
        --  index of 'ifEntry' associated with network device
        --  passed as decimal string, NOT as binary index
        --  (for device types 'hrDeviceNetwork' in HR Device table)

        --  Disk Storage table in Device group of IETF HR MIB (RFC 2790)
      * KA  'hrDiskStorageAccess'
        --  syntax 'INTEGER (1..2)' (enumeration)
        --  access (including write-protect) of disk storage device
        --  passed as decimal string or as access enum label
        --  (eg, 'readOnly'), NOT as binary value
        --  (for device types 'hrDeviceDiskStorage' in HR Device table)

      * KM  'hrDiskStorageMedia'
        --  syntax 'INTEGER (1..8)' (enumeration)
        --  type of media used in disk storage device
        --  passed as decimal string or as media enum label
        --  (eg, 'hardDisk'), NOT as binary value
        --  (for device types 'hrDeviceDiskStorage' in HR Device table)

      * KR  'hrDiskStorageRemoveble'
        --  syntax 'Boolean' (true/false, defined in IETF HR MIB)
        --  indicates if media MAY be removed for disk storage device
        --  (note the spelling error in 'hrDiskStorageRemoveble' !!)
        --  passed as decimal string or as boolean enum label
        --  (eg, 'true'), NOT as binary value
        --  (for device types 'hrDeviceDiskStorage' in HR Device table)

      * KC  'hrDiskStorageCapacity'
        --  syntax 'KBytes' (kilobytes, defined in IETF HR MIB)
        --  total size of disk storage device
        --  passed as decimal string, NOT as binary value
        --  (for device types 'hrDeviceDiskStorage' in HR Device table)

        --  Partition table in Device group of IETF HR MIB (RFC 2790)
      * XX  'hrPartitionIndex'
        --  syntax 'INTEGER (1..2147483647)'
        --  index of disk storage partition
        --  (REQUIRED for 'entityCreate')
        --  passed as decimal string, NOT as binary index
        --  (for device types 'hrDeviceDiskStorage' in HR Device table)

      * XL  'hrPartitionLabel'
        --  syntax 'InternationalDisplayString (SIZE (0..128))'
        --  textual description of disk storage partition
        --  passed in dynamic locale


        --  (see 'xcmGenCurrentLocalizationIndex')
        --  (for device types 'hrDeviceDiskStorage' in HR Device table)

      * XI  'hrPartitionID'
        --  syntax 'OCTET STRING (SIZE (0..128))'
        --  descriptor (possibly binary) of disk storage partition
        --  passed as hexadecimal string, NOT as binary value
        --  (for device types 'hrDeviceDiskStorage' in HR Device table)

      * XS  'hrPartitionSize'
        --  syntax 'KBytes' (kilobytes, defined in IETF HR MIB)
        --  total size of disk storage partition
        --  passed as decimal string, NOT as binary value
        --  (for device types 'hrDeviceDiskStorage' in HR Device table)

      * XF  'hrPartitionFSIndex'
        --  syntax 'INTEGER (0..2147483647)'
        --  (see 'hrFSIndex' in IETF HR MIB)
        --  index of 'hrFSEntry' mounted on disk storage partition
        --  or zero, if none
        --  passed as decimal string, NOT as binary value
        --  (exactly ONE file system MAY be mounted on a partition)
        --  (note that multiple partitions MAY support ONE file system,
        --  but multiple file systems MAY NOT reside on ONE partition)
        --  (for device types 'hrDeviceDiskStorage' in HR Device table)

        --  File System table in Device group of IETF HR MIB (RFC 2790)
      * FX  'hrFSIndex'
        --  syntax 'INTEGER (1..2147483647)'
        --  index of file system
        --  (REQUIRED for 'entityCreate')
        --  passed as decimal string, NOT as binary index
        --  (for device types 'hrDeviceDiskStorage' in HR Device table)

      * FM  'hrFSMountPoint'
        --  syntax 'InternationalDisplayString (SIZE (0..128))'
        --  path name of the root of file system
        --  passed in dynamic locale
        --  (see 'xcmGenCurrentLocalizationIndex')
        --  (for device types 'hrDeviceDiskStorage' in HR Device table)

      * FR  'hrFSRemoteMountPoint'
        --  syntax 'InternationalDisplayString (SIZE (0..128))'
        --  name or address of server file system is mounted from
        --  passed in dynamic locale
        --  (see 'xcmGenCurrentLocalizationIndex')
        --  (for device types 'hrDeviceDiskStorage' in HR Device table)

      * FY  'hrFSType'
        --  syntax 'OBJECT IDENTIFIER'
        --  (see 'hrFSTypes' in IETF HR MIB)
        --  type of file system
        --  passed as dotted decimal OID or as file system type label
        --  (eg, 'hrFSiso9660'), NOT as binary 'OBJECT IDENTIFIER'


        --  (for device types 'hrDeviceDiskStorage' in HR Device table)

      * FA  'hrFSAccess'
        --  syntax 'INTEGER (1..2)' (enumeration)
        --  access of WHOLE file system (NOT individual files)
        --  passed as decimal string or as access enum label
        --  (eg, 'readOnly'), NOT as binary value
        --  (for device types 'hrDeviceDiskStorage' in HR Device table)

      * FB  'hrFSBootable'
        --  syntax 'Boolean' (true/false, defined in IETF HR MIB)
        --  indicates if file system is bootable
        --  passed as decimal string or as boolean enum label
        --  (eg, 'true'), NOT as binary value
        --  (for device types 'hrDeviceDiskStorage' in HR Device table)

      * FS  'hrFSStorageIndex'
        --  syntax 'INTEGER (0..2147483647)'
        --  (see 'hrStorageIndex' in IETF HR MIB)
        --  index of 'hrStorageEntry' for file system
        --  or zero, if none
        --  passed as decimal string, NOT as binary value
        --  (exactly ONE file system MAY be mounted on a partition)
        --  (note that multiple partitions MAY support ONE file system,
        --  but multiple file systems MAY NOT reside on ONE partition)
        --  (for device types 'hrDeviceDiskStorage' in HR Device table)

        --  Software Running group of IETF HR MIB (RFC 2790)
      * RO  'hrSWOSIndex'
        --  syntax 'INTEGER (1..2147483647)'
        --  index of operating system running software conceptual row
        --  passed as decimal string, NOT as binary index

      * RX  'hrSWRunIndex'
        --  syntax 'INTEGER (1..2147483647)'
        --  index of host system running software conceptual row
        --  (REQUIRED for 'entityCreate')
        --  passed as decimal string, NOT as binary index

      * RN  'hrSWRunName'
        --  syntax 'InternationalDisplayString (SIZE (0..64))'
        --  textual description of running software,
        --  including manufacturer, revision, local name, and
        --  (optionally) serial number
        --  passed in dynamic locale
        --  (see 'xcmGenCurrentLocalizationIndex')

      * RI  'hrSWRunID'
        --  syntax 'ProductID'
        --  (manufacturer defined object identifier)
        --  product ID of running software
        --  passed as dotted decimal OID or as software product ID label
        --  (eg, 'xcmPidStarship20'), NOT as binary object identifier


      * RF  'hrSWRunPath'
        --  syntax 'InternationalDisplayString (SIZE (0..128))'
        --  initial load path (file) of running software
        --  passed in dynamic locale
        --  (see 'xcmGenCurrentLocalizationIndex')

      * RP  'hrSWRunParameters'
        --  syntax 'InternationalDisplayString (SIZE (0..128))'
        --  initial load parameters (arguments) of running software
        --  passed in dynamic locale
        --  (see 'xcmGenCurrentLocalizationIndex')

      * RY  'hrSWRunType'
        --  syntax 'INTEGER (1..4)' (enumeration)
        --  type of running software
        --  passed as decimal string or as software type enum label
        --  (eg, 'application'), NOT as binary value

        --  Software Installed group of IETF HR MIB (RFC 2790)
      * WX  'hrSWInstalledIndex'
        --  syntax 'INTEGER (1..2147483647)'
        --  index of host system installed software conceptual row
        --  (REQUIRED for 'entityCreate')
        --  passed as decimal string, NOT as binary index

      * WN  'hrSWInstalledName'
        --  syntax 'InternationalDisplayString (SIZE (0..64))'
        --  textual description of installed software,
        --  including manufacturer, revision, local name, and
        --  (optionally) serial number
        --  passed in dynamic locale
        --  (see 'xcmGenCurrentLocalizationIndex')

      * WI  'hrSWInstalledID'
        --  syntax 'ProductID'
        --  (manufacturer defined object identifier)
        --  product ID of installed software
        --  passed as dotted decimal OID or as software product ID label
        --  (eg, 'xcmPidStarship20'), NOT as binary object identifier

      * WY  'hrSWInstalledType'
        --  syntax 'INTEGER (1..4)' (enumeration)
        --  type of installed software
        --  passed as decimal string or as software type enum label
        --  (eg, 'application'), NOT as binary value

        --  Color Calibration Information
      * CN  [Color Name - no object mapping]
        --  syntax 'DisplayString (SIZE (2))'
        --  name of a color (color plus level)
        --  color:  C=cyan, M=magenta, Y=yellow, K=Black
        --  color:  R=red, G=green, B=blue
        --  level:  S=shadow, M=midbalance, H=highlight, W=whitepoint


        --  (eg, 'CN=CS:' specifies a color name of 'cyan-shadow')
        --  (see 'TCxx' system color calibration tests below)
      * CV  [Color Value - no object mapping]
        --  syntax 'INTEGER (0..100)'
        --  value of a color (specified by previous 'CN=xx' element)
        --  (eg, 'CV=20:' specifies a color value of '20')
        --  (see 'TCxx' system color calibration tests below)

        --  SNMP Community Names (for SNMPv1c and SNMPv2c)
      * CO  [Community Name Ordinal - no direct object mapping]
        --  syntax 'Ordinal32'
        --  ordinal for storing the 'CR|CW|CT' value below to an array
        --  (eg, 'CO=1' refers to object 'xcmGenBaseSNMPxxxCommunity')
        --  (see 'CR', 'CW', and 'CT' below)
      * CR  'xcmGenBaseSNMPReadCommunity'
        --  syntax 'XcmFixedLocaleDisplayString (SIZE (0..255))'
        --  read community name for SNMP 'Get|GetNext|GetBulk' PDUs
        --  passed in fixed locale (see 'xcmGenFixedLocalizationIndex')
        --  (eg, 'CR=:' clears all read community names)
        --  (eg, 'CR=public:' sets a read community name of 'public')
      * CW  'xcmGenBaseSNMPWriteCommunity'
        --  syntax 'XcmFixedLocaleDisplayString (SIZE (0..255))'
        --  write community name for SNMP 'Set|Get|GetNext|GetBulk' PDUs
        --  passed in fixed locale (see 'xcmGenFixedLocalizationIndex')
      * CT  'xcmGenBaseSNMPTrapCommunity'
        --  syntax 'XcmFixedLocaleDisplayString (SIZE (0..255))'
        --  trap community name for SNMP 'Inform|Trap' PDUs
        --  passed in fixed locale (see 'xcmGenFixedLocalizationIndex')

        --  Job Data from XCMI Job Monitoring MIB (41jobmon)
      * JA  'xcmJobSubmittingApplication'
        --  syntax 'CodeIndexedStringIndex'
        --  job programmatic originator (as opposed to job human owner)
        --  passed in fixed locale (see 'xcmGenFixedLocalizationIndex')

      * JC  'xcmJobClientId'
        --  syntax 'XcmGlobalUniqueID'
        --  job client-assigned identifier
        --  passed as dotted decimal string, NOT as a binary OID

      * JD  'xcmDocName'
        --  syntax 'CodeIndexedStringIndex'
        --  document name
        --  passed in fixed locale (see 'xcmGenFixedLocalizationIndex')

      * JF  'xcmDocFileName'
        --  syntax 'CodeIndexedStringIndex'
        --  document filename (MAY be used for print-by-reference)
        --  passed in fixed locale (see 'xcmGenFixedLocalizationIndex')

      * JH  'jobHoldSet' in 'xcmJobStateReasons'
        --  syntax 'TruthValue'
        --  job hold (for creating job with held-by-user condition)
        --  passed as '1' (true) or '2' (false), NOT as binary value


      * JM  'xcmJobMessageFromAdministrator'
        --  syntax 'CodeIndexedStringIndex'
        --  job message from system administrator
        --  passed in fixed locale (see 'xcmGenFixedLocalizationIndex')

      * JN  'xcmJobName'
        --  syntax 'CodeIndexedStringIndex'
        --  job name
        --  passed in fixed locale (see 'xcmGenFixedLocalizationIndex')

      * JO  'xcmJobOwner'
        --  syntax 'CodeIndexedStringIndex'
        --  job human owner (as opposed to job programmatic originator)
        --  passed in fixed locale (see 'xcmGenFixedLocalizationIndex')

      * JP  'xcmJobPriority'
        --  syntax 'INTEGER (0..100)'
        --  job priority (0=unspecified, 1=lowest, 100=highest)
        --  passed as decimal string, NOT as binary index

      * JR  'xcmJobRetentionPeriod'
        --  syntax 'Cardinal32'
        --  job retention period (in seconds after completion)
        --  passed as decimal string, NOT as binary value

      * JS  'xcmJobServiceType'
        --  syntax 'XcmJMJobServiceTypeOID' (OBJECT IDENTIFIER)
        --  job service type
        --  passed as dotted decimal OID or as job service type label
        --  (eg, 'xcmJobServicePrintOID'),
        --  NOT as binary 'OBJECT IDENTIFIER'

      * JT  'xcmJobProcessAfter'
        --  syntax 'DateAndTime'
        --  job process after calendar date and time
        --  passed as dotted decimal string (ie, 'yyyy.mm.dd.hh.mm.ss'),
        --  NOT as binary value

      * JU  'xcmJobComment'
        --  syntax 'CodeIndexedStringIndex'
        --  job comment from user (eg, for banner sheet)
        --  passed in fixed locale (see 'xcmGenFixedLocalizationIndex')

      * JW  ['system job' standard type - no object mapping]
        --  syntax 'DisplayString'
        --  'system job' standard type (standardized below)
        --  (REQUIRED for 'deviceJobCreate')
        --  passed as ASCII string, NOT as localized string
        --  (copied to 'xcmJobName', unless 'JN' tag is specified)

      * JX  ['system job' extended type - no object mapping]
        --  syntax 'DisplayString'
        --  'system job' extended type (freeform, no standards)


        --  (OPTIONAL for 'deviceJobCreate')
        --  passed as ASCII string, NOT as localized string
        --  (appended to 'xcmJobName', unless 'JN' tag is specified)

        XCMI standard 'system job' types for use in 'JW' arguments
        (in 'xcmHrDevMgmtCommandData' and 'xcmSimpleJobMgmtData') and
        for the value of 'xcmJobName' (unless 'JN' tag is specified)
        are as follows:

        --  Accounting Reports
      * ACCT    (basic) accounting report
      * AEXT    (extended) accounting report

        --  Configuration Reports
      * CONF    (basic) system configuration report
      * CEXT    (extended) system configuration report
      * CMEM    (installed) memory configuration report
      * CMSR    media (supported and ready) configuration report
      * CNET    network interfaces configuration report
      * COPT    (installed) optional devices configuration report
      * CPDL    (JCL and/or PDL) interpreters configuration report
      * CPRO    network protocols configuration report
      * CSWI    (installed) software configuration report

        --  Demos
      * DEMO    (basic) demo job
      * DEXT    (extended) demo job

        --  Font Reports
      * FONT    (basic) fonts report
      * FEXT    (extended) fonts report
      * FPCL    (installed) HP PCL fonts report
      * FPSX    (installed) Adobe PostScript fonts report

        --  List Directories and/or Files
        --  See section 3.4.1 'List Directory (LIST) Requests'
        --  in XCMI Ext to Host Resources TC.
      * LIST    list tree of disk directories (but NOT contents)
      * LALL    list tree of disk directories (including all files)
      * LDIR    list (specific) disk directory
      * LERR    list system error file
      * LLOG    list system log file
      * LFIL    list (specific) file

        --  Local UI Menu Reports
      * MENU    (basic) local UI menu tree report
      * MEXT    (extended) local UI menu tree report

        --  Document Resources Reports
      * RSRC    (basic) document resources report
      * REXT    (extended) document resources report

        --  System Tests
      * TEST    (basic) system test


      * TEXT    (extended) system test
      * TMEM    (installed) memory verfication test report
      * TNET    network interfaces verification test report
      * TOPT    (installed) optional devices test report
      * TPAT    print test pattern (especially for printers and copiers)
      * TPDL    (JCL and/or PDL) interpreters system test report
      * TPRO    network protocols verification test report
      * TSWI    (installed) software verfication test report

        --  System Color Calibration Tests
      * TCAC    print automatic color chart (auto calibration)
      * TCBC    print balance chart (manual calibration)
      * TCCC    print corrected color chart (color calibration)
      * TCSC    scan automatic color chart (auto calibration)
      * TCTC    print tone chart (manual calibration)
      * TCUC    print uncorrected color chart (color calibration)
      * TCBV    set balance values (manual calibration)
      * TCTV    set tone values (manual calibration)

        --  User Reports
      * USER    (basic) configured users report
      * UEXT    (extended) configured users report

        The above XCMI standard 'tags' MAY be extended in the future."
    REFERENCE
        "See:   Section 4 'Print Utilities' (pages 71 to 212) of
                POSIX Sys Admin (IEEE 1387.4 / Draft 8, October 1994).
        See:    'hrDeviceStatus' in the Device group of the
                IETF Host Resources MIB (RFC 2790).
        See:    Section 3.4 'XCMI Standard Tagged Management Data' and
                Section 3.5 'Simple Device Management Requests' in
                XCMI Ext to Host Resources TC.
        See:    Section 3.5.3 'Secure Simple Device Mgmt Requests' in
                XCMI Security TC."
    SYNTAX      OCTET STRING (SIZE (2))

XcmHrDevPowerModeType ::= TEXTUAL-CONVENTION
    STATUS      current
    DESCRIPTION
        "A device power mode type, used by system administrators
        of this device for power management details.

        Usage:  Used in 'devicePowerModeType' Device Detail, to clearly
        identify the referenced power mode (without resort to strings)."
    SYNTAX      INTEGER {
        other(1),                       -- other power mode type
        unknown(2),                     -- unknown power mode type
        --  XCMI simple device power modes, supported in
        --  Device Calendar, Device Mgmt, and Device Power groups via
        --  'XcmHrDevMgmtCommandRequest' and 'XcmHrDevInfoConditions'
        readyMode(3),                   -- 'warmUp|powerToReady' in
                                        -- 'XcmHrDevMgmtCommandRequest'
        standbyMode(4),                 -- 'coolDown|powerToStandby' in
                                        -- 'XcmHrDevMgmtCommandRequest'


        sleepMode(5),                   -- 'energySave|powerToSleep' in
                                        -- 'XcmHrDevMgmtCommandRequest'
        offMode(6)                      -- 'shutdown|quiesce' in
                                        -- 'XcmHrDevMgmtCommandRequest'
        --  XCMI advanced device power modes, supported in
        --  Device Detail group via
        --  'XcmHrDevDetailType' of 'devicePowerModeType'
        --  ...to be supplied
    }

XcmHrDevPowerTimeUnit ::= TEXTUAL-CONVENTION
    STATUS      current
    DESCRIPTION
        "A device power cycle time unit, used by system administrators
        of this device for power management cycle times.

        Usage:  Used to scale the values in the Device Power group, for
        convenience and (optional) high resolution."
    SYNTAX      INTEGER {
        other(1),                       -- other time unit
        unknown(2),                     -- unknown time unit
        microsecond(3),                 -- 1 microsecond
        millisecond(4),                 -- 1 millisecond
        second(5),                      -- 1 second
        kilosecond(6),                  -- 1 kilosecond
        megasecond(7),                  -- 1 megasecond
        minute(8),                      -- 1 minute
        hour(9),                        -- 1 hour
        day(10),                        -- 1 day
        week(11),                       -- 1 week
        month(12),                      -- 1 month
        year(13)                        -- 1 year
    }

XcmHrDevTrafficUnit ::= TEXTUAL-CONVENTION
    STATUS      current
    DESCRIPTION
        "The type of traffic unit used to measure input and/or output
        traffic for this device.

        Usage:  The use of either 'other' or 'unknown' is uninformative
        and SHOULD be avoided by conforming implementations.

        Usage:  'mediaImage' - SHOULD be used ONLY for softcopy
                INPUT page images (scan, copy, fax, etc.).
                'mediaImpression' - SHOULD be used ONLY for hardcopy
                OUTPUT page impressions (print, copy, fax, etc.)
                'mediaSheet' - SHOULD be used ONLY for hardcopy
                OUTPUT and does NOT always equal output pages
                (e.g., duplex or N-up printing)."
    SYNTAX      INTEGER {
        other(1),                       -- other traffic unit         
        unknown(2),                     -- unknown traffic unit       
        binaryBit(11),                  -- 1 bit


        binaryNibble(12),               -- 4 bits
        binaryOctet(13),                -- 8 bits
        binaryLine(14),                 -- 1 to N bits (eg, video line)
        textCharacter(15),              -- 5 to 8 bits
        textWord(16),                   -- 1 to N characters
        textLine(17),                   -- 1 to N characters
        textSentence(18),               -- 1 to N words
        textParagraph(19),              -- 1 to N sentences
        mediaBlock(20),                 -- 1 media-specific block
        mediaSector(21),                -- 1 media-specific sector
        mediaRow(22),                   -- 1 media-specific row
        mediaColumn(23),                -- 1 media-specific column
        mediaPacket(24),                -- 1 media-specific packet
        mediaCell(25),                  -- 1 media-specific cell
        mediaImage(26),                 -- 1 media-specific image
        mediaImpression(27),            -- 1 media-specific impression
        mediaSheet(28),                 -- 1 media-specific sheet
        lengthInch(29),                 -- 1 English inch
        lengthFoot(30),                 -- 1 English foot
        lengthYard(31),                 -- 1 English yard
        lengthMile(32),                 -- 1 English mile
        lengthMicrometer(33),           -- 1 micrometer
        lengthMillimeter(34),           -- 1 millimeter
        lengthCentimeter(35),           -- 1 centimeter
        lengthMeter(36),                -- 1 meter
        lengthKilometer(37),            -- 1 kilometer
        volumeMicroliter(38),           -- 1 microliter
        volumeMilliliter(39),           -- 1 milliliter
        volumeLiter(40),                -- 1 liter
        volumeKiloliter(41),            -- 1 kiloliter
        weightMicrogram(42),            -- 1 microgram
        weightMilligram(43),            -- 1 milligram
        weightGram(44),                 -- 1 gram
        weightKilogram(45),             -- 1 kilogram
        areaSqInch(50),                 -- 1 square inch
        areaSqFoot(51),                 -- 1 square Foot
        areaSqYard(52),                 -- 1 square Yard
        areaSqMile(53),                 -- 1 square Mile
        areaSqMicrometer(54),           -- 1 square Micrometer
        areaSqMillimeter(55),           -- 1 square Millimeter
        areaSqCentimeter(56),           -- 1 square Centimeter
        areaSqMeter(57),                -- 1 square Meter
        areaSqKilometer(58),            -- 1 square Kilometer
        areaSheet(59),                  -- Area in "sheets" 
        media100Image(60),              -- 100 media-specific image
        media100Impression(61),         -- 100 media-specific impression
        media100Sheet(62),              -- 100 media-specific sheet
        length100Foot(63),              -- 100 English feet
        length100Meter(64),             -- 100 meter (a hectometer)
        area100SqFoot(65),              -- 100 square Feet
        area10SqMeter(66),              -- 10 square Meters 
        area100Sheet(67),               -- 100 times area of a sheet
        document(68),                   -- 1 document


--      Note that 10 sqMeters = 107.584 sqFeet.
--      The area of a "sheet" is defined as the area in square meters 
--      divided by 16 rounded to the nearest integer but at least 1.

        inkStick(100),                   -- 1 = one ink stick
        totalItemsConsumed(101) 

    }

XcmHrGroupSupport ::= TEXTUAL-CONVENTION
    STATUS      current
    DESCRIPTION
        "The terse conformance statement of ALL mandatory, conditionally
        mandatory, and optional IETF Host Resources MIB (RFC 2790)
        and XCMI Ext to Host Resources MIB objects which are
        supported by this management agent implementation (ie, version)
        on this host system, specified in a bit-mask.

        The current set of values (which MAY be extended in the future)
        is given below:

        --  IETF Host Resources MIB object groups
              1 : hrSystemGroup                 -- 2**0
              2 : hrStorageGroup                -- 2**1
              4 : hrDeviceGroup                 -- 2**2
              8 : hrSWRunGroup                  -- 2**3
             16 : hrSWRunPerfGroup              -- 2**4
             32 : hrSWInstalledGroup            -- 2**5
        --  XCMI Ext to Host Resources MIB object groups
             64 : xcmHrDevInfoGroup             -- 2**6
            128 : xcmHrDevHelpGroup             -- 2**7
            256 : xcmHrDevMgmtGroup             -- 2**8
            512 : xcmHrDevPowerGroup            -- 2**9
           1024 : xcmHrDevTrafficGroup          -- 2**10
           2048 : xcmHrSystemFaultGroup         -- 2**11
           4096 : xcmHrGeneralGroup             -- 2**12
           8192 : xcmHrDevCalendarGroup         -- 2**13
          16384 : xcmHrSWRunGroup               -- 2**14
          32768 : xcmHrSWInstalledGroup         -- 2**15
          65536 : xcmHrDevDetailGroup           -- 2**16
         131072 : xcmHrStorageExtGroup          -- 2**17
         262144 : xcmHrStorageDetailGroup       -- 2**18
         524288 : xcmHrDevCoverGroup            -- 2**19
        1048576 : xcmHrDevAlertGroup            -- 2**20
        2097152 : xcmHrConsoleScreenGroup       -- 2**21
        4194304 : xcmHrConsoleTabGroup          -- 2**22
        --  IETF Host Resources MIB tables for specific device types
       33554432 : hrProcessorTable              -- 2**25
       67108864 : hrNetworkTable                -- 2**26
      134217728 : hrPrinterTable                -- 2**27
      268435456 : hrDiskStorageTable            -- 2**28
      536870912 : hrPartitionTable              -- 2**29
     1073741824 : hrFSTable                     -- 2**30


        -- 2**31 NOT used, due to 'Integer32|Cardinal32' semantics

        Usage:  Conforming management agents SHALL accurately
        report their support for IETF Host Resources MIB (RFC 2790)
        and XCMI Ext to Host Resources MIB object groups."
    SYNTAX      INTEGER (0..2147483647)  -- biggest int = 2**31-1

XcmHrSWRunXStatus ::= TEXTUAL-CONVENTION
    STATUS      current
    DESCRIPTION
        "An extended software status, used by system administrators and
        end users of this software (here, read 'state' for 'status').

        Note:   This extended software status is present for future
        extensions."
    REFERENCE
        "See:   'hrSWRunStatus' in the basic Software Running Group
        of the IETF Host Resources MIB (RFC 2790)."
    SYNTAX      INTEGER {
        none(0),
        other(1),
        unknown(2)
    }

XcmHrStorageDetailType ::= TEXTUAL-CONVENTION
    STATUS      current
    DESCRIPTION
        "The type of the storage detail information specified
        in this conceptual row in the 'xcmHrStorageDetailTable'.

        Usage:  Used to describe system-, program-, or thread-level
        memory allocations/reservations.

        Usage:  'hrStorageEntry' and (optionally) 'xcmHrStorageEntry'
        MAY be referenced via 'xcmSecServiceHrStorageIndex' in the
        Service group of the XCMI Security MIB.

        Usage:  Conforming management stations and management agents
        SHALL implement specified semantics for storage detail types."

--    * 'other'
--    * 'unknown'
--
--      -   Storage general info
--    * 'storageName'
--      - storage administrative name in directory (primary name)
--      - type - (XcmFixedLocaleDisplayString)
--      - subtype - '...ValueOID' (directory in XCMI Comms Config TC)
--      - (eg, 'xcmCOInternetDNS')
--      - data - '...ValueString'
--      - (eg, 'showstopper.sample.com')
--    * 'storageAlias'
--      - storage administrative alias in directory (alternate name)


--      - type - (XcmFixedLocaleDisplayString)
--      - subtype - '...ValueOID' (directory in XCMI Comms Config TC)
--      - (eg, 'xcmCOInternetDNS')
--      - data - '...ValueString'
--      - (eg, 'LaserRat')
--    * 'storageType'
--      - storage type
--      - see - 'hrStorageType' in IETF HR MIB
--      - type - (OBJECT IDENTIFIER)
--      - data - '...ValueOID'
--      - (eg, 'hrStorageRam')
--    * 'storageDescription'
--      - storage description
--      - see - 'hrStorageDescr' in IETF HR MIB
--      - type - (XcmFixedLocaleDisplayString)
--      - data - '...ValueString'
--      - (eg, 'RAM Memory')
--    * 'storageAllocationUnits'
--      - storage allocation block size (in octets)
--      - type - (Cardinal32) 'hrStorageAllocationUnits'
--      - data - '...ValueInteger'
--      - (eg, '4096')
--    * 'storageTree'
--      - storage tree prefix to name/alias in directory
--      - type - (XcmFixedLocaleDisplayString)
--      - subtype - '...ValueOID' (directory in XCMI Comms Config TC)
--      - (eg, 'xcmCONetwareNDS')
--      - data - '...ValueString'
--      - (MAY also appear in 'storageName')
--    * 'storageContext'
--      - storage context prefix to name/alias in directory
--      - type - (XcmFixedLocaleDisplayString)
--      - subtype - '...ValueOID' (directory in XCMI Comms Config TC)
--      - (eg, 'xcmCONetwareNDS')
--      - data - '...ValueString'
--      - (MAY also appear in 'storageName')
--
--      -   System/Program/Thread storage details
--    * 'storageInputBuffer'
--      - network or standard input buffer size
--      - type - (Cardinal32)
--      - data - '...ValueInteger'
--      - positive integer = size in 'hrStorageAllocationUnits'
--      - zero = no size specified
--    * 'storageOutputBuffer'
--      - network or standard output buffer size
--      - type - (Cardinal32)
--      - data - '...ValueInteger'
--      - positive integer = size in 'hrStorageAllocationUnits'
--      - zero = no size specified
--    * 'storageImageBuffer'
--      - frame buffer size
--      - type - (Cardinal32)
--      - data - '...ValueInteger'


--      - positive integer = size in 'hrStorageAllocationUnits'
--      - zero = no size specified
--    * 'storageMarkerBuffer'
--      - marker buffer size (for hardcopy)
--      - type - (Cardinal32)
--      - data - '...ValueInteger'
--      - positive integer = size in 'hrStorageAllocationUnits'
--      - zero = no size specified
--    * 'storagePageBuffer'
--      - interpreter buffer size (for softcopy)
--      - type - (Cardinal32)
--      - data - '...ValueInteger'
--      - positive integer = size in 'hrStorageAllocationUnits'
--      - zero = no size specified
--    * 'storageTranslationBuffer'
--      - translation/localization buffer size
--      - type - (Cardinal32)
--      - data - '...ValueInteger'
--      - positive integer = size in 'hrStorageAllocationUnits'
--      - zero = no size specified
--    * 'storageWorkingBuffer'
--      - working buffer size
--      - type - (Cardinal32)
--      - data - '...ValueInteger'
--      - positive integer = size in 'hrStorageAllocationUnits'
--      - zero = no size specified
--
--      -   Interpreter storage details
--    * 'storageFontCache'
--      - interpreter font cache size
--      - type - (Cardinal32)
--      - data - '...ValueInteger'
--      - positive integer = size in 'hrStorageAllocationUnits'
--      - zero = no size specified
--    * 'storageFormCache'
--      - interpreter form cache size
--      - type - (Cardinal32)
--      - data - '...ValueInteger'
--      - positive integer = size in 'hrStorageAllocationUnits'
--      - zero = no size specified
--    * 'storageLogoCache'
--      - interpreter logo cache size
--      - type - (Cardinal32)
--      - data - '...ValueInteger'
--      - positive integer = size in 'hrStorageAllocationUnits'
--      - zero = no size specified
--    * 'storageMacroCache'
--      - interpreter macro cache size
--      - type - (Cardinal32)
--      - data - '...ValueInteger'
--      - positive integer = size in 'hrStorageAllocationUnits'
--      - zero = no size specified
--    * 'storageStyleCache'
--      - interpreter style cache size


--      - type - (Cardinal32)
--      - data - '...ValueInteger'
--      - positive integer = size in 'hrStorageAllocationUnits'
--      - zero = no size specified
--
--      -   Program/Thread storage details
--    * 'storageHeapMemory'
--      - program/thread heap memory size
--      - type - (Cardinal32)
--      - data - '...ValueInteger'
--      - positive integer = size in 'hrStorageAllocationUnits'
--      - zero = no size specified
--    * 'storagePrefixMemory'
--      - program/thread prefix memory size
--      - type - (Cardinal32)
--      - data - '...ValueInteger'
--      - positive integer = size in 'hrStorageAllocationUnits'
--      - zero = no size specified
--    * 'storageStackMemory'
--      - program/thread stack memory size
--      - type - (Cardinal32)
--      - data - '...ValueInteger'
--      - positive integer = size in 'hrStorageAllocationUnits'
--      - zero = no size specified
--    * 'storageWorkingMemory'
--      - program/thread working memory size
--      - type - (Cardinal32)
--      - data - '...ValueInteger'
--      - positive integer = size in 'hrStorageAllocationUnits'
--      - zero = no size specified
--
--      -   Storage addressing details
--    * 'storageBaseAddress'
--      - storage base address (physical or logical)
--      - type - (Cardinal32)
--      - data - '...ValueInteger'
--      - (eg, '0xF800')
--    * 'storageWordSize'
--      - storage addressability (word size in octets)
--      - type - (Cardinal32)
--      - data - '...ValueInteger'
--      - (eg, '4')
--    * 'storagePageSize'
--      - storage page size (in octets)
--      - type - (Cardinal32)
--      - data - '...ValueInteger'
--      - (eg, '8192')
    REFERENCE
        "See:   'xcmHrStorageDetailUnit' for units of storage detail."
    SYNTAX      INTEGER {
        other(1),
        unknown(2),
        --  Storage general info
        storageName(3),                 -- storage name (primary name)


        storageAlias(4),                -- storage alias (other name)
        storageType(5),                 -- storage type (R/W)
        storageDescription(6),          -- storage description (R/W)
        storageAllocationUnits(7),      -- storage allocation block size
        storageTree(8),                 -- storage directory tree
        storageContext(9),              -- storage context
        --  System/Program/Thread storage details
        storageInputBuffer(10),         -- network or standard input
        storageOutputBuffer(11),        -- network or standard output
        storageImageBuffer(12),         -- frame buffer
        storageMarkerBuffer(13),        -- marker buffer (hardcopy)
        storagePageBuffer(14),          -- interpreter buffer (softcopy)
        storageTranslationBuffer(15),   -- translate/localize buffer
        storageWorkingBuffer(16),       -- working buffer
        --  Interpreter storage details
        storageFontCache(20),           -- interpreter font cache
        storageFormCache(21),           -- interpreter form cache
        storageLogoCache(22),           -- interpreter logo cache
        storageMacroCache(23),          -- interpreter macro cache
        storageStyleCache(24),          -- interpreter style cache
        --  Program/Thread storage details
        storageHeapMemory(30),          -- program/thread heap memory
        storagePrefixMemory(31),        -- program/thread prefix memory
        storageStackMemory(32),         -- program/thread stack memory
        storageWorkingMemory(33),       -- program/thread working memory
        --  Storage addressing details
        storageBaseAddress(40),         -- storage base address
        storageWordSize(41),            -- storage addressability
        storagePageSize(42)             -- storage page size
    }

XcmHrStorageRealization ::= TEXTUAL-CONVENTION
    STATUS      current
    DESCRIPTION
        "An extended storage type (or storage 'realization'),
        used by system administrators and end users of this storage.

        Usage:  The use of either 'other' or 'unknown' is uninformative
        and SHOULD be avoided by conforming implementations.

      * 'physicalSystem' - 'real' memory installed on a 'system'
        whose product is found via 'xcmHrStorageProductDeviceIndex' and
        whose CPU is found via 'xcmHrStoragePlatformDeviceIndex' and
        whose self is found via 'xcmHrStorageMatchingDeviceIndex';
      * 'physicalProgram' - 'real' memory assigned to a 'program'
        (memory which is 'pinned' and is NOT paged to disk storage)
        whose program is found via 'xcmHrStorageSWRunIndex';
      * 'physicalThread' - 'real' memory assigned to a 'thread'
        (memory which is 'pinned' and is NOT paged to disk storage)
        whose program/thread is found via 'xcmHrStorageSWRunIndex';
      * 'logicalSystem' - 'virtual' memory assigned to a 'system'
        (memory which is NOT 'pinned' and MAY be paged to disk storage)
        whose product is found via 'xcmHrStorageProductDeviceIndex' and
        whose CPU is found via 'xcmHrStoragePlatformDeviceIndex' and


        whose self is found via 'xcmHrStorageMatchingDeviceIndex';
      * 'logicalProgram' - 'virtual' memory assigned to a 'program'
        (memory which is NOT 'pinned' and MAY be paged to disk storage)
        whose program is found via 'xcmHrStorageSWRunIndex';
      * 'logicalThread' - 'virtual' memory assigned to a 'thread'
        (memory which is NOT 'pinned' and MAY be paged to disk storage)
        whose program/thread is found via 'xcmHrStorageSWRunIndex'."
    REFERENCE
        "See:   'XcmHrDevInfoRealization' textual convention in
                the XCMI Ext to Host Resources TC.
        See:    'xcmHrDevInfoRealization' in the Device Info group of
                the XCMI Ext to Host Resources MIB."
    SYNTAX      INTEGER {
        other(1),                       -- other storage       
        unknown(2),                     -- unknown storage     
        physicalSystem(10),             -- 'real' system storage
        physicalProgram(11),            -- 'real' program storage
        physicalThread(12),             -- 'real' thread storage
        logicalSystem(20),              -- 'virtual' system storage
        logicalProgram(21),             -- 'virtual' program storage
        logicalThread(22)               -- 'virtual' thread storage
    }

XcmHrDpaAvailability ::= TEXTUAL-CONVENTION
    STATUS      current
    DESCRIPTION
        "The generic availability of this system, device, service, etc."
    REFERENCE
        "See:   Section 9.1.6.6 '[Generic attribute] Availability' and
                Annex A 'id-val-availability-...'
                in DPA (ISO/IEC 10175-1 Final Text, March 1996)."
    --  The following enum values are identical to the final arcs of
    --  the ISO DPA 'id-val-availability-...' OIDs
    SYNTAX      INTEGER {
        high(1),
        normal(2),
        low(3),
        none(5),
        unknown(6)
    }

XcmHrDpaConditions ::= TEXTUAL-CONVENTION
    STATUS      current
    DESCRIPTION
        "The generic conditions (ie, state reasons) of this system,
        device, service, etc, specified in a bit-mask.

        --  DPA - Service level operations
        --  See section D.2.3 of DPA Mgmt Service (ISO 10175-3)
        --  and section 4 of POSIX DPA Client (IEEE 1387.4)
              1 : cleanedByOperator             -- 2**0
              2 : cleanedBySystem               -- 2**1
                --  all jobs deleted by operator/system
                --  'serviceClean' in 'XcmSvcMonServiceMgmtOperation'


                --  'pdclean' in POSIX DPA Client
              4 : disabledByOperator            -- 2**2
              8 : disabledBySystem              -- 2**3
                --  all new jobs rejected by system
                --  'serviceDisable' in 'XcmSvcMonServiceMgmtOperation'
                --  'pddisable' in POSIX DPA Client
             16 : pausedByOperator              -- 2**4
             32 : pausedBySystem                -- 2**5
                --  all existing job output suspended on system
                --  'servicePause' in 'XcmSvcMonServiceMgmtOperation'
                --  'pdpause' in POSIX DPA Client
             64 : shutdownByOperator            -- 2**6 - 'pdshutdown'
            128 : shutdownBySystem              -- 2**7 - 'pdshutdown'
                --  service state is 'terminating', then 'unavailable'
                --  'serviceShutdown' in 'XcmSvcMonServiceMgmtOperation'
                --  'pdshutdown' in POSIX DPA Client

        --  XCMI - Service level extended operations
            256 : diagnosedByOperator           -- 2**8
            512 : diagnosedBySystem             -- 2**9
                --  'serviceDiagnose' in 'XcmSvcMonServiceMgmtOperation'
           1024 : resetByOperator               -- 2**10
           2048 : resetBySystem                 -- 2**11
                --  'serviceReset[Cold|Warm|Factory]'
                --  in 'XcmSvcMonServiceMgmtOperation'
           4096 : startedByOperator             -- 2**12
           8192 : startedBySystem               -- 2**13
                --  'service[Create|Install|Upgrade|Restart]'
                --  in 'XcmSvcMonServiceMgmtOperation'

        --  XCMI - Document service activities (during 'ready' state)
          65536 : activeCopy                    -- 2**16
         131072 : activePrint                   -- 2**17
         262144 : activeScan                    -- 2**18
         524288 : activeFaxReceive              -- 2**19
        1048576 : activeFaxSend                 -- 2**20
        2097152 : activeFileReceive             -- 2**21
        4194304 : activeFileSend                -- 2**22
        8388608 : activeMailReceive             -- 2**23
       16777216 : activeMailSend                -- 2**24
       33554432 : activeImageProcess            -- 2**25
       67108864 : activeOCR                     -- 2**26
      134217728 : activeDistribute              -- 2**27

        Usage:  The above 'conditions' augment the service state in
        'xcmSvcMonService[Current|Previous]State' and the service mgmt
        information in 'xcmSvcMonServiceMgmt[Operation|InProgress]'.

        Usage:  Conforming management agents SHALL report all
        'conditions' of entities accurately.  'Conditions' occur within
        or across 'states' in a finite state machine implementation of a
        system, device, service, etc.

        Usage:  A service with 'xcmSvcMonServiceCurrentState' of


        'ready(1)' might have 'xcmSvcMonServiceConditions' of
        'disabledByOperator', indicating that the service will not
        accept new jobs.

        Usage:  Multi-bit examples of 'xcmSvcMonServiceConditions' are
        'disabledByOperator' concurrently with 'pausedByOperator' and
        'activePrint' concurrently with 'activeMailSend'."
    REFERENCE
        "See:   Section 9.5.4 'Server-state',
                section 9.1.6.4 '[Generic attribute] State', and
                Annex A 'id-val-state-...'
                in DPA (ISO/IEC 10175-1 Final Text, March 1996).
        See:    Section D.2.3 'Server State Transitions'
                in DPA Mgmt Service (ISO 10175-3 Draft, October 1996).
        See:    Section 4 'Printing Utilities - Command Line Interface'
                in POSIX DPA Client (IEEE 1387.4, October 1994)."
    SYNTAX      INTEGER (0..2147483647)  -- biggest int = 2**31-1

XcmHrDpaJobValidateSupport ::= TEXTUAL-CONVENTION
    STATUS      current
    DESCRIPTION
        "The job validation support of this system, service, etc,
        specified in a bit-mask.

        The current set of values (which MAY be extended in the future)
        is given below:

            --  ISO DPA standard values
              1 : validateAndProcess    -- generalized from DPA 'print'
              2 : validateSubmitOnly    -- error check, do NOT process
            --  XCMI standard values
              4 : validateSyntaxOnly    -- check syntax only
              8 : validateSemanticsOnly -- check syntax/ranges/states
             16 : validateLocalOnly     -- check semantic/local services
             32 : validateDistributed   -- check distributed services
             64 : validateCreateLocal   -- create local child jobs
            128 : validateCreateRemote  -- create remote child jobs

        Usage:  Conforming management agents SHALL accurately
        report their support for job validation modes."
    REFERENCE
        "See:   Section 9.5.10 'Job-validates-supported' (server),
                section 9.2.4.12 'Job-validate' (job), and
                Annex A 'id-val-job-validate-...'
                in DPA (ISO/IEC 10175-1 Final Text, March 1996)."
    SYNTAX      INTEGER (0..2147483647)  -- biggest int = 2**31-1

XcmHrDpaObjectClassSupport ::= TEXTUAL-CONVENTION
    STATUS      current
    DESCRIPTION
        "The object class support of this system, service, etc,
        specified in a bit-mask.

        The current set of values (which MAY be extended in the future)


        is given below:

            --  ISO DPA standard values
              1 : generic                       -- 2**0
              2 : job                           -- 2**1
              4 : printer                       -- 2**2
              8 : server                        -- 2**3
             16 : medium                        -- 2**4
             32 : font                          -- 2**5
            256 : transferMethod                -- 2**8
            512 : deliveryMethod                -- 2**9
           1024 : auxiliarySheet                -- 2**10
           2048 : finishing                     -- 2**11
           4096 : output                        -- 2**12
           8192 : imposition                    -- 2**13
          16384 : scheduler                     -- 2**14
          32768 : document                      -- 2**15
          65536 : resource                      -- 2**16
         131072 : initialValueJob               -- 2**17
         262144 : initialValueDocument          -- 2**18
         524288 : resourceContext               -- 2**19
        1048576 : auxiliarySheetPackage         -- 2**20
            --  XCMI standard values
       16777216 : deviceHostSystem              -- 2**24
       33554432 : deviceScanner                 -- 2**25
       67108864 : deviceCopier                  -- 2**26
      134217728 : deviceFax                     -- 2**27
      268435456 : deviceMailbox                 -- 2**28
      536870912 : deviceFinisher                -- 2**29
     1073741824 : deviceCRU                     -- 2**30

        -- 2**31 NOT used, due to 'Integer32|Cardinal32' semantics

        Usage:  Conforming management agents SHALL accurately
        report their support for object classes (ISO DPA and XCMI)."
    REFERENCE
        "See:   Section 9.5.5 'Object-classes-supported' (server),
                section 9.1.6.1 'Object-class' (system),
                Annex A 'id-oc-...'
                in DPA (ISO/IEC 10175-1 Final Text, March 1996)."
    SYNTAX      INTEGER (0..2147483647)  -- biggest int = 2**31-1

XcmHrDpaState ::= TEXTUAL-CONVENTION
    STATUS      current
    DESCRIPTION
        "The generic state of this object (system, device, service,
        etc.).  The following standard values are defined (in section
        9.1.6.4 'State' of ISO 10175-1):

      * 'ready' - This object is ready to be used without human
        intervention.
      * 'onRequest' - This object requires human intervention in order
        to be used.
      * 'unavailable' - This object is NOT available for use even with


        human intervention.
      * 'unknown' - This state of this object is NOT known.
      * 'busy' - This object is temporarily inaccessible due to dynamic
        constraints, but will become 'ready' without human intervention.
      * 'initializing' - This object is being initialized (and is
        therefore temporarily inaccessible).
      * 'terminating' - This object is being terminated (and is
        therefore permanently inaccessible)."
    REFERENCE
        "See:   Section 9.1.6.4 '[Generic attribute] State' and
                Annex A 'id-val-state-...'
                in DPA (ISO/IEC 10175-1 Final Text, March 1996)."
    --  The following enum values are identical to the final arcs of
    --  the ISO DPA 'id-val-state-...' OIDs
    SYNTAX      INTEGER {
        ready(1),
        onRequest(2),
        unavailable(3),
        unknown(4),
        busy(5),
        initializing(6),
        terminating(7)
    }

XcmHrSuppliesClassTC ::= TEXTUAL-CONVENTION
    STATUS    current
    DESCRIPTION
       "The type of a supply."
    SYNTAX    INTEGER {
       other(1),
       unknown(2),
       replenishable(3),     -- Parts a customer will have
                             -- on hand such as staples
       customerReplacable(4),-- CRUs
       serviceReplacable(5), -- HFSIs
       rarelyReplaced(6),    -- Service can order these parts.
       notReplacable(7)      -- Parts that don't wear out
    }

XcmHrDetailTableEnumTC ::= TEXTUAL-CONVENTION
    STATUS    current
    DESCRIPTION
       "The table referenced by a row in the xcmHrDetail
       table.  Add additional tables as details are
       required."
    SYNTAX    INTEGER {
       suppliesTable(1),        -- A detail for xcmHrSuppliesTable
       markerSuppliesTable(2),  -- A detail for prtMarkerSuppliesTable
       finisherSuppliesTable(3) -- A detail for finSuppliesTable
    }


XcmHrConsoleDefaultService ::= TEXTUAL-CONVENTION
    STATUS      current
    DESCRIPTION
        "The default service shown on the console user interface."
    SYNTAX      INTEGER {
        copyService(1),
        scanService(2),
        faxService(3),
        printService(4)
    }

--
--          The HRX TC Dummy Group (DO NOT USE)
--
--          DO NOT USE - Present to suppress compiler warnings ONLY!
--
--          Note:  The following objects have 'odd' use of case in their
--          names (ie, 'xCm...'), in order to make obvious their related
--          textual conventions

xCmHrDummy          OBJECT IDENTIFIER ::= { xcmHrTC 999 }

xCmHrDevCalendarDayOfWeek OBJECT-TYPE
    SYNTAX      XcmHrDevCalendarDayOfWeek
    MAX-ACCESS  not-accessible
    STATUS      current
    DESCRIPTION "Dummy - DO NOT USE"
    ::= { xCmHrDummy 1 }

xCmHrDevCalendarTimeOfDay OBJECT-TYPE
    SYNTAX      XcmHrDevCalendarTimeOfDay
    MAX-ACCESS  not-accessible
    STATUS      current
    DESCRIPTION "Dummy - DO NOT USE"
    ::= { xCmHrDummy 2 }

xCmHrDevDetailType OBJECT-TYPE
    SYNTAX      XcmHrDevDetailType
    MAX-ACCESS  not-accessible
    STATUS      current
    DESCRIPTION "Dummy - DO NOT USE"
    ::= { xCmHrDummy 3 }

xCmHrDevDetailUnitClass OBJECT-TYPE
    SYNTAX      XcmHrDevDetailUnitClass
    MAX-ACCESS  not-accessible
    STATUS      current
    DESCRIPTION "Dummy - DO NOT USE"
    ::= { xCmHrDummy 4 }

xCmHrDevInfoRealization OBJECT-TYPE
    SYNTAX      XcmHrDevInfoRealization
    MAX-ACCESS  not-accessible


    STATUS      current
    DESCRIPTION "Dummy - DO NOT USE"
    ::= { xCmHrDummy 5 }

xCmHrDevInfoStatus OBJECT-TYPE
    SYNTAX      XcmHrDevInfoStatus
    MAX-ACCESS  not-accessible
    STATUS      current
    DESCRIPTION "Dummy - DO NOT USE"
    ::= { xCmHrDummy 6 }

xCmHrDevInfoXStatus OBJECT-TYPE
    SYNTAX      XcmHrDevInfoXStatus
    MAX-ACCESS  not-accessible
    STATUS      current
    DESCRIPTION "Dummy - DO NOT USE"
    ::= { xCmHrDummy 7 }

xCmHrDevInfoConditions OBJECT-TYPE
    SYNTAX      XcmHrDevInfoConditions
    MAX-ACCESS  not-accessible
    STATUS      current
    DESCRIPTION "Dummy - DO NOT USE"
    ::= { xCmHrDummy 8 }

xCmHrDevInfoXConditions OBJECT-TYPE
    SYNTAX      XcmHrDevInfoXConditions
    MAX-ACCESS  not-accessible
    STATUS      current
    DESCRIPTION "Dummy - DO NOT USE"
    ::= { xCmHrDummy 9 }

xCmHrDevMgmtCommandRequest OBJECT-TYPE
    SYNTAX      XcmHrDevMgmtCommandRequest
    MAX-ACCESS  not-accessible
    STATUS      current
    DESCRIPTION "Dummy - DO NOT USE"
    ::= { xCmHrDummy 10 }

xCmHrDevMgmtCommandData OBJECT-TYPE
    SYNTAX      XcmHrDevMgmtCommandData
    MAX-ACCESS  not-accessible
    STATUS      current
    DESCRIPTION "Dummy - DO NOT USE"
    ::= { xCmHrDummy 11 }

xCmHrDevMgmtCommandDataTag OBJECT-TYPE
    SYNTAX      XcmHrDevMgmtCommandDataTag
    MAX-ACCESS  not-accessible
    STATUS      current
    DESCRIPTION "Dummy - DO NOT USE"
    ::= { xCmHrDummy 12 }

xCmHrDevPowerModeType OBJECT-TYPE


    SYNTAX      XcmHrDevPowerModeType
    MAX-ACCESS  not-accessible
    STATUS      current
    DESCRIPTION "Dummy - DO NOT USE"
    ::= { xCmHrDummy 13 }

xCmHrDevPowerTimeUnit OBJECT-TYPE
    SYNTAX      XcmHrDevPowerTimeUnit
    MAX-ACCESS  not-accessible
    STATUS      current
    DESCRIPTION "Dummy - DO NOT USE"
    ::= { xCmHrDummy 14 }

xCmHrDevTrafficUnit OBJECT-TYPE
    SYNTAX      XcmHrDevTrafficUnit
    MAX-ACCESS  not-accessible
    STATUS      current
    DESCRIPTION "Dummy - DO NOT USE"
    ::= { xCmHrDummy 15 }

xCmHrGroupSupport OBJECT-TYPE
    SYNTAX      XcmHrGroupSupport
    MAX-ACCESS  not-accessible
    STATUS      current
    DESCRIPTION "Dummy - DO NOT USE"
    ::= { xCmHrDummy 16 }

xCmHrSWRunXStatus OBJECT-TYPE
    SYNTAX      XcmHrSWRunXStatus
    MAX-ACCESS  not-accessible
    STATUS      current
    DESCRIPTION "Dummy - DO NOT USE"
    ::= { xCmHrDummy 17 }

xCmHrStorageDetailType OBJECT-TYPE
    SYNTAX      XcmHrStorageDetailType
    MAX-ACCESS  not-accessible
    STATUS      current
    DESCRIPTION "Dummy - DO NOT USE"
    ::= { xCmHrDummy 18 }

xCmHrStorageRealization OBJECT-TYPE
    SYNTAX      XcmHrStorageRealization
    MAX-ACCESS  not-accessible
    STATUS      current
    DESCRIPTION "Dummy - DO NOT USE"
    ::= { xCmHrDummy 19 }

xCmHrDpaAvailability OBJECT-TYPE
    SYNTAX      XcmHrDpaAvailability
    MAX-ACCESS  not-accessible
    STATUS      current
    DESCRIPTION "Dummy - DO NOT USE"
    ::= { xCmHrDummy 20 }


xCmHrDpaConditions OBJECT-TYPE
    SYNTAX      XcmHrDpaConditions
    MAX-ACCESS  not-accessible
    STATUS      current
    DESCRIPTION "Dummy - DO NOT USE"
    ::= { xCmHrDummy 21 }

xCmHrDpaJobValidateSupport OBJECT-TYPE
    SYNTAX      XcmHrDpaJobValidateSupport
    MAX-ACCESS  not-accessible
    STATUS      current
    DESCRIPTION "Dummy - DO NOT USE"
    ::= { xCmHrDummy 22 }

xCmHrDpaObjectClassSupport OBJECT-TYPE
    SYNTAX      XcmHrDpaObjectClassSupport
    MAX-ACCESS  not-accessible
    STATUS      current
    DESCRIPTION "Dummy - DO NOT USE"
    ::= { xCmHrDummy 23 }

xCmHrDpaState OBJECT-TYPE
    SYNTAX      XcmHrDpaState
    MAX-ACCESS  not-accessible
    STATUS      current
    DESCRIPTION "Dummy - DO NOT USE"
    ::= { xCmHrDummy 24 }

xCmHrDetailTableEnumTC OBJECT-TYPE
    SYNTAX      XcmHrDetailTableEnumTC
    MAX-ACCESS  not-accessible
    STATUS      current
    DESCRIPTION "Dummy - DO NOT USE"
    ::= { xCmHrDummy 25 }

xCmHrSuppliesClassTC OBJECT-TYPE
    SYNTAX      XcmHrSuppliesClassTC
    MAX-ACCESS  not-accessible
    STATUS      current
    DESCRIPTION "Dummy - DO NOT USE"
    ::= { xCmHrDummy 26 }

xCmHrConsoleDefaultService OBJECT-TYPE
    SYNTAX      XcmHrConsoleDefaultService
    MAX-ACCESS  not-accessible
    STATUS      current
    DESCRIPTION "Dummy - DO NOT USE"
    ::= { xCmHrDummy 27 }
END

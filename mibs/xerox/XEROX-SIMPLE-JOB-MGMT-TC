XEROX-SIMPLE-JOB-MGMT-TC DEFINITIONS ::= BEGIN

--  Module: Simple Job Mgmt TC
--  File    42jobmtc.mib
--  Date:   17 September 2002 - Version 5.10.pub

--  Textual Conventions companion to the XCMI Simple Job Mgmt MIB

IMPORTS
    MODULE-IDENTITY, OBJECT-TYPE
            FROM SNMPv2-SMI             -- IETF RFC 1442/1902/2578
    TEXTUAL-CONVENTION
            FROM SNMPv2-TC              -- IETF RFC 1443/1903/2579
    xeroxCommonMIB
            FROM XEROX-COMMON-MIB;

xcmSimpleJobMgmtTC MODULE-IDENTITY
    LAST-UPDATED "0209170000Z" -- 17 September 2002
    ORGANIZATION "Xerox Corporation - XCMI Working Group"
    CONTACT-INFO
        "           XCMI Editors
        Email:      coherence@crt.xerox.com

        "
    DESCRIPTION
        "Version:   5.10.pub

        Textual Conventions companion to the XCMI Simple Job Mgmt MIB,
        the MIB module for performing lightweight management of jobs
        in network accessible host systems.

        See:    Document Printing Application - Part 1: Abstract Service
                (ISO/IEC 10175-1 / Final Text, March 1996).
        See:    POSIX System Administration - Part 4: Print Interfaces
                (IEEE 1387.4 / Draft 8, October 1994).
        See:    OSI Reference Model - Part 1:  Basic Reference Model
                (CCITT X.200:1992 | ISO 7498-1:1992).

        Copyright (C) 1997-2002 Xerox Corporation. All Rights Reserved."
    ::= { xeroxCommonMIB 75 }

--
--          Simple Job Mgmt TC
--
--          Textual Conventions


XcmSimpleJobMgmtGroupSupport ::= TEXTUAL-CONVENTION
    STATUS      current
    DESCRIPTION
        "The terse conformance statement of ALL mandatory, conditionally
        mandatory, and optional XCMI Simple Job Mgmt MIB groups
        supported by this management agent implementation (ie, version)
        on this host system, specified in a bit-mask.

        The current set of values (which may be extended in the future)
        is given below:

              1 : simpleJobBaseGroup
              2 : simpleJobMgmtGroup
              4 : simpleJobInterceptGroup

        Usage:  Conforming management agents shall ALWAYS accurately
        report their support for XCMI Simple Job Mgmt MIB groups."
    SYNTAX      INTEGER (0..2147483647)  -- biggest int = 2**31-1

XcmSimpleJobMgmtOperation ::= TEXTUAL-CONVENTION
    STATUS      current
    DESCRIPTION
        "The simple job management operation associated with
        this conceptual row in the 'xcmSimpleJobMgmtTable'
        and the 'xcmJobGenBasicTable' (XCMI Job Monitoring MIB), OR
        this conceptual row in the 'xcmSimpleJobInterceptTable'
        and the 'xcmJobClientId' object (XCMI Job Monitoring MIB).

        Note:   The enum of '0' (zero) in this textual convention is
        illegal in strict SMIv1 (see section 3.2.1.1 of RFC 1155), so
        this TC must be converted to an integer range for pure SMIv1."
    REFERENCE
        "See:   Section 4 'Print Utilities' (pages 71 to 212) of
                POSIX Sys Admin (IEEE 1387.4 / Draft 8, October 1994).
        See:    OBJECT clauses in MODULE-COMPLIANCE macro of
                XCMI Simple Job Mgmt MIB, for compliance info."
    SYNTAX      INTEGER {
        none(0),                        -- No operation
        other(1),                       -- Other operation
        unknown(2),                     -- Unknown operation
        --  POSIX - Job level operations (on/off-system jobs)
        jobCreate(1401),                -- 'pdpr' (submit job)
        jobDelete(1402),                -- 'pddelete' (destroy job)
        jobList(1403),                  -- 'pdls' (list job attributes)
        jobSet(1404),                   -- 'pdset' (set job attributes)
        jobPause(1408),                 -- 'pdpause' (hold job)
        jobResume(1409),                -- 'pdresume' (release job)
        jobInterrupt(1411),             -- 'pdinterrupt' (interrupt job)
        jobModify(1412),                -- 'pdmod' (set job attributes)
        jobPromote(1413),               -- 'pdpromote' (set to next job)
        jobRemove(1414),                -- 'pdrm' (cancel job)
        jobResubmit(1415),              -- 'pdresubmit' (resubmit job)
        jobManage(2401),                -- for future extensions
        --  POSIX - Document level operations (on/off-system jobs)


        docDelete(1502),                -- 'pddelete' (destroy document)
        docList(1503),                  -- 'pdls' (list doc attributes)
        docSet(1504),                   -- 'pdset' (set doc attributes)
        docModify(1512),                -- 'pdmod' (set doc attributes)
        docRemove(1514),                -- 'pdrm' (cancel document)
        docManage(2501)                 -- for future extensions
    }

XcmSimpleJobMgmtData ::= TEXTUAL-CONVENTION
    STATUS      current
    DESCRIPTION
        "The simple job management data associated with
        this conceptual row in the 'xcmSimpleJobMgmtTable'
        and the 'xcmJobGenBasicTable' (XCMI Job Monitoring MIB), OR
        this conceptual row in the 'xcmSimpleJobInterceptTable'
        and the 'xcmJobClientId' object (XCMI Job Monitoring MIB)."
    REFERENCE
        "See:   Security Config, Account, and User groups in
                XCMI Security MIB.
        See:    Section 6.6 'Security in DPA' (pages 38 to 39) of
                DPA (ISO 10175-1 / Final Text, March 1996).
        See:    Section 4 'Print Utilities' (pages 71 to 212) of
                POSIX Sys Admin (IEEE 1387.4 / Draft 8, October 1994).
        See:    OBJECT clauses in MODULE-COMPLIANCE macro of
                XCMI Simple Job Mgmt MIB, for compliance info."
    SYNTAX      OCTET STRING (SIZE (0..255))

--
--          Simple TC Dummy Group (DO NOT USE)
--
--          DO NOT USE - Present to suppress compiler warnings ONLY!
--
--          Note:  The following objects have 'odd' use of case in their
--          names (ie, 'xCm...'), in order to make obvious their related
--          textual conventions

xCmSimpleJobDummy   OBJECT IDENTIFIER ::= { xcmSimpleJobMgmtTC 999 }

xCmSimpleJobMgmtGroupSupport OBJECT-TYPE
    SYNTAX      XcmSimpleJobMgmtGroupSupport
    MAX-ACCESS  not-accessible
    STATUS      current
    DESCRIPTION "Dummy - DO NOT USE"
    ::= { xCmSimpleJobDummy 1 }

xCmSimpleJobMgmtOperation OBJECT-TYPE
    SYNTAX      XcmSimpleJobMgmtOperation
    MAX-ACCESS  not-accessible
    STATUS      current
    DESCRIPTION "Dummy - DO NOT USE"
    ::= { xCmSimpleJobDummy 2 }

xCmSimpleJobMgmtData OBJECT-TYPE
    SYNTAX      XcmSimpleJobMgmtData


    MAX-ACCESS  not-accessible
    STATUS      current
    DESCRIPTION "Dummy - DO NOT USE"
    ::= { xCmSimpleJobDummy 3 }

END

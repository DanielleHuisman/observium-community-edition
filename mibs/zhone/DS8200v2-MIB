-- $Header:   K:/WanSuite/archives/include/pvcs/ds8200v2.mib,v   1.40   Mar 19 2004 08:53:38   mikeh  $

DS8200v2-MIB DEFINITIONS ::= BEGIN

IMPORTS enterprises, 
        TimeTicks, 
        OBJECT-TYPE,
        MODULE-IDENTITY                 FROM SNMPv2-SMI
		DisplayString					FROM SNMPv2-TC
		verilink,hbu                    FROM DS8200v2-TC-MIB;

tinterfaces MODULE-IDENTITY
    LAST-UPDATED "0008180000Z" 
         ORGANIZATION "Verilink Corporation"
         CONTACT-INFO
            "support@verilink.com
             + 1 800 285 2755"
         DESCRIPTION
            "DS8200v2 MIB."
    ::= { hbu 2 }  
    --  { enterprises verilink hbu branch#2 (ipad is branch#1)

mgmtPorts       OBJECT IDENTIFIER ::= { tinterfaces 1 }
dbu             OBJECT IDENTIFIER ::= { tinterfaces 2 }
t1e1            OBJECT IDENTIFIER ::= { tinterfaces 3 }
ddsNet          OBJECT IDENTIFIER ::= { tinterfaces 4 }
serialDte       OBJECT IDENTIFIER ::= { tinterfaces 5 }
analogDte       OBJECT IDENTIFIER ::= { tinterfaces 6 }
connection      OBJECT IDENTIFIER ::= { tinterfaces 7 }
maintenance     OBJECT IDENTIFIER ::= { tinterfaces 8 }
performance     OBJECT IDENTIFIER ::= { tinterfaces 9 }
itable          OBJECT IDENTIFIER ::= { tinterfaces 10 }
traplog         OBJECT IDENTIFIER ::= { tinterfaces 11 }
unitUtilities   OBJECT IDENTIFIER ::= { tinterfaces 12 }
productInfo     OBJECT IDENTIFIER ::= { tinterfaces 13 }
netAPS          OBJECT IDENTIFIER ::= { tinterfaces 14 }

-- productInfo section
-- brought in from old TxPort.MIB

productModelNumber  OBJECT-TYPE
    SYNTAX        DisplayString( SIZE(0..100) )
    MAX-ACCESS    read-only
    STATUS        current
    DESCRIPTION
        "This string displays the units model number"
    ::= { productInfo 1 }

productModelDescr  OBJECT-TYPE
    SYNTAX      DisplayString( SIZE(0..100) )
    MAX-ACCESS  read-only
    STATUS      current
    DESCRIPTION
        "This string displays a brief description of the unit"
    ::= { productInfo 2 }    

productElementId  OBJECT-TYPE
    SYNTAX      DisplayString( SIZE(0..100) )
    MAX-ACCESS  read-write
    STATUS      current
    DESCRIPTION
        "This string is the same information that is in the 
        element id field located in the utilities Screen of 
        the unit's user interface. This field can be set from 
        either location."
    ::= { productInfo 3 }
    
productSoftwareRev  OBJECT-TYPE
    SYNTAX      DisplayString( SIZE(0..100) )
    MAX-ACCESS  read-only
    STATUS      current
    DESCRIPTION
        "This string reports the units current software revision"
    ::= { productInfo 4 }

productHardwareRev  OBJECT-TYPE
    SYNTAX      DisplayString( SIZE(0..100) )
    MAX-ACCESS  read-only
    STATUS      current
    DESCRIPTION
        "This string reports the units hardware revision"
    ::= { productInfo 5 }
    
productSerialNum  OBJECT-TYPE
    SYNTAX      DisplayString( SIZE(0..100) )
    MAX-ACCESS  read-only
    STATUS      current
    DESCRIPTION
        "This string displays the unit's serial number"
    ::= { productInfo 6 }

productPhysicalAddress  OBJECT-TYPE
    SYNTAX      DisplayString( SIZE(0..100) )
    MAX-ACCESS  read-only
    STATUS      current
    DESCRIPTION
        "This string displays the unit's physical ethernet 
        address"
    ::= { productInfo 7 }

productNmsAddress  OBJECT-TYPE
    SYNTAX      DisplayString( SIZE(0..100) )
    MAX-ACCESS  read-only
    STATUS      current
    DESCRIPTION
        "This string displays the unit's NMS address which
        is used to identify it to the TxPORT management products"
    ::= { productInfo 8 }

productLabelTable  OBJECT-TYPE
	SYNTAX  SEQUENCE OF ProductLabelTableEntry
	MAX-ACCESS  not-accessible
	STATUS  current
	DESCRIPTION
		"The Product Label Table."
	::= { productInfo 9 }

productLabelTableEntry     OBJECT-TYPE
	SYNTAX  ProductLabelTableEntry
	MAX-ACCESS  not-accessible
	STATUS  current
	DESCRIPTION
		"An entry in the product label table."
	INDEX   { labelTableIndex }
	::= { productLabelTable 1 }

ProductLabelTableEntry ::=
	SEQUENCE
	{
	labelTableIndex                 INTEGER,
	labelTableLabel                 DisplayString,
	labelTableValue                 DisplayString
	}

labelTableIndex        OBJECT-TYPE
    SYNTAX      INTEGER(1..3)
    MAX-ACCESS  not-accessible
    STATUS      current
    DESCRIPTION
        "The index into the ProductLabelTable."
    ::= { productLabelTableEntry 1 }

labelTableLabel         OBJECT-TYPE
    SYNTAX      DisplayString(SIZE(0..20))
    MAX-ACCESS  read-write
    STATUS      current
    DESCRIPTION
        "A product label."
    ::= { productLabelTableEntry 2 }
    
labelTableValue        OBJECT-TYPE
    SYNTAX      DisplayString(SIZE(0..50))
    MAX-ACCESS  read-write
    STATUS      current
    DESCRIPTION
        "The data associated with the label."
    ::= { productLabelTableEntry 3 }

-- mgmtPorts section
-- this section contains the configuration settings for the management ports 

mgmtPortsTable  OBJECT-TYPE
	SYNTAX  SEQUENCE OF MgmtPortsTableEntry
	MAX-ACCESS  not-accessible
	STATUS  current
	DESCRIPTION
		"The Management Ports table."
	::= { mgmtPorts 1 }

mgmtPortsTableEntry     OBJECT-TYPE
	SYNTAX  MgmtPortsTableEntry
	MAX-ACCESS  not-accessible
	STATUS  current
	DESCRIPTION
		"An entry in the Management Ports table."
	INDEX   { mgmtPortsTableIndex }
	::= { mgmtPortsTable 1 }

MgmtPortsTableEntry ::=
	SEQUENCE
	{
	mgmtPortsTableIndex             INTEGER,
	mgmtPortsDescription            DisplayString,
	mgmtPortsElementID              DisplayString,
	mgmtPortsMode                   INTEGER,
	mgmtPortsDialPrefix             DisplayString,
	mgmtPortsPrimaryDialString      DisplayString,
	mgmtPortsSecondaryDialString    DisplayString,
	mgmtPortsExtInitString          DisplayString,
	mgmtPortsCompressedSlip         INTEGER,
	mgmtPortsInternalModem          INTEGER
	}

mgmtPortsTableIndex     OBJECT-TYPE
	SYNTAX  INTEGER
	MAX-ACCESS  read-only
	STATUS  current
	DESCRIPTION
		"The index into the Management Ports table."
	::= { mgmtPortsTableEntry 1 }

mgmtPortsDescription    OBJECT-TYPE
	SYNTAX  DisplayString( SIZE(0..40) )
	MAX-ACCESS  read-only
	STATUS  current
	DESCRIPTION
		"Contains a textual description of the port."
	::= { mgmtPortsTableEntry 2 }

mgmtPortsElementID      OBJECT-TYPE
	SYNTAX  DisplayString( SIZE(0..27) )
	MAX-ACCESS  read-write
	STATUS  current
	DESCRIPTION
		"This object signifies the name of the device."
	::= { mgmtPortsTableEntry 3 }

mgmtPortsMode   OBJECT-TYPE
	SYNTAX  INTEGER
		{
		other(1),
		disabled(2),
		coadial(3),
		coadirect(4),
		extAlarmOnOpen(5),
		extAlarmOnClosed(6),
		slipdial(7),
		slipdirect(8)
		}
	MAX-ACCESS  read-write
	STATUS  current
	DESCRIPTION
		"This object signifies the method used by the port to report alarms."
	::= { mgmtPortsTableEntry 4 }

mgmtPortsDialPrefix     OBJECT-TYPE
	SYNTAX  DisplayString( SIZE(0..38) )
	MAX-ACCESS  read-write
	STATUS  current
	DESCRIPTION
		"This object contains the dial string prefix for a modem connected to the port."
	::= { mgmtPortsTableEntry 5 }

mgmtPortsPrimaryDialString      OBJECT-TYPE
	SYNTAX  DisplayString( SIZE(0..30) )
	MAX-ACCESS  read-write
	STATUS  current
	DESCRIPTION
		"This object contains the primary dial string for a modem connected to the port."
	::= { mgmtPortsTableEntry 6 }

mgmtPortsSecondaryDialString    OBJECT-TYPE
	SYNTAX  DisplayString( SIZE(0..30) )
	MAX-ACCESS  read-write
	STATUS  current
	DESCRIPTION
		"This object contains the secondary dial string for a modem connected to the port."
	::= { mgmtPortsTableEntry 7 }

mgmtPortsExtInitString  OBJECT-TYPE
	SYNTAX  DisplayString( SIZE(0..38) )
	MAX-ACCESS  read-write
	STATUS  current
	DESCRIPTION
		"This object contains the init string for a modem connected to the port."
	::= { mgmtPortsTableEntry 8 }
	
mgmtPortsCompressedSlip OBJECT-TYPE
	SYNTAX  INTEGER
		{
		other(1),
		enabled(2),
		disabled(3),
		auto(4)
		}
	MAX-ACCESS  read-write
	STATUS  current
	DESCRIPTION
		"This object specifies if SLIP compression is to be used."
	::= { mgmtPortsTableEntry 9 }

mgmtPortsInternalModem OBJECT-TYPE
	SYNTAX  INTEGER
		{
		other(1),
		notPresent(2),
		enabled(3),
		disabled(4)
		}
	MAX-ACCESS  read-write
	STATUS  current
	DESCRIPTION
		"This object signifies if the internal modem (when present) is enabled."
	::= { mgmtPortsTableEntry 10 }

-- dbu section
-- dial backup options for devices which have integrated or 
-- optional dial backup units

dbuConfigTable  OBJECT-TYPE
	SYNTAX  SEQUENCE OF DbuConfigTableEntry
	MAX-ACCESS  not-accessible
	STATUS  current
	DESCRIPTION
		"The Dial Backup Configuration Table."
	::= { dbu 1 }

dbuConfigTableEntry     OBJECT-TYPE
	SYNTAX  DbuConfigTableEntry
	MAX-ACCESS  not-accessible
	STATUS  current
	DESCRIPTION
		"An entry in the Dial Backup Configuration table."
	INDEX   { dbuNearIndex, dbuFarIndex, dbuConfigTableIndex }
	::= { dbuConfigTable 1 }

DbuConfigTableEntry ::=
	SEQUENCE
	{
	dbuNearIndex            INTEGER,
	dbuFarIndex             INTEGER,
	dbuConfigTableIndex     INTEGER,
	dbuDescription          DisplayString,
	dbuRate                 INTEGER,
	dbuMode                 INTEGER,
	dbuFormat               INTEGER,
	dbuNumber               DisplayString,
	dbuStatus               INTEGER,
	dbuCommand              INTEGER,
	dbuActivator1           INTEGER,
	dbuActivator2           INTEGER,
	dbuDialStr              DisplayString,
	dbuInitStr              DisplayString,
	dbuHangupStr            DisplayString,
	dbuPasswordStr          DisplayString,
	dbuSecurity             INTEGER,
	dbuDtrDial              INTEGER,
	dbuISDNSwitchType       INTEGER,
	dbuISDNSwitchVersion    INTEGER,
	dbuISDNTEI              INTEGER,
	dbuISDNSPID             DisplayString,
	dbuISDNDDNUM            DisplayString
	}

dbuNearIndex            OBJECT-TYPE
	SYNTAX  INTEGER
	MAX-ACCESS  read-only
	STATUS  current
	DESCRIPTION
		"Selects the near device."
	::= { dbuConfigTableEntry 1 }

dbuFarIndex             OBJECT-TYPE
	SYNTAX  INTEGER
	MAX-ACCESS  read-only
	STATUS  current
	DESCRIPTION
		"Selects the far device."
	::= { dbuConfigTableEntry 2 }
 
dbuConfigTableIndex     OBJECT-TYPE
	SYNTAX  INTEGER
	MAX-ACCESS  read-only
	STATUS  current
	DESCRIPTION
		"The index into the Dial Backup table."
	::= { dbuConfigTableEntry 3 }

dbuDescription  OBJECT-TYPE
	SYNTAX  DisplayString( SIZE(0..40) )
	MAX-ACCESS  read-only
	STATUS  current
	DESCRIPTION
		"Contains a textual description of the dbu."
	::= { dbuConfigTableEntry 4 }

dbuRate OBJECT-TYPE
	SYNTAX  INTEGER 
		{
		dbuRateOther(1),
		dbuRate2400(2),
		dbuRate4800(3),
		dbuRate9600(4),
		dbuRate19200(5),
		dbuRate38400(6),
		dbuRate56000(7),
		dbuRate57600(8),
		dbuRate64000(9)
		}
	MAX-ACCESS  read-write
	STATUS  current
	DESCRIPTION
		"This object is the identifier of the current DDS
DBU rate. The values mean:
dbuRate2400
   the DBU interface is operating at 2400bps
dbuRate4800
   the DBU interface is operating at 4800bps
dbuRate9600
   the DBU interface is operating at 9600bps
dbuRate19200
   the DBU interface is operating at 19200bps
dbuRate38400
   the DBU interface is operating at 38400bps
dbuRate56000
   the DBU interface is operating at 56000bps
dbuRate57600
   the DBU interface is operating at 57600bps
dbuRate64000
   the DBU interface is operating at 64000bps"
	::=  { dbuConfigTableEntry 5 }

dbuMode OBJECT-TYPE
	SYNTAX  INTEGER 
		{
		dbuModeOther(1),
		dbuModeOrig(2),
		dbuModeAnsw(3),
		dbuModeNotAvail(4),
		dbuModeCallbackOrig(5),
		dbuModeCallbackAnsw(6),
		dbuModeMaster(7),
		dbuModeSlave(8)
		}
	MAX-ACCESS  read-write
	STATUS  current
	DESCRIPTION
		"This object is the identifier of the current
mode that the Dial Backup Unit is operating
in. The values mean:
dbuModeOrig
   The dial backup unit is operating in the
   originate mode
dbuModeAnsw
   The dial backup unit is operating in the
   answer mode
dbuModeNotAvail
   The dial backup unit's mode is not
   available
dbuModeCallbackOrig
   The dial backup unit is operating in the
   callback originate mode
dbuModeCallbackAnsw
   The dial backup unit is operating in the
   callback mode
dbuModeMaster
   The dial backup unit is configured as a 
   master unit 
dbuModeSlave
   The dial backup unit is configured as a
   slave unit"
	::=  { dbuConfigTableEntry 6 }

dbuFormat       OBJECT-TYPE
	SYNTAX  INTEGER 
		{
		dbuFormatOther(1),
		dbuFormatSync(2),
		dbuFormatAsync(3),
		dbuFormatNotAvail(4)
		}
	MAX-ACCESS  read-write
	STATUS  current
	DESCRIPTION
		"This object is the identifier of the current
format that the Dial Backup Unit is operating
in. The values mean:
dbuFormatSync
   The dial backup unit is operating in the
   synchronous format
dbuFormatAsync
   The dial backup unit is operating in the
   asynchronous format
dbuFormatNotAvail
   The dial backup unit's format is
   not available"
	::=  { dbuConfigTableEntry 7 }

dbuNumber       OBJECT-TYPE
	SYNTAX  DisplayString( SIZE(0..100) )
	MAX-ACCESS  read-write
	STATUS  current
	DESCRIPTION
		"This string is the currently programmed number
for the dial backup unit to call"
	::=  { dbuConfigTableEntry 8 }

dbuStatus       OBJECT-TYPE
	SYNTAX  INTEGER 
		{
		dbuStatusOther(1),
		dbuStatusDisabled(2),
		dbuStatusEnabled(3),
		dbuStatusActive(4),
		dbuStatusLocked(5),
		dbuStatusConnecting(6),
		dbuStatusDisallowed(7),
		dbuStatusAwaitingCall(8),
		dbuStatusDialing(9),
		dbuStatusDisconnecting(10),
		dbuStatusTesting(11),
		dbuStatusTestPassed(12),
		dbuStatusTestFailed(13)
		}
	MAX-ACCESS  read-only
	STATUS  current
	DESCRIPTION
		"This object is the identifier of the current
Dial Backup Unit operating status.
The values mean:
dbuStatusDisabled
   The dial backup unit is either not
   installed or disabled
dbuStatusEnabled
   The dial backup unit is installed
   and enabled
dbuStatusActive
   The dial backup unit is currently
   active
dbuStatusLocked
   The dial backup unit is in a locked
   state
dbuStatusConnecting
   The dial backup unit is in the process
   of connecting
dbuStatusDisallowed
   The dial backup unit is currently not
   allowed to activate due to the Time
   Of Day Enable settings
dbuStatusAwaitingCall
   The dial backup unit is in the process
   of waiting for an incoming call
dbuStatusDialing
   The dial backup unit is in the process
   of placing a call
dbuStatusDisconnecting
   The dial backup unit is in the process
   of disconnecting
dbuStatusTesting
   The dial backup unit is in the process 
   of testing
dbuStatusTestPassed
   The dial backup unit has passed a self-test
dbuStatusTestFailed
   The dial backup unit has failed a self-test"
	::=  { dbuConfigTableEntry 9 }

dbuCommand      OBJECT-TYPE
	SYNTAX  INTEGER 
		{
		dbuCommandOther(1),
		dbuCommandDisable(2),
		dbuCommandEnable(3),
		dbuCommandActivate(4),
		dbuCommandLock(5),
		dbuCommandEnableDaily(6),
		dbuCommandTest(7)
		}
	MAX-ACCESS  read-write
	STATUS  current
	DESCRIPTION
		"This object is the identifier of the current
setting that the Dial Backup Unit is operating
in. The values mean:
dbuCommandDisable
   The dial backup unit is not to operate
dbuCommandEnable
   The dial backup unit is to operate, subject
   to Activator and line conditions only
dbuCommandActivate
   The dial backup unit is to operate,
   irregardless of line conditions
dbuCommandLock
   The dial backup unit is to continue operating,
   irregardless of line conditions
dbuCommandEnableDaily
   The dial backup unit is to operate, subject
   to Activator, line conditions, and the Time
   Of Day Enable fields
dbuCommandTest
   The dial backup unit is commanded to test
   the link."
	::=  { dbuConfigTableEntry 10 }

dbuActivator1   OBJECT-TYPE
	SYNTAX  INTEGER 
		{
		dbuActivatorOther(1),
		dbuActivatorLOS(2),
		dbuActivatorOOS(3),
		dbuActivatorOOF(4),
		dbuActivatorAny(5),
		dbuActivatorES(6),
		dbuActivatorSES(7),
		dbuActivatorUAS(8),
		dbuActivatorLOF(9),
		dbuActivatorRAS(10),
		dbuActivatorAIS(11),
		dbuActivatorBPV(12)
		}
	MAX-ACCESS  read-write
	STATUS  current
	DESCRIPTION
		"This object is the identifier of the current
trigger that will activate the Dial Backup
Unit. The values mean:
dbuActivatorLOS
   The dial backup unit is activated by a
   LOS alarm condition
dbuActivatorOOS
   The dial backup unit is activated by an
   OOS alarm condition
dbuActivatorOOF
   The dial backup unit is activated by an
   OOF alarm condition
dbuActivatorAny
   The dial backup unit is activated by a
   LOS, OOS, or OOF alarm condition
dbuActivatorES
   The dial backup unit is activated by an
   ES alarm condition
dbuActivatorSES
   The dial backup unit is activated by an
   SES alarm condition
dbuActivatorUAS
   The dial backup unit is activated by an
   UAS alarm condition
dbuActivatorLOF
   The dial backup unit is activated by an
   LOF alarm condition
dbuActivatorRAS
   The dial backup unit is activated by an
   RAS alarm condition
dbuActivatorAIS
   The dial backup unit is activated by an
   AIS alarm condition
dbuActivatorBPV
   The dial backup unit is activated by an
   BPV alarm condition"
	::=  { dbuConfigTableEntry 11 }

dbuActivator2   OBJECT-TYPE
	SYNTAX  INTEGER 
		{
		dbuActivatorOther(1),
		dbuActivatorLOS(2),
		dbuActivatorOOS(3),
		dbuActivatorOOF(4),
		dbuActivatorAny(5),
		dbuActivatorES(6),
		dbuActivatorSES(7),
		dbuActivatorUAS(8),
		dbuActivatorLOF(9),
		dbuActivatorRAS(10),
		dbuActivatorAIS(11),
		dbuActivatorBPV(12)
		}
	MAX-ACCESS  read-write
	STATUS  current
	DESCRIPTION
		"This object is the identifier of the current
trigger that will activate the Dial Backup
Unit. The values mean:
dbuActivatorLOS
   The dial backup unit is activated by a
   LOS alarm condition
dbuActivatorOOS
   The dial backup unit is activated by a
   OOS alarm condition
dbuActivatorOOF
   The dial backup unit is activated by a
   OOF alarm condition
dbuActivatorAny
   The dial backup unit is activated by a
   LOS, OOS, or OOF alarm condition
dbuActivatorES
   The dial backup unit is activated by an
   ES alarm condition
dbuActivatorSES
   The dial backup unit is activated by an
   SES alarm condition
dbuActivatorUAS
   The dial backup unit is activated by an
   UAS alarm condition
dbuActivatorLOF
   The dial backup unit is activated by an
   LOF alarm condition
dbuActivatorRAS
   The dial backup unit is activated by an
   RAS alarm condition
dbuActivatorAIS
   The dial backup unit is activated by an
   AIS alarm condition
dbuActivatorBPV
   The dial backup unit is activated by an
   BPV alarm condition"
	::=  { dbuConfigTableEntry 12 }

dbuDialStr      OBJECT-TYPE
	SYNTAX  DisplayString( SIZE(0..50) )
	MAX-ACCESS  read-write
	STATUS  current
	DESCRIPTION
		"This string is the dial string sent to the dial backup unit during every connection attempt"
	::=  { dbuConfigTableEntry 13 }
	
dbuInitStr      OBJECT-TYPE
	SYNTAX  DisplayString( SIZE(0..50) )
	MAX-ACCESS  read-write
	STATUS  current
	DESCRIPTION
		"This string is the initialization string sent to the dial backup unit before every connection attempt"
	::=  { dbuConfigTableEntry 14 }

dbuHangupStr    OBJECT-TYPE
	SYNTAX  DisplayString( SIZE(0..50) )
	MAX-ACCESS  read-write
	STATUS  current
	DESCRIPTION
		"This string is the hangup command string sent to the dial backup unit after every successful call"
	::=  { dbuConfigTableEntry 15 }

dbuPasswordStr  OBJECT-TYPE
	SYNTAX  DisplayString( SIZE(0..8) )
	MAX-ACCESS  read-write
	STATUS  current
	DESCRIPTION
		"This string is the prompt character and password string for the dial backup unit in Callback DBU"
	::=  { dbuConfigTableEntry 16 }

dbuSecurity     OBJECT-TYPE
	SYNTAX  INTEGER
		{
		dbuSecurityOther(1),
		dbuSecurityDisable(2),
		dbuSecurityEnable(3)
		}
	MAX-ACCESS  read-write
	STATUS  current
	DESCRIPTION
		"Enables security on dial backup unit."
	::= { dbuConfigTableEntry 17 }
	
dbuDtrDial      OBJECT-TYPE
	SYNTAX  INTEGER
		{
		dbuDtrDialOther(1),
		dbuDtrDialDisable(2),
		dbuDtrDialEnable(3)
		}
	MAX-ACCESS  read-write
	STATUS  current
	DESCRIPTION
		"Enables DTR dial feature on dial backup unit."
	::= { dbuConfigTableEntry 18 }

dbuISDNSwitchType       OBJECT-TYPE
	SYNTAX  INTEGER
	MAX-ACCESS  read-write
	STATUS  current
	DESCRIPTION
		"Specifies the switch type for the ISDN DBU."
	::= { dbuConfigTableEntry 19 }

dbuISDNSwitchVersion    OBJECT-TYPE
	SYNTAX  INTEGER
		{
		dbuISDNSwitchVersionOther(1),
		dbuISDNSwitchVersionNational1(2),
		dbuISDNSwitchVersionATTP2P(3),
		dbuISDNSwitchVersionATTMP(4),
		dbuISDNSwitchVersionDMS100PVCIC0(5),
		dbuISDNSwitchVersionDMS100PVCIC1(6)
		}
	MAX-ACCESS  read-write
	STATUS  current
	DESCRIPTION
		"Specifies the switch version for the ISDN DBU."
	::= { dbuConfigTableEntry 20 }

dbuISDNTEI      OBJECT-TYPE
	SYNTAX  INTEGER
		{
		dbuISDNTEIOther(1),
		dbuISDNTEIDisable(2),
		dbuISDNTEIAuto(3),
		dbuISDNTEI0(4),
		dbuISDNTEI1(5),
		dbuISDNTEI2(6),
		dbuISDNTEI3(7),
		dbuISDNTEI4(8),
		dbuISDNTEI5(9),
		dbuISDNTEI6(10),
		dbuISDNTEI7(11),
		dbuISDNTEI8(12),
		dbuISDNTEI9(13),
		dbuISDNTEI10(14),
		dbuISDNTEI11(15),
		dbuISDNTEI12(16),
		dbuISDNTEI13(17),
		dbuISDNTEI14(18),
		dbuISDNTEI15(19),
		dbuISDNTEI16(20),
		dbuISDNTEI17(21),
		dbuISDNTEI18(22),
		dbuISDNTEI19(23),
		dbuISDNTEI20(24),
		dbuISDNTEI21(25),
		dbuISDNTEI22(26),
		dbuISDNTEI23(27),
		dbuISDNTEI24(28),
		dbuISDNTEI25(29),
		dbuISDNTEI26(30),
		dbuISDNTEI27(31),
		dbuISDNTEI28(32),
		dbuISDNTEI29(33),
		dbuISDNTEI30(34),
		dbuISDNTEI31(35),
		dbuISDNTEI32(36),
		dbuISDNTEI33(37),
		dbuISDNTEI34(38),
		dbuISDNTEI35(39),
		dbuISDNTEI36(40),
		dbuISDNTEI37(41),
		dbuISDNTEI38(42),
		dbuISDNTEI39(43),
		dbuISDNTEI40(44),
		dbuISDNTEI41(45),
		dbuISDNTEI42(46),
		dbuISDNTEI43(47),
		dbuISDNTEI44(48),
		dbuISDNTEI45(49),
		dbuISDNTEI46(50),
		dbuISDNTEI47(51),
		dbuISDNTEI48(52),
		dbuISDNTEI49(53),
		dbuISDNTEI50(54),
		dbuISDNTEI51(55),
		dbuISDNTEI52(56),
		dbuISDNTEI53(57),
		dbuISDNTEI54(58),
		dbuISDNTEI55(59),
		dbuISDNTEI56(60),
		dbuISDNTEI57(61),
		dbuISDNTEI58(62),
		dbuISDNTEI59(63),
		dbuISDNTEI60(64),
		dbuISDNTEI61(65),
		dbuISDNTEI62(66),
		dbuISDNTEI63(67)
		}
	MAX-ACCESS  read-write
	STATUS  current
	DESCRIPTION
		"Specifies the ISDN DBU TEI."
	::= { dbuConfigTableEntry 21 }

dbuISDNSPID     OBJECT-TYPE
	SYNTAX  DisplayString(SIZE(0..20))
	MAX-ACCESS  read-write
	STATUS  current
	DESCRIPTION
		"Specifies the SPID for the ISDN DBU."
	::= { dbuConfigTableEntry 22 }

dbuISDNDDNUM    OBJECT-TYPE
	SYNTAX  DisplayString(SIZE(0..20))
	MAX-ACCESS  read-write
	STATUS  current
	DESCRIPTION
		"Specifies the Data Directory Number for the ISDN DBU."
	::= { dbuConfigTableEntry 23 }

dbuResetStringsTable    OBJECT-TYPE
	SYNTAX  SEQUENCE OF DbuResetStringsEntry
	MAX-ACCESS  not-accessible
	STATUS  current
	DESCRIPTION
		"A table of COLD START reprogramming strings for the dial backup unit."
	::= { dbu 2 }

dbuResetStringsEntry    OBJECT-TYPE
	SYNTAX  DbuResetStringsEntry
	MAX-ACCESS  not-accessible
	STATUS  current
	DESCRIPTION
		"An entry in the dbuResetStringsTable."
	INDEX   { dbuResetNearIndex, dbuResetFarIndex, dbuResetConfigEntryIndex, dbuResetStringsIndex }
	::= { dbuResetStringsTable 1 }

DbuResetStringsEntry ::=
	SEQUENCE
	{
	dbuResetNearIndex               INTEGER,
	dbuResetFarIndex                INTEGER,
	dbuResetConfigEntryIndex        INTEGER,
	dbuResetStringsIndex            INTEGER,
	dbuResetString                  DisplayString
	}

dbuResetNearIndex               OBJECT-TYPE
	SYNTAX  INTEGER
	MAX-ACCESS  read-only
	STATUS  current
	DESCRIPTION
		"Selects the near device."
	::= { dbuResetStringsEntry 1 }

dbuResetFarIndex                OBJECT-TYPE
	SYNTAX  INTEGER
	MAX-ACCESS  read-only
	STATUS  current
	DESCRIPTION
		"Selects the far device."
	::= { dbuResetStringsEntry 2 }

dbuResetConfigEntryIndex        OBJECT-TYPE
	SYNTAX  INTEGER
	MAX-ACCESS  read-only
	STATUS  current
	DESCRIPTION
		"The index into the Dial Backup table."
	::= { dbuResetStringsEntry 3 }

dbuResetStringsIndex    OBJECT-TYPE
	SYNTAX  INTEGER
	MAX-ACCESS  read-only
	STATUS  current
	DESCRIPTION
		"The index into the dbuResetStringsTable."
	::= { dbuResetStringsEntry 4 }

dbuResetString  OBJECT-TYPE
	SYNTAX  DisplayString( SIZE(0..50) )
	MAX-ACCESS  read-write
	STATUS  current
	DESCRIPTION
		"This string is one of the dial backup unit's COLD START reprogramming strings"
	::=  { dbuResetStringsEntry 5 }

dbuStartStopTable       OBJECT-TYPE
	SYNTAX  SEQUENCE OF DbuStartStopTableEntry
	MAX-ACCESS  not-accessible
	STATUS  current
	DESCRIPTION
		"The Dial Backup StartStop Table."
	::= { dbu 3 }

dbuStartStopTableEntry  OBJECT-TYPE
	SYNTAX  DbuStartStopTableEntry
	MAX-ACCESS  not-accessible
	STATUS  current
	DESCRIPTION
		"An entry in the Dial Backup Start Stop table."
	INDEX   { dbuStartStopNearIndex, dbuStartStopFarIndex, dbuStartStopConfigEntryIndex, dbuStartStopDayOfWeek }
	::= { dbuStartStopTable 1 }

DbuStartStopTableEntry ::=
	SEQUENCE
	{
	dbuStartStopNearIndex           INTEGER,
	dbuStartStopFarIndex            INTEGER,
	dbuStartStopConfigEntryIndex    INTEGER,
	dbuStartStopDayOfWeek           INTEGER,
	dbuStart                        INTEGER,
	dbuStop                         INTEGER
	}

dbuStartStopNearIndex           OBJECT-TYPE
	SYNTAX  INTEGER
	MAX-ACCESS  read-only
	STATUS  current
	DESCRIPTION
		"Selects the near device."
	::= { dbuStartStopTableEntry 1 }

dbuStartStopFarIndex            OBJECT-TYPE
	SYNTAX  INTEGER
	MAX-ACCESS  read-only
	STATUS  current
	DESCRIPTION
		"Selects the far device."
	::= { dbuStartStopTableEntry 2 }

dbuStartStopConfigEntryIndex    OBJECT-TYPE
	SYNTAX  INTEGER
	MAX-ACCESS  read-only
	STATUS  current
	DESCRIPTION
		"The index into the Dial Backup table."
	::= { dbuStartStopTableEntry 3 }

dbuStartStopDayOfWeek   OBJECT-TYPE
	SYNTAX  INTEGER
		{
		dbuStartStopSunday(1),
		dbuStartStopMonday(2),
		dbuStartStopTuesday(3),
		dbuStartStopWednesday(4),
		dbuStartStopThursday(5),
		dbuStartStopFriday(6),
		dbuStartStopSaturday(7)
		}
	MAX-ACCESS  read-only
	STATUS  current
	DESCRIPTION
		"The index into the Dial Backup Start Stop times table."
	::= { dbuStartStopTableEntry 4 }

dbuStart        OBJECT-TYPE
	SYNTAX  INTEGER 
		{
		dbuStartHour00(1),
		dbuStartHour01(2),
		dbuStartHour02(3),
		dbuStartHour03(4),
		dbuStartHour04(5),
		dbuStartHour05(6),
		dbuStartHour06(7),
		dbuStartHour07(8),
		dbuStartHour08(9),
		dbuStartHour09(10),
		dbuStartHour10(11),
		dbuStartHour11(12),
		dbuStartHour12(13),
		dbuStartHour13(14),
		dbuStartHour14(15),
		dbuStartHour15(16),
		dbuStartHour16(17),
		dbuStartHour17(18),
		dbuStartHour18(19),
		dbuStartHour19(20),
		dbuStartHour20(21),
		dbuStartHour21(22),
		dbuStartHour22(23),
		dbuStartHour23(24)
		}
	MAX-ACCESS  read-write
	STATUS  current
	DESCRIPTION
		"This object is the beginning of an allowable window for Dial Backup Activation."
	::=  { dbuStartStopTableEntry 5 }

dbuStop OBJECT-TYPE
	SYNTAX  INTEGER 
		{
		dbuStopHour00(1),
		dbuStopHour01(2),
		dbuStopHour02(3),
		dbuStopHour03(4),
		dbuStopHour04(5),
		dbuStopHour05(6),
		dbuStopHour06(7),
		dbuStopHour07(8),
		dbuStopHour08(9),
		dbuStopHour09(10),
		dbuStopHour10(11),
		dbuStopHour11(12),
		dbuStopHour12(13),
		dbuStopHour13(14),
		dbuStopHour14(15),
		dbuStopHour15(16),
		dbuStopHour16(17),
		dbuStopHour17(18),
		dbuStopHour18(19),
		dbuStopHour19(20),
		dbuStopHour20(21),
		dbuStopHour21(22),
		dbuStopHour22(23),
		dbuStopHour23(24)
		}
	MAX-ACCESS  read-write
	STATUS  current
	DESCRIPTION
		"This object is the end of an allowable window for Dial Backup Activation."
	::=  { dbuStartStopTableEntry 6 }

-- t1e1 section, contains T1 and E1 Network and DTE interface table

t1e1ConfigTable OBJECT-TYPE
	SYNTAX  SEQUENCE OF T1e1ConfigTableEntry
	MAX-ACCESS  not-accessible
	STATUS  current
	DESCRIPTION
		"The T1 and E1 Configuration Table."
	::= { t1e1 1 }

t1e1ConfigTableEntry    OBJECT-TYPE
	SYNTAX  T1e1ConfigTableEntry
	MAX-ACCESS  not-accessible
	STATUS  current
	DESCRIPTION
		"An entry in the t1e1Table."
	INDEX   { t1e1ConfigNearIndex, t1e1ConfigFarIndex, t1e1ConfigIndex }
	::= { t1e1ConfigTable 1 }

T1e1ConfigTableEntry ::=
	SEQUENCE
	{
	t1e1ConfigNearIndex     INTEGER,
	t1e1ConfigFarIndex      INTEGER,
	t1e1ConfigIndex         INTEGER,
	t1e1Description         DisplayString,
	t1e1Mode                INTEGER,
	t1e1FrameType           INTEGER,
	t1e1LineCode            INTEGER,
	t1e1LineBuildOut        INTEGER,
	t1e1Timing              INTEGER,
	t1e1StationInTiming     INTEGER,
	t1e1StationTiming       INTEGER,
	t1e1PRM                 INTEGER,
	t1e1ZeroSuppress        INTEGER,
	t1e1NationalBit         INTEGER,
	t1e1KeepAlive           INTEGER,
	t1e1CRC4Mode            INTEGER,
	t1e1DSXLevel            INTEGER,
	t1e1CRC                 INTEGER,
	t1e1FDLPassThrough      INTEGER,
	t1e1AudibleAlarm        INTEGER,
	t1e1Function            INTEGER,
	t1e1EBitGeneration      INTEGER,
	t1e1RAIGeneration       INTEGER,
	t1e1SpareBitInsertion   INTEGER,
	t1e1Sa4In               OCTET STRING,
	t1e1Sa5In               OCTET STRING,
	t1e1Sa6In               OCTET STRING,
	t1e1Sa7In               OCTET STRING,
	t1e1Sa8In               OCTET STRING,
	t1e1Sa4Out              OCTET STRING,
	t1e1Sa5Out              OCTET STRING,
	t1e1Sa6Out              OCTET STRING,
	t1e1Sa7Out              OCTET STRING,
	t1e1Sa8Out              OCTET STRING
	}

t1e1ConfigNearIndex             OBJECT-TYPE
	SYNTAX  INTEGER
	MAX-ACCESS  read-only
	STATUS  current
	DESCRIPTION
		"Selects the near device."
	::= { t1e1ConfigTableEntry 1 }

t1e1ConfigFarIndex              OBJECT-TYPE
	SYNTAX  INTEGER
	MAX-ACCESS  read-only
	STATUS  current
	DESCRIPTION
		"Selects the far device."
	::= { t1e1ConfigTableEntry 2 }

t1e1ConfigIndex         OBJECT-TYPE
	SYNTAX  INTEGER
	MAX-ACCESS  read-only
	STATUS  current
	DESCRIPTION
		"This object is the index into the t1e1Table."
	::= { t1e1ConfigTableEntry 3 }

t1e1Description OBJECT-TYPE
	SYNTAX  DisplayString( SIZE(0..40) )
	MAX-ACCESS  read-only
	STATUS  current
	DESCRIPTION
		"Contains a textual description of the port."
	::= { t1e1ConfigTableEntry 4 }

t1e1Mode        OBJECT-TYPE
	SYNTAX  INTEGER
		{
		t1e1ModeOther(1),
		t1e1ModeDTE(2),
		t1e1ModeNetwork(3)
		}
	MAX-ACCESS  read-write
	STATUS  current
	DESCRIPTION
		"This object identifies the port as either a Network (long-haul) or DTE (short-haul) port."
	::= { t1e1ConfigTableEntry 5 }

t1e1FrameType   OBJECT-TYPE
	SYNTAX  INTEGER
		{
		t1e1FrameTypeOther(1),
		t1e1FrameTypeESF(2),
		t1e1FrameTypeD4(3),
		t1e1FrameTypeCCSCRC(4),
		t1e1FrameTypeCCS(5),
		t1e1FrameTypeCAS(6),
		t1e1FrameTypeCASCRC(7),
		t1e1FrameTypeUnframed(8),
		t1e1FrameTypeV3(9),
		t1e1FrameTypeT1Unframed(10)
		}
	MAX-ACCESS  read-write
	STATUS  current
	DESCRIPTION     
		"Selects the framing for the network side of the DSU/CSU."
	::= { t1e1ConfigTableEntry 6 }

t1e1LineCode    OBJECT-TYPE
	SYNTAX  INTEGER
		{
		t1e1LineCodeOther(1),
		t1e1LineCodeAMI(2),
		t1e1LineCodeB8ZS(3),
		t1e1LineCodeHDB3(4)     
		}
	MAX-ACCESS  read-write
	STATUS  current
	DESCRIPTION
		"Selects the network side line coding."
	::= { t1e1ConfigTableEntry 7 }

t1e1LineBuildOut        OBJECT-TYPE
	SYNTAX  INTEGER
		{
		t1e1LineBuildOutOther(1),
		t1e1LineBuildOut0db(2),
		t1e1LineBuildOut75db(3),
		t1e1LineBuildOut15db(4),
		t1e1LineBuildOut225db(5)
		}
	MAX-ACCESS  read-write
	STATUS  current
	DESCRIPTION
		"Selects the line build out for the network interface.  The options are:
t1e1LineBuildOut0db     indicates a line build out of 0db
t1e1LineBuildOut75db   indicates a line build out of -7.5db
t1e1LineBuildOut15db    indicates a line build out of -15db
t1e1LineBuildOut225db  indicates a line build out of -22.5db"
	::= { t1e1ConfigTableEntry 8 }

t1e1Timing      OBJECT-TYPE
	SYNTAX  INTEGER
		{
		t1e1TimingOther(1),
		t1e1TimingInternal(2),
		t1e1TimingNetwork(3),
		t1e1TimingT1DTE(4),
		t1e1TimingStation(5),
		t1e1TimingStaClock(6),

		t1e1TimingPort1(7),
		t1e1TimingPort2(8),
		t1e1TimingPort3(9),
		t1e1TimingPort4(10),
		t1e1TimingPort5(11),
		t1e1TimingPort6(12),
		t1e1TimingPort7(13),
		t1e1TimingPort8(14),
		t1e1TimingPort9(15),
		t1e1TimingPort10(16),
		t1e1TimingPort11(17),
		t1e1TimingPort12(18),
		t1e1TimingPort13(19),
		t1e1TimingPort14(20),
		t1e1TimingPort15(21),
		t1e1TimingPort16(22),
		t1e1TimingPort17(23),
		t1e1TimingPort18(24),
		t1e1TimingPort19(25),
		t1e1TimingPort20(26),
		t1e1TimingPort21(27),
		t1e1TimingPort22(28),
		t1e1TimingPort23(29),
		t1e1TimingPort24(30),
		t1e1TimingPort25(31),
		t1e1TimingPort26(32),
		t1e1TimingPort27(33),
		t1e1TimingPort28(34),
		t1e1TimingPort29(35),
		t1e1TimingPort30(36),
		t1e1TimingPort31(37),
		t1e1TimingPort32(38),

		t1e1TimingSlot2PortA(39),
		t1e1TimingSlot2PortB(40),
		t1e1TimingSlot3PortA(41),
		t1e1TimingSlot3PortB(42),
		t1e1TimingSlot4PortA(43),
		t1e1TimingSlot4PortB(44),
		t1e1TimingSlot5PortA(45),
		t1e1TimingSlot5PortB(46),
		t1e1TimingSlot6PortA(47),
		t1e1TimingSlot6PortB(48),

		t1e1TimingSlot2Dsu1PortA(49),
		t1e1TimingSlot2Dsu1PortB(50),
		t1e1TimingSlot2Dsu2PortA(51),
		t1e1TimingSlot2Dsu2PortB(52),
		t1e1TimingSlot2Dsu3PortA(53),
		t1e1TimingSlot2Dsu3PortB(54),
		t1e1TimingSlot2Dsu4PortA(55),
		t1e1TimingSlot2Dsu4PortB(56),
		t1e1TimingSlot2Dsu5PortA(57),
		t1e1TimingSlot2Dsu5PortB(58),
		t1e1TimingSlot2Dsu6PortA(59),
		t1e1TimingSlot2Dsu6PortB(60),

		t1e1TimingSlot3Dsu1PortA(61),
		t1e1TimingSlot3Dsu1PortB(62),
		t1e1TimingSlot3Dsu2PortA(63),
		t1e1TimingSlot3Dsu2PortB(64),
		t1e1TimingSlot3Dsu3PortA(65),
		t1e1TimingSlot3Dsu3PortB(66),
		t1e1TimingSlot3Dsu4PortA(67),
		t1e1TimingSlot3Dsu4PortB(68),
		t1e1TimingSlot3Dsu5PortA(69),
		t1e1TimingSlot3Dsu5PortB(70),
		t1e1TimingSlot3Dsu6PortA(71),
		t1e1TimingSlot3Dsu6PortB(72),

		t1e1TimingSlot4Dsu1PortA(73),
		t1e1TimingSlot4Dsu1PortB(74),
		t1e1TimingSlot4Dsu2PortA(75),
		t1e1TimingSlot4Dsu2PortB(76),
		t1e1TimingSlot4Dsu3PortA(77),
		t1e1TimingSlot4Dsu3PortB(78),
		t1e1TimingSlot4Dsu4PortA(79),
		t1e1TimingSlot4Dsu4PortB(80),
		t1e1TimingSlot4Dsu5PortA(81),
		t1e1TimingSlot4Dsu5PortB(82),
		t1e1TimingSlot4Dsu6PortA(83),
		t1e1TimingSlot4Dsu6PortB(84),

		t1e1TimingSlot5Dsu1PortA(85),
		t1e1TimingSlot5Dsu1PortB(86),
		t1e1TimingSlot5Dsu2PortA(87),
		t1e1TimingSlot5Dsu2PortB(88),
		t1e1TimingSlot5Dsu3PortA(89),
		t1e1TimingSlot5Dsu3PortB(90),
		t1e1TimingSlot5Dsu4PortA(91),
		t1e1TimingSlot5Dsu4PortB(92),
		t1e1TimingSlot5Dsu5PortA(93),
		t1e1TimingSlot5Dsu5PortB(94),
		t1e1TimingSlot5Dsu6PortA(95),
		t1e1TimingSlot5Dsu6PortB(96),

		t1e1TimingSlot6Dsu1PortA(97),
		t1e1TimingSlot6Dsu1PortB(98),
		t1e1TimingSlot6Dsu2PortA(99),
		t1e1TimingSlot6Dsu2PortB(100),
		t1e1TimingSlot6Dsu3PortA(101),
		t1e1TimingSlot6Dsu3PortB(102),
		t1e1TimingSlot6Dsu4PortA(103),
		t1e1TimingSlot6Dsu4PortB(104),
		t1e1TimingSlot6Dsu5PortA(105),
		t1e1TimingSlot6Dsu5PortB(106),
		t1e1TimingSlot6Dsu6PortA(107),
		t1e1TimingSlot6Dsu6PortB(108)
		}
	MAX-ACCESS  read-write
	STATUS  current
	DESCRIPTION
		"Sets the timing source to synchronize the unit's internal timing generators."
	::= { t1e1ConfigTableEntry 9 }

t1e1StationInTiming OBJECT-TYPE
	SYNTAX  INTEGER
		{
		t1e1StationInTimingOther(1),
		t1e1StationInTimingNX56(2),
		t1e1StationInTimingNX64(3),
		t1e1StationInTiming1544(4),
		t1e1StationInTiming2048(5)
		}
	MAX-ACCESS  read-write
	STATUS  current
	DESCRIPTION
		"Selects the input timing if t1e1Timing is set to Station."
	::= { t1e1ConfigTableEntry 10 }

t1e1StationTiming OBJECT-TYPE
	SYNTAX  INTEGER
	MAX-ACCESS  read-write
	STATUS  current
	DESCRIPTION
		"Selects the N-multiple when Station Input Timing is set to either NX56 or NX65.  The N range is 1..24"
	::= { t1e1ConfigTableEntry 11 }

t1e1PRM OBJECT-TYPE
	SYNTAX  INTEGER
		{
		t1e1PRMOther(1),
		t1e1PRMDisable(2),
		t1e1PRMEnable(3)
		}
	MAX-ACCESS  read-write
	STATUS  current
	DESCRIPTION
		"Enables the ANSI T1.403 Performance Report Message functions."
	::= { t1e1ConfigTableEntry 12 }

t1e1ZeroSuppress        OBJECT-TYPE
	SYNTAX  INTEGER
		{
		t1e1ZeroOther(1),
		t1e1ZeroDisable(2),
		t1e1ZeroEnable(3)
		}
	MAX-ACCESS  read-write
	STATUS  current
	DESCRIPTION
		"Determines whether ones density insertion is activated after 15 zeros .  To ensure compliance with TR54016, this field must be enabled."
	::= { t1e1ConfigTableEntry 13 }

t1e1NationalBit OBJECT-TYPE
	SYNTAX  INTEGER
		{
		t1e1NationalOther(1),
		t1e1NationalNone(2),
		t1e1NationalSA4(3),
		t1e1NationalSA5(4),
		t1e1NationalSA6(5),
		t1e1NationalSA7(6),
		t1e1NationalSA8(7)
		}
	MAX-ACCESS  read-write
	STATUS  current
	DESCRIPTION
		"Selects a national bit to create a 4-kbps datalink between the endpoint units."
	::= { t1e1ConfigTableEntry 14 }

t1e1KeepAlive   OBJECT-TYPE
	SYNTAX  INTEGER
		{
		t1e1KeepAliveOther(1),
		t1e1KeepAliveUnframedOnes(2),
		t1e1KeepAliveFramedOnes(3),
		t1e1KeepAliveLoop(4)
		}
	MAX-ACCESS  read-write
	STATUS  current
	DESCRIPTION
		"Selects keep alive framed and unframed ones when the unit detects LOS or OOF."
	::= { t1e1ConfigTableEntry 15 }

t1e1CRC4Mode            OBJECT-TYPE
	SYNTAX  INTEGER
		{
		t1e1CRC4Other(1),
		t1e1CRC4Disabled(2),
		t1e1CRC4Enabled(3)
		}
	MAX-ACCESS  read-write
	STATUS  current
	DESCRIPTION
		"Selects whether CRC4 is enabled or disabled."
	::= { t1e1ConfigTableEntry 16 }

t1e1DSXLevel            OBJECT-TYPE
	SYNTAX  INTEGER
		{
		t1e1DSXOther(1),
		t1e1DSX0110(2),
		t1e1DSX111220(3),
		t1e1DSX221330(4),
		t1e1DSX331440(5),
		t1e1DSX441550(6),
		t1e1DSX551660(7),
		t1e1DSX661up(8)
		}
	MAX-ACCESS  read-write
	STATUS  current
	DESCRIPTION
		"Selects the DSX1 interface output level."
	::= { t1e1ConfigTableEntry 17 }

t1e1CRC OBJECT-TYPE
	SYNTAX  INTEGER
		{
		t1e1CRCOther(1),
		t1e1CRCPass(2),
		t1e1CRCRegenerate(3)
		}
	MAX-ACCESS  read-write
	STATUS  current
	DESCRIPTION
		"Determines whether received CRC data is passed through or regenerated."
	::= { t1e1ConfigTableEntry 18 }

t1e1FDLPassThrough      OBJECT-TYPE
	SYNTAX  INTEGER
		{
		t1e1FDLPassThroughOther(1),
		t1e1FDLPassThroughPass(2),
		t1e1FDLPassThroughTerminate(3)
		}
	MAX-ACCESS  read-write
	STATUS  current
	DESCRIPTION
		"Determines whether the ESF FDL passes through the CSU or terminates."
	::= { t1e1ConfigTableEntry 19 }

t1e1AudibleAlarm        OBJECT-TYPE
	SYNTAX  INTEGER
		{
		t1e1AudibleAlarmOther(1),
		t1e1AudibleAlarmDisabled(2),
		t1e1AudibleAlarmEnabled(3)
		}
	MAX-ACCESS  read-write
	STATUS  current
	DESCRIPTION
		"If applicable, Enables or Disables the CSU's internal buzzer which alerts users of an alarm condition."
	::= { t1e1ConfigTableEntry 20 }

t1e1Function            OBJECT-TYPE
	SYNTAX  INTEGER
		{
		t1e1FunctionOther(1),
		t1e1FunctionNetwork(2),
		t1e1FunctionSlaved(3),
		t1e1FunctionBackup(4)
		}
	MAX-ACCESS  read-write
	STATUS  current
	DESCRIPTION
		"Specifies the function the network port will perform in the unit.
		The options are:
		t1e1FunctionNetwork  (Independent network port)
		t1e1FunctionSlaved   (Slaved to another network port)
		t1e1FunctionBackup   (Automatic Protection Switching Backup for another network port)"
	::= { t1e1ConfigTableEntry 21 }

t1e1EBitGeneration            OBJECT-TYPE
	SYNTAX  INTEGER
		{
		other(1),
		disabled(2),
		enabled(3)
		}
	MAX-ACCESS  read-write
	STATUS  current
	DESCRIPTION
		""
	::= { t1e1ConfigTableEntry 22 }
 
t1e1RAIGeneration            OBJECT-TYPE
	SYNTAX  INTEGER
		{
		other(1),
		disabled(2),
		enabled(3)
		}
	MAX-ACCESS  read-write
	STATUS  current
	DESCRIPTION
		""
	::= { t1e1ConfigTableEntry 23 }
 
t1e1SpareBitInsertion         OBJECT-TYPE
	SYNTAX  INTEGER
		{
		other(1),
		disabled(2),
		enabled(3)
		}
	MAX-ACCESS  read-write
	STATUS  current
	DESCRIPTION
		""
	::= { t1e1ConfigTableEntry 24 }
 
t1e1Sa4In                     OBJECT-TYPE
	SYNTAX  OCTET STRING( SIZE(8) )
	MAX-ACCESS  read-only
	STATUS  current
	DESCRIPTION
		""
	::= { t1e1ConfigTableEntry 25 }
 
 
t1e1Sa5In                     OBJECT-TYPE
	SYNTAX  OCTET STRING( SIZE(8) )
	MAX-ACCESS  read-only
	STATUS  current
	DESCRIPTION
		""
	::= { t1e1ConfigTableEntry 26 }
 
t1e1Sa6In                     OBJECT-TYPE
	SYNTAX  OCTET STRING( SIZE(8) )
	MAX-ACCESS  read-only
	STATUS  current
	DESCRIPTION
		""
	::= { t1e1ConfigTableEntry 27 }
 
t1e1Sa7In                     OBJECT-TYPE
	SYNTAX  OCTET STRING( SIZE(8) )
	MAX-ACCESS  read-only
	STATUS  current
	DESCRIPTION
		""
	::= { t1e1ConfigTableEntry 28 }
 
t1e1Sa8In                     OBJECT-TYPE
	SYNTAX  OCTET STRING( SIZE(8) )
	MAX-ACCESS  read-only
	STATUS  current
	DESCRIPTION
		""
	::= { t1e1ConfigTableEntry 29 }
 
t1e1Sa4Out                    OBJECT-TYPE
	SYNTAX  OCTET STRING( SIZE(8) )
	MAX-ACCESS  read-write
	STATUS  current
	DESCRIPTION
		""
	::= { t1e1ConfigTableEntry 30 }
 
t1e1Sa5Out                    OBJECT-TYPE
	SYNTAX  OCTET STRING( SIZE(8) )
	MAX-ACCESS  read-write
	STATUS  current
	DESCRIPTION
		""
	::= { t1e1ConfigTableEntry 31 }
 
t1e1Sa6Out                    OBJECT-TYPE
	SYNTAX  OCTET STRING( SIZE(8) )
	MAX-ACCESS  read-write
	STATUS  current
	DESCRIPTION
		""
	::= { t1e1ConfigTableEntry 32 }
 
t1e1Sa7Out                    OBJECT-TYPE
	SYNTAX  OCTET STRING( SIZE(8) )
	MAX-ACCESS  read-write
	STATUS  current
	DESCRIPTION
		""
	::= { t1e1ConfigTableEntry 33 }
 
t1e1Sa8Out                    OBJECT-TYPE
	SYNTAX  OCTET STRING( SIZE(8) )
	MAX-ACCESS  read-write
	STATUS  current
	DESCRIPTION
		""
	::= { t1e1ConfigTableEntry 34 }
 
t1e1AlarmTable  OBJECT-TYPE
	SYNTAX  SEQUENCE OF T1e1AlarmTableEntry
	MAX-ACCESS  not-accessible
	STATUS  current
	DESCRIPTION
		"The T1 and E1 Alarm Table."
	::= { t1e1 2 }

t1e1AlarmTableEntry     OBJECT-TYPE
	SYNTAX  T1e1AlarmTableEntry
	MAX-ACCESS  not-accessible
	STATUS  current
	DESCRIPTION
		"An entry in the t1e1Table."
	INDEX   { t1e1AlarmNearIndex, t1e1AlarmFarIndex, t1e1AlarmIndex }
	::= { t1e1AlarmTable 1 }

T1e1AlarmTableEntry ::=
	SEQUENCE
	{
	t1e1AlarmNearIndex      INTEGER,
	t1e1AlarmFarIndex       INTEGER,
	t1e1AlarmIndex          INTEGER,

	t1e1StatusSummary       DisplayString,
	t1e1AlarmSummary        DisplayString,

	t1e1ESStatus            INTEGER,
	t1e1ESCount             INTEGER,
	t1e1ESThreshold         INTEGER,
	t1e1ESAlarm             INTEGER,

	t1e1SESStatus           INTEGER,
	t1e1SESCount            INTEGER,
	t1e1SESThreshold        INTEGER,
	t1e1SESAlarm            INTEGER,

	t1e1LOSSStatus          INTEGER,
	t1e1LOSSCount           INTEGER,
	t1e1LOSSThreshold       INTEGER,
	t1e1LOSSAlarm           INTEGER,

	t1e1UASStatus           INTEGER,
	t1e1UASCount            INTEGER,
	t1e1UASThreshold        INTEGER,
	t1e1UASAlarm            INTEGER,

	t1e1CSSStatus           INTEGER,
	t1e1CSSCount            INTEGER,
	t1e1CSSThreshold        INTEGER,
	t1e1CSSAlarm            INTEGER,
	
	t1e1BPVSStatus          INTEGER,
	t1e1BPVSCount           INTEGER,
	t1e1BPVSThreshold       INTEGER,
	t1e1BPVSAlarm           INTEGER,
	
	t1e1OOFSStatus          INTEGER,
	t1e1OOFSCount           INTEGER,
	t1e1OOFSThreshold       INTEGER,
	t1e1OOFSAlarm           INTEGER,

	t1e1AISStatus           INTEGER,
	t1e1AISCount            INTEGER,
	t1e1AISThreshold        INTEGER,
	t1e1AISAlarm            INTEGER,

	t1e1RASStatus           INTEGER,
	t1e1RASCount            INTEGER,
	t1e1RASThreshold        INTEGER,
	t1e1RASAlarm            INTEGER,

	t1e1AlarmResetTimer     INTEGER,
	t1e1AlarmReset          INTEGER
	}

t1e1AlarmNearIndex              OBJECT-TYPE
	SYNTAX  INTEGER
	MAX-ACCESS  read-only
	STATUS  current
	DESCRIPTION
		"Selects the near device."
	::= { t1e1AlarmTableEntry 1 }

t1e1AlarmFarIndex               OBJECT-TYPE
	SYNTAX  INTEGER
	MAX-ACCESS  read-only
	STATUS  current
	DESCRIPTION
		"Selects the far device."
	::= { t1e1AlarmTableEntry 2 }

t1e1AlarmIndex          OBJECT-TYPE
	SYNTAX  INTEGER
	MAX-ACCESS  read-only
	STATUS  current
	DESCRIPTION
		"This object is the index into the t1e1Table."
	::= { t1e1AlarmTableEntry 3 }

t1e1StatusSummary       OBJECT-TYPE
	SYNTAX  DisplayString (SIZE(0..80))
	MAX-ACCESS  read-only
	STATUS  current
	DESCRIPTION
		"This object provides a summary of the port status."
	::= { t1e1AlarmTableEntry 4 }

t1e1AlarmSummary        OBJECT-TYPE
	SYNTAX  DisplayString (SIZE(0..80))
	MAX-ACCESS  read-only
	STATUS  current
	DESCRIPTION
		"This object provides a summary of the port alarms."
	::= { t1e1AlarmTableEntry 5 }

t1e1ESStatus    OBJECT-TYPE
	SYNTAX  INTEGER
		{
		t1e1StatusOther(1),
		t1e1StatusNoES(2),
		t1e1StatusES(3)
		}
	MAX-ACCESS  read-only
	STATUS  current
	DESCRIPTION
		"Reports if an Errored Second condition exists."
	::= { t1e1AlarmTableEntry 6 }

t1e1ESCount     OBJECT-TYPE
	SYNTAX  INTEGER
	MAX-ACCESS  read-only
	STATUS  current
	DESCRIPTION
		"This count contains the number of consecutive seconds an Errored Second condition has existed."
	::= { t1e1AlarmTableEntry 7 }

t1e1ESThreshold OBJECT-TYPE
	SYNTAX  INTEGER
	MAX-ACCESS  read-write
	STATUS  current
	DESCRIPTION     
		"Sets the Errored Seconds alarm threshold.  Setting this field to 0 disables the alarm.  The threshold can be set to any value in the range 0 to 900."
	::= { t1e1AlarmTableEntry 8 }

t1e1ESAlarm     OBJECT-TYPE
	SYNTAX  INTEGER
		{
		t1e1ESAlarmOther(1),
		t1e1ESAlarmNone(2),
		t1e1ESAlarmThresholdExceeded(3)
		}
	MAX-ACCESS  read-only
	STATUS  current
	DESCRIPTION     
		"This status indicates if the Errors Seconds threshold is exceeded."
	::= { t1e1AlarmTableEntry 9 }

t1e1SESStatus   OBJECT-TYPE
	SYNTAX  INTEGER
		{
		t1e1StatusOther(1),
		t1e1StatusNoSES(2),
		t1e1StatusSES(3)
		}
	MAX-ACCESS  read-only
	STATUS  current
	DESCRIPTION
		"Reports if a Severely Errored condition exists."
	::= { t1e1AlarmTableEntry 10 }

t1e1SESCount    OBJECT-TYPE
	SYNTAX  INTEGER
	MAX-ACCESS  read-only
	STATUS  current
	DESCRIPTION
		"This count contains the number of consecutive seconds a Severely Errored condition has existed."
	::= { t1e1AlarmTableEntry 11 }

t1e1SESThreshold        OBJECT-TYPE
	SYNTAX  INTEGER
	MAX-ACCESS  read-write
	STATUS  current
	DESCRIPTION     
		"Sets the Severely Errored seconds alarm threshold.  Setting this field to 0 disables the alarm.  The threshold can be set to any value in the range 0 to 900."
	::= { t1e1AlarmTableEntry 12 }

t1e1SESAlarm    OBJECT-TYPE
	SYNTAX  INTEGER
		{
		t1e1SESAlarmOther(1),
		t1e1SESAlarmNone(2),
		t1e1SESAlarmThresholdExceeded(3)
		}
	MAX-ACCESS  read-only
	STATUS  current
	DESCRIPTION     
		"This status indicates if the Severely Errors Seconds threshold is exceeded."
	::= { t1e1AlarmTableEntry 13 }

t1e1LOSSStatus  OBJECT-TYPE
	SYNTAX  INTEGER
		{
		t1e1StatusOther(1),
		t1e1StatusNoLOSS(2),
		t1e1StatusLOSS(3)
		}
	MAX-ACCESS  read-only
	STATUS  current
	DESCRIPTION
		"Reports if a Loss of Signal condition exists."
	::= { t1e1AlarmTableEntry 14 }

t1e1LOSSCount   OBJECT-TYPE
	SYNTAX  INTEGER
	MAX-ACCESS  read-only
	STATUS  current
	DESCRIPTION
		"This count contains the number of consecutive seconds a Loss of Signal condition has existed."
	::= { t1e1AlarmTableEntry 15 }

t1e1LOSSThreshold       OBJECT-TYPE
	SYNTAX  INTEGER
	MAX-ACCESS  read-write
	STATUS  current
	DESCRIPTION     
		"Sets the Loss of Signal seconds alarm threshold.  Setting this field to 0 disables the alarm.  The threshold can be set to any value in the range 0 to 900."
	::= { t1e1AlarmTableEntry 16 }

t1e1LOSSAlarm   OBJECT-TYPE
	SYNTAX  INTEGER
		{
		t1e1LOSSAlarmOther(1),
		t1e1LOSSAlarmNone(2),
		t1e1LOSSAlarmThresholdExceeded(3)
		}
	MAX-ACCESS  read-only
	STATUS  current
	DESCRIPTION     
		"This status indicates if the Loss of Signal Seconds threshold is exceeded."
	::= { t1e1AlarmTableEntry 17 }

t1e1UASStatus   OBJECT-TYPE
	SYNTAX  INTEGER
		{
		t1e1StatusOther(1),
		t1e1StatusNoUAS(2),
		t1e1StatusUAS(3)
		}
	MAX-ACCESS  read-only
	STATUS  current
	DESCRIPTION
		"Reports if an Unavailable condition exists."
	::= { t1e1AlarmTableEntry 18 }

t1e1UASCount    OBJECT-TYPE
	SYNTAX  INTEGER
	MAX-ACCESS  read-only
	STATUS  current
	DESCRIPTION
		"This count contains the number of consecutive seconds an Unavailable condition has existed."
	::= { t1e1AlarmTableEntry 19 }

t1e1UASThreshold        OBJECT-TYPE
	SYNTAX  INTEGER
	MAX-ACCESS  read-write
	STATUS  current
	DESCRIPTION     
		"Sets the unavailable seconds alarm threshold.  Setting this field to 0 disables the alarm.  The threshold can be set to any value in the range 0 to 900."
	::= { t1e1AlarmTableEntry 20 }

t1e1UASAlarm    OBJECT-TYPE
	SYNTAX  INTEGER
		{
		t1e1UASAlarmOther(1),
		t1e1UASAlarmNone(2),
		t1e1UASAlarmThresholdExceeded(3)
		}
	MAX-ACCESS  read-only
	STATUS  current
	DESCRIPTION     
		"This status indicates if the Unavailable Seconds threshold is exceeded."
	::= { t1e1AlarmTableEntry 21 }

t1e1CSSStatus   OBJECT-TYPE
	SYNTAX  INTEGER
		{
		t1e1StatusOther(1),
		t1e1StatusNoCSS(2),
		t1e1StatusCSS(3)
		}
	MAX-ACCESS  read-only
	STATUS  current
	DESCRIPTION
		"Reports if a Controlled Slip condition exists."
	::= { t1e1AlarmTableEntry 22 }

t1e1CSSCount    OBJECT-TYPE
	SYNTAX  INTEGER
	MAX-ACCESS  read-only
	STATUS  current
	DESCRIPTION
		"This count contains the number of consecutive seconds in which at least one Controlled Slip occurred."
	::= { t1e1AlarmTableEntry 23 }

t1e1CSSThreshold        OBJECT-TYPE
	SYNTAX  INTEGER
	MAX-ACCESS  read-write
	STATUS  current
	DESCRIPTION     
		"Sets the Controlled Slip seconds alarm threshold.  Setting this field to 0 disables the alarm.  The threshold can be set to any value in the range 0 to 900."
	::= { t1e1AlarmTableEntry 24 }

t1e1CSSAlarm    OBJECT-TYPE
	SYNTAX  INTEGER
		{
		t1e1CSSAlarmOther(1),
		t1e1CSSAlarmNone(2),
		t1e1CSSAlarmThresholdExceeded(3)
		}
	MAX-ACCESS  read-only
	STATUS  current
	DESCRIPTION     
		"This status indicates if the Controlled Slip seconds threshold is exceeded."
	::= { t1e1AlarmTableEntry 25 }

t1e1BPVSStatus  OBJECT-TYPE
	SYNTAX  INTEGER
		{
		t1e1StatusOther(1),
		t1e1StatusNoBPVS(2),
		t1e1StatusBPVS(3)
		}
	MAX-ACCESS  read-only
	STATUS  current
	DESCRIPTION
		"Reports if a Bipolar Violation Error condition exists."
	::= { t1e1AlarmTableEntry 26 }

t1e1BPVSCount   OBJECT-TYPE
	SYNTAX  INTEGER
	MAX-ACCESS  read-only
	STATUS  current
	DESCRIPTION
		"This count contains the number of consecutive seconds a Bipolar Violation Error condition has existed."
	::= { t1e1AlarmTableEntry 27 }

t1e1BPVSThreshold       OBJECT-TYPE
	SYNTAX  INTEGER
	MAX-ACCESS  read-write
	STATUS  current
	DESCRIPTION     
		"Sets the Bipolar Violation Error seconds alarm threshold.  Setting this field to 0 disables the alarm.  The threshold can be set to any value in the range 0 to 900."
	::= { t1e1AlarmTableEntry 28 }

t1e1BPVSAlarm   OBJECT-TYPE
	SYNTAX  INTEGER
		{
		t1e1BPVSAlarmOther(1),
		t1e1BPVSAlarmNone(2),
		t1e1BPVSAlarmThresholdExceeded(3)
		}
	MAX-ACCESS  read-only
	STATUS  current
	DESCRIPTION     
		"This status indicates if the Bipolar Violation Error seconds threshold is exceeded."
	::= { t1e1AlarmTableEntry 29 }

t1e1OOFSStatus  OBJECT-TYPE
	SYNTAX  INTEGER
		{
		t1e1StatusOther(1),
		t1e1StatusNoOOF(2),
		t1e1StatusOOF(3)
		}
	MAX-ACCESS  read-only
	STATUS  current
	DESCRIPTION
		"Indicates that the unit is unable to synchronize on the incoming framing pattern."
	::= { t1e1AlarmTableEntry 30 }

t1e1OOFSCount   OBJECT-TYPE
	SYNTAX  INTEGER
	MAX-ACCESS  read-only
	STATUS  current
	DESCRIPTION
		"This count contains the number of consecutive seconds an OOF condition has existed."
	::= { t1e1AlarmTableEntry 31 }

t1e1OOFSThreshold       OBJECT-TYPE
	SYNTAX  INTEGER
	MAX-ACCESS  read-write
	STATUS  current
	DESCRIPTION     
		"Sets the OOF seconds alarm threshold.  Setting this field to 0 disables the alarm.  The threshold can be set to any value in the range 0 to 900."
	::= { t1e1AlarmTableEntry 32 }

t1e1OOFSAlarm   OBJECT-TYPE
	SYNTAX  INTEGER
		{
		t1e1OOFSAlarmOther(1),
		t1e1OOFSAlarmNone(2),
		t1e1OOFSAlarmExists(3)
		}
	MAX-ACCESS  read-only
	STATUS  current
	DESCRIPTION
		"Indicates if an OOF seconds alarm condition exists."
	::= { t1e1AlarmTableEntry 33 }

t1e1AISStatus   OBJECT-TYPE
	SYNTAX  INTEGER
		{
		t1e1StatusOther(1),
		t1e1StatusNoAIS(2),
		t1e1StatusAIS(3)
		}
	MAX-ACCESS  read-only
	STATUS  current
	DESCRIPTION
		"Indicates that the unit is receiving an unframed all ones pattern."
	::= { t1e1AlarmTableEntry 34 }

t1e1AISCount   OBJECT-TYPE
	SYNTAX  INTEGER
	MAX-ACCESS  read-only
	STATUS  current
	DESCRIPTION
		"This count contains the number of consecutive seconds an Unframed All Ones condition has existed."
	::= { t1e1AlarmTableEntry 35 }

t1e1AISThreshold       OBJECT-TYPE
	SYNTAX  INTEGER
	MAX-ACCESS  read-write
	STATUS  current
	DESCRIPTION     
		"Sets the AIS seconds alarm threshold.  Setting this field to 0 disables the alarm.  The threshold can be set to any value in the range 0 to 900."
	::= { t1e1AlarmTableEntry 36 }

t1e1AISAlarm    OBJECT-TYPE
	SYNTAX  INTEGER
		{
		t1e1AISAlarmOther(1),
		t1e1AISAlarmNone(2),
		t1e1AISAlarmExists(3)
		}
	MAX-ACCESS  read-only
	STATUS  current
	DESCRIPTION
		"Indicates if an Unframed All Ones alarm condition exists."
	::= { t1e1AlarmTableEntry 37 }

t1e1RASStatus   OBJECT-TYPE
	SYNTAX  INTEGER
		{
		t1e1RASStatusOther(1),
		t1e1RASStatusNoRAS(2),
		t1e1RASStatusRAS(3)
		}
	MAX-ACCESS  read-only
	STATUS  current
	DESCRIPTION
		"Reports if a Remote (Yellow) Alarm condition exists."
	::= { t1e1AlarmTableEntry 38 }

t1e1RASCount   OBJECT-TYPE
	SYNTAX  INTEGER
	MAX-ACCESS  read-only
	STATUS  current
	DESCRIPTION
		"This count contains the number of consecutive seconds a Remote (Yellow) Alarm condition has existed."
	::= { t1e1AlarmTableEntry 39 }

t1e1RASThreshold       OBJECT-TYPE
	SYNTAX  INTEGER
	MAX-ACCESS  read-write
	STATUS  current
	DESCRIPTION     
		"Sets the RAS seconds alarm threshold.  Setting this field to 0 disables the alarm.  The threshold can be set to any value in the range 0 to 900."
	::= { t1e1AlarmTableEntry 40 }

t1e1RASAlarm    OBJECT-TYPE
	SYNTAX  INTEGER
		{
		t1e1RASAlarmOther(1),
		t1e1RASAlarmNone(2),
		t1e1RASAlarmExists(3)
		}
	MAX-ACCESS  read-only
	STATUS  current
	DESCRIPTION     
		"This status indicates if a Remote (Yellow) Alarm exists."
	::= { t1e1AlarmTableEntry 41 }

t1e1AlarmResetTimer       OBJECT-TYPE
	SYNTAX  INTEGER
	MAX-ACCESS  read-write
	STATUS  current
	DESCRIPTION     
		"Sets the Alarm Reset Timer, this field can be set to any value in the range 0 to 900."
	::= { t1e1AlarmTableEntry 42 }


t1e1AlarmReset    OBJECT-TYPE
	SYNTAX  INTEGER
		{
		t1e1AlarmResetOther(1),
		t1e1AlarmResetClearAlarms(2)
		}
	MAX-ACCESS  read-write
	STATUS  current
	DESCRIPTION     
		"This is used to clear the current alarm counts."
	::= { t1e1AlarmTableEntry 43 }


-- ddsNet section, contains DDS Network interface table

ddsNetConfigTable       OBJECT-TYPE
	SYNTAX  SEQUENCE OF DdsNetConfigTableEntry
	MAX-ACCESS  not-accessible
	STATUS  current
	DESCRIPTION
		"The dds Network Interface Configuration Table."
	::= { ddsNet 1 }

ddsNetConfigTableEntry  OBJECT-TYPE
	SYNTAX  DdsNetConfigTableEntry
	MAX-ACCESS  not-accessible
	STATUS  current
	DESCRIPTION
		"An entry in the Network Interface Table."
	INDEX   { ddsNetConfigNearIndex, ddsNetConfigFarIndex, ddsNetConfigIndex }
	::= { ddsNetConfigTable 1 }

DdsNetConfigTableEntry ::=
	SEQUENCE
	{
	ddsNetConfigNearIndex   INTEGER,
	ddsNetConfigFarIndex    INTEGER,
	ddsNetConfigIndex       INTEGER,

	ddsNetDescription       DisplayString,
	ddsNetRate              INTEGER,
	ddsNetMode              INTEGER,
	ddsNetTimingSource      INTEGER,
	ddsNetRemComm           INTEGER,
	ddsNetCircuitAssur      INTEGER,
	ddsNetAntiStrTimer      INTEGER
	}

ddsNetConfigNearIndex           OBJECT-TYPE
	SYNTAX  INTEGER
	MAX-ACCESS  read-only
	STATUS  current
	DESCRIPTION
		"Selects the near device."
	::= { ddsNetConfigTableEntry 1 }

ddsNetConfigFarIndex            OBJECT-TYPE
	SYNTAX  INTEGER
	MAX-ACCESS  read-only
	STATUS  current
	DESCRIPTION
		"Selects the far device."
	::= { ddsNetConfigTableEntry 2 }

ddsNetConfigIndex       OBJECT-TYPE
	SYNTAX  INTEGER
	MAX-ACCESS  read-only
	STATUS  current
	DESCRIPTION
		"Index into the ddsNetConfigTable."
	::= { ddsNetConfigTableEntry 3 }

ddsNetDescription       OBJECT-TYPE
	SYNTAX  DisplayString( SIZE(0..40) )
	MAX-ACCESS  read-write
	STATUS  current
	DESCRIPTION
		"Contains a textual description of the port."
	::= { ddsNetConfigTableEntry 4 }

ddsNetRate  OBJECT-TYPE
	SYNTAX  INTEGER  
		{
		ddsNetRate2400(1),
		ddsNetRate4800(2),
		ddsNetRate9600(3),
		ddsNetRate19200(4),
		ddsNetRate38400(5),
		ddsNetRate56000(6),
		ddsNetRate64000(7)
		}
	MAX-ACCESS  read-write
	STATUS  current
	DESCRIPTION
		"This object is the identifier of the current DDS network rate. The values mean:
ddsNetRate2400
   the DDS network interface is operating at
   2400bps
ddsNetRate4800
   the DDS network interface is operating at
   4800bps
ddsNetRate9600
   the DDS network interface is operating at
   9600bps
ddsNetRate19200
   the DDS network interface is operating at
   19200bps
ddsNetRate38400
   the DDS network interface is operating at
   38400bps
ddsNetRate56000
   the DDS network interface is operating at
   56000bps
ddsNetRate64000
   the DDS network interface is operating at
   64000bps"
	::=  { ddsNetConfigTableEntry 5 }

ddsNetMode  OBJECT-TYPE
	SYNTAX  INTEGER 
		{
		ddsNetModeNormal(1),
		ddsNetModeProprietaryTXPI(2),
		ddsNetMode64KClearChannel(3),
		ddsNetMode64KCCProprietaryTXPII(4)
		}
	MAX-ACCESS  read-write
	STATUS  current
	DESCRIPTION
		"This variable describes mode in which data is
being sent from the DDS unit back towards the
network. Changing the value of this variable can
cause a loss of remote communications.
The values mean:
ddsNetModeNormal (DDS-I)
   normal data mode of operation
ddsNetModeProprietaryTXPI (DDS-I)
   data being sent out on the DDS network is
   in a proprietary mode to allow for remote
   communications, rate adaption, and SYNC to
   ASYNC modes
ddsNetMode64KClearChannel (DDS-II)
   A special case of DDS-II, where the line rate is 72K,
   the data rate is 64K, and there is no secondary channel.
ddsNetMode64KCCProprietaryTXPII (DDS-II)
   A special case of DDS-II, where the line rate is 72K,
   the data rate is 64K, and there is no secondary channel.
   In addition, the data being sent out on the DDS network
   is in a proprietary mode to allow for remote communications,
   rate adaption, SYNC to ASYNC, and/or TDM modes."
	::=  { ddsNetConfigTableEntry 6 }
	

ddsNetTimingSource  OBJECT-TYPE
	SYNTAX  INTEGER 
		{
		ddsNetTimingNet(1),
		ddsNetTimingInt(2),
		ddsNetTimingDTE(3),
		ddsNetTimingPort1(4),
		ddsNetTimingPort2(5)
		}
	MAX-ACCESS  read-write
	STATUS  current
	DESCRIPTION
		"This variable describes the current timing source for
the DDS network interface. The values mean:
ddsNetTimingNet
   unit dependant upon network for DDS network
   interface timing
ddsNetTimingInt
   unit supplying timing for DDS network
   interface
ddsNetTimingDTE
   unit dependant upon DTE device for network
   interface timing
ddsNetTimingPort1
   unit dependant upon serial port 1 device for network
   interface timing
ddsNetTimingPort2
   unit dependant upon serial port 2 device for network
   interface timing"
	::=  { ddsNetConfigTableEntry 7 }
	
ddsNetRemComm  OBJECT-TYPE
	SYNTAX  INTEGER 
		{
		ddsNetRemCommEnabled(1),
		ddsNetRemCommDisabled(2),
		ddsNetRemCommNotAvailable(3)
		}
	MAX-ACCESS  read-only
	STATUS  current
	DESCRIPTION
		"This variable describes the current setting for the
remote communications link. The values mean:
ddsNetRemCommEnabled
   remote communications can be carried out end
   to end
ddsNetRemCommDisabled
   remote communications are not allowed
ddsNetRemCommNotAvailable
   this unit does not support remote
   communications"
	::=  { ddsNetConfigTableEntry 8 }

ddsNetCircuitAssur  OBJECT-TYPE
	SYNTAX  INTEGER 
		{
		ddsNetCircuitAssurEnabled(1),
		ddsNetCircuitAssurDisabled(2),
		ddsNetCircuitAssurNotAvailable(3)
		}
	MAX-ACCESS  read-write
	STATUS  current
	DESCRIPTION
		"This variable describes the current setting for the
circuit assurance option. The values mean:
ddsNetCircuitAssurEnabled
   Circuit Assurance is enabled and the
   integrity of the DDS loop will be maintained
ddsNetCircuitAssurDisabled
   Circuit Assurance is disabled
ddsNetCircuitAssurNotAvailable
   this unit does not support Circuit Assurance"
	::=  { ddsNetConfigTableEntry 9 }

ddsNetAntiStrTimer  OBJECT-TYPE
	SYNTAX  INTEGER 
		{
		ddsNetAntiStrTimerOff(1),
		ddsNetAntiStrTimer10(2),
		ddsNetAntiStrTimer30(3),
		ddsNetAntiStrTimer60(4)
		}
	MAX-ACCESS  read-write
	STATUS  current
	DESCRIPTION
		"This variable describes the current setting for the
anti streaming timer. The values mean:
ddsNetAntiStrTimerOff
   the AntiStreaming Timer is off
ddsNetAntiStrTimer10
   the AntiStreaming Timer is set to 10 seconds
ddsNetAntiStrTimer30
   the AntiStreaming Timer is set to 30 seconds
ddsNetAntiStrTimer60
   the AntiStreaming Timer is set to 60 seconds"
	::=  { ddsNetConfigTableEntry 10 }

ddsNetAlarmTable        OBJECT-TYPE
	SYNTAX  SEQUENCE OF DdsNetAlarmTableEntry
	MAX-ACCESS  not-accessible
	STATUS  current
	DESCRIPTION
		"The dds Network Interface Alarm Table."
	::= { ddsNet 2 }

ddsNetAlarmTableEntry   OBJECT-TYPE
	SYNTAX  DdsNetAlarmTableEntry
	MAX-ACCESS  not-accessible
	STATUS  current
	DESCRIPTION
		"An entry in the ddsNetAlarmTable."
	INDEX   { ddsNetAlarmNearIndex, ddsNetAlarmFarIndex, ddsNetAlarmIndex }
	::= { ddsNetAlarmTable 1 }

DdsNetAlarmTableEntry ::=
	SEQUENCE
	{
	ddsNetAlarmNearIndex    INTEGER,
	ddsNetAlarmFarIndex     INTEGER,
	ddsNetAlarmIndex        INTEGER,

	ddsNetStatusSummary     DisplayString,
	ddsNetAlarmSummary      DisplayString,

	ddsNetLOSStatus         INTEGER,
	ddsNetLOSCount          INTEGER,
	ddsNetLOSThreshold      INTEGER,
	ddsNetLOSAlarm          INTEGER,

	ddsNetOOFStatus         INTEGER,
	ddsNetOOFCount          INTEGER,
	ddsNetOOFThreshold      INTEGER,
	ddsNetOOFAlarm          INTEGER,

	ddsNetOOSStatus         INTEGER,
	ddsNetOOSCount          INTEGER,
	ddsNetOOSThreshold      INTEGER,
	ddsNetOOSAlarm          INTEGER,

	ddsNetFDLStatus         INTEGER,
	ddsNetFDLCount          INTEGER,
	ddsNetFDLThreshold      INTEGER,
	ddsNetFDLAlarm          INTEGER,

	ddsNetAlarmResetTimer   INTEGER,
	ddsNetAlarmReset        INTEGER,

	ddsNetBPVStatus         INTEGER,
	ddsNetBPVCount          INTEGER,
	ddsNetBPVThreshold      INTEGER,
	ddsNetBPVAlarm          INTEGER
	}

ddsNetAlarmNearIndex            OBJECT-TYPE
	SYNTAX  INTEGER
	MAX-ACCESS  read-only
	STATUS  current
	DESCRIPTION
		"Selects the near device."
	::= { ddsNetAlarmTableEntry 1 }

ddsNetAlarmFarIndex             OBJECT-TYPE
	SYNTAX  INTEGER
	MAX-ACCESS  read-only
	STATUS  current
	DESCRIPTION
		"Selects the far device."
	::= { ddsNetAlarmTableEntry 2 }

ddsNetAlarmIndex        OBJECT-TYPE
	SYNTAX  INTEGER
	MAX-ACCESS  read-only
	STATUS  current
	DESCRIPTION
		"Index into the ddsNetAlarmTable."
	::= { ddsNetAlarmTableEntry 3 }


ddsNetStatusSummary     OBJECT-TYPE
	SYNTAX  DisplayString (SIZE(0..80))
	MAX-ACCESS  read-only
	STATUS  current
	DESCRIPTION
		"This object provides a summary of the port status."
	::= { ddsNetAlarmTableEntry 4 }

ddsNetAlarmSummary      OBJECT-TYPE
	SYNTAX  DisplayString (SIZE(0..80))
	MAX-ACCESS  read-only
	STATUS  current
	DESCRIPTION
		"This object provides a summary of the port alarms."
	::= { ddsNetAlarmTableEntry 5 }

ddsNetLOSStatus OBJECT-TYPE
	SYNTAX  INTEGER
		{
		ddsNetStatusLOSOther(1),
		ddsNetStatusNoLOS(2),
		ddsNetStatusLOS(3)
		}
	MAX-ACCESS  read-only
	STATUS  current
	DESCRIPTION
		"Reports if a Loss of Signal condition exists."
	::= { ddsNetAlarmTableEntry 6 }

ddsNetLOSCount  OBJECT-TYPE
	SYNTAX  INTEGER
	MAX-ACCESS  read-only
	STATUS  current
	DESCRIPTION
		"This count contains the number of consecutive seconds the unit received signal has been interrupted."
	::= { ddsNetAlarmTableEntry 7 }

ddsNetLOSThreshold      OBJECT-TYPE
	SYNTAX  INTEGER
		{
		ddsNetLOSThresholdOther(1),
		ddsNetLOSThresholdNone(2),
		ddsNetLOSThreshold1(3),
		ddsNetLOSThreshold2(4),
		ddsNetLOSThreshold3(5),
		ddsNetLOSThreshold4(6),
		ddsNetLOSThreshold5(7),
		ddsNetLOSThreshold10(8),
		ddsNetLOSThreshold20(9),
		ddsNetLOSThreshold30(10)
		}
	MAX-ACCESS  read-write
	STATUS  current
	DESCRIPTION
		"A period, measured in seconds, in which the DDS received signal is interrupted."
	::= { ddsNetAlarmTableEntry 8 }

ddsNetLOSAlarm  OBJECT-TYPE
	SYNTAX  INTEGER
		{
		ddsNetLOSAlarmOther(1),
		ddsNetLOSAlarmNone(2),
		ddsNetLOSAlarmThresholdExceeded(3)
		}
	MAX-ACCESS  read-only
	STATUS  current
	DESCRIPTION     
		"This status indicates if the Loss of Signal Seconds threshold is exceeded."
	::= { ddsNetAlarmTableEntry 9 }

ddsNetOOFStatus OBJECT-TYPE
	SYNTAX  INTEGER
		{
		ddsNetStatusOOFOther(1),
		ddsNetStatusNoOOF(2),
		ddsNetStatusOOF(3)
		}
	MAX-ACCESS  read-only
	STATUS  current
	DESCRIPTION
		"Reports if an Out of Frame condition exists."
	::= { ddsNetAlarmTableEntry 10 }

ddsNetOOFCount          OBJECT-TYPE
	SYNTAX  INTEGER
	MAX-ACCESS  read-only
	STATUS  current
	DESCRIPTION
		"This count contains the number of consecutive seconds the unit has received the out of frame code."
	::= { ddsNetAlarmTableEntry 11 }

ddsNetOOFThreshold      OBJECT-TYPE
	SYNTAX  INTEGER
		{
		ddsNetOOFThresholdOther(1),
		ddsNetOOFThresholdNone(2),
		ddsNetOOFThreshold1(3),
		ddsNetOOFThreshold2(4),
		ddsNetOOFThreshold3(5),
		ddsNetOOFThreshold4(6),
		ddsNetOOFThreshold5(7),
		ddsNetOOFThreshold10(8),
		ddsNetOOFThreshold20(9),
		ddsNetOOFThreshold30(10)
		}
	MAX-ACCESS  read-write
	STATUS  current
	DESCRIPTION
		"A period, measured in seconds, in which the Out Of Frame code is received or a frame sync loss occurred."
	::= { ddsNetAlarmTableEntry 12 }

ddsNetOOFAlarm OBJECT-TYPE
	SYNTAX  INTEGER
		{
		ddsNetOOFSAlarmOther(1),
		ddsNetOOFSAlarmNone(2),
		ddsNetOOFSAlarmThresholdExceeded(3)
		}
	MAX-ACCESS  read-only
	STATUS  current
	DESCRIPTION     
		"This status indicates if the Out of Frame Seconds threshold is exceeded."
	::= { ddsNetAlarmTableEntry 13 }

ddsNetOOSStatus OBJECT-TYPE
	SYNTAX  INTEGER
		{
		ddsNetStatusOOSOther(1),
		ddsNetStatusNoOOS(2),
		ddsNetStatusOOS(3)
		}
	MAX-ACCESS  read-only
	STATUS  current
	DESCRIPTION
		"Reports if Out of Service codes are received."
	::= { ddsNetAlarmTableEntry 14 }

ddsNetOOSCount  OBJECT-TYPE
	SYNTAX  INTEGER
	MAX-ACCESS  read-only
	STATUS  current
	DESCRIPTION
		"This count contains the number of consecutive seconds the unit has received the out of service code."
	::= { ddsNetAlarmTableEntry 15 }

ddsNetOOSThreshold      OBJECT-TYPE
	SYNTAX  INTEGER
		{
		ddsNetOOSThresholdOther(1),
		ddsNetOOSThresholdNone(2),
		ddsNetOOSThreshold1(3),
		ddsNetOOSThreshold2(4),
		ddsNetOOSThreshold3(5),
		ddsNetOOSThreshold4(6),
		ddsNetOOSThreshold5(7),
		ddsNetOOSThreshold10(8),
		ddsNetOOSThreshold20(9),
		ddsNetOOSThreshold30(10)
		}
	MAX-ACCESS  read-write
	STATUS  current
	DESCRIPTION
		"A period, measured in seconds, in which the Out Of Service code is received."
	::= { ddsNetAlarmTableEntry 16 }

ddsNetOOSAlarm  OBJECT-TYPE
	SYNTAX  INTEGER
		{
		ddsNetOOSAlarmOther(1),
		ddsNetOOSAlarmNone(2),
		ddsNetOOSAlarmThresholdExceeded(3)
		}
	MAX-ACCESS  read-only
	STATUS  current
	DESCRIPTION     
		"This status indicates if the Out of Service Seconds threshold is exceeded."
	::= { ddsNetAlarmTableEntry 17 }

ddsNetFDLStatus OBJECT-TYPE
	SYNTAX  INTEGER
		{
		ddsNetStatusFDLOther(1),
		ddsNetStatusNoFDL(2),
		ddsNetStatusFDL(3)
		}
	MAX-ACCESS  read-only
	STATUS  current
	DESCRIPTION
		"Reports if Facility Data Link errors have occurred."
	::= { ddsNetAlarmTableEntry 18 }

ddsNetFDLCount  OBJECT-TYPE
	SYNTAX  INTEGER
	MAX-ACCESS  read-only
	STATUS  current
	DESCRIPTION
		"This count contains the number of consecutive seconds in which FDL errors have occurred."
	::= { ddsNetAlarmTableEntry 19 }

ddsNetFDLThreshold      OBJECT-TYPE
	SYNTAX  INTEGER
		{
		ddsNetFDLThresholdOther(1),
		ddsNetFDLThresholdNone(2),
		ddsNetFDLThreshold1(3),
		ddsNetFDLThreshold2(4),
		ddsNetFDLThreshold3(5),
		ddsNetFDLThreshold4(6),
		ddsNetFDLThreshold5(7),
		ddsNetFDLThreshold10(8),
		ddsNetFDLThreshold20(9),
		ddsNetFDLThreshold30(10)
		}
	MAX-ACCESS  read-write
	STATUS  current
	DESCRIPTION
		"A period, measured in seconds, in which FDL errors have occurred."
	::= { ddsNetAlarmTableEntry 20 }

ddsNetFDLAlarm  OBJECT-TYPE
	SYNTAX  INTEGER
		{
		ddsNetFDLAlarmOther(1),
		ddsNetFDLAlarmNone(2),
		ddsNetFDLAlarmThresholdExceeded(3)
		}
	MAX-ACCESS  read-only
	STATUS  current
	DESCRIPTION     
		"This status indicates if the Facility Data Link threshold is exceeded."
	::= { ddsNetAlarmTableEntry 21 }

ddsNetAlarmResetTimer       OBJECT-TYPE
	SYNTAX  INTEGER
	MAX-ACCESS  read-write
	STATUS  current
	DESCRIPTION     
		"Sets the Alarm Reset Timer, this field can be set to any value in the range 0 to 900."
	::= { ddsNetAlarmTableEntry 22 }


ddsNetAlarmReset    OBJECT-TYPE
	SYNTAX  INTEGER
		{
		ddsNetAlarmResetOther(1),
		ddsNetAlarmResetClearAlarms(2)
		}
	MAX-ACCESS  read-write
	STATUS  current
	DESCRIPTION     
		"This is used to clear the current alarm counts."
	::= { ddsNetAlarmTableEntry 23 }

ddsNetBPVStatus OBJECT-TYPE
	SYNTAX  INTEGER
		{
		ddsNetStatusBPVOther(1),
		ddsNetStatusNoBPV(2),
		ddsNetStatusBPV(3)
		}
	MAX-ACCESS  read-only
	STATUS  current
	DESCRIPTION
		"Reports if a Bipolar violation event occurred in the last second."
	::= { ddsNetAlarmTableEntry 24 }

ddsNetBPVCount  OBJECT-TYPE
	SYNTAX  INTEGER
	MAX-ACCESS  read-only
	STATUS  current
	DESCRIPTION
		"This count contains the number of consecutive seconds the unit received bipolar violations."
	::= { ddsNetAlarmTableEntry 25 }

ddsNetBPVThreshold      OBJECT-TYPE
	SYNTAX  INTEGER
		{
		ddsNetBPVThresholdOther(1),
		ddsNetBPVThresholdNone(2),
		ddsNetBPVThreshold1(3),
		ddsNetBPVThreshold2(4),
		ddsNetBPVThreshold3(5),
		ddsNetBPVThreshold4(6),
		ddsNetBPVThreshold5(7),
		ddsNetBPVThreshold10(8),
		ddsNetBPVThreshold20(9),
		ddsNetBPVThreshold30(10)
		}
	MAX-ACCESS  read-write
	STATUS  current
	DESCRIPTION
		"A period, measured in seconds, in which the unit receives bipolar violations
		before an alarm is triggered."
	::= { ddsNetAlarmTableEntry 26 }

ddsNetBPVAlarm  OBJECT-TYPE
	SYNTAX  INTEGER
		{
		ddsNetBPVAlarmOther(1),
		ddsNetBPVAlarmNone(2),
		ddsNetBPVAlarmThresholdExceeded(3)
		}
	MAX-ACCESS  read-only
	STATUS  current
	DESCRIPTION     
		"This status indicates if the Bipolar violation Seconds threshold is exceeded."
	::= { ddsNetAlarmTableEntry 27 }



-- serialDte section

serialDteConfigTable	OBJECT-TYPE
	SYNTAX  SEQUENCE OF SerialDteConfigTableEntry
	MAX-ACCESS  not-accessible
	STATUS  current
	DESCRIPTION
		"The Serial DTE Config Table."
	::= { serialDte 1 }

serialDteConfigTableEntry	OBJECT-TYPE
	SYNTAX  SerialDteConfigTableEntry
	MAX-ACCESS  not-accessible
	STATUS  current
	DESCRIPTION
		"An entry in the serial DTE Config Table."
	INDEX   { serialDteConfigNearIndex, serialDteConfigFarIndex, serialDteConfigIndex }
	::= { serialDteConfigTable 1 }

SerialDteConfigTableEntry ::=
	SEQUENCE
	{
	serialDteConfigNearIndex	INTEGER,
	serialDteConfigFarIndex		INTEGER,
	serialDteConfigIndex		INTEGER,

	serialDteDescription		DisplayString,
	serialDteType			INTEGER,
	serialDteRate			INTEGER,
	serialDteInvertData		INTEGER,

	serialDteFormat			INTEGER,
	serialDteParity			INTEGER,
	serialDteStopBit		INTEGER,
	serialDteMode			INTEGER,

	serialDteDSR			INTEGER,
	serialDteDCD			INTEGER,
	serialDteRTS			INTEGER,
	serialDteRTSDelay		INTEGER,
	serialDteDTR			INTEGER,
	serialDteCTS			INTEGER,
	serialDteV54			INTEGER,
	serialDteLL			INTEGER,
	serialDteRL			INTEGER,
	serialDteStartChannel		INTEGER,
	serialDteNumberOfChannels	INTEGER,
	serialDteTxClock		INTEGER,
	serialDteBundle			INTEGER,
	serialDteChannelRate		INTEGER,
	serialDteInvertClock		INTEGER,
	serialDteCharSize		INTEGER,
	serialDteFlowControl		INTEGER,
	serialDtePinStatus		DisplayString,
	serialDteInInvertClock		INTEGER
	}

serialDteConfigNearIndex	OBJECT-TYPE
	SYNTAX  INTEGER
	MAX-ACCESS  read-only
	STATUS  current
	DESCRIPTION
		"Selects the near device."
	::= { serialDteConfigTableEntry 1 }

serialDteConfigFarIndex	OBJECT-TYPE
	SYNTAX  INTEGER
	MAX-ACCESS  read-only
	STATUS  current
	DESCRIPTION
		"Selects the far device."
	::= { serialDteConfigTableEntry 2 }

serialDteConfigIndex	OBJECT-TYPE
	SYNTAX  INTEGER
	MAX-ACCESS  read-only
	STATUS  current
	DESCRIPTION
		"Index into the DteTable."
	::= { serialDteConfigTableEntry 3 }

serialDteDescription	OBJECT-TYPE
	SYNTAX  DisplayString( SIZE(0..40) )
	MAX-ACCESS  read-only
	STATUS  current
	DESCRIPTION
		"Contains a textual description of the port."
	::= { serialDteConfigTableEntry 4 }

serialDteType	OBJECT-TYPE
	SYNTAX  INTEGER
		{
		serialDteTypeOther(1),
		serialDteTypeV35(2),
		serialDteTypeRS232(3),
		serialDteTypeEIA530(4),
		serialDteTypeX21(5),
		serialDteTypeV36(6),
		serialDteTypeEIA530A(7)
		}
	MAX-ACCESS  read-write
	STATUS  current
	DESCRIPTION
		"Selects the DTE port type if applicable."
	::= { serialDteConfigTableEntry 5 }

serialDteRate	OBJECT-TYPE
	SYNTAX  INTEGER
		{
		serialDteRateOther(1),
		serialDteRate2400(2),
		serialDteRate4800(3),
		serialDteRate9600(4),
		serialDteRate19200(5),
		serialDteRate38400(6),
		serialDteRate52000(7),
		serialDteRate56000(8),
		serialDteRate57600(9),
		serialDteRate60000(10),
		serialDteRate64000(11),
		serialDteRate112000(12),
		serialDteRate128000(13),
		serialDteRate168000(14),
		serialDteRate192000(15),
		serialDteRate224000(16),
		serialDteRate256000(17),
		serialDteRate280000(18),
		serialDteRate320000(19),
		serialDteRate336000(20),
		serialDteRate384000(21),
		serialDteRate392000(22),
		serialDteRate448000(23),
		serialDteRate504000(24),
		serialDteRate512000(25),
		serialDteRate560000(26),
		serialDteRate576000(27),
		serialDteRate616000(28),
		serialDteRate640000(29),
		serialDteRate672000(30),
		serialDteRate704000(31),
		serialDteRate728000(32),
		serialDteRate768000(33),
		serialDteRate784000(34),
		serialDteRate832000(35),
		serialDteRate840000(36),
		serialDteRate896000(37),
		serialDteRate952000(38),
		serialDteRate960000(39),
		serialDteRate1008000(40),
		serialDteRate1024000(41),
		serialDteRate1064000(42),
		serialDteRate1088000(43),
		serialDteRate1120000(44),
		serialDteRate1152000(45),
		serialDteRate1176000(46),
		serialDteRate1216000(47),
		serialDteRate1232000(48),
		serialDteRate1280000(49),
		serialDteRate1288000(50),
		serialDteRate1344000(51),
		serialDteRate1400000(52),
		serialDteRate1408000(53),
		serialDteRate1456000(54),
		serialDteRate1472000(55),
		serialDteRate1512000(56),
		serialDteRate1536000(57),
		serialDteRate1568000(58),
		serialDteRate1600000(59),
		serialDteRate1624000(60),
		serialDteRate1664000(61),
		serialDteRate1680000(62),
		serialDteRate1728000(63),
		serialDteRate1736000(64),
		serialDteRate1792000(65),
		serialDteRate1856000(66),
		serialDteRate1920000(67),
		serialDteRate1984000(68),
		serialDteRate2048000(69),
		serialDteRate1200(70),
		serialDteRate14400(71),
		serialDteRate28800(72),
		serialDteRate48000(73),
		serialDteRate31200(74),
		serialDteRate115200(75),
		serialDteRate2112000(76),
		serialDteRate2176000(77),
		serialDteRate2240000(78),
		serialDteRate2304000(79),
		serialDteRate300(80),
		serialDteRate600(81),
		serialDteRate3072000(82),
		serialDteRate4096000(83)
		}
	MAX-ACCESS  read-write
	STATUS  current
	DESCRIPTION
		"Selects the DTE port bit."
	::= { serialDteConfigTableEntry 6 }

serialDteInvertData	OBJECT-TYPE
	SYNTAX  INTEGER
		{
		serialDteInvertDataOther(1),
		serialDteInvertDataDisabled(2),
		serialDteInvertDataEnabled(3)
		}
	MAX-ACCESS  read-write
	STATUS  current
	DESCRIPTION
		"Specifies whether transmit and receive are inverted at the port."
	::= { serialDteConfigTableEntry 7 }

serialDteFormat	OBJECT-TYPE
	SYNTAX  INTEGER
		{
		serialDteFormatOther(1),
		serialDteFormatSync(2),
		serialDteFormatAsync(3),
		serialDteFormatNotAvail(4)
		}
		MAX-ACCESS  read-write
		STATUS  current
		DESCRIPTION
		"This variable describes the current operations format
of the DTE interface. The values mean:
serialDteFormatSync
   The DTE interface is currently set to operate
   in Synchronous clocking format
serialDteFormatAsync
   The DTE interface is currently set to operate
   in the Asynchronous clocking format
serialDteFormatNotAvail
   The DTE interface operating format is not
   available"
	::=  { serialDteConfigTableEntry 8 }

-- The DTE Parity is only valid when the DTE Mode is set to ASYNC

serialDteParity	OBJECT-TYPE
	SYNTAX  INTEGER
		{
		serialDteParityOther(1),
		serialDteParityNone(2),
		serialDteParityOdd(3),
		serialDteParityEven(4),
		serialDteParityMark(5),
		serialDteParitySpace(6),
		serialDteParityNotAvail(7)
		}
	MAX-ACCESS  read-write
	STATUS  current
	DESCRIPTION
		"This variable describes the current parity selected
for the DTE interface. This variable is only valid
when the DTE Mode is set to ASYNC. The values mean:
serialDteParityNone
   The DTE interface is currently set for
   no parity bit checking or generation
serialDteParityOdd
   The DTE interface is currently set
   for odd parity
serialDteParityEven
   The DTE interface is currently set
   for even parity
serialDteParityMark
   The DTE interface is currently set
   for mark parity
serialDteParitySpace
   The DTE interface is currently set
   for space parity
serialDteParityNotAvail
   The parity setting on the DTE interface is not
   available."
	::=  { serialDteConfigTableEntry 9 }

-- The Stop bit setting is only valid when the DTE interface is set to
-- ASYNC operation.

serialDteStopBit	OBJECT-TYPE
	SYNTAX  INTEGER
		{
		serialDteStopBitOther(1),
		serialDteStopBit1(2),
		serialDteStopBit2(3),
		serialDteStopBitNotAvail(4)
		}
	MAX-ACCESS  read-write
	STATUS  current
	DESCRIPTION
		"This variable describes the stop bit setting for the
DTE interface. This variable is only valid when the
DTE interface is set to ASYNC. The values mean:
serialDteStopBit1
   The DTE interface is configured to operate in
   the ASYNC mode with 1 stop bit
serialDteStopBit2
   The DTE interface is configured to operate in
   the ASYNC mode with 2 stop bits
serialDteStopBitNotAvail
   The stop bit information is not available. The
   DTE interface is probably configured for
   synchronous operation."
	::= { serialDteConfigTableEntry 10 }

serialDteMode	OBJECT-TYPE
	SYNTAX  INTEGER
		{
		serialDteModeOther(1),
		serialDteModeDDSI(2),
		serialDteModeDDSII(3),
		serialDteModeTxpINormal(4),
		serialDteModeTxpITDM(5),
		serialDteModeTxpIINormal(6),
		serialDteModeTxpIITDM(7)
		}
	MAX-ACCESS  read-write
	STATUS  current
	DESCRIPTION
		"This variable describes mode in which data is
being sent from the DDS unit back towards the network. "
	::=  { serialDteConfigTableEntry 11 }

serialDteDSR	OBJECT-TYPE
	SYNTAX  INTEGER
		{
		serialDteDSROther(1),
		serialDteDSRTestOff(2),
		serialDteDSRForcedOn(3),
		serialDteDSRForcedOff(4),
		serialDteDSRInternal(5)
		}
	MAX-ACCESS  read-write
	STATUS  current
	DESCRIPTION
		"Selects DSR behavior."
	::= { serialDteConfigTableEntry 12 }

serialDteDCD	OBJECT-TYPE
	SYNTAX  INTEGER
		{
		serialDteDCDOther(1),
		serialDteDCDIdleOff(2),
		serialDteDCDForcedOn(3),
		serialDteDCDForcedOff(4),
		serialDteDCDInternal(5),
		serialDteDCDFarRTS(6)
		}
	MAX-ACCESS  read-write
	STATUS  current
	DESCRIPTION
		"Selects DCD behavior."
	::= { serialDteConfigTableEntry 13 }

serialDteRTS	OBJECT-TYPE
	SYNTAX  INTEGER
		{
		serialDteRTSOther(1),
		serialDteRTSNormal(2),
		serialDteRTSForcedOn(3),
		serialDteRTSExternal(4)
		}
	MAX-ACCESS  read-write
	STATUS  current
	DESCRIPTION
		"Selects RTS behavior."
	::= { serialDteConfigTableEntry 14 }

serialDteRTSDelay	OBJECT-TYPE
	SYNTAX  INTEGER
		{
		serialDteRTSDelayOther(1),
		serialDteRTSDelayNormal(2),
		serialDteRTSDelayLong(3)
		}
	MAX-ACCESS  read-write
	STATUS  current
	DESCRIPTION
		"Selects RTS to CTS transition delay."
	::= { serialDteConfigTableEntry 15 }
	
serialDteDTR	OBJECT-TYPE
	SYNTAX  INTEGER
		{
		serialDteDTROther(1),
		serialDteDTRFalse(2),
		serialDteDTRTrue(3)
		}
	MAX-ACCESS  read-only
	STATUS  current
	DESCRIPTION
		"Reports if DTR from the DTE device is false."
	::= { serialDteConfigTableEntry 16 }

serialDteCTS	OBJECT-TYPE
	SYNTAX  INTEGER
		{
		serialDteCTSOther(1),
		serialDteCTSForceTrue(2),
		serialDteCTSForceFalse(3),
		serialDteCTSInternal(4)
		}
	MAX-ACCESS  read-write
	STATUS  current
	DESCRIPTION
		"Specifies the control of the CTS signal at the port."
	::= { serialDteConfigTableEntry 17 }

serialDteV54	OBJECT-TYPE
	SYNTAX  INTEGER
		{
		serialDteV54Other(1),
		serialDteV54Disable(2),
		serialDteV54Enable(3)
		}
	MAX-ACCESS  read-write
	STATUS  current
	DESCRIPTION
		"Specifies if the unit should respond to inband V.54 loop commands."
	::= { serialDteConfigTableEntry 18 }

serialDteLL	OBJECT-TYPE
	SYNTAX  INTEGER
		{
		serialDteLLOther(1),
		serialDteLLDisable(2),
		serialDteLLEnable(3)
		}
	MAX-ACCESS  read-write
	STATUS  current
	DESCRIPTION
		"Specifies if the unit should respond to local loop activation by the local loopback signal (EIA530 or RS-232 pin 18)."
	::= { serialDteConfigTableEntry 19 }

serialDteRL	OBJECT-TYPE
	SYNTAX  INTEGER
		{
		serialDteRLOther(1),
		serialDteRLDisable(2),
		serialDteRLEnable(3)
		}
	MAX-ACCESS  read-write
	STATUS  current
	DESCRIPTION
		"Specifies if the unit should respond to remote loop activation by the remote loopback signal (EIA530 or RS-232 pin 21)."
	::= { serialDteConfigTableEntry 20 }

serialDteStartChannel	OBJECT-TYPE
	SYNTAX  INTEGER
	MAX-ACCESS  read-write
	STATUS  current
	DESCRIPTION
		"Specifies the starting channel for the interface."
	::= { serialDteConfigTableEntry 21 }

serialDteNumberOfChannels	OBJECT-TYPE
	SYNTAX  INTEGER
	MAX-ACCESS  read-write
	STATUS  current
	DESCRIPTION
		"Specifies the number of channels allocated to the interface."
	::= { serialDteConfigTableEntry 22 }

serialDteTxClock	OBJECT-TYPE
	SYNTAX  INTEGER
		{
		serialDteTxClockOther(1),
		serialDteTxClockInternal(2),
		serialDteTxClockExternal(3),
		serialDteTxClockOversample(4)
		}
	MAX-ACCESS  read-write
	STATUS  current
	DESCRIPTION
		"Specifies how the interface derives its transmit clock."
	::= { serialDteConfigTableEntry 23 }

serialDteBundle	OBJECT-TYPE
	SYNTAX  INTEGER
		{
		other(1),
		contiguous(2),
		alternate(3)
		}
	MAX-ACCESS  read-write
	STATUS  current
	DESCRIPTION
		"Specifies the allocation pattern of channels assigned
		 to the serial port."
	::= { serialDteConfigTableEntry 24 }

serialDteChannelRate	OBJECT-TYPE
	SYNTAX  INTEGER
		{
		other(1),
		nx56k(2),
		nx64k(3)
		}
	MAX-ACCESS  read-write
	STATUS  current
	DESCRIPTION
		"Specifies the rate of all channels assigned to the serial port."
	::= { serialDteConfigTableEntry 25 }

serialDteInvertClock	OBJECT-TYPE
	SYNTAX	INTEGER
		{
		other(1),
		disabled(2),
		enabled(3)
		}
	MAX-ACCESS  read-write
	STATUS  current
	DESCRIPTION
		"Specifies if an inverted clock is used to send data from the serial port."
	::= { serialDteConfigTableEntry 26 }

serialDteCharSize	OBJECT-TYPE
	SYNTAX	INTEGER
		{
		other(1),
		five(2),
		six(3),
		seven(4),
		eight(5)
		}
	MAX-ACCESS	read-write
	STATUS  current
	DESCRIPTION
		"Specifies the number of bits per character. This variable is 
		valid in ASYNC mode."
	::= {serialDteConfigTableEntry 27 }

serialDteFlowControl	OBJECT-TYPE
	SYNTAX INTEGER
		{
		other(1),
		none(2),
		xonXoff(3),
		rtsCts(4)
		}
	MAX-ACCESS  read-write
	STATUS  current
	DESCRIPTION
		"Specifies the Flow control to use.  This variable is 
		valid only in ASYNC mode."
	::= { serialDteConfigTableEntry 28 }
	
serialDtePinStatus	OBJECT-TYPE
	SYNTAX  DisplayString (SIZE(0..80))
	MAX-ACCESS  read-only
	STATUS  current
	DESCRIPTION
		"This object provides a summary of the Serial port pin status."
	::= { serialDteConfigTableEntry 29 }

serialDteInInvertClock	OBJECT-TYPE
	SYNTAX	INTEGER
		{
		other(1),
		disabled(2),
		enabled(3)
		}
	MAX-ACCESS  read-write
	STATUS  current
	DESCRIPTION
		"Specifies to use the inverted clock edge for data clocked into the serial port."
	::= { serialDteConfigTableEntry 30 }

-- Dte Alarm Table

serialDteAlarmTable     OBJECT-TYPE
	SYNTAX  SEQUENCE OF SerialDteAlarmTableEntry
	MAX-ACCESS  not-accessible
	STATUS  current
	DESCRIPTION
		"The Serial DTE Alarm Table."
	::= { serialDte 2 }

serialDteAlarmTableEntry        OBJECT-TYPE
	SYNTAX  SerialDteAlarmTableEntry
	MAX-ACCESS  not-accessible
	STATUS  current
	DESCRIPTION
		"An entry in the serial DTE Alarm Table."
	INDEX   { serialDteAlarmNearIndex, serialDteAlarmFarIndex, serialDteAlarmIndex }
	::= { serialDteAlarmTable 1 }

SerialDteAlarmTableEntry ::=
	SEQUENCE
	{
	serialDteAlarmNearIndex         INTEGER,
	serialDteAlarmFarIndex          INTEGER,
	serialDteAlarmIndex             INTEGER,
	serialDteDTRAlarmControl        INTEGER,
	serialDteDTRAlarmStatus         INTEGER,

	serialDteStatusSummary     DisplayString,
	serialDteAlarmSummary      DisplayString,

	serialDteASCStatus         INTEGER,
	serialDteASCCount          INTEGER,
	serialDteASCThreshold      INTEGER,
	serialDteASCAlarm          INTEGER,

	serialDteFDLStatus         INTEGER,
	serialDteFDLCount          INTEGER,
	serialDteFDLThreshold      INTEGER,
	serialDteFDLAlarm          INTEGER,

	serialDteLOSStatus         INTEGER,
	serialDteLOSCount          INTEGER,
	serialDteLOSThreshold      INTEGER,
	serialDteLOSAlarm          INTEGER
	}

serialDteAlarmNearIndex         OBJECT-TYPE
	SYNTAX  INTEGER
	MAX-ACCESS  read-only
	STATUS  current
	DESCRIPTION
		"Selects the near device."
	::= { serialDteAlarmTableEntry 1 }

serialDteAlarmFarIndex          OBJECT-TYPE
	SYNTAX  INTEGER
	MAX-ACCESS  read-only
	STATUS  current
	DESCRIPTION
		"Selects the far device."
	::= { serialDteAlarmTableEntry 2 }

serialDteAlarmIndex     OBJECT-TYPE
	SYNTAX  INTEGER
	MAX-ACCESS  read-only
	STATUS  current
	DESCRIPTION
		"Index into the serialDteAlarmTable."
	::= { serialDteAlarmTableEntry 3 }

serialDteDTRAlarmControl        OBJECT-TYPE
	SYNTAX  INTEGER
		{
		serialDteDTRAlarmOther(1),
		serialDteDTRAlarmDisable(2),
		serialDteDTRAlarmEnable(3)
		}
	MAX-ACCESS  read-write
	STATUS  current
	DESCRIPTION
		"Specifies if the unit should alarm on loss of DTR."
	::= { serialDteAlarmTableEntry 4 }

serialDteDTRAlarmStatus OBJECT-TYPE
	SYNTAX  INTEGER
		{
		serialDteDTRAlarmOther(1),
		serialDteDTRAlarmNone(2),
		serialDteDTRAlarmActive(3)
		}
	MAX-ACCESS  read-only
	STATUS  current
	DESCRIPTION     
		"This status indicates a DTR Loss alarm is active."
	::= { serialDteAlarmTableEntry 5 }

serialDteStatusSummary     OBJECT-TYPE
	SYNTAX  DisplayString (SIZE(0..80))
	MAX-ACCESS  read-only
	STATUS  current
	DESCRIPTION
		"This object provides a summary of the port status."
	::= { serialDteAlarmTableEntry 6 }

serialDteAlarmSummary      OBJECT-TYPE
	SYNTAX  DisplayString (SIZE(0..80))
	MAX-ACCESS  read-only
	STATUS  current
	DESCRIPTION
		"This object provides a summary of the port alarms."
	::= { serialDteAlarmTableEntry 7 }

serialDteASCStatus OBJECT-TYPE
	SYNTAX  INTEGER
		{
		serialDteStatusASCOther(1),
		serialDteStatusNoASC(2),
		serialDteStatusASC(3)
		}
	MAX-ACCESS  read-only
	STATUS  current
	DESCRIPTION
		"Reports if an ASC condition exists on the interface."
	::= { serialDteAlarmTableEntry 8 }

serialDteASCCount  OBJECT-TYPE
	SYNTAX  INTEGER
	MAX-ACCESS  read-only
	STATUS  current
	DESCRIPTION
		"This count contains the number of ASC seconds received by the interface."
	::= { serialDteAlarmTableEntry 9 }

serialDteASCThreshold      OBJECT-TYPE
	SYNTAX  INTEGER
	MAX-ACCESS  read-write
	STATUS  current
	DESCRIPTION
		"The number of ASC seconds that must be received before an alarm is declared."
	::= { serialDteAlarmTableEntry 10 }

serialDteASCAlarm  OBJECT-TYPE
	SYNTAX  INTEGER
		{
		serialDteASCAlarmOther(1),
		serialDteASCAlarmNone(2),
		serialDteASCAlarmThresholdExceeded(3)
		}
	MAX-ACCESS  read-only
	STATUS  current
	DESCRIPTION     
		"This status indicates if the ASC Seconds threshold is exceeded."
	::= { serialDteAlarmTableEntry 11 }

serialDteFDLStatus OBJECT-TYPE
	SYNTAX  INTEGER
		{
		serialDteStatusFDLOther(1),
		serialDteStatusNoFDL(2),
		serialDteStatusFDL(3)
		}
	MAX-ACCESS  read-only
	STATUS  current
	DESCRIPTION
		"Reports if an FDL error condition exists on the interface."
	::= { serialDteAlarmTableEntry 12 }

serialDteFDLCount  OBJECT-TYPE
	SYNTAX  INTEGER
	MAX-ACCESS  read-only
	STATUS  current
	DESCRIPTION
		"This count contains the number of FDL errored seconds received by the interface."
	::= { serialDteAlarmTableEntry 13 }

serialDteFDLThreshold      OBJECT-TYPE
	SYNTAX  INTEGER
	MAX-ACCESS  read-write
	STATUS  current
	DESCRIPTION
		"The number of FDL errored seconds that must be received before an alarm is declared."
	::= { serialDteAlarmTableEntry 14 }

serialDteFDLAlarm  OBJECT-TYPE
	SYNTAX  INTEGER
		{
		serialDteFDLAlarmOther(1),
		serialDteFDLAlarmNone(2),
		serialDteFDLAlarmThresholdExceeded(3)
		}
	MAX-ACCESS  read-only
	STATUS  current
	DESCRIPTION     
		"This status indicates if the FDL Errored Seconds threshold is exceeded."
	::= { serialDteAlarmTableEntry 15 }

serialDteLOSStatus OBJECT-TYPE
	SYNTAX  INTEGER
		{
		serialDteStatusLOSOther(1),
		serialDteStatusNoLOS(2),
		serialDteStatusLOS(3)
		}
	MAX-ACCESS  read-only
	STATUS  current
	DESCRIPTION
		"Reports if an LOS condition exists on the interface."
	::= { serialDteAlarmTableEntry 16 }

serialDteLOSCount  OBJECT-TYPE
	SYNTAX  INTEGER
	MAX-ACCESS  read-only
	STATUS  current
	DESCRIPTION
		"This count contains the number of LOS seconds received by the interface."
	::= { serialDteAlarmTableEntry 17 }

serialDteLOSThreshold      OBJECT-TYPE
	SYNTAX  INTEGER
	MAX-ACCESS  read-write
	STATUS  current
	DESCRIPTION
		"The number of LOS seconds that must be received before an alarm is declared."
	::= { serialDteAlarmTableEntry 18 }

serialDteLOSAlarm  OBJECT-TYPE
	SYNTAX  INTEGER
		{
		serialDteLOSAlarmOther(1),
		serialDteLOSAlarmNone(2),
		serialDteLOSAlarmThresholdExceeded(3)
		}
	MAX-ACCESS  read-only
	STATUS  current
	DESCRIPTION     
		"This status indicates if the LOS Seconds threshold is exceeded."
	::= { serialDteAlarmTableEntry 19 }

-- analog DTE section

analogDteTable  OBJECT-TYPE
	SYNTAX  SEQUENCE OF AnalogDteTableEntry
	MAX-ACCESS  not-accessible
	STATUS  current
	DESCRIPTION
		"The Analog DTE Table."
	::= { analogDte 1 }

analogDteTableEntry     OBJECT-TYPE
	SYNTAX  AnalogDteTableEntry
	MAX-ACCESS  not-accessible
	STATUS  current
	DESCRIPTION
		"An entry in the Analog DTE Table."
	INDEX   { analogDteNearIndex, analogDteFarIndex, analogDteIndex }
	::= { analogDteTable 1 }

AnalogDteTableEntry ::=
	SEQUENCE
	{
	analogDteNearIndex      INTEGER,
	analogDteFarIndex       INTEGER,
	analogDteIndex          INTEGER,

	analogDteDescription    DisplayString,
	analogDteCardType       INTEGER,        
	analogDteMode           INTEGER,
	analogDteState          INTEGER,
	analogDteElementID      DisplayString,
	analogDteSignalling     INTEGER,
	analogDteDNISDelay      INTEGER,
	analogDteTxGain         INTEGER,
	analogDteRxGain         INTEGER
	}

analogDteNearIndex              OBJECT-TYPE
	SYNTAX  INTEGER
	MAX-ACCESS  read-only
	STATUS  current
	DESCRIPTION
		"Selects the near device."
	::= { analogDteTableEntry 1 }

analogDteFarIndex               OBJECT-TYPE
	SYNTAX  INTEGER
	MAX-ACCESS  read-only
	STATUS  current
	DESCRIPTION
		"Selects the far device."
	::= { analogDteTableEntry 2 }

analogDteIndex  OBJECT-TYPE
	SYNTAX  INTEGER
	MAX-ACCESS  read-only
	STATUS  current
	DESCRIPTION
		"Index into the analogDteTable."
	::= { analogDteTableEntry 3 }

analogDteDescription    OBJECT-TYPE
	SYNTAX  DisplayString( SIZE(0..40) )
	MAX-ACCESS  read-only
	STATUS  current
	DESCRIPTION
		"Contains a textual description of the port."
	::= { analogDteTableEntry 4 }

analogDteCardType       OBJECT-TYPE
	SYNTAX  INTEGER
		{
		analogDteCardTypeOther(1),
		analogDteCardTypeFXS(2),
		analogDteCardTypeFXO(3),
		analogDteCardType4WEM(4)
		}
	MAX-ACCESS  read-only
	STATUS  current
	DESCRIPTION
		"Identifies the analog DTE card type."
	::= { analogDteTableEntry 5 }

analogDteMode   OBJECT-TYPE
	SYNTAX  INTEGER
		{
		analogDteModeOther(1),
		analogDteModeSpare(2),
		analogDteModeActive(3)
		}
	MAX-ACCESS  read-write
	STATUS  current
	DESCRIPTION
		"Selects whether the port is actively assigned to a network channel or not used."
	::= { analogDteTableEntry 6 }

analogDteState  OBJECT-TYPE
	SYNTAX  INTEGER
		{
		analogDteStateOther(1),
		analogDteStateIdle(2),
		analogDteStateBusy(3)
		}
	MAX-ACCESS  read-only
	STATUS  current
	DESCRIPTION
		"Displays the port status as either in the Busy or Idle state."
	::= { analogDteTableEntry 7 }

analogDteElementID      OBJECT-TYPE
	SYNTAX  DisplayString( SIZE(0..20) )
	MAX-ACCESS  read-write
	STATUS  current
	DESCRIPTION
		"This object signifies the name of the device."
	::= { analogDteTableEntry 8 }

analogDteSignalling     OBJECT-TYPE
	SYNTAX  INTEGER
		{
		analogDteSignallingOther(1),
		analogDteSignallingFXSLS(2),
		analogDteSignallingFXSGS(3),
		analogDteSignallingUVG(4),
		analogDteSignallingMEGLS(5),
		analogDteSignallingMEGGS(6),
		analogDteSignallingMEGRLS(7),
		analogDteSignallingMEGRGS(8),
		analogDteSignallingPLAR(9),
		analogDteSignallingSLC96(10),
		analogDteSignallingDIDDNIS(11),
		analogDteSignallingDNISWLS(12),
		analogDteSignallingDNISDLS(13),
		analogDteSignallingDNISWRLS(14),
		analogDteSignallingDNISDRLS(15),
		analogDteSignallingDNISWGS(16),
		analogDteSignallingDNISDGS(17),
		analogDteSignallingDNISWRGS(18),
		analogDteSignallingDNISDRGS(19),
		analogDteSignallingFXOLS(20),
		analogDteSignallingFXOGS(21),
		analogDteSignallingFXOUVG(22),
		analogDteSignallingFXOUVGR(23),
		analogDteSignalling4WEMTYPE1(24),
		analogDteSignalling4WEMTYPE2(25),
		analogDteSignalling4WEMTYPE3(26),
		analogDteSignalling4WEMTYPE4(27),
		analogDteSignalling4WEMTYPE5(28),
		analogDteSignalling4WEMTO(29)
		}
	MAX-ACCESS  read-write
	STATUS  current
	DESCRIPTION
		"Selects the supervisory operation of the port."
	::= { analogDteTableEntry 9 }

analogDteDNISDelay      OBJECT-TYPE
	SYNTAX  INTEGER
		{
		analogDteDNISDelayOther(1),
		analogDteDNISDelay1Second(2),
		analogDteDNISDelay2Seconds(3),
		analogDteDNISDelay3Seconds(4),
		analogDteDNISDelay4Seconds(5),
		analogDteDNISDelay5Seconds(6)
		}
	MAX-ACCESS  read-write
	STATUS  current
	DESCRIPTION
		"If the signalling mode has a delay, it can be set from 1 to 5 seconds."
	::= { analogDteTableEntry 10 }

analogDteTxGain OBJECT-TYPE
	SYNTAX  INTEGER
		{
		analogDteTxGainOther(1),
		analogDteTxGain3DB(2),
		analogDteTxGain2DB(3),
		analogDteTxGain1DB(4),
		analogDteTxGain0DB(5),
		analogDteTxGainm1DB(6),
		analogDteTxGainm2DB(7),
		analogDteTxGainm3DB(8),
		analogDteTxGainm4DB(9),
		analogDteTxGainm5DB(10),
		analogDteTxGainm6DB(11),
		analogDteTxGainm7DB(12),
		analogDteTxGainm8DB(13),
		analogDteTxGainm9DB(14),
		analogDteTxGainm10DB(15)
		}
	MAX-ACCESS  read-write
	STATUS  current
	DESCRIPTION
		"Selects the transmit gain.  Values prefixed with m are negative."
	::= { analogDteTableEntry 11 }

analogDteRxGain         OBJECT-TYPE
	SYNTAX  INTEGER
		{
		analogDteRxGainOther(1),
		analogDteRxGain2DB(2),
		analogDteRxGain1DB(3),
		analogDteRxGain0DB(4),
		analogDteRxGainm1DB(5),
		analogDteRxGainm2DB(6),
		analogDteRxGainm3DB(7),
		analogDteRxGainm4DB(8),
		analogDteRxGainm5DB(9),
		analogDteRxGainm6DB(10),
		analogDteRxGainm7DB(11),
		analogDteRxGainm8DB(12),
		analogDteRxGainm9DB(13),
		analogDteRxGainm10DB(14),
		analogDteRxGainm11DB(15),
		analogDteRxGainm12DB(16),
		analogDteRxGainm13DB(17),
		analogDteRxGainm14DB(18),
		analogDteRxGainm15DB(19),
		analogDteRxGainm16DB(20)
		}
	MAX-ACCESS  read-write
	STATUS  current
	DESCRIPTION
		"Selects the receive gain.  Values prefixed with m are negative."
	::= { analogDteTableEntry 12 }

-- connection table
-- allows for configuration/connection of dte ports to network ports

connectionTable OBJECT-TYPE
	SYNTAX  SEQUENCE OF ConnectionTableEntry
	MAX-ACCESS  not-accessible
	STATUS  current
	DESCRIPTION
		"The connection table."
	::= { connection 1 }

connectionTableEntry    OBJECT-TYPE
	SYNTAX  ConnectionTableEntry
	MAX-ACCESS  not-accessible
	STATUS  current
	DESCRIPTION
		"An entry in the connection table."
	INDEX   { connectionNearIndex, connectionFarIndex, connectionTableIndex }
	::= { connectionTable 1 }

ConnectionTableEntry ::=
	SEQUENCE
	{
	connectionNearIndex             INTEGER,
	connectionFarIndex              INTEGER,
	connectionTableIndex            INTEGER,
	connectionTableDescription      DisplayString
	}

connectionNearIndex             OBJECT-TYPE
	SYNTAX  INTEGER
	MAX-ACCESS  read-only
	STATUS  current
	DESCRIPTION
		"Selects the near device."
	::= { connectionTableEntry 1 }

connectionFarIndex              OBJECT-TYPE
	SYNTAX  INTEGER
	MAX-ACCESS  read-only
	STATUS  current
	DESCRIPTION
		"Selects the far device."
	::= { connectionTableEntry 2 }

connectionTableIndex    OBJECT-TYPE
	SYNTAX  INTEGER
	MAX-ACCESS  read-only
	STATUS  current
	DESCRIPTION
		"The index into the connection table."
	::= { connectionTableEntry 3 }

connectionTableDescription      OBJECT-TYPE
	SYNTAX  DisplayString(SIZE(0..60))
	MAX-ACCESS  read-only
	STATUS  current
	DESCRIPTION
		"A description of the connection."
	::= { connectionTableEntry 4 }

connectionChannelTable  OBJECT-TYPE
	SYNTAX  SEQUENCE OF ConnectionChannelEntry
	MAX-ACCESS  not-accessible
	STATUS  current
	DESCRIPTION
		"The channel-level connection table."
	::= { connection 2 }

connectionChannelEntry  OBJECT-TYPE
	SYNTAX  ConnectionChannelEntry
	MAX-ACCESS  not-accessible
	STATUS  current
	DESCRIPTION
		"An entry in the connectionChannelTable."
	INDEX   { connectionChannelNearIndex, connectionChannelFarIndex, connectionChannelLineIndex, connectionChannelIndex }
	::= { connectionChannelTable 1 }

ConnectionChannelEntry ::=
	SEQUENCE
	{
	connectionChannelNearIndex      INTEGER,
	connectionChannelFarIndex       INTEGER,
	connectionChannelLineIndex      INTEGER,
	connectionChannelIndex          INTEGER,
	channelInterfaceAssignment      INTEGER,
	channelInterfaceDescription     DisplayString,
	channelInterfaceChannel         INTEGER,
	channelSignalling		INTEGER
	}

connectionChannelNearIndex              OBJECT-TYPE
	SYNTAX  INTEGER
	MAX-ACCESS  read-only
	STATUS  current
	DESCRIPTION
		"Selects the near device."
	::= { connectionChannelEntry 1 }

connectionChannelFarIndex               OBJECT-TYPE
	SYNTAX  INTEGER
	MAX-ACCESS  read-only
	STATUS  current
	DESCRIPTION
		"Selects the far device."
	::= { connectionChannelEntry 2 }

connectionChannelLineIndex     OBJECT-TYPE
	SYNTAX  INTEGER
	MAX-ACCESS  read-only
	STATUS  current
	DESCRIPTION
		"Selects instance of line."
	::= { connectionChannelEntry 3 }

connectionChannelIndex  OBJECT-TYPE
	SYNTAX  INTEGER
	MAX-ACCESS  read-only
	STATUS  current
	DESCRIPTION
		"The index into the connection table."
	::= { connectionChannelEntry 4 }

channelInterfaceAssignment  OBJECT-TYPE
	SYNTAX  INTEGER
		{
		other(1),
		unassigned(2),
		dTE(3),
		remComm(4),
		port1(5),
		port2(6),
		port3(7),
		port4(8),
		port5(9),
		port6(10),
		port7(11),
		port8(12),
		port9(13),
		port10(14),
		port11(15),
		port12(16),
		port13(17),
		port14(18),
		port15(19),
		port16(20),
		port17(21),
		port18(22),
		port19(23),
		port20(24),
		port21(25),
		port22(26),
		port23(27),
		port24(28),
		port25(29),
		port26(30),
		port27(31),
		port28(32),
		port29(33),
		port30(34),
		port31(35),
		port32(36),

		slot2PortA(37),
		slot2PortB(38),
		slot3PortA(39),
		slot3PortB(40),
		slot4PortA(41),
		slot4PortB(42),
		slot5PortA(43),
		slot5PortB(44),
		slot6PortA(45),
		slot6PortB(46),

		slot2Dsu1PortA(47),
		slot2Dsu1PortB(48),
		slot2Dsu2PortA(49),
		slot2Dsu2PortB(50),
		slot2Dsu3PortA(51),
		slot2Dsu3PortB(52),
		slot2Dsu4PortA(53),
		slot2Dsu4PortB(54),
		slot2Dsu5PortA(55),
		slot2Dsu5PortB(56),
		slot2Dsu6PortA(57),
		slot2Dsu6PortB(58),

		slot3Dsu1PortA(59),
		slot3Dsu1PortB(60),
		slot3Dsu2PortA(61),
		slot3Dsu2PortB(62),
		slot3Dsu3PortA(63),
		slot3Dsu3PortB(64),
		slot3Dsu4PortA(65),
		slot3Dsu4PortB(66),
		slot3Dsu5PortA(67),
		slot3Dsu5PortB(68),
		slot3Dsu6PortA(69),
		slot3Dsu6PortB(70),

		slot4Dsu1PortA(71),
		slot4Dsu1PortB(72),
		slot4Dsu2PortA(73),
		slot4Dsu2PortB(74),
		slot4Dsu3PortA(75),
		slot4Dsu3PortB(76),
		slot4Dsu4PortA(77),
		slot4Dsu4PortB(78),
		slot4Dsu5PortA(79),
		slot4Dsu5PortB(80),
		slot4Dsu6PortA(81),
		slot4Dsu6PortB(82),

		slot5Dsu1PortA(83),
		slot5Dsu1PortB(84),
		slot5Dsu2PortA(85),
		slot5Dsu2PortB(86),
		slot5Dsu3PortA(87),
		slot5Dsu3PortB(88),
		slot5Dsu4PortA(89),
		slot5Dsu4PortB(90),
		slot5Dsu5PortA(91),
		slot5Dsu5PortB(92),
		slot5Dsu6PortA(93),
		slot5Dsu6PortB(94),

		slot6Dsu1PortA(95),
		slot6Dsu1PortB(96),
		slot6Dsu2PortA(97),
		slot6Dsu2PortB(98),
		slot6Dsu3PortA(99),
		slot6Dsu3PortB(100),
		slot6Dsu4PortA(101),
		slot6Dsu4PortB(102),
		slot6Dsu5PortA(103),
		slot6Dsu5PortB(104),
		slot6Dsu6PortA(105),
		slot6Dsu6PortB(106)
		}

	MAX-ACCESS  read-write
	STATUS  current
	DESCRIPTION
		"The channel assignment."
	::= { connectionChannelEntry 5 }

channelInterfaceDescription     OBJECT-TYPE
	SYNTAX  DisplayString(SIZE(0..40))
	MAX-ACCESS  read-only
	STATUS  current
	DESCRIPTION
		"Contains a description of the interface channel connection."
	::= { connectionChannelEntry 6 }

channelInterfaceChannel OBJECT-TYPE
	SYNTAX  INTEGER
	MAX-ACCESS  read-write
	STATUS  current
	DESCRIPTION
		"Displays the corresponding channel of the interface channel connection."
	::= { connectionChannelEntry 7 }

channelSignalling	OBJECT-TYPE
	SYNTAX	INTEGER
		{
		other(1),
		clearChannel(2),
		robbedBit(3)
		}
	MAX-ACCESS	read-write
	STATUS  current
	DESCRIPTION
		"Allows a selection of Clear Channel or Robbed Bit signalling for each DS0."
	::= { connectionChannelEntry 8 }

-- maintenance section
-- controls tests

--
-- BERT Table
--

bertTable       OBJECT-TYPE
	SYNTAX  SEQUENCE OF BertTableEntry
	MAX-ACCESS  not-accessible
	STATUS  current
	DESCRIPTION
		"BERT control table."
	::= { maintenance 1 }

bertTableEntry  OBJECT-TYPE
	SYNTAX  BertTableEntry
	MAX-ACCESS  not-accessible
	STATUS  current
	DESCRIPTION
		"An entry in the BERT control table."
	INDEX   { bertNearIndex, bertFarIndex, bertIndex }
	::= { bertTable 1 }

BertTableEntry ::=
	SEQUENCE
	{
	bertNearIndex           INTEGER,
	bertFarIndex            INTEGER,
	bertIndex               INTEGER,
	bertPattern             INTEGER,
	bertLength              INTEGER,
	bertPatternSync         INTEGER,
	bertElapsedTime         INTEGER,
	bertBitErrors           INTEGER,
	bertErroredSeconds      INTEGER,
	bertPercentEFS          INTEGER,
	bertCommand             INTEGER
	}

bertNearIndex           OBJECT-TYPE
	SYNTAX  INTEGER
	MAX-ACCESS  read-only
	STATUS  current
	DESCRIPTION
		"Selects the near device."
	::= { bertTableEntry 1 }

bertFarIndex            OBJECT-TYPE
	SYNTAX  INTEGER
	MAX-ACCESS  read-only
	STATUS  current
	DESCRIPTION
		"Selects the far device."
	::= { bertTableEntry 2 }

bertIndex       OBJECT-TYPE
	SYNTAX  INTEGER
	MAX-ACCESS  read-only
	STATUS  current
	DESCRIPTION
		"The index into the BERT control table.  Selects which BERT chip to use."
	::= { bertTableEntry 3 }

bertPattern     OBJECT-TYPE
	SYNTAX  INTEGER
		{
		bertPatternOther(1),
		bertPatternQRSS(2),
		bertPattern63(3),
		bertPattern511(4),
		bertPattern2047(5),
		bertPattern215(6),
		bertPattern220(7),
		bertPattern223(8),
		bertPattern1in8(9),
		bertPattern3in24(10),
		bertPatternALT(11),
		bertPatternCLEAR(12)
		}
	MAX-ACCESS  read-write
	STATUS  current
	DESCRIPTION
		"Selects the test pattern to be used."
	::= { bertTableEntry 4 }

bertLength      OBJECT-TYPE
	SYNTAX  INTEGER
		{
		bertLengthOther(1),
		bertLength15minutes(2),
		bertLength30minutes(3),
		bertLength60minutes(4),
		bertLength24hours(5),
		bertLengthContinuous(6)
		}
	MAX-ACCESS  read-write
	STATUS  current
	DESCRIPTION
		"Specifies how long the test should run."
	::= { bertTableEntry 5 }

bertPatternSync OBJECT-TYPE
	SYNTAX  INTEGER
		{
		bertPatternSyncOther(1),
		bertPatternSyncNoTest(2),
		bertPatternSyncNoSync(3),
		bertPatternSyncInsync(4)
		}
	MAX-ACCESS  read-only
	STATUS  current
	DESCRIPTION
		"Displays the current state of pattern sync during a test."
	::= { bertTableEntry 6 }

bertElapsedTime OBJECT-TYPE
	SYNTAX  INTEGER
	MAX-ACCESS  read-only
	STATUS  current
	DESCRIPTION
		"Displays the amount of time elapsed since a timed test began in seconds."
	::= { bertTableEntry 7 }

bertBitErrors   OBJECT-TYPE
	SYNTAX  INTEGER
	MAX-ACCESS  read-only
	STATUS  current
	DESCRIPTION
		"Displays the total number of bit errors detected since the test began."
	::= { bertTableEntry 8 }

bertErroredSeconds      OBJECT-TYPE
	SYNTAX  INTEGER
	MAX-ACCESS  read-only
	STATUS  current
	DESCRIPTION
		"Displays the number of asynchronous errored seconds that have been detected since the test began."
	::= { bertTableEntry 9 }

bertPercentEFS  OBJECT-TYPE
	SYNTAX  INTEGER
	MAX-ACCESS  read-only
	STATUS  current
	DESCRIPTION
		"Displays a ratio derived from the number of error free seconds divided by the number of seconds accumulated in elapsed time."
	::= { bertTableEntry 10 }

bertCommand     OBJECT-TYPE
	SYNTAX  INTEGER
		{
		bertCommandOther(1),
		bertCommandStart(2),
		bertCommandStop(3),
		bertCommandResetErrors(4),
		bertCommandInjectError(5)
		}
	MAX-ACCESS  read-write
	STATUS  current
	DESCRIPTION
		"Issues a test command for the interface."
	::= { bertTableEntry 11 }

bertInterfaceTable      OBJECT-TYPE
	SYNTAX  SEQUENCE OF BertInterfaceTableEntry
	MAX-ACCESS  not-accessible
	STATUS  current
	DESCRIPTION
		"BERT control interface table."
	::= { maintenance 2 }

bertInterfaceTableEntry OBJECT-TYPE
	SYNTAX  BertInterfaceTableEntry
	MAX-ACCESS  not-accessible
	STATUS  current
	DESCRIPTION
		"An entry in the BERT control interface table."
	INDEX   { bertInterfaceNearIndex, bertInterfaceFarIndex, bertChipIndex, bertInterfaceIndex }
	::= { bertInterfaceTable 1 }

BertInterfaceTableEntry ::=
	SEQUENCE
	{
	bertInterfaceNearIndex      INTEGER,
	bertInterfaceFarIndex       INTEGER,
	bertChipIndex               INTEGER,
	bertInterfaceIndex          INTEGER,
	bertInterfaceSetting        INTEGER,
	bertInterfaceService	    INTEGER,
	bertInterfaceChannelRate    INTEGER
	}

bertInterfaceNearIndex          OBJECT-TYPE
	SYNTAX  INTEGER
	MAX-ACCESS  read-only
	STATUS  current
	DESCRIPTION
		"Selects the near device."
	::= { bertInterfaceTableEntry 1 }

bertInterfaceFarIndex           OBJECT-TYPE
	SYNTAX  INTEGER
	MAX-ACCESS  read-only
	STATUS  current
	DESCRIPTION
		"Selects the far device."
	::= { bertInterfaceTableEntry 2 }

bertChipIndex           OBJECT-TYPE
	SYNTAX  INTEGER
	MAX-ACCESS  read-only
	STATUS  current
	DESCRIPTION
		"Selects which BERT chip to use."
	::= { bertInterfaceTableEntry 3 }

bertInterfaceIndex      OBJECT-TYPE
	SYNTAX  INTEGER
	MAX-ACCESS  read-only
	STATUS  current
	DESCRIPTION
		"An index into the MIB-II interfaces table; the interface for the BERT settings."
	::= { bertInterfaceTableEntry 4 }

bertInterfaceSetting    OBJECT-TYPE
	SYNTAX  INTEGER
		{
		bertInterfaceSettingOther(1),
		bertInterfaceSettingIdle(2),
		bertInterfaceSettingChannel1(3),
		bertInterfaceSettingChannel2(4),
		bertInterfaceSettingChannel3(5),
		bertInterfaceSettingChannel4(6),
		bertInterfaceSettingChannel5(7),
		bertInterfaceSettingChannel6(8),
		bertInterfaceSettingChannel7(9),
		bertInterfaceSettingChannel8(10),
		bertInterfaceSettingChannel9(11),
		bertInterfaceSettingChannel10(12),
		bertInterfaceSettingChannel11(13),
		bertInterfaceSettingChannel12(14),
		bertInterfaceSettingChannel13(15),
		bertInterfaceSettingChannel14(16),
		bertInterfaceSettingChannel15(17),
		bertInterfaceSettingChannel16(18),
		bertInterfaceSettingChannel17(19),
		bertInterfaceSettingChannel18(20),
		bertInterfaceSettingChannel19(21),
		bertInterfaceSettingChannel20(22),
		bertInterfaceSettingChannel21(23),
		bertInterfaceSettingChannel22(24),
		bertInterfaceSettingChannel23(25),
		bertInterfaceSettingChannel24(26),
		bertInterfaceSettingChannel25(27),
		bertInterfaceSettingChannel26(28),
		bertInterfaceSettingChannel27(29),
		bertInterfaceSettingChannel28(30),
		bertInterfaceSettingChannel29(31),
		bertInterfaceSettingChannel30(32),
		bertInterfaceSettingChannel31(33),
		bertInterfaceSettingChannel32(34),
 		bertInterfaceSettingNet(35),
		bertInterfaceSettingDTE(36),
		bertInterfaceSettingNotEnabled(37),
		bertInterfaceSettingUseService(38)
		}
	MAX-ACCESS  read-write
	STATUS  current
	DESCRIPTION
		"Specifies where to send the BERT pattern."
	::= { bertInterfaceTableEntry 5 }

bertInterfaceService   OBJECT-TYPE
	SYNTAX  	INTEGER
	MAX-ACCESS  read-write
	STATUS  	current
	DESCRIPTION
		"Specifies the service (see ipadv2.mib) to BERT.  The bandwidth associated with 
		the service will get the BERT pattern."
	::= { bertInterfaceTableEntry 6 }

bertInterfaceChannelRate   OBJECT-TYPE
	SYNTAX  INTEGER
			{
			other(1),
            nx56k(2),
			nx64k(3)
			}
	MAX-ACCESS  read-write
	STATUS  current
	DESCRIPTION
		"Specifies the network channel rate for all channels involved
		in a network BERT."
	::= { bertInterfaceTableEntry 7 }

--        
-- Test Table
--

testTable       OBJECT-TYPE
	SYNTAX  SEQUENCE OF TestTableEntry
	MAX-ACCESS  not-accessible
	STATUS  current
	DESCRIPTION
		"Test control table."
	::= { maintenance 3 }

testTableEntry  OBJECT-TYPE
	SYNTAX  TestTableEntry
	MAX-ACCESS  not-accessible
	STATUS  current
	DESCRIPTION
		"An entry in the testTable."
	INDEX   { testNearIndex, testFarIndex, testTableIndex }
	::= { testTable 1 }
	
TestTableEntry ::=
	SEQUENCE
	{
	testNearIndex           INTEGER,
	testFarIndex            INTEGER,
	testTableIndex          INTEGER,
	testType                INTEGER,
	testLoopDirection       INTEGER,
	testFarLLBFraming       INTEGER,
	testLoopInitiator       INTEGER,
	testDefaultLoopType     INTEGER
	}

testNearIndex           OBJECT-TYPE
	SYNTAX  INTEGER
	MAX-ACCESS  read-only
	STATUS  current
	DESCRIPTION
		"Selects the near device."
	::= { testTableEntry 1 }

testFarIndex            OBJECT-TYPE
	SYNTAX  INTEGER
	MAX-ACCESS  read-only
	STATUS  current
	DESCRIPTION
		"Selects the far device."
	::= { testTableEntry 2 }

testTableIndex  OBJECT-TYPE
	SYNTAX  INTEGER
	MAX-ACCESS  read-only
	STATUS  current
	DESCRIPTION
		"The index into the testTable, one entry for each interface."
	::= { testTableEntry 3 }

testType        OBJECT-TYPE
	SYNTAX  INTEGER
		{
		testTypeOther(1),
		testTypeNoTest(2),
		testTypePLB(3),
		testTypeLLB(4),
		testtypeMLB(5),
		testTypeFarPLB(6),
		testTypeFarLLB(7),
		testTypeFarMLB(8),
		testTypePortLoop(9),
		testTypeV54Loop(10),    
		testTypeFarV54Loop(11),
		testTypeFarPortLoop(12),
		testTypeTDM(13),
		testTypeFarPortUnloop(14),
		testTypeFarV54Unloop(15),
		testTypeDualLoop(16),
		testTypeNetworkSideTransparent(17),
		testTypeNetworkSideNonTransparent(18),
		testTypeCustomerSideTransparent(19),
		testTypeCustomerSideNonTransparent(20)
		}
	MAX-ACCESS  read-write
	STATUS  current
	DESCRIPTION
		"Identifies the test type for the interface."
	::= { testTableEntry 4 }

testLoopDirection       OBJECT-TYPE
	SYNTAX INTEGER  
		{
		testLoopOther(1),
		testLoopUnidirectional(2),
		testLoopBidirectional(3)
		}
	MAX-ACCESS read-write
	STATUS current
	DESCRIPTION
		"This object is the identifier of the current unit loop mode. The values mean:
testLoopUnidirectional
   Line, Data, and V54 loops will be unidirectional
   Local loop will be bidirectional
testLoopBidirectional
   All loops will be bidirectional"
	::= { testTableEntry 5 }

 
testFarLLBFraming       OBJECT-TYPE
	SYNTAX  INTEGER
		{
		testFarLLBFramingOther(1),
		testFarLLBFramingUnframed(2),
		testFarLLBFramingFramed(3)
		}
	MAX-ACCESS  read-write
	STATUS  current
	DESCRIPTION
		"This setting, for Far LLB tests on T1 lines, must match the far end unit loop code framing."
	::= { testTableEntry 6 }

testLoopInitiator       OBJECT-TYPE
	SYNTAX INTEGER  
		{
		testLoopInitiatorOther(1),
		testLoopInitiatorLMP(2),
		testLoopInitiatorSNMP(3),
		testLoopInitiatorWeb(4),
		testLoopInitiatorEOC(5),
		testLoopInitiatorButtons(6),
		testLoopInitiatorDCEControl(7),
		testLoopInitiatorISDNPRAV3(8)
		}
	MAX-ACCESS read-only
	STATUS current
	DESCRIPTION
		"Indicates who started the loop."
	::= { testTableEntry 7 }
 
testDefaultLoopType     OBJECT-TYPE
	SYNTAX INTEGER  
		{
		testDefaultLoopTypeOther(1),
		testDefaultLoopTypeTransparent(2),
		testDefaultLoopTypeNonTransparent(3),
		testDefaultLoopTypeDual(4)
		}
	MAX-ACCESS read-write
	STATUS current
	DESCRIPTION
		"Identifies the default loop type."
	::= { testTableEntry 8 }
 
 
-- performance section
-- performance section

performance24Table      OBJECT-TYPE
	SYNTAX  SEQUENCE OF Performance24TableEntry
	MAX-ACCESS  not-accessible
	STATUS  current
	DESCRIPTION
		"Performance table, contains TR54016 standard and enhanced data."
	::= { performance 1 }

performance24TableEntry OBJECT-TYPE
	SYNTAX  Performance24TableEntry
	MAX-ACCESS  not-accessible
	STATUS  current
	DESCRIPTION
		"An entry in the performance24Table."
	INDEX   { performance24NearIndex, performance24FarIndex, performance24InterfaceIndex, performance24Index }
	::= { performance24Table 1 }

Performance24TableEntry ::=
	SEQUENCE
	{
	performance24NearIndex  INTEGER,
	performance24FarIndex   INTEGER,
	performance24InterfaceIndex      INTEGER,
	performance24Index      INTEGER,
	performance24ES         INTEGER,
	performance24BES        INTEGER,
	performance24SES        INTEGER,
	performance24UAS        INTEGER,
	performance24LOFC       INTEGER,
	performance24CSS        INTEGER,
	performance24CRCES      INTEGER,
	performance24OOFS       INTEGER,
	performance24LOSS       INTEGER,
	performance24AISS       INTEGER,
	performance24RAS        INTEGER,
	performance24BPVS       INTEGER,
	performance24timestamp  TimeTicks
	}

performance24NearIndex          OBJECT-TYPE
	SYNTAX  INTEGER
	MAX-ACCESS  read-only
	STATUS  current
	DESCRIPTION
		"Selects the near device."
	::= { performance24TableEntry 1 }

performance24FarIndex           OBJECT-TYPE
	SYNTAX  INTEGER
	MAX-ACCESS  read-only
	STATUS  current
	DESCRIPTION
		"Selects the far device."
	::= { performance24TableEntry 2 }

performance24InterfaceIndex           OBJECT-TYPE
	SYNTAX  INTEGER
	MAX-ACCESS  read-only
	STATUS  current
	DESCRIPTION
		"Selects the interface."
	::= { performance24TableEntry 3 }


performance24Index      OBJECT-TYPE
	SYNTAX  INTEGER
		{
		performance24Summary(1),
		performance24Current(2),

		performance24period1(3),
		performance24period2(4),
		performance24period3(5),
		performance24period4(6),
		performance24period5(7),
		performance24period6(8),
		performance24period7(9),
		performance24period8(10),
		performance24period9(11),

		performance24period10(12),
		performance24period11(13),
		performance24period12(14),
		performance24period13(15),
		performance24period14(16),
		performance24period15(17),
		performance24period16(18),
		performance24period17(19),
		performance24period18(20),
		performance24period19(21),

		performance24period20(22),
		performance24period21(23),
		performance24period22(24),
		performance24period23(25),
		performance24period24(26),
		performance24period25(27),
		performance24period26(28),
		performance24period27(29),
		performance24period28(30),
		performance24period29(31),

		performance24period30(32),
		performance24period31(33),
		performance24period32(34),
		performance24period33(35),
		performance24period34(36),
		performance24period35(37),
		performance24period36(38),
		performance24period37(39),
		performance24period38(40),
		performance24period39(41),

		performance24period40(42),
		performance24period41(43),
		performance24period42(44),
		performance24period43(45),
		performance24period44(46),
		performance24period45(47),
		performance24period46(48),
		performance24period47(49),
		performance24period48(50),
		performance24period49(51),

		performance24period50(52),
		performance24period51(53),
		performance24period52(54),
		performance24period53(55),
		performance24period54(56),
		performance24period55(57),
		performance24period56(58),
		performance24period57(59),
		performance24period58(60),
		performance24period59(61),

		performance24period60(62),
		performance24period61(63),
		performance24period62(64),
		performance24period63(65),
		performance24period64(66),
		performance24period65(67),
		performance24period66(68),
		performance24period67(69),
		performance24period68(70),
		performance24period69(71),

		performance24period70(72),
		performance24period71(73),
		performance24period72(74),
		performance24period73(75),
		performance24period74(76),
		performance24period75(77),
		performance24period76(78),
		performance24period77(79),
		performance24period78(80),
		performance24period79(81),

		performance24period80(82),
		performance24period81(83),
		performance24period82(84),
		performance24period83(85),
		performance24period84(86),
		performance24period85(87),
		performance24period86(88),
		performance24period87(89),
		performance24period88(90),
		performance24period89(91),

		performance24period90(92),
		performance24period91(93),
		performance24period92(94),
		performance24period93(95),
		performance24period94(96),
		performance24period95(97),
		performance24period96(98)
		}
	MAX-ACCESS  read-only
	STATUS  current
	DESCRIPTION
		"The index into the 24-hour performance table."
	::= { performance24TableEntry 4 }

performance24ES OBJECT-TYPE
	SYNTAX  INTEGER
	MAX-ACCESS  read-only
	STATUS  current
	DESCRIPTION
		"The number of Errored Seconds for the 15-minute period."
	::= { performance24TableEntry 5 }

performance24BES        OBJECT-TYPE
	SYNTAX  INTEGER
	MAX-ACCESS  read-only
	STATUS  current
	DESCRIPTION
		"The number of Bursty Errored Seconds for the 15-minute period."
	::= { performance24TableEntry 6 }

performance24SES        OBJECT-TYPE
	SYNTAX  INTEGER
	MAX-ACCESS  read-only
	STATUS  current
	DESCRIPTION
		"The number of Severely Errored Seconds for the 15-minute period."
	::= { performance24TableEntry 7 }

performance24UAS        OBJECT-TYPE
	SYNTAX  INTEGER
	MAX-ACCESS  read-only
	STATUS  current
	DESCRIPTION
		"The number of Unavailable Seconds for the 15-minute period."
	::= { performance24TableEntry 8 }

performance24LOFC       OBJECT-TYPE
	SYNTAX  INTEGER
	MAX-ACCESS  read-only
	STATUS  current
	DESCRIPTION
		"The number of Loss of Frame Counts for the 15-minute period."
	::= { performance24TableEntry 9 }

performance24CSS        OBJECT-TYPE
	SYNTAX  INTEGER
	MAX-ACCESS  read-only
	STATUS  current
	DESCRIPTION
		"The number of Controlled Slip Seconds for the 15-minute period."
	::= { performance24TableEntry 10 }

performance24CRCES      OBJECT-TYPE
	SYNTAX  INTEGER
	MAX-ACCESS  read-only
	STATUS  current
	DESCRIPTION
		"The number of CRC Errored Seconds for the 15-minute period."
	::= { performance24TableEntry 11 }

performance24OOFS       OBJECT-TYPE
	SYNTAX  INTEGER
	MAX-ACCESS  read-only
	STATUS  current
	DESCRIPTION
		"The number of Out of Frame Seconds for the 15-minute period."
	::= { performance24TableEntry 12 }

performance24LOSS       OBJECT-TYPE
	SYNTAX  INTEGER
	MAX-ACCESS  read-only
	STATUS  current
	DESCRIPTION
		"The number of Loss of Signal Seconds for the 15-minute period."
	::= { performance24TableEntry 13 }

performance24AISS       OBJECT-TYPE
	SYNTAX  INTEGER
	MAX-ACCESS  read-only
	STATUS  current
	DESCRIPTION
		"The number of Alarm Indication Signal Seconds for the 15-minute period."
	::= { performance24TableEntry 14 }

performance24RAS        OBJECT-TYPE
	SYNTAX  INTEGER
	MAX-ACCESS  read-only
	STATUS  current
	DESCRIPTION
		"The number of Remote Alarm (Yellow) Seconds for the 15-minute period."
	::= { performance24TableEntry 15 }

performance24BPVS       OBJECT-TYPE
	SYNTAX  INTEGER
	MAX-ACCESS  read-only
	STATUS  current
	DESCRIPTION
		"The number of Bipolar Violation Seconds for the 15-minute period."
	::= { performance24TableEntry 16 }

performance24timestamp	OBJECT-TYPE
	SYNTAX	TimeTicks
	MAX-ACCESS	read-only
	STATUS	current
	DESCRIPTION
		"The value of sysUpTime when the statistics were last updated."
	::= { performance24TableEntry 17 }
	
performance30Table      OBJECT-TYPE
	SYNTAX  SEQUENCE OF Performance30TableEntry
	MAX-ACCESS  not-accessible
	STATUS  current
	DESCRIPTION
		"Performance table, contains TR54016 standard and enhanced 30-day data."
	::= { performance 2 }

performance30TableEntry OBJECT-TYPE
	SYNTAX  Performance30TableEntry
	MAX-ACCESS  not-accessible
	STATUS  current
	DESCRIPTION
		"An entry in the performance30Table."
	INDEX   { performance30NearIndex, performance30FarIndex, performance30InterfaceIndex, performance30Index }
	::= { performance30Table 1 }

Performance30TableEntry ::=
	SEQUENCE
	{
	performance30NearIndex  INTEGER,
	performance30FarIndex   INTEGER,
	performance30InterfaceIndex INTEGER,
	performance30Index      INTEGER,
	performance30ES         INTEGER,
	performance30BES        INTEGER,
	performance30SES        INTEGER,
	performance30UAS        INTEGER,
	performance30LOFC       INTEGER,
	performance30CSS        INTEGER,
	performance30CRCES      INTEGER,
	performance30OOFS       INTEGER,
	performance30LOSS       INTEGER,
	performance30AISS       INTEGER,
	performance30RAS        INTEGER,
	performance30BPVS       INTEGER,
	performance30timestamp  TimeTicks
	}

performance30NearIndex          OBJECT-TYPE
	SYNTAX  INTEGER
	MAX-ACCESS  read-only
	STATUS  current
	DESCRIPTION
		"Selects the near device."
	::= { performance30TableEntry 1 }

performance30FarIndex           OBJECT-TYPE
	SYNTAX  INTEGER
	MAX-ACCESS  read-only
	STATUS  current
	DESCRIPTION
		"Selects the far device."
	::= { performance30TableEntry 2 }

performance30InterfaceIndex           OBJECT-TYPE
	SYNTAX  INTEGER
	MAX-ACCESS  read-only
	STATUS  current
	DESCRIPTION
		"Selects the interface."
	::= { performance30TableEntry 3 }

performance30Index      OBJECT-TYPE
	SYNTAX  INTEGER
		{
		performance30Summary(1),

		performance30day1(2),
		performance30day2(3),
		performance30day3(4),
		performance30day4(5),
		performance30day5(6),
		performance30day6(7),
		performance30day7(8),
		performance30day8(9),
		performance30day9(10),
		performance30day10(11),
		performance30day11(12),
		performance30day12(13),
		performance30day13(14),
		performance30day14(15),
		performance30day15(16),
		performance30day16(17),
		performance30day17(18),
		performance30day18(19),
		performance30day19(20),
		performance30day20(21),
		performance30day21(22),
		performance30day22(23),
		performance30day23(24),
		performance30day24(25),
		performance30day25(26),
		performance30day26(27),
		performance30day27(28),
		performance30day28(29),
		performance30day29(30),
		performance30day30(31)
		}
	MAX-ACCESS  read-only
	STATUS  current
	DESCRIPTION
		"The index into the 30-day performance table."
	::= { performance30TableEntry 4 }

performance30ES OBJECT-TYPE
	SYNTAX  INTEGER
	MAX-ACCESS  read-only
	STATUS  current
	DESCRIPTION
		"The number of Errored Seconds for the 1-day period."
	::= { performance30TableEntry 5 }

performance30BES        OBJECT-TYPE
	SYNTAX  INTEGER
	MAX-ACCESS  read-only
	STATUS  current
	DESCRIPTION
		"The number of Bursty Errored Seconds for the 1-day period."
	::= { performance30TableEntry 6 }

performance30SES        OBJECT-TYPE
	SYNTAX  INTEGER
	MAX-ACCESS  read-only
	STATUS  current
	DESCRIPTION
		"The number of Severely Errored Seconds for the 1-day period."
	::= { performance30TableEntry 7 }

performance30UAS        OBJECT-TYPE
	SYNTAX  INTEGER
	MAX-ACCESS  read-only
	STATUS  current
	DESCRIPTION
		"The number of Unavailable Seconds for the 1-day period."
	::= { performance30TableEntry 8 }

performance30LOFC       OBJECT-TYPE
	SYNTAX  INTEGER
	MAX-ACCESS  read-only
	STATUS  current
	DESCRIPTION
		"The number of Loss of Frame Counts for the 1-day period."
	::= { performance30TableEntry 9 }

performance30CSS        OBJECT-TYPE
	SYNTAX  INTEGER
	MAX-ACCESS  read-only
	STATUS  current
	DESCRIPTION
		"The number of Controlled Slip Seconds for the 1-day period."
	::= { performance30TableEntry 10 }

performance30CRCES      OBJECT-TYPE
	SYNTAX  INTEGER
	MAX-ACCESS  read-only
	STATUS  current
	DESCRIPTION
		"The number of CRC Errored Seconds for the 1-day period."
	::= { performance30TableEntry 11 }

performance30OOFS       OBJECT-TYPE
	SYNTAX  INTEGER
	MAX-ACCESS  read-only
	STATUS  current
	DESCRIPTION
		"The number of Out of Frame Seconds for the 1-day period."
	::= { performance30TableEntry 12 }

performance30LOSS       OBJECT-TYPE
	SYNTAX  INTEGER
	MAX-ACCESS  read-only
	STATUS  current
	DESCRIPTION
		"The number of Loss of Signal Seconds for the 1-day period."
	::= { performance30TableEntry 13 }

performance30AISS       OBJECT-TYPE
	SYNTAX  INTEGER
	MAX-ACCESS  read-only
	STATUS  current
	DESCRIPTION
		"The number of Alarm Indication Signal Seconds for the 1-day period."
	::= { performance30TableEntry 14 }

performance30RAS        OBJECT-TYPE
	SYNTAX  INTEGER
	MAX-ACCESS  read-only
	STATUS  current
	DESCRIPTION
		"The number of Remote Alarm (Yellow) Seconds for the 1-day period."
	::= { performance30TableEntry 15 }

performance30BPVS       OBJECT-TYPE
	SYNTAX  INTEGER
	MAX-ACCESS  read-only
	STATUS  current
	DESCRIPTION
		"The number of Bipolar Violation Seconds for the 1-day period."
	::= { performance30TableEntry 16 }

performance30timestamp	OBJECT-TYPE
	SYNTAX	TimeTicks
	MAX-ACCESS	read-only
	STATUS	current
	DESCRIPTION
		"The value of sysUpTime when the statistics were last updated."
	::= { performance30TableEntry 17 }

-- itable
-- requests a list of all interfaces on a device

iTable  OBJECT-TYPE
	SYNTAX  SEQUENCE OF ITableEntry
	MAX-ACCESS  not-accessible
	STATUS  current
	DESCRIPTION
		"The interface table."
	::= { itable 1 }

iTableEntry     OBJECT-TYPE
	SYNTAX  ITableEntry
	MAX-ACCESS  not-accessible
	STATUS  current
	DESCRIPTION
		"An entry in the interface table."
	INDEX   { iTableNearIndex, iTableFarIndex, iTableIndex }
	::= { iTable 1 }

ITableEntry ::=
	SEQUENCE
	{
	iTableNearIndex     INTEGER,
	iTableFarIndex      INTEGER,
	iTableIndex         INTEGER,
	iDescription	    DisplayString,
	iType               INTEGER,
	iSlot               INTEGER,
	iPort               INTEGER,
	iStatus 	    INTEGER
	}

iTableNearIndex OBJECT-TYPE
	SYNTAX  INTEGER
	MAX-ACCESS  read-only
	STATUS  current
	DESCRIPTION
		"Selects the near device."
	::= { iTableEntry 1 }

iTableFarIndex             OBJECT-TYPE
	SYNTAX  INTEGER
	MAX-ACCESS  read-only
	STATUS  current
	DESCRIPTION
		"Selects the far device."
	::= { iTableEntry 2 }
 
iTableIndex     OBJECT-TYPE
	SYNTAX  INTEGER
	MAX-ACCESS  read-only
	STATUS  current
	DESCRIPTION
		"The index into the interface table, used for addressing in above tables."
	::= { iTableEntry 3 }

iDescription    OBJECT-TYPE
	SYNTAX  DisplayString( SIZE(0..80) )
	MAX-ACCESS  read-only
	STATUS  current
	DESCRIPTION
		"Description of the interface."
	::= { iTableEntry 4 }

iType   OBJECT-TYPE
	SYNTAX  INTEGER
		{
		disabled(0),
		v35(1),
		eia530(2),
		rs232(3),
		voice(4),
		hsdata(5),
		dualt1dte(6),
		dualddsv1(7),
		hexdds(8),
		ocudp(9),
		x21(10),
		dualddsv2(11),

		rfdl(128),
		alt(129),
		t1dte(130),
		didte(131),
		t1ntw(132),
		e1ntw(133),
		ddsntw(134),
		ddsdte(135),
		ddsdbu(136),
		fxs(137),
		fxo(138),
		eandm(139),

		e1sig(192)
		}
	MAX-ACCESS  read-only
	STATUS  current
	DESCRIPTION
		"Enumerated interface type."
	::= { iTableEntry 5 }

iSlot   OBJECT-TYPE
	SYNTAX  INTEGER
	MAX-ACCESS  read-only
	STATUS  current
	DESCRIPTION
		"Device-dependent slot in which the interface resides."
	::= { iTableEntry 6 }

iPort   OBJECT-TYPE
	SYNTAX  INTEGER 
	MAX-ACCESS  read-only
	STATUS  current
	DESCRIPTION
		"Device-dependent port in which the interface resides."
	::= { iTableEntry 7 }

iStatus    OBJECT-TYPE
	SYNTAX  INTEGER
		{
		iStatusOther(1),
		iStatusOK(2),
		iStatusErrored(3),
		iStatusAlarmed(4),
		iStatusTesting(5),
		iStatusUnassigned(6),
		iStatusLoopDetected(7)
		}
	MAX-ACCESS  read-only
	STATUS  current
	DESCRIPTION
		"Status of the interface."
	::= { iTableEntry 8 }

-- traplog
-- a table of the most recent snmp traps
-- note that the near and far indices are simply elements in the table,
-- not indices as in the above tables...

traplogTable  OBJECT-TYPE
	SYNTAX  SEQUENCE OF TraplogEntry
	MAX-ACCESS  not-accessible
	STATUS  current
	DESCRIPTION
		"The traplog table."
	::= { traplog 1 }

traplogEntry    OBJECT-TYPE
	SYNTAX  TraplogEntry
	MAX-ACCESS  not-accessible
	STATUS  current
	DESCRIPTION
		"An entry in the traplog table."
	INDEX   { traplogIndex }
	::= { traplogTable 1 }

TraplogEntry ::=
    SEQUENCE
    {
    traplogIndex                INTEGER,
    traplogNearIndex            INTEGER,
    traplogFarIndex             INTEGER,
    traplogInterfaceIndex       INTEGER,
    traplogTrapNum              INTEGER,
    traplogTimeStamp            DisplayString,
    traplogDeviceType           INTEGER,
    traplogOID1                 DisplayString,
    traplogDescription1         DisplayString,
    traplogValue1               DisplayString,
    traplogOID2                 DisplayString,
    traplogDescription2         DisplayString,
    traplogValue2               DisplayString,
    traplogOID3                 DisplayString,
    traplogDescription3         DisplayString,
    traplogValue3               DisplayString
    }

traplogIndex     OBJECT-TYPE
	SYNTAX  INTEGER
	MAX-ACCESS  read-only
	STATUS  current
	DESCRIPTION
		"The index into the traplog table."
	::= { traplogEntry 1 }

traplogNearIndex        OBJECT-TYPE
	SYNTAX  INTEGER
	MAX-ACCESS  read-only
	STATUS  current
	DESCRIPTION
		"Specifies the near device."
	::= { traplogEntry 2 }

traplogFarIndex             OBJECT-TYPE
	SYNTAX  INTEGER
	MAX-ACCESS  read-only
	STATUS  current
	DESCRIPTION
		"Specifies the far device."
	::= { traplogEntry 3 }

traplogInterfaceIndex             OBJECT-TYPE
	SYNTAX  INTEGER
	MAX-ACCESS  read-only
	STATUS  current
	DESCRIPTION
		"Specifies the interface."
	::= { traplogEntry 4 }
 
traplogTrapNum  OBJECT-TYPE
	SYNTAX  INTEGER
	MAX-ACCESS  read-only
	STATUS  current
	DESCRIPTION
		"The SNMP trap id."
	::= { traplogEntry 5 }

traplogTimeStamp        OBJECT-TYPE
	SYNTAX  DisplayString(SIZE(0..40))
	MAX-ACCESS  read-only
	STATUS  current
	DESCRIPTION
		"Time the SNMP was generated."
	::= { traplogEntry 6 }

traplogDeviceType	OBJECT-TYPE
	SYNTAX	INTEGER
		{
		other(1),
		none(2),
		t12000(3),
		e12048(4),
		e13021(5),
		t13000(6),
		t13001(7),
		t13002(8),
		t13030(9),
		t13060(10),
		t13101(11),
		t13102(12),
		t13111(13),
		t13112(14),
		dds4001(15),
		dds4101(16),
		dds4051(17),
		dds4151(18),
		dds41TDM(19),
		generic54016(20),
		wanSuite(21)
		}
	MAX-ACCESS	read-only
	STATUS	current
	DESCRIPTION
		"Specifies the device type for the trap."
	::= { traplogEntry 7 }

traplogOID1        OBJECT-TYPE
	SYNTAX  DisplayString(SIZE(0..80))
	MAX-ACCESS  read-only
	STATUS  current
	DESCRIPTION
		"SNMP Object ID of 1st varbind."
	::= { traplogEntry 8 }

traplogDescription1        OBJECT-TYPE
	SYNTAX  DisplayString(SIZE(0..80))
	MAX-ACCESS  read-only
	STATUS  current
	DESCRIPTION
		"Description of 1st varbind."
	::= { traplogEntry 9 }

traplogValue1        OBJECT-TYPE
	SYNTAX  DisplayString(SIZE(0..80))
	MAX-ACCESS  read-only
	STATUS  current
	DESCRIPTION
		"Value of of 1st varbind."
	::= { traplogEntry 10 }

traplogOID2        OBJECT-TYPE
	SYNTAX  DisplayString(SIZE(0..80))
	MAX-ACCESS  read-only
	STATUS  current
	DESCRIPTION
		"SNMP Object ID of 2nd varbind."
	::= { traplogEntry 11 }

traplogDescription2        OBJECT-TYPE
	SYNTAX  DisplayString(SIZE(0..80))
	MAX-ACCESS  read-only
	STATUS  current
	DESCRIPTION
		"Description of 2nd varbind."
	::= { traplogEntry 12 }

traplogValue2        OBJECT-TYPE
	SYNTAX  DisplayString(SIZE(0..80))
	MAX-ACCESS  read-only
	STATUS  current
	DESCRIPTION
		"Value of of 2nd varbind."
	::= { traplogEntry 13 }

traplogOID3        OBJECT-TYPE
	SYNTAX  DisplayString(SIZE(0..80))
	MAX-ACCESS  read-only
	STATUS  current
	DESCRIPTION
		"SNMP Object ID of 3rd varbind."
	::= { traplogEntry 14 }

traplogDescription3        OBJECT-TYPE
	SYNTAX  DisplayString(SIZE(0..80))
	MAX-ACCESS  read-only
	STATUS  current
	DESCRIPTION
		"Description of 3rd varbind."
	::= { traplogEntry 15 }

traplogValue3        OBJECT-TYPE
	SYNTAX  DisplayString(SIZE(0..80))
	MAX-ACCESS  read-only
	STATUS  current
	DESCRIPTION
		"Value of of 3rd varbind."
	::= { traplogEntry 16 }

-- end traplogTableEntry

traplogDeleteEntry      OBJECT-TYPE
	SYNTAX  INTEGER
	MAX-ACCESS  read-write
	STATUS  current
	DESCRIPTION
		"Writing the index of a trap to this object will delete 
		the trap entry.  Writing an index value of 0 will delete
		all entries."
	::= { traplog 2 }

traplogSortOption       OBJECT-TYPE
	SYNTAX  INTEGER
		{
		other(1),
		ascendingtimestamp(2),
		ascendingunit(3)
		}
	MAX-ACCESS  read-write
	STATUS  current
	DESCRIPTION
		"Determines the order in which traps are presented."
	::= { traplog 3 }

traplogLastTimeStamp       OBJECT-TYPE
	SYNTAX  TimeTicks
	MAX-ACCESS  read-only
	STATUS  current
	DESCRIPTION
		"The timestamp of the newest trap in the trap log."
	::= { traplog 4 }

-- unitUtilities
-- a table of unit utilities options

unitUtilitiesTable  OBJECT-TYPE
	SYNTAX  SEQUENCE OF UnitUtilitiesTableEntry
	MAX-ACCESS  not-accessible
	STATUS  current
	DESCRIPTION
		"The unit utilities table."
	::= { unitUtilities 1 }

unitUtilitiesTableEntry  OBJECT-TYPE
	SYNTAX  UnitUtilitiesTableEntry
	MAX-ACCESS  not-accessible
	STATUS  current
	DESCRIPTION
		"An entry in the unit utilities table."
	INDEX   { unitUtilitiesNearIndex, unitUtilitiesFarIndex }
	::= { unitUtilitiesTable 1 }

UnitUtilitiesTableEntry ::=
	SEQUENCE
	{
	unitUtilitiesNearIndex		    INTEGER,
	unitUtilitiesFarIndex		    INTEGER,
	unitUtilitiesLocalPassword	    DisplayString,
	unitUtilitiesTime	 	        DisplayString,
	unitUtilitiesDate		        DisplayString,
	unitUtilitiesMaintenanceReset	INTEGER,
	unitUtilitiesAlarmResetTimer	INTEGER,
	unitUtilitiesAlarmClear		    INTEGER,
	unitUtilitiesSaveConfig         INTEGER,
	unitUtilitiesRestartStatus	INTEGER,
	unitUtilitiesReadOnlyPassword	DisplayString,
	unitUtilitiesPasswordLockoutEnable	INTEGER,
	unitUtilitiesPasswordLockoutStatus	INTEGER,
	unitUtilitiesPasswordLockoutClear	INTEGER
	}

unitUtilitiesNearIndex   OBJECT-TYPE
	SYNTAX  INTEGER
	MAX-ACCESS  read-only
	STATUS  current
	DESCRIPTION
		"Selects the near device."
	::= { unitUtilitiesTableEntry 1 }

unitUtilitiesFarIndex    OBJECT-TYPE
	SYNTAX  INTEGER
	MAX-ACCESS  read-only
	STATUS  current
	DESCRIPTION
		"Selects the far device."
	::= { unitUtilitiesTableEntry 2 }

unitUtilitiesLocalPassword       OBJECT-TYPE
	SYNTAX  DisplayString
	MAX-ACCESS  read-write
	STATUS  current
	DESCRIPTION
		"The password for local access to a device (VT100, front panel)."
	::= { unitUtilitiesTableEntry 3 }

unitUtilitiesTime OBJECT-TYPE     
	SYNTAX  DisplayString( SIZE(0..8) )
	MAX-ACCESS  read-write
	STATUS  current
	DESCRIPTION
	"This string is the current time as known to the device.  The current time may be entered in this field using the HHMMSS format.  For example, 3:45AM is entered as 034500 and 3:45PM is entered as 154500."
	::= { unitUtilitiesTableEntry 4 }

unitUtilitiesDate OBJECT-TYPE     
	SYNTAX  DisplayString( SIZE(0..8) )
	MAX-ACCESS  read-write
	STATUS  current
	DESCRIPTION
	"This string is the current date as known to the device.  The current date may be entered in this field using the MMDDYY format.  For example, July 4, 1997 is entered as 070497."
	::= { unitUtilitiesTableEntry 5 }

unitUtilitiesMaintenanceReset OBJECT-TYPE
	SYNTAX  INTEGER
		{
		other(1),
		reset(2),
		restart(3),
		resetProfile1(4),
		resetProfile2(5),
		resetProfile3(6),
		resetProfile4(7),
		resetProfile5(8),
		resetProfile6(9),
		resetProfile7(10),
		resetProfile8(11),
		resetProfile9(12),
		resetProfile10(13),
		resetProfile11(14),
		resetProfile12(15),
		resetProfile13(16),
		resetProfile14(17),
		resetProfile15(18),
		resetProfile16(19),
		resetProfile17(20),
		resetProfile18(21),
		resetProfile19(22),
		resetProfile20(23),
		resetProfile21(24)
		}
	MAX-ACCESS  read-write
	STATUS  current
	DESCRIPTION
	"This field allows resetting the device to default values by reloading the start-up default configuration parameters."
	::= { unitUtilitiesTableEntry 6 }

unitUtilitiesAlarmResetTimer	OBJECT-TYPE
	SYNTAX	INTEGER
	MAX-ACCESS	read-write
	STATUS  current
	DESCRIPTION
	"This field allows setting a timer which will cause all existing alarms on the device to be cleared upon expiration.  The counter is in seconds."
	::= { unitUtilitiesTableEntry 7 }

unitUtilitiesAlarmClear	OBJECT-TYPE
	SYNTAX	INTEGER
		{
		utilitiesAlarmClearOther(1),
		utilitiesAlarmClearNow(2)
		}
	MAX-ACCESS	read-write
	STATUS	current
	DESCRIPTION
	"Writing a value of utilitiesAlarmClearNow(2) to this field causes all existing alarms to be cleared immediately."
	::= { unitUtilitiesTableEntry 8 }

unitUtilitiesSaveConfig OBJECT-TYPE
	SYNTAX  INTEGER
			{
			other(1),
			saveConfig(2)
			}
	MAX-ACCESS  read-write
	STATUS  current
	DESCRIPTION
	"This field commands the unit to save its configuration."
	::= { unitUtilitiesTableEntry 9 }

unitUtilitiesRestartStatus OBJECT-TYPE
	SYNTAX  INTEGER
	{
		other(1),
		notNeeded(2),
		recommended(3),
		required(4)
	}
	MAX-ACCESS  read-only
	STATUS  current
	DESCRIPTION
		"This parameter indicates if the unit configuration needs to be saved and restarted.
		notNeeded - A save and restart is not needed at this time.
		recommended - A save and restart is recommended for optimal performance but not required.
		required - A save and restart is required for the unit to implement the altered configuration."
	::= { unitUtilitiesTableEntry 10 }

unitUtilitiesReadOnlyPassword       OBJECT-TYPE
	SYNTAX  DisplayString
	MAX-ACCESS  read-write
	STATUS  current
	DESCRIPTION
		"The password for read only access to a device (VT100, front panel)."
	::= { unitUtilitiesTableEntry 11 }

unitUtilitiesPasswordLockoutEnable OBJECT-TYPE
	SYNTAX  INTEGER
	{
		other(1),
		disabled(2),
		enabled(3)
	}
	MAX-ACCESS  read-write
	STATUS  current
	DESCRIPTION
		"This parameter is used to enable or disable the password lockout feature."
	::= { unitUtilitiesTableEntry 12 }

unitUtilitiesPasswordLockoutStatus OBJECT-TYPE
	SYNTAX  INTEGER
	{
		other(1),
		disabled(2),
		enabled(3),
		locked(4)
	}
	MAX-ACCESS  read-only
	STATUS  current
	DESCRIPTION
		"This parameter indicates if the password lockout feature is enabled
		or disabled, and if it is enabled this parameter may reflect if the
		password is indeed locked."
	::= { unitUtilitiesTableEntry 13 }

unitUtilitiesPasswordLockoutClear OBJECT-TYPE
	SYNTAX  INTEGER
	{
		other(1),
		unlock(2)
	}
	MAX-ACCESS  read-write
	STATUS  current
	DESCRIPTION
		"This parameter is used to unlock a locked password."
	::= { unitUtilitiesTableEntry 14 }


-- ----------------------------------------------------------------------
-- netAPS section
-- ----------------------------------------------------------------------


netAPSConfigTable	OBJECT-TYPE
	SYNTAX  SEQUENCE OF NetAPSConfigTableEntry
	MAX-ACCESS  not-accessible
	STATUS  current
	DESCRIPTION
		"One to One network Automatic Protection Switching (APS) configuration parameters table."
	::= { netAPS 1 }

netAPSConfigTableEntry	OBJECT-TYPE
	SYNTAX  NetAPSConfigTableEntry
	MAX-ACCESS  not-accessible
	STATUS  current
	DESCRIPTION
		"An entry in the netAPSConfigTable."
	INDEX   { netAPSConfigNearIndex, netAPSConfigFarIndex, netAPSConfigifIndex }
	::= { netAPSConfigTable 1 }

NetAPSConfigTableEntry ::=
	SEQUENCE
	{
		netAPSConfigNearIndex		INTEGER,
		netAPSConfigFarIndex		INTEGER,
		netAPSConfigifIndex		INTEGER,
		netAPSConfigOtherifIndex	INTEGER,
		netAPSConfigMode		INTEGER,
		netAPSConfigRevert		INTEGER,
		netAPSConfigManualInhibit	INTEGER,
		netAPSConfigAvailabilityTimer	INTEGER,
		netAPSConfigESThreshold		INTEGER,
		netAPSConfigESCount		INTEGER,
		netAPSConfigESSwitchEvent	INTEGER,
		netAPSConfigCSESThreshold	INTEGER,
		netAPSConfigCSESCount		INTEGER,
		netAPSConfigCSESSwitchEvent	INTEGER,
		netAPSConfigStatusBitmap	INTEGER,
		netAPSConfigStatusString	DisplayString,
		netAPSConfigTimeInInterval	INTEGER,
		netAPSConfigValidIntervals	INTEGER,
		netAPSConfigValidDays		INTEGER,
		netAPSConfigReset		INTEGER
	}

netAPSConfigNearIndex	OBJECT-TYPE
	SYNTAX  INTEGER
	MAX-ACCESS  read-only
	STATUS  current
	DESCRIPTION
		"Selects the near device."
	::= { netAPSConfigTableEntry 1 }

netAPSConfigFarIndex	OBJECT-TYPE
	SYNTAX  INTEGER
	MAX-ACCESS  read-only
	STATUS  current
	DESCRIPTION
		"Selects the far device."
	::= { netAPSConfigTableEntry 2 }

netAPSConfigifIndex	OBJECT-TYPE
	SYNTAX  INTEGER
	MAX-ACCESS  read-only
	STATUS  current
	DESCRIPTION
		"Selects the MIB-II ifIndex."
	::= { netAPSConfigTableEntry 3 }

netAPSConfigOtherifIndex	OBJECT-TYPE
	SYNTAX  INTEGER
	MAX-ACCESS  read-write
	STATUS  current
	DESCRIPTION
		"MIB-II ifIndex of the other interface involved with the APS."
	::= { netAPSConfigTableEntry 4 }

netAPSConfigMode	OBJECT-TYPE
	SYNTAX  INTEGER
	{
		other(1),
		tr54017(2),
		autoABswitch(3),
		masterAltCarrier(4),
		slaveAltCarrier(5)
	}
	MAX-ACCESS  read-write
	STATUS  current
	DESCRIPTION
		"tr54017 - Implements TR54017
		autoABswitch - Implements a single ended A/B switch between two independent lines
		masterAltCarrier - Master side of alternate carrier APS
		slaveAltCarrier - Slave side of alternate carrier APS"
	::= { netAPSConfigTableEntry 5 }

netAPSConfigRevert	OBJECT-TYPE
	SYNTAX  INTEGER
	{
		other(1),
		disabled(2),
		enabled(3)
	}
	MAX-ACCESS  read-write
	STATUS  current
	DESCRIPTION
		"disabled - Service does not return to the primary line until the backup line fails.
		enabled - Service automatically returns to the primary line when the primary line is able to carry service again."
	::= { netAPSConfigTableEntry 6 }

netAPSConfigManualInhibit	OBJECT-TYPE
	SYNTAX  INTEGER
	{
		other(1),
		disabled(2),
		thisLine(3),
		otherLine(4)
	}
	MAX-ACCESS  read-write
	STATUS  current
	DESCRIPTION
		"Disabled - Neither line is manually inhibited from carrying service.
		ThisLine - This line is manually inhibited from carrying service.
		OtherLine - The other line is manually inhibited from carrying service."
	::= { netAPSConfigTableEntry 7 }

netAPSConfigAvailabilityTimer	OBJECT-TYPE
	SYNTAX  INTEGER
	MAX-ACCESS  read-write
	STATUS  current
	DESCRIPTION
		"The line availability timer represents the minimum amount of time that is free of errors in active events that must expire before this line is returned to service availability.
		The timer is in seconds ranging from 0 - 900 seconds."
	::= { netAPSConfigTableEntry 8 }

netAPSConfigESThreshold	OBJECT-TYPE
	SYNTAX  INTEGER
	MAX-ACCESS  read-write
	STATUS  current
	DESCRIPTION
		"This parameter is the number of erred seconds in a 15-minute period needed before a transfer request is triggered.
		A setting of zero disables this trigger."
	::= { netAPSConfigTableEntry 9 }

netAPSConfigESCount	OBJECT-TYPE
	SYNTAX  INTEGER
	MAX-ACCESS  read-only
	STATUS  current
	DESCRIPTION
		"This parameter is the number of erred seconds in the current 15-minute interval.
		This count is reset at the beginning of a new 15-minute interval."
	::= { netAPSConfigTableEntry 10 }

netAPSConfigESSwitchEvent	OBJECT-TYPE
	SYNTAX  INTEGER
	{
		other(1),
		normal(2),
		triggered(3)
	}
	MAX-ACCESS  read-only
	STATUS  current
	DESCRIPTION
		"This status indicates if exceeding the ES threshold caused a transfer to the other line."
	::= { netAPSConfigTableEntry 11 }

netAPSConfigCSESThreshold	OBJECT-TYPE
	SYNTAX  INTEGER
	MAX-ACCESS  read-write
	STATUS  current
	DESCRIPTION
		"This parameter is the number of consecutive SES needed before a transfer request is triggered.
		A setting of zero disables this trigger."
	::= { netAPSConfigTableEntry 12 }

netAPSConfigCSESCount	OBJECT-TYPE
	SYNTAX  INTEGER
	MAX-ACCESS  read-only
	STATUS  current
	DESCRIPTION
		"This parameter is the number of consecutive SES detected.
		This count stops when 900 is reached and is reset when a non-SES is detected."
	::= { netAPSConfigTableEntry 13 }

netAPSConfigCSESSwitchEvent	OBJECT-TYPE
	SYNTAX  INTEGER
	{
		other(1),
		normal(2),
		triggered(3)
	}
	MAX-ACCESS  read-only
	STATUS  current
	DESCRIPTION
		"This status indicates if exceeding the consecutive SES threshold caused a transfer to the other line."
	::= { netAPSConfigTableEntry 14 }

netAPSConfigStatusBitmap	OBJECT-TYPE
	SYNTAX  INTEGER
	MAX-ACCESS  read-only
	STATUS  current
	DESCRIPTION
		"TR54017 defined bitmap status for this line interface:
		Value is 1 if this line is carrying service.
		Value is 2 if this line is in a failed state.
		Value is 4 if this line is in an inhibit state.
		Value is 8 if this line is looped back.
		Value is 16 if the other line is in a failed state.
		Value is 32 if the other line is in an inhibit state.
		Value is 64 if the other line is looped back.
		Value is 128 if the manual inhibit is active
		Note that multiple status conditions may exist at the same time.

		The failed state is determined when carrier fails, or the ES threshold is reached, or the consecutive SES threshold is reached.

		The inhibit state is set when the manual inhibit setting affects this line or the line is inhibited by the remote end."
	::= { netAPSConfigTableEntry 15 }

netAPSConfigStatusString	OBJECT-TYPE
	SYNTAX  DisplayString( SIZE(0..80) )
	MAX-ACCESS  read-only
	STATUS  current
	DESCRIPTION
		"ASCII string version of netAPSConfigStatusBitmap for this line status bits"
	::= { netAPSConfigTableEntry 16 }

netAPSConfigTimeInInterval	OBJECT-TYPE
	SYNTAX  INTEGER
	MAX-ACCESS  read-only
	STATUS  current
	DESCRIPTION
		"The number of seconds into the netAPSHist24Table current interval."
	::= { netAPSConfigTableEntry 17 }

netAPSConfigValidIntervals	OBJECT-TYPE
	SYNTAX  INTEGER
	MAX-ACCESS  read-only
	STATUS  current
	DESCRIPTION
		"The number of valid intervals in the netAPSHist24Table"
	::= { netAPSConfigTableEntry 18 }

netAPSConfigValidDays	OBJECT-TYPE
	SYNTAX  INTEGER
	MAX-ACCESS  read-only
	STATUS  current
	DESCRIPTION
		"The number of valid days in the netAPSHist30Table"
	::= { netAPSConfigTableEntry 19 }

netAPSConfigReset	OBJECT-TYPE
	SYNTAX  INTEGER
	{
		other(1),
		clearAlarms(2),
		clearHistory(3)
	}
	MAX-ACCESS  read-write
	STATUS  current
	DESCRIPTION
		"This action parameter does the following when the given value is set:
		other - Does nothing
		clearAlarms - Clear the APS events and counts
		clearHistory - Clear the APS history table statistics"
	::= { netAPSConfigTableEntry 20 }


-- ----------------------------------------------------------------------


netAPSHist24Table	OBJECT-TYPE
	SYNTAX  SEQUENCE OF NetAPSHist24TableEntry
	MAX-ACCESS  not-accessible
	STATUS  current
	DESCRIPTION
		"History table, contains Network APS historical data."
	::= { netAPS 2 }

netAPSHist24TableEntry	OBJECT-TYPE
	SYNTAX  NetAPSHist24TableEntry
	MAX-ACCESS  not-accessible
	STATUS  current
	DESCRIPTION
		"An entry in the netAPSHist24Table."
	INDEX   { netAPSHist24NearIndex, netAPSHist24FarIndex, netAPSHist24ifIndex, netAPSHist24Index }
	::= { netAPSHist24Table 1 }

NetAPSHist24TableEntry ::=
	SEQUENCE
	{
		netAPSHist24NearIndex		INTEGER,
		netAPSHist24FarIndex		INTEGER,
		netAPSHist24ifIndex		INTEGER,
		netAPSHist24Index		INTEGER,
		netAPSHist24Timestamp		TimeTicks,
		netAPSHist24StatusBitmap	INTEGER,
		netAPSHist24StatusString	DisplayString,
		netAPSHist24Occurrences		INTEGER,
		netAPSHist24Duration		INTEGER
	}

netAPSHist24NearIndex	OBJECT-TYPE
	SYNTAX  INTEGER
	MAX-ACCESS  read-only
	STATUS  current
	DESCRIPTION
		"Selects the near device."
	::= { netAPSHist24TableEntry 1 }

netAPSHist24FarIndex	OBJECT-TYPE
	SYNTAX  INTEGER
	MAX-ACCESS  read-only
	STATUS  current
	DESCRIPTION
		"Selects the far device."
	::= { netAPSHist24TableEntry 2 }

netAPSHist24ifIndex	OBJECT-TYPE
	SYNTAX  INTEGER
	MAX-ACCESS  read-only
	STATUS  current
	DESCRIPTION
		"Selects the MIB-II ifIndex."
	::= { netAPSHist24TableEntry 3 }


netAPSHist24Index	OBJECT-TYPE
	SYNTAX  INTEGER
	{
		statSummary(1),
		statCurrent(2),

		statPeriod1(3),
		statPeriod2(4),
		statPeriod3(5),
		statPeriod4(6),
		statPeriod5(7),
		statPeriod6(8),
		statPeriod7(9),
		statPeriod8(10),
		statPeriod9(11),

		statPeriod10(12),
		statPeriod11(13),
		statPeriod12(14),
		statPeriod13(15),
		statPeriod14(16),
		statPeriod15(17),
		statPeriod16(18),
		statPeriod17(19),
		statPeriod18(20),
		statPeriod19(21),

		statPeriod20(22),
		statPeriod21(23),
		statPeriod22(24),
		statPeriod23(25),
		statPeriod24(26),
		statPeriod25(27),
		statPeriod26(28),
		statPeriod27(29),
		statPeriod28(30),
		statPeriod29(31),

		statPeriod30(32),
		statPeriod31(33),
		statPeriod32(34),
		statPeriod33(35),
		statPeriod34(36),
		statPeriod35(37),
		statPeriod36(38),
		statPeriod37(39),
		statPeriod38(40),
		statPeriod39(41),

		statPeriod40(42),
		statPeriod41(43),
		statPeriod42(44),
		statPeriod43(45),
		statPeriod44(46),
		statPeriod45(47),
		statPeriod46(48),
		statPeriod47(49),
		statPeriod48(50),
		statPeriod49(51),

		statPeriod50(52),
		statPeriod51(53),
		statPeriod52(54),
		statPeriod53(55),
		statPeriod54(56),
		statPeriod55(57),
		statPeriod56(58),
		statPeriod57(59),
		statPeriod58(60),
		statPeriod59(61),

		statPeriod60(62),
		statPeriod61(63),
		statPeriod62(64),
		statPeriod63(65),
		statPeriod64(66),
		statPeriod65(67),
		statPeriod66(68),
		statPeriod67(69),
		statPeriod68(70),
		statPeriod69(71),

		statPeriod70(72),
		statPeriod71(73),
		statPeriod72(74),
		statPeriod73(75),
		statPeriod74(76),
		statPeriod75(77),
		statPeriod76(78),
		statPeriod77(79),
		statPeriod78(80),
		statPeriod79(81),

		statPeriod80(82),
		statPeriod81(83),
		statPeriod82(84),
		statPeriod83(85),
		statPeriod84(86),
		statPeriod85(87),
		statPeriod86(88),
		statPeriod87(89),
		statPeriod88(90),
		statPeriod89(91),

		statPeriod90(92),
		statPeriod91(93),
		statPeriod92(94),
		statPeriod93(95),
		statPeriod94(96),
		statPeriod95(97),
		statPeriod96(98)
	}
	MAX-ACCESS  read-only
	STATUS  current
	DESCRIPTION
		"The index into the 24-hour history table."
	::= { netAPSHist24TableEntry 4 }

netAPSHist24Timestamp	OBJECT-TYPE
	SYNTAX	TimeTicks
	MAX-ACCESS	read-only
	STATUS	current
	DESCRIPTION
		"The value of sysUpTime when the statistics were last updated."
	::= { netAPSHist24TableEntry 5 }

netAPSHist24StatusBitmap	OBJECT-TYPE
	SYNTAX  INTEGER
	MAX-ACCESS  read-only
	STATUS  current
	DESCRIPTION
		"TR54017 defined bitmap status for this line interface:
		Value is 1 if this line is carrying service.
		Value is 2 if this line is in a failed state.
		Value is 4 if this line is in an inhibit state.
		Value is 8 if this line is looped back.
		Value is 16 if the other line is in a failed state.
		Value is 32 if the other line is in an inhibit state.
		Value is 64 if the other line is looped back.
		Value is 128 if the manual inhibit is active
		Note that multiple status conditions may exist at the same time.

		The failed state is determined when carrier fails, or the ES threshold is reached, or the consecutive SES threshold is reached.

		The inhibit state is set when the manual inhibit setting affects this line or the line is inhibited by the remote end."
	::= { netAPSHist24TableEntry 6 }

netAPSHist24StatusString	OBJECT-TYPE
	SYNTAX  DisplayString( SIZE(0..80) )
	MAX-ACCESS  read-only
	STATUS  current
	DESCRIPTION
		"ASCII string version of netAPSHist24StatusBitmap for this line status bits"
	::= { netAPSHist24TableEntry 7 }

netAPSHist24Occurrences	OBJECT-TYPE
	SYNTAX  INTEGER
	MAX-ACCESS  read-only
	STATUS  current
	DESCRIPTION
		"This parameter is the total number of times the service was transferred between lines."
	::= { netAPSHist24TableEntry 8 }

netAPSHist24Duration	OBJECT-TYPE
	SYNTAX  INTEGER
	MAX-ACCESS  read-only
	STATUS  current
	DESCRIPTION
		"This parameter is the number of seconds the service was provided on this line."
	::= { netAPSHist24TableEntry 9 }


-- ----------------------------------------------------------------------

	
netAPSHist30Table	OBJECT-TYPE
	SYNTAX  SEQUENCE OF NetAPSHist30TableEntry
	MAX-ACCESS  not-accessible
	STATUS  current
	DESCRIPTION
		"History table, contains Network APS 30-day historical data."
	::= { netAPS 3 }

netAPSHist30TableEntry	OBJECT-TYPE
	SYNTAX  NetAPSHist30TableEntry
	MAX-ACCESS  not-accessible
	STATUS  current
	DESCRIPTION
		"An entry in the netAPSHist30Table."
	INDEX   { netAPSHist30NearIndex, netAPSHist30FarIndex, netAPSHist30ifIndex, netAPSHist30Index }
	::= { netAPSHist30Table 1 }

NetAPSHist30TableEntry ::=
	SEQUENCE
	{
		netAPSHist30NearIndex		INTEGER,
		netAPSHist30FarIndex		INTEGER,
		netAPSHist30ifIndex		INTEGER,
		netAPSHist30Index		INTEGER,
		netAPSHist30Timestamp		TimeTicks,
		netAPSHist30StatusBitmap	INTEGER,
		netAPSHist30StatusString	DisplayString,
		netAPSHist30Occurrences		INTEGER,
		netAPSHist30Duration		INTEGER
	}

netAPSHist30NearIndex	OBJECT-TYPE
	SYNTAX  INTEGER
	MAX-ACCESS  read-only
	STATUS  current
	DESCRIPTION
		"Selects the near device."
	::= { netAPSHist30TableEntry 1 }

netAPSHist30FarIndex	OBJECT-TYPE
	SYNTAX  INTEGER
	MAX-ACCESS  read-only
	STATUS  current
	DESCRIPTION
		"Selects the far device."
	::= { netAPSHist30TableEntry 2 }

netAPSHist30ifIndex	OBJECT-TYPE
	SYNTAX  INTEGER
	MAX-ACCESS  read-only
	STATUS  current
	DESCRIPTION
		"Selects the MIB-II ifIndex."
	::= { netAPSHist30TableEntry 3 }

netAPSHist30Index	OBJECT-TYPE
	SYNTAX  INTEGER
	{
		statSummary(1),
 
		statDay1(2),
		statDay2(3),
		statDay3(4),
		statDay4(5),
		statDay5(6),
		statDay6(7),
		statDay7(8),
		statDay8(9),
		statDay9(10),
 
		statDay10(11),
		statDay11(12),
		statDay12(13),
		statDay13(14),
		statDay14(15),
		statDay15(16),
		statDay16(17),
		statDay17(18),
		statDay18(19),
		statDay19(20),
 
		statDay20(21),
		statDay21(22),
		statDay22(23),
		statDay23(24),
		statDay24(25),
		statDay25(26),
		statDay26(27),
		statDay27(28),
		statDay28(29),
		statDay29(30),
 
		statDay30(31)
	}
	MAX-ACCESS  read-only
	STATUS  current
	DESCRIPTION
		"The index into the 30-day history table."
	::= { netAPSHist30TableEntry 4 }

netAPSHist30Timestamp	OBJECT-TYPE
	SYNTAX	TimeTicks
	MAX-ACCESS	read-only
	STATUS	current
	DESCRIPTION
		"The value of sysUpTime when the statistics were last updated."
	::= { netAPSHist30TableEntry 5 }

netAPSHist30StatusBitmap	OBJECT-TYPE
	SYNTAX  INTEGER
	MAX-ACCESS  read-only
	STATUS  current
	DESCRIPTION
		"TR54017 defined bitmap status for this line interface:
		Value is 1 if this line is carrying service.
		Value is 2 if this line is in a failed state.
		Value is 4 if this line is in an inhibit state.
		Value is 8 if this line is looped back.
		Value is 16 if the other line is in a failed state.
		Value is 32 if the other line is in an inhibit state.
		Value is 64 if the other line is looped back.
		Value is 128 if the manual inhibit is active
		Note that multiple status conditions may exist at the same time.

		The failed state is determined when carrier fails, or the ES threshold is reached, or the consecutive SES threshold is reached.

		The inhibit state is set when the manual inhibit setting affects this line or the line is inhibited by the remote end."
	::= { netAPSHist30TableEntry 6 }

netAPSHist30StatusString	OBJECT-TYPE
	SYNTAX  DisplayString( SIZE(0..80) )
	MAX-ACCESS  read-only
	STATUS  current
	DESCRIPTION
		"ASCII string version of netAPSHist30StatusBitmap for this line status bits"
	::= { netAPSHist30TableEntry 7 }

netAPSHist30Occurrences	OBJECT-TYPE
	SYNTAX  INTEGER
	MAX-ACCESS  read-only
	STATUS  current
	DESCRIPTION
		"This parameter is the total number of times the service was transferred between lines."
	::= { netAPSHist30TableEntry 8 }

netAPSHist30Duration	OBJECT-TYPE
	SYNTAX  INTEGER
	MAX-ACCESS  read-only
	STATUS  current
	DESCRIPTION
		"This parameter is the number of seconds the service was provided on this line."
	::= { netAPSHist30TableEntry 9 }

END

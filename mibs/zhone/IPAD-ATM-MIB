-- $Header:   K:/WanSuite/archives/include/pvcs/ipadatm.mib,v   1.13   Aug 21 2003 09:50:16   leen  $

IPAD-ATM-MIB DEFINITIONS ::= BEGIN

IMPORTS IpAddress, TimeTicks,OBJECT-TYPE, MODULE-IDENTITY  FROM SNMPv2-SMI
	DisplayString                       		FROM SNMPv2-TC
	ipad                                           FROM IPADv2-MIB;

ipadAtm MODULE-IDENTITY
         LAST-UPDATED "0003270001Z"
         ORGANIZATION "Verilink Corporation"
         CONTACT-INFO
             "support@verilink.com
             1-800-926-0085"
         DESCRIPTION
            "The IPAD ATM MIB."
         ::= { ipad 25 }

ipadAtmParms           OBJECT IDENTIFIER ::= { ipadAtm 1 }
ipadAtmStatsParms      OBJECT IDENTIFIER ::= { ipadAtm 2 }
ipadAtmVccParms        OBJECT IDENTIFIER ::= { ipadAtm 3 }
ipadAtmVccStatsParms   OBJECT IDENTIFIER ::= { ipadAtm 4 }
ipadAtmCesParms        OBJECT IDENTIFIER ::= { ipadAtm 5 }
ipadAtmFrParms         OBJECT IDENTIFIER ::= { ipadAtm 6 }

-- Atm If parameters

ipadAtmTable OBJECT-TYPE
    SYNTAX    SEQUENCE OF IpadAtmTableEntry
    MAX-ACCESS  not-accessible
    STATUS    current
    DESCRIPTION
        "Table of ATM parameters."
    ::= { ipadAtmParms 1 }

ipadAtmTableEntry OBJECT-TYPE
    SYNTAX  IpadAtmTableEntry
    MAX-ACCESS  not-accessible
    STATUS  current
    DESCRIPTION
        "An entry in the ipad ATM parameter table."
    INDEX   { ipadAtmIfIndex }
    ::= { ipadAtmTable 1 }

IpadAtmTableEntry ::=
    SEQUENCE
    {
    ipadAtmIfIndex                    INTEGER,
    ipadAtmOperStatus		      INTEGER,
    ipadAtmVccsOpenedOK		      INTEGER,
    ipadAtmVccsNotOpened              INTEGER,
    ipadAtmAlarmReset		      INTEGER,
    ipadAtmOverSubscriptionFactor     INTEGER,
    ipadAtmLineBandwidth              INTEGER,
    ipadAtmAAL5Bandwidth              INTEGER,
    ipadAtmOverSubBandwidth           INTEGER,
    ipadAtmCbrUsedBandwidth           INTEGER,
    ipadAtmVbrUsedBandwidth           INTEGER,
    ipadAtmUbrUsedBandwidth           INTEGER,
    ipadAtmQos0Pcr                    INTEGER
    }

ipadAtmIfIndex       OBJECT-TYPE
    SYNTAX  INTEGER
    MAX-ACCESS  read-only
    STATUS  current
    DESCRIPTION
        "The index into the ATM table."
    ::= { ipadAtmTableEntry 1 }

ipadAtmOperStatus    OBJECT-TYPE
    SYNTAX  INTEGER {
		    other(1),
		    down(2),
		    upNoCellSync(3),
		    upCellSync(4)
		    }
    MAX-ACCESS  read-only
    STATUS  current
    DESCRIPTION
        "The up/down status of this atm interface."
    ::= { ipadAtmTableEntry 2 }

ipadAtmVccsOpenedOK  OBJECT-TYPE
    SYNTAX  INTEGER
    MAX-ACCESS  read-only
    STATUS  current
    DESCRIPTION
        "The current number of successfully opened VCCs on this ATM interface."
    ::= { ipadAtmTableEntry 3 }

ipadAtmVccsNotOpened OBJECT-TYPE
    SYNTAX  INTEGER
    MAX-ACCESS  read-only
    STATUS  current
    DESCRIPTION
        "The current number of VCCs that were not successfully opened on this ATM interface."
    ::= { ipadAtmTableEntry 4 }

ipadAtmAlarmReset OBJECT-TYPE
    SYNTAX  INTEGER {
		    other(1),
		    clearAlarms(2),
		    clearStats(3)
		    }
    MAX-ACCESS  read-write
    STATUS  current
    DESCRIPTION
        "Reset the alarms or statistics of this ATM interface."
    ::= { ipadAtmTableEntry 5 }

ipadAtmOverSubscriptionFactor OBJECT-TYPE
    SYNTAX  INTEGER(1..10)
    MAX-ACCESS  read-write
    STATUS  current
    DESCRIPTION
        "The current over-subscription-factor for this ATM interface.
	Used for VBR and UBR VC connection admission control
	to allow the either VBR or UBR service category connections to
	collectively use more bandwidth than is available in order
	to make use of the statistical multiplexing of the connections.
	The PCR of each individual VC is limited to the interface's line rate.
	However when multiple VCs are configured, the sum of their PCR
	values can go up to (OverSubscriptionFactor * (line-rate) / 53*8).
	A value of 1 indicates no oversubscription allowed.
	A value of 5 indicates 5 times oversubscription allowed.
	Note that CBR connections cannot be oversubscribed.
	Also, if CES is in use on the interface, all AAL5 connections
	have their PCR limited to the amount which the line rate can support
	above the commitment for CES, and the oversubscription applies
	only to that bandwidth above the CES commitment."
    ::= { ipadAtmTableEntry 6 }

ipadAtmLineBandwidth OBJECT-TYPE
    SYNTAX  INTEGER
    MAX-ACCESS  read-only
    STATUS  current
    DESCRIPTION
        "The current ATM Line interface Bandwidth in cells per second."
    ::= { ipadAtmTableEntry 7 }

ipadAtmAAL5Bandwidth OBJECT-TYPE
    SYNTAX  INTEGER
    MAX-ACCESS  read-only
    STATUS  current
    DESCRIPTION
        "The current AAL5 Bandwidth in cells per second."
    ::= { ipadAtmTableEntry 8 }

ipadAtmOverSubBandwidth OBJECT-TYPE
    SYNTAX  INTEGER
    MAX-ACCESS  read-only
    STATUS  current
    DESCRIPTION
        "The AAL5 Oversubscription Bandwidth in cells per second.
	This value is ipadAtmAAL5Bandwidth multiplied by the
	ipadAtmOversubscriptionFactor."
    ::= { ipadAtmTableEntry 9 }

ipadAtmCbrUsedBandwidth OBJECT-TYPE
    SYNTAX  INTEGER
    MAX-ACCESS  read-only
    STATUS  current
    DESCRIPTION
        "The amount of AAL5 Bandwidth allocated
		to CBR VCs in cells per second."
    ::= { ipadAtmTableEntry 10 }

ipadAtmVbrUsedBandwidth OBJECT-TYPE
    SYNTAX  INTEGER
    MAX-ACCESS  read-only
    STATUS  current
    DESCRIPTION
        "The amount of AAL5 Bandwidth allocated
	to VBR VCs in cells per second. When OversubscriptionFactor
	is greater than 1, this value can exceed ipadAtmAAL5Bandwidth."
    ::= { ipadAtmTableEntry 11 }

ipadAtmUbrUsedBandwidth OBJECT-TYPE
    SYNTAX  INTEGER
    MAX-ACCESS  read-only
    STATUS  current
    DESCRIPTION
        "The amount of AAL5 Bandwidth allocated
	to UBR VCs in cells per second. When OversubscriptionFactor
	is greater than 1, this value can exceed ipadAtmAAL5Bandwidth."
    ::= { ipadAtmTableEntry 12 }

ipadAtmQos0Pcr OBJECT-TYPE
    SYNTAX  INTEGER
    MAX-ACCESS  read-only
    STATUS  current
    DESCRIPTION
        "The value of PCR to be used for each VC which has
	no specified QOS profile (0). The VC is configured as UBR with
	the given Peak Cell Rate."
    ::= { ipadAtmTableEntry 13 }

-- ATM Statistics

ipadAtmStatsTable OBJECT-TYPE
    SYNTAX    SEQUENCE OF IpadAtmStatsTableEntry
    MAX-ACCESS  not-accessible
    STATUS    current
    DESCRIPTION
        "Table of ATM statistics."
    ::= { ipadAtmStatsParms 1 }

ipadAtmStatsTableEntry OBJECT-TYPE
    SYNTAX  IpadAtmStatsTableEntry
    MAX-ACCESS  not-accessible
    STATUS  current
    DESCRIPTION
        "An entry in the ipad ATM Stats parameter table."
    INDEX   { ipadAtmStatsIndex, ipadAtmStatsPeriodIndex }
    ::= { ipadAtmStatsTable 1 }

IpadAtmStatsTableEntry ::=
    SEQUENCE
    {
    ipadAtmStatsIndex                    INTEGER,
    ipadAtmStatsPeriodIndex              INTEGER,
    ipadAtmStatsTimeStamp                TimeTicks,
    ipadAtmStatsRxFramesOK               INTEGER,
    ipadAtmStatsTxFramesOK		 INTEGER,
    ipadAtmStatsRxFramesError            INTEGER,
    ipadAtmStatsTxFramesError		 INTEGER,
    ipadAtmStatsRxBytesOK                INTEGER,
    ipadAtmStatsTxBytesOK		 INTEGER,
    ipadAtmStatsLostSync		 INTEGER,
    ipadAtmStatsOamCellsRx               INTEGER,
    ipadAtmStatsOamCellsTx		 INTEGER
    }

ipadAtmStatsIndex       OBJECT-TYPE
    SYNTAX  INTEGER
    MAX-ACCESS  read-only
    STATUS  current
    DESCRIPTION
        "The index representing the ATM interface."
    ::= { ipadAtmStatsTableEntry 1 }

ipadAtmStatsPeriodIndex	OBJECT-TYPE
    SYNTAX  INTEGER
    MAX-ACCESS  read-only
    STATUS  current
    DESCRIPTION
        "The index representing the period for the ATM stats entry."
    ::= { ipadAtmStatsTableEntry 2 }

ipadAtmStatsTimeStamp	OBJECT-TYPE
    SYNTAX	TimeTicks
    MAX-ACCESS	read-only
    STATUS	current
    DESCRIPTION
    	"The value of sysUpTime the last time the statistics were updated."
    ::= { ipadAtmStatsTableEntry 3 }

 ipadAtmStatsRxFramesOK       OBJECT-TYPE
    SYNTAX  INTEGER
    MAX-ACCESS  read-only
    STATUS  current
    DESCRIPTION
        "The number of error-free frames received during the period."
    ::= { ipadAtmStatsTableEntry 4 }

ipadAtmStatsTxFramesOK	OBJECT-TYPE
    SYNTAX  INTEGER
    MAX-ACCESS  read-only
    STATUS  current
    DESCRIPTION
        "The number of frames successfully transmitted during the period."
    ::= { ipadAtmStatsTableEntry 5 }

ipadAtmStatsRxFramesError       OBJECT-TYPE
    SYNTAX  INTEGER
    MAX-ACCESS  read-only
    STATUS  current
    DESCRIPTION
        "The number of errored frames received during the period."
    ::= { ipadAtmStatsTableEntry 6 }

ipadAtmStatsTxFramesError	OBJECT-TYPE
    SYNTAX  INTEGER
    MAX-ACCESS  read-only
    STATUS  current
    DESCRIPTION
        "The number of transmitted frames that were errored."
    ::= { ipadAtmStatsTableEntry 7 }

ipadAtmStatsRxBytesOK       OBJECT-TYPE
    SYNTAX  INTEGER
    MAX-ACCESS  read-only
    STATUS  current
    DESCRIPTION
        "The number of error-free bytes received during the period."
    ::= { ipadAtmStatsTableEntry 8 }

ipadAtmStatsTxBytesOK	OBJECT-TYPE
    SYNTAX  INTEGER
    MAX-ACCESS  read-only
    STATUS  current
    DESCRIPTION
        "The number of successfully transmitted bytes during the period."
    ::= { ipadAtmStatsTableEntry 9 }

ipadAtmStatsLostSync	OBJECT-TYPE
    SYNTAX  INTEGER
    MAX-ACCESS  read-only
    STATUS  current
    DESCRIPTION
        "The number of times sync has been lost or recovered."
    ::= { ipadAtmStatsTableEntry 10 }

ipadAtmStatsOamCellsRx OBJECT-TYPE
    SYNTAX  INTEGER
    MAX-ACCESS  read-only
    STATUS  current
    DESCRIPTION
        "The number of OAM cells received on this ATM link."
    ::= { ipadAtmStatsTableEntry 11 }
 
ipadAtmStatsOamCellsTx OBJECT-TYPE
    SYNTAX  INTEGER
    MAX-ACCESS  read-only
    STATUS  current
    DESCRIPTION
        "The number of OAM cells transmitted on this ATM link."
    ::= { ipadAtmStatsTableEntry 12 }
 

-- Vcc parameters

ipadAtmVccTable OBJECT-TYPE
    SYNTAX    SEQUENCE OF IpadAtmVccTableEntry
    MAX-ACCESS  not-accessible
    STATUS    current
    DESCRIPTION
        "Table of Virtual Channel parameters."
    ::= { ipadAtmVccParms 1 }

ipadAtmVccTableEntry OBJECT-TYPE
    SYNTAX  IpadAtmVccTableEntry
    MAX-ACCESS  not-accessible
    STATUS  current
    DESCRIPTION
        "An entry in the ipad ATM Vcc parameter table."
    INDEX   { ipadAtmVccIndex, ipadAtmVccVpiIndex, ipadAtmVccVciIndex }
    ::= { ipadAtmVccTable 1 }

IpadAtmVccTableEntry ::=
    SEQUENCE
    {
    ipadAtmVccIndex                   INTEGER,
    ipadAtmVccVpiIndex         	      INTEGER,
    ipadAtmVccVciIndex 	              INTEGER,
    ipadAtmVccEncapsulationType       INTEGER,
    ipadAtmVccTrafficType	      INTEGER,
    ipadAtmVccChannelRate	      INTEGER,
    ipadAtmVccAlarmReset	      INTEGER,
    ipadAtmVccSLATimer  	      INTEGER,
    ipadAtmVccRemoteFramesOffered     INTEGER,
    ipadAtmVccFramesReceived	      INTEGER,
    ipadAtmVccRemoteDataOffered	      INTEGER,
    ipadAtmVccDataReceived	      INTEGER,
    ipadAtmVccRemoteActive	      INTEGER,
    ipadAtmVccRemoteVpi               INTEGER,
    ipadAtmVccRemoteVci               INTEGER,
    ipadAtmVccRemoteIPAddress	      IpAddress,
    ipadAtmVccRemoteUnitId	      DisplayString,
 
    ipadAtmVccEtoeLoopbackCommand     INTEGER,
    ipadAtmVccEtoeLoopbackState       INTEGER,
    ipadAtmVccEtoeLoopbackCellsTx     INTEGER,
    ipadAtmVccEtoeLoopbackCellsRx     INTEGER,
    ipadAtmVccEtoeLoopbackRttMin      INTEGER,
    ipadAtmVccEtoeLoopbackRttMax      INTEGER,
    ipadAtmVccEtoeLoopbackRttAvg      INTEGER,
 
    ipadAtmVccSegLoopbackCommand      INTEGER,
    ipadAtmVccSegLoopbackState        INTEGER,
    ipadAtmVccSegLoopbackCellsTx      INTEGER,
    ipadAtmVccSegLoopbackCellsRx      INTEGER,
    ipadAtmVccSegLoopbackRttMin       INTEGER,
    ipadAtmVccSegLoopbackRttMax       INTEGER,
    ipadAtmVccSegLoopbackRttAvg       INTEGER,
 
    ipadAtmVccEtoeContCheckCommand    INTEGER, 
    ipadAtmVccEtoeContCheckAutoActivate INTEGER,
    ipadAtmVccEtoeContCheckType       INTEGER, 
    ipadAtmVccEtoeContCheckTypeInUse  INTEGER, 
    ipadAtmVccEtoeContCheckStatus     INTEGER, 
    ipadAtmVccEtoeContCheckCellsTx    INTEGER, 
    ipadAtmVccEtoeContCheckCellsRx    INTEGER, 
 
    ipadAtmVccEtoeAisStatus           INTEGER,
    ipadAtmVccEtoeRdiStatus           INTEGER
    }

ipadAtmVccIndex       OBJECT-TYPE
    SYNTAX  INTEGER
    MAX-ACCESS  read-only
    STATUS  current
    DESCRIPTION
        "The index into the ATM VCC table, corresponding to ifIndex."
    ::= { ipadAtmVccTableEntry 1 }

ipadAtmVccVpiIndex    OBJECT-TYPE
    SYNTAX  INTEGER
    MAX-ACCESS  read-only
    STATUS  current
    DESCRIPTION
        "The VPI for the VCC."
    ::= { ipadAtmVccTableEntry 2 }

ipadAtmVccVciIndex    OBJECT-TYPE
    SYNTAX  INTEGER
    MAX-ACCESS  read-only
    STATUS  current
    DESCRIPTION
        "The VCI for the VCC."
    ::= { ipadAtmVccTableEntry 3 }

ipadAtmVccEncapsulationType OBJECT-TYPE
    SYNTAX  INTEGER {
		    other(1),
		    serialPPPoA(2),
		    vcMux(3),
		    llcMux(4),
		    serialHDLCoA(5),
			frf5(6),
			frf8(7)
		    }
    MAX-ACCESS  read-write
    STATUS  current
    DESCRIPTION
        "The encapsulation method used on this VCC.
        vcMux indicates null encapsulation and may be used
        for IP routing or PPP applications.
        llcMux indicates LLC encapsulation and may be used
        for IP routing, bridging, and PPP applications.
        serialPPPoA and serialHDLCoA indicate serial port applications."
    ::= { ipadAtmVccTableEntry 4 }

ipadAtmVccTrafficType OBJECT-TYPE
    SYNTAX  INTEGER  {
    		     other(1),
		     cbr(2),
		     rtVbr(3),
		     nrtVbr(4),
		     abr(5),
		     ubr(6)
		     }
    MAX-ACCESS  read-only
    STATUS  current
    DESCRIPTION
        "The traffic type of this VCC."
    ::= { ipadAtmVccTableEntry 5 }

ipadAtmVccChannelRate OBJECT-TYPE
    SYNTAX  INTEGER
    MAX-ACCESS  read-only
    STATUS  current
    DESCRIPTION
        "The channel rate for this VCC."
    ::= { ipadAtmVccTableEntry 6 }

ipadAtmVccAlarmReset OBJECT-TYPE
    SYNTAX  INTEGER {
		    other(1),
		    clearAlarms(2),
		    clearStats(3)
		    }
    MAX-ACCESS  read-write
    STATUS  current
    DESCRIPTION
        "Reset the alarms or statistics of this VCC."
    ::= { ipadAtmVccTableEntry 7 }

ipadAtmVccSLATimer OBJECT-TYPE
    SYNTAX  INTEGER 
    MAX-ACCESS  read-write
    STATUS  current
    DESCRIPTION
        "The time in seconds between SLA measurement packets being sent."
    ::= { ipadAtmVccTableEntry 8 }

ipadAtmVccRemoteFramesOffered OBJECT-TYPE
    SYNTAX  INTEGER
    MAX-ACCESS  read-only
    STATUS  current
    DESCRIPTION
        "The number of frames offered by the remote device."
    ::= { ipadAtmVccTableEntry 9 }

ipadAtmVccFramesReceived OBJECT-TYPE
    SYNTAX  INTEGER
    MAX-ACCESS  read-only
    STATUS  current
    DESCRIPTION
        "The number of frames received by this device."
    ::= { ipadAtmVccTableEntry 10 }

ipadAtmVccRemoteDataOffered OBJECT-TYPE
    SYNTAX  INTEGER
    MAX-ACCESS  read-only
    STATUS  current
    DESCRIPTION
        "The number of data bytes offered by the remote device."
    ::= { ipadAtmVccTableEntry 11 }

ipadAtmVccDataReceived OBJECT-TYPE
    SYNTAX  INTEGER
    MAX-ACCESS  read-only
    STATUS  current
    DESCRIPTION
        "The number of data bytes received by this device."
    ::= { ipadAtmVccTableEntry 12 }

ipadAtmVccRemoteActive OBJECT-TYPE
    SYNTAX  INTEGER {
	    	    other(1),
	            inactive(2),
	            active(3)
	            }
    MAX-ACCESS  read-only
    STATUS  current
    DESCRIPTION
        "The current state of the remote device as detected by the local device."
    ::= { ipadAtmVccTableEntry 13 }

ipadAtmVccRemoteVpi OBJECT-TYPE
    SYNTAX  INTEGER
    MAX-ACCESS  read-only
    STATUS  current
    DESCRIPTION
        "The remote VPI."
    ::= { ipadAtmVccTableEntry 14 }
 
ipadAtmVccRemoteVci  OBJECT-TYPE
    SYNTAX  INTEGER
    MAX-ACCESS  read-only
    STATUS  current
    DESCRIPTION
        "The remote VCI."
    ::= { ipadAtmVccTableEntry 15 }

ipadAtmVccRemoteIPAddress  OBJECT-TYPE
    SYNTAX  IpAddress
    MAX-ACCESS  read-only
    STATUS  current
    DESCRIPTION
        "The IP Address of the device connected to the remote end of this VCC."
    ::= { ipadAtmVccTableEntry 16 }

ipadAtmVccRemoteUnitId  OBJECT-TYPE
    SYNTAX  DisplayString
    MAX-ACCESS  read-only
    STATUS  current
    DESCRIPTION
        "The Unit ID assigned to the devie connected to the remote end of this VCC."
    ::= { ipadAtmVccTableEntry 17 }
 
ipadAtmVccEtoeLoopbackCommand OBJECT-TYPE
    SYNTAX  INTEGER {
		    other(1),
		    start(2),
		    stop(3)
		    }
    MAX-ACCESS  read-write
    STATUS  current
    DESCRIPTION
        "A command to issue on the VCC Loopback.
	The start command is used to start an OAM F5 VCC loopback.
	The stop command is used to terminate the OAM loopback.
	The statistics variables associated with the OAM loopback
	are automatically cleared when a loopback is started."
    ::= { ipadAtmVccTableEntry 18 }
 
ipadAtmVccEtoeLoopbackState OBJECT-TYPE
    SYNTAX  INTEGER {
		    inactive(1),
		    active(2),
		    loopback(3)
		    }
    MAX-ACCESS  read-only
    STATUS  current
    DESCRIPTION
        "The state of this VCC loopback function.
	The active state means OAM F5 loopback cells are being
	sent from this endpoint once every 5 seconds.
	The loopback state means that OAM F5 loopback cells are being
	received and returned from this endpoint."
    ::= { ipadAtmVccTableEntry 19 }
 
ipadAtmVccEtoeLoopbackCellsTx OBJECT-TYPE
    SYNTAX  INTEGER 
    MAX-ACCESS  read-only
    STATUS  current
    DESCRIPTION
        "The number of OAM F5 Loopback cells transmitted
	for this VCC."
    ::= { ipadAtmVccTableEntry 20 }
 
ipadAtmVccEtoeLoopbackCellsRx OBJECT-TYPE
    SYNTAX  INTEGER 
    MAX-ACCESS  read-only
    STATUS  current
    DESCRIPTION
        "The number of OAM F5 Loopback cells received
	for this VCC."
    ::= { ipadAtmVccTableEntry 21 }
 
ipadAtmVccEtoeLoopbackRttMin OBJECT-TYPE
    SYNTAX  INTEGER
    MAX-ACCESS  read-only
    STATUS  current
    DESCRIPTION
        "The minimum round trip time in milliseconds
	between sending a loopback cell and receiving
	the returned loopback cell."
    ::= { ipadAtmVccTableEntry 22 }
 
ipadAtmVccEtoeLoopbackRttMax OBJECT-TYPE
    SYNTAX  INTEGER
    MAX-ACCESS  read-only
    STATUS  current
    DESCRIPTION
        "The maximum round trip time in milliseconds
	between sending a loopback cell and receiving
	the returned loopback cell."
    ::= { ipadAtmVccTableEntry 23 }
 
ipadAtmVccEtoeLoopbackRttAvg OBJECT-TYPE
    SYNTAX  INTEGER
    MAX-ACCESS  read-only
    STATUS  current
    DESCRIPTION
        "The average round trip time in milliseconds
	between sending a loopback cell and receiving
	the returned loopback cell."
    ::= { ipadAtmVccTableEntry 24 }
 
 
ipadAtmVccSegLoopbackCommand OBJECT-TYPE
    SYNTAX  INTEGER {
		    other(1),
		    start(2),
		    stop(3)
		    }
    MAX-ACCESS  read-write
    STATUS  current
    DESCRIPTION
        "A command to issue on the VCC Loopback.
	The start command is used to start an OAM F5 VCC loopback.
	The stop command is used to terminate the OAM loopback.
	The statistics variables associated with the OAM loopback
	are automatically cleared when a loopback is started."
    ::= { ipadAtmVccTableEntry 25 }
 
ipadAtmVccSegLoopbackState OBJECT-TYPE
    SYNTAX  INTEGER {
		    inactive(1),
		    active(2),
		    loopback(3)
		    }
    MAX-ACCESS  read-only
    STATUS  current
    DESCRIPTION
        "The state of this VCC loopback function.
	The active state means OAM F5 loopback cells are being
	sent from this endpoint once every 5 seconds.
	The loopback state means that OAM F5 loopback cells are being
	received and returned from this endpoint."
    ::= { ipadAtmVccTableEntry 26 }
 
ipadAtmVccSegLoopbackCellsTx OBJECT-TYPE
    SYNTAX  INTEGER 
    MAX-ACCESS  read-only
    STATUS  current
    DESCRIPTION
        "The number of OAM F5 Loopback cells transmitted
	for this VCC."
    ::= { ipadAtmVccTableEntry 27 }
 
ipadAtmVccSegLoopbackCellsRx OBJECT-TYPE
    SYNTAX  INTEGER 
    MAX-ACCESS  read-only
    STATUS  current
    DESCRIPTION
        "The number of OAM F5 Loopback cells received
	for this VCC."
    ::= { ipadAtmVccTableEntry 28 }
 
ipadAtmVccSegLoopbackRttMin OBJECT-TYPE
    SYNTAX  INTEGER
    MAX-ACCESS  read-only
    STATUS  current
    DESCRIPTION
        "The minimum round trip time in milliseconds
	between sending a loopback cell and receiving
	the returned loopback cell."
    ::= { ipadAtmVccTableEntry 29 }
 
ipadAtmVccSegLoopbackRttMax OBJECT-TYPE
    SYNTAX  INTEGER
    MAX-ACCESS  read-only
    STATUS  current
    DESCRIPTION
        "The maximum round trip time in milliseconds
	between sending a loopback cell and receiving
	the returned loopback cell."
    ::= { ipadAtmVccTableEntry 30 }
 
ipadAtmVccSegLoopbackRttAvg OBJECT-TYPE
    SYNTAX  INTEGER
    MAX-ACCESS  read-only
    STATUS  current
    DESCRIPTION
        "The average round trip time in milliseconds
	between sending a loopback cell and receiving
	the returned loopback cell."
    ::= { ipadAtmVccTableEntry 31 }
 
 
ipadAtmVccEtoeContCheckCommand OBJECT-TYPE
    SYNTAX  INTEGER {
		    other(1),
		    activate(2),
		    deactivate(3)
		    }
    MAX-ACCESS  read-write
    STATUS  current
    DESCRIPTION
        "ipadAtmVccEtoeContCheckCommand is used to request
		activation or deactivation of the End-to-End continuity check
		on this VCC."
    ::= { ipadAtmVccTableEntry 32 }
 
ipadAtmVccEtoeContCheckAutoActivate OBJECT-TYPE
    SYNTAX  INTEGER {
		    other(1),
		    disable(2),
		    enable(3)
		    }
    MAX-ACCESS  read-write
    STATUS  current
    DESCRIPTION
        "ipadAtmVccEtoeContCheckAutoActivate indicates whether
	End-to-End continuity check is automatically activated on this VCC.
	A Value of disable means CC is not automatically activated.
	A value of enable permits CC to be automatically activated
	after the VCC connection is established."
    ::= { ipadAtmVccTableEntry 33 }
 
ipadAtmVccEtoeContCheckType OBJECT-TYPE
    SYNTAX  INTEGER {
		    none(1),
		    sink(2),
		    source(3),
		    sinkAndSource(4)
		    }
    MAX-ACCESS  read-only
    STATUS  current
    DESCRIPTION
        "Default Continuity Check Type used for this VCC.
		A value of none selects no continuity check.
		A value of sink, source, or sinkAndSource selects the respective
		continuity check functions.
		ipadAtmVccEtoeContCheckType can only be changed when
		CC is not currently active."
    ::= { ipadAtmVccTableEntry 34 }

ipadAtmVccEtoeContCheckTypeInUse OBJECT-TYPE
    SYNTAX  INTEGER {
		    none(1),
		    sink(2),
		    source(3),
		    sinkAndSource(4)
		    }
    MAX-ACCESS  read-only
    STATUS  current
    DESCRIPTION
        "The current Continuity Check Type in use for this VCC.
		ipadAtmVccEtoeContCheckTypeInUse may differ from
		ipadAtmVccEtoeContCheckType if CC is activated via inband OAM."
    ::= { ipadAtmVccTableEntry 35 }

ipadAtmVccEtoeContCheckStatus OBJECT-TYPE
    SYNTAX  INTEGER {
		    ready(1),
		    active(2),
		    activationFailed(3),
		    activating(4),
		    deactivating(5)
		    }
    MAX-ACCESS  read-only
    STATUS  current
    DESCRIPTION
        "The current state of Continuity Check for this VCC.
	In the ready state, no CC is being performed.
	The ready state indicates CC is permitted to be activated.
	The activating state indicates CC has been requested
	and is being activated. During activation, an OAM activation
	cell is sent to the opposite endpoint to request CC.
	Once an activation confirmed cell is received, the 
	state is then changed to active.
	Reception of an activation denied response or a multiple
	of 3 ten-second time outs waiting for a confirmation
	will result in an activationFailed state.
	CC sourcing is performed when state is active or activating.
	CC sinking is performed when state is active."
    ::= { ipadAtmVccTableEntry 36 }
 
ipadAtmVccEtoeContCheckCellsTx OBJECT-TYPE
    SYNTAX  INTEGER
    MAX-ACCESS  read-only
    STATUS  current
    DESCRIPTION
        "The number of CC cells transmitted for this VCC for
		CC Sourcing function."
    ::= { ipadAtmVccTableEntry 37 }
 
ipadAtmVccEtoeContCheckCellsRx OBJECT-TYPE
    SYNTAX  INTEGER
    MAX-ACCESS  read-only
    STATUS  current
    DESCRIPTION
        "The number of CC cells received for this VCC for
		the CC Sinking function."
    ::= { ipadAtmVccTableEntry 38 }
 
ipadAtmVccEtoeAisStatus OBJECT-TYPE
    SYNTAX  INTEGER {
		    noAis(1),
		    ais(2)
		    }
    MAX-ACCESS  read-only
    STATUS  current
    DESCRIPTION
        "The current e-t-e_VC-AIS state."
    ::= { ipadAtmVccTableEntry 39 }
 
ipadAtmVccEtoeRdiStatus OBJECT-TYPE
    SYNTAX  INTEGER {
		    noRdi(1),
		    rdi(2)
		    }
    MAX-ACCESS  read-only
    STATUS  current
    DESCRIPTION
        "The current e-t-e_VC-RDI state."
    ::= { ipadAtmVccTableEntry 40 }
 

-- ATM VCC Statistics

ipadAtmVccStatsTable OBJECT-TYPE
    SYNTAX    SEQUENCE OF IpadAtmVccStatsTableEntry
    MAX-ACCESS  not-accessible
    STATUS    current
    DESCRIPTION
        "Table of ATM statistics."
    ::= { ipadAtmVccStatsParms 1 }

ipadAtmVccStatsTableEntry OBJECT-TYPE
    SYNTAX  IpadAtmVccStatsTableEntry
    MAX-ACCESS  not-accessible
    STATUS  current
    DESCRIPTION
        "An entry in the ipad ATM VccStats parameter table."
    INDEX   { ipadAtmVccStatsIndex, ipadAtmVccStatsVpiIndex,
              ipadAtmVccStatsVciIndex, ipadAtmVccStatsPeriodIndex }
    ::= { ipadAtmVccStatsTable 1 }

IpadAtmVccStatsTableEntry ::=
    SEQUENCE
    {
    ipadAtmVccStatsIndex                INTEGER,
    ipadAtmVccStatsVpiIndex		INTEGER,
    ipadAtmVccStatsVciIndex		INTEGER,
    ipadAtmVccStatsPeriodIndex          INTEGER,
    ipadAtmVccStatsTimeStamp         	TimeTicks,
    ipadAtmVccStatsRxFramesOK		INTEGER,
    ipadAtmVccStatsTxFramesOK		INTEGER,
    ipadAtmVccStatsRxFramesError        INTEGER,
    ipadAtmVccStatsTxFramesError	INTEGER,
    ipadAtmVccStatsRxFramesCLP		INTEGER,
    ipadAtmVccStatsRxFramesCI		INTEGER,
    ipadAtmVccStatsRxFramesAbort	INTEGER,
    ipadAtmVccStatsRxFramesLenViolation INTEGER,
    ipadAtmVccStatsRxFramesCRCError	INTEGER,
    ipadAtmVccStatsRxFramesTimeout	INTEGER,
    ipadAtmVccStatsRxFramesHCSError	INTEGER,
    ipadAtmVccStatsRxFramesNoBuffer	INTEGER,
    ipadAtmVccStatsRxCellsOK		INTEGER,
    ipadAtmVccStatsTxCellsOK		INTEGER,			        
    ipadAtmVccStatsRxBytesOK            INTEGER,
    ipadAtmVccStatsTxBytesOK		INTEGER,
    ipadAtmVccStatsDelayPeak          	INTEGER,
    ipadAtmVccStatsDelayAverage       	INTEGER,
    ipadAtmVccStatsRoundTripTimeouts  	INTEGER,
    ipadAtmVccStatsRemoteFramesOffered	INTEGER,
    ipadAtmVccStatsFramesReceived	INTEGER,
    ipadAtmVccStatsFDR			DisplayString,
    ipadAtmVccStatsRemoteDataOffered	INTEGER,
    ipadAtmVccStatsDataReceived	  	INTEGER,
    ipadAtmVccStatsDDR	    		DisplayString,
    ipadAtmVccStatsUAS                	INTEGER
    }

ipadAtmVccStatsIndex       OBJECT-TYPE
    SYNTAX  INTEGER
    MAX-ACCESS  read-only
    STATUS  current
    DESCRIPTION
        "The index representing the ATM interface."
    ::= { ipadAtmVccStatsTableEntry 1 }

ipadAtmVccStatsVpiIndex       OBJECT-TYPE
    SYNTAX  INTEGER
    MAX-ACCESS  read-only
    STATUS  current
    DESCRIPTION
        "The index representing the VPI of the VCC."
    ::= { ipadAtmVccStatsTableEntry 2 }

ipadAtmVccStatsVciIndex       OBJECT-TYPE
    SYNTAX  INTEGER
    MAX-ACCESS  read-only
    STATUS  current
    DESCRIPTION
        "The index representing the VCI of the VCC."
    ::= { ipadAtmVccStatsTableEntry 3 }
    
ipadAtmVccStatsPeriodIndex	OBJECT-TYPE
    SYNTAX  INTEGER
    MAX-ACCESS  read-only
    STATUS  current
    DESCRIPTION
        "The index representing the period for the VCC stats entry."
    ::= { ipadAtmVccStatsTableEntry 4 }

ipadAtmVccStatsTimeStamp	OBJECT-TYPE
    SYNTAX	TimeTicks
    MAX-ACCESS	read-only
    STATUS	current
    DESCRIPTION
    	"The value of sysUpTime the last time the statistics were updated."
    ::= { ipadAtmVccStatsTableEntry 5 }

ipadAtmVccStatsRxFramesOK       OBJECT-TYPE
    SYNTAX  INTEGER
    MAX-ACCESS  read-only
    STATUS  current
    DESCRIPTION
        "The number of error-free frames received this period."
    ::= { ipadAtmVccStatsTableEntry 6 }

ipadAtmVccStatsTxFramesOK       OBJECT-TYPE
    SYNTAX  INTEGER
    MAX-ACCESS  read-only
    STATUS  current
    DESCRIPTION
        "The number of frames successfully transmitted during this period."
    ::= { ipadAtmVccStatsTableEntry 7 }

ipadAtmVccStatsRxFramesError       OBJECT-TYPE
    SYNTAX  INTEGER
    MAX-ACCESS  read-only
    STATUS  current
    DESCRIPTION
        "The number of errored frames received this period."
    ::= { ipadAtmVccStatsTableEntry 8 }

ipadAtmVccStatsTxFramesError       OBJECT-TYPE
    SYNTAX  INTEGER
    MAX-ACCESS  read-only
    STATUS  current
    DESCRIPTION
        "The number of frames that were not successfully transmitted during this period."
    ::= { ipadAtmVccStatsTableEntry 9 }

ipadAtmVccStatsRxFramesCLP       OBJECT-TYPE
    SYNTAX  INTEGER
    MAX-ACCESS  read-only
    STATUS  current
    DESCRIPTION
        "The number of frames received with CLP set during the period."
    ::= { ipadAtmVccStatsTableEntry 10 }

ipadAtmVccStatsRxFramesCI       OBJECT-TYPE
    SYNTAX  INTEGER
    MAX-ACCESS  read-only
    STATUS  current
    DESCRIPTION
        "The number of frames received with congestion set during the period."
    ::= { ipadAtmVccStatsTableEntry 11 }

ipadAtmVccStatsRxFramesAbort       OBJECT-TYPE
    SYNTAX  INTEGER
    MAX-ACCESS  read-only
    STATUS  current
    DESCRIPTION
        "The number of frames whose reception was aborted during the period."
    ::= { ipadAtmVccStatsTableEntry 12 }

ipadAtmVccStatsRxFramesLenViolation       OBJECT-TYPE
    SYNTAX  INTEGER
    MAX-ACCESS  read-only
    STATUS  current
    DESCRIPTION
        "The number of frames received with a length violation during the period."
    ::= { ipadAtmVccStatsTableEntry 13 }

ipadAtmVccStatsRxFramesCRCError       OBJECT-TYPE
    SYNTAX  INTEGER
    MAX-ACCESS  read-only
    STATUS  current
    DESCRIPTION
        "The number of frames received with CRC errors during the period."
    ::= { ipadAtmVccStatsTableEntry 14 }

ipadAtmVccStatsRxFramesTimeout       OBJECT-TYPE
    SYNTAX  INTEGER
    MAX-ACCESS  read-only
    STATUS  current
    DESCRIPTION
        "The number of frames whose reception timed out during the period."
    ::= { ipadAtmVccStatsTableEntry 15 }

ipadAtmVccStatsRxFramesHCSError       OBJECT-TYPE
    SYNTAX  INTEGER
    MAX-ACCESS  read-only
    STATUS  current
    DESCRIPTION
        "The number of frames received with an HCS error in a cell."
    ::= { ipadAtmVccStatsTableEntry 16 }

ipadAtmVccStatsRxFramesNoBuffer       OBJECT-TYPE
    SYNTAX  INTEGER
    MAX-ACCESS  read-only
    STATUS  current
    DESCRIPTION
        "The number of frames discarded due to the lack of buffers."
    ::= { ipadAtmVccStatsTableEntry 17 }

ipadAtmVccStatsRxCellsOK       OBJECT-TYPE
    SYNTAX  INTEGER
    MAX-ACCESS  read-only
    STATUS  current
    DESCRIPTION
        "The number of cells successfully received."
    ::= { ipadAtmVccStatsTableEntry 18 }

ipadAtmVccStatsTxCellsOK       OBJECT-TYPE
    SYNTAX  INTEGER
    MAX-ACCESS  read-only
    STATUS  current
    DESCRIPTION
        "The number of cells successfully transmitted."
    ::= { ipadAtmVccStatsTableEntry 19 }

ipadAtmVccStatsRxBytesOK       OBJECT-TYPE
    SYNTAX  INTEGER
    MAX-ACCESS  read-only
    STATUS  current
    DESCRIPTION
        "The number of bytes successfully received."
    ::= { ipadAtmVccStatsTableEntry 20 }

ipadAtmVccStatsTxBytesOK       OBJECT-TYPE
    SYNTAX  INTEGER
    MAX-ACCESS  read-only
    STATUS  current
    DESCRIPTION
        "The number of bytes successfully transmitted."
    ::= { ipadAtmVccStatsTableEntry 21 }

ipadAtmVccStatsDelayPeak       OBJECT-TYPE
    SYNTAX  INTEGER
    MAX-ACCESS  read-only
    STATUS  current
    DESCRIPTION
        "The peak delay measured during this period."
    ::= { ipadAtmVccStatsTableEntry 22 }

ipadAtmVccStatsDelayAverage       OBJECT-TYPE
    SYNTAX  INTEGER
    MAX-ACCESS  read-only
    STATUS  current
    DESCRIPTION
        "The average delay measured during this period."
    ::= { ipadAtmVccStatsTableEntry 23 }

ipadAtmVccStatsRoundTripTimeouts        OBJECT-TYPE
    SYNTAX  INTEGER
    MAX-ACCESS  read-only
    STATUS  current
    DESCRIPTION
        "The number of round trip delay message timeouts measured."
    ::= { ipadAtmVccStatsTableEntry 24 }

ipadAtmVccStatsRemoteFramesOffered       OBJECT-TYPE
    SYNTAX  INTEGER
    MAX-ACCESS  read-only
    STATUS  current
    DESCRIPTION
        "The number of frames offered by the remote device."
    ::= { ipadAtmVccStatsTableEntry 25 }

ipadAtmVccStatsFramesReceived       OBJECT-TYPE
    SYNTAX  INTEGER
    MAX-ACCESS  read-only
    STATUS  current
    DESCRIPTION
        "The number of frames received by the local device."
    ::= { ipadAtmVccStatsTableEntry 26 }

ipadAtmVccStatsFDR       OBJECT-TYPE
    SYNTAX  DisplayString
    MAX-ACCESS  read-only
    STATUS  current
    DESCRIPTION
        "The calculated frame delivery ratio."
    ::= { ipadAtmVccStatsTableEntry 27 }

ipadAtmVccStatsRemoteDataOffered       OBJECT-TYPE
    SYNTAX  INTEGER
    MAX-ACCESS  read-only
    STATUS  current
    DESCRIPTION
        "The number of data bytes offered by the remote device."
    ::= { ipadAtmVccStatsTableEntry 28 }

ipadAtmVccStatsDataReceived       OBJECT-TYPE
    SYNTAX  INTEGER
    MAX-ACCESS  read-only
    STATUS  current
    DESCRIPTION
        "The number of data bytes received by the local device."
    ::= { ipadAtmVccStatsTableEntry 29 }

ipadAtmVccStatsDDR       OBJECT-TYPE
    SYNTAX  DisplayString
    MAX-ACCESS  read-only
    STATUS  current
    DESCRIPTION
        "The calculated data delivery ratio."
    ::= { ipadAtmVccStatsTableEntry 30 }

ipadAtmVccStatsUAS       OBJECT-TYPE
    SYNTAX  INTEGER
    MAX-ACCESS  read-only
    STATUS  current
    DESCRIPTION
        "The number of seconds which the remote device was unavailable."
    ::= { ipadAtmVccStatsTableEntry 31 }

-- CES parameters

ipadAtmCesTable OBJECT-TYPE
    SYNTAX    SEQUENCE OF IpadAtmCesTableEntry
    MAX-ACCESS  not-accessible
    STATUS    current
    DESCRIPTION
        "Table of CES parameters."
    ::= { ipadAtmCesParms 1 }

ipadAtmCesTableEntry OBJECT-TYPE
    SYNTAX  IpadAtmCesTableEntry
    MAX-ACCESS  not-accessible
    STATUS  current
    DESCRIPTION
        "An entry in the ipad ATM CES parameter table."
    INDEX   { ipadAtmCesIndex }
    ::= { ipadAtmCesTable 1 }

IpadAtmCesTableEntry ::=
    SEQUENCE
    {
    ipadAtmCesIndex                   INTEGER,
    ipadAtmCesPayloadScrambling	      INTEGER,
    ipadAtmCesAutoChannelConfiguration INTEGER
    }

ipadAtmCesIndex       OBJECT-TYPE
    SYNTAX  INTEGER
    MAX-ACCESS  read-only
    STATUS  current
    DESCRIPTION
        "The index into the ATM CES table."
    ::= { ipadAtmCesTableEntry 1 }

ipadAtmCesPayloadScrambling    OBJECT-TYPE
    SYNTAX  INTEGER
    {
    other(1),
    disable(2),
    enable(3)
    }
    MAX-ACCESS  read-write
    STATUS  current
    DESCRIPTION
        "ipadAtmCesPayloadScrambling indicates whether CES payload scrambling
		is enabled."
    ::= { ipadAtmCesTableEntry 2 }

ipadAtmCesAutoChannelConfiguration    OBJECT-TYPE
    SYNTAX  INTEGER
    {
    other(1),
    disable(2),
    enable(3)
    }
    MAX-ACCESS  read-write
    STATUS  current
    DESCRIPTION
        "ipadAtmCesAutoChannelConfiguration indicates whether the CES channel
		configuration should be dynamic based on available line bandwidth."
    ::= { ipadAtmCesTableEntry 3 }

-- ATM - Frame Relay parameters

-- ATM FRF5 Service Table

-- This table contains a set of parameters used
-- to select FRF5 Interworking Function Modes 

ipadAtmFrf5SvcTable OBJECT-TYPE
    SYNTAX    SEQUENCE OF IpadAtmFrf5SvcTableEntry
    MAX-ACCESS  not-accessible
    STATUS    current
    DESCRIPTION
        "Table of ATM FRF5 profile parameters."
    ::= { ipadAtmFrParms 1 }

ipadAtmFrf5SvcTableEntry OBJECT-TYPE
    SYNTAX  IpadAtmFrf5SvcTableEntry
    MAX-ACCESS  not-accessible
    STATUS  current
    DESCRIPTION
        "An entry in the ipad ATM FRF5 service table."
    INDEX   { ipadAtmFrf5SvcIfIndex, ipadAtmFrf5SvcVpiIndex, ipadAtmFrf5SvcVciIndex }
    ::= { ipadAtmFrf5SvcTable 1 }

IpadAtmFrf5SvcTableEntry ::=
    SEQUENCE
    {
	ipadAtmFrf5SvcIfIndex                INTEGER,
	ipadAtmFrf5SvcVpiIndex		     INTEGER,
	ipadAtmFrf5SvcVciIndex		     INTEGER,
	ipadAtmFrf5SvcDeToClpMappingMode     INTEGER,
	ipadAtmFrf5SvcClpToDeMappingMode     INTEGER,
	ipadAtmFrf5SvcN1                     INTEGER,
	ipadAtmFrf5SvcN2                     INTEGER,
	ipadAtmFrf5SvcN3                     INTEGER,
	ipadAtmFrf5SvcT1                     INTEGER,
	ipadAtmFrf5SvcT2                     INTEGER,
	ipadAtmFrf5SvcActive		     INTEGER,
	ipadAtmFrf5SvcAddDLCI        	     INTEGER,
	ipadAtmFrf5SvcDeleteDLCI     	     INTEGER
    }

ipadAtmFrf5SvcIfIndex       	OBJECT-TYPE
    SYNTAX  INTEGER
    MAX-ACCESS  read-only
    STATUS  current
    DESCRIPTION
        "The index representing the ATM interface."
    ::= { ipadAtmFrf5SvcTableEntry 1 }

ipadAtmFrf5SvcVpiIndex       	OBJECT-TYPE
    SYNTAX  INTEGER
    MAX-ACCESS  read-only
    STATUS  current
    DESCRIPTION
        "The index representing the VPI of the VCC."
    ::= { ipadAtmFrf5SvcTableEntry 2 }

ipadAtmFrf5SvcVciIndex       	OBJECT-TYPE
    SYNTAX  INTEGER
    MAX-ACCESS  read-only
    STATUS  current
    DESCRIPTION
        "The index representing the VCI of the VCC."
    ::= { ipadAtmFrf5SvcTableEntry 3 }

ipadAtmFrf5SvcDeToClpMappingMode    OBJECT-TYPE
    SYNTAX  INTEGER
    {
    mode1(1),
    mode2Const0(2),
    mode2Const1(3)
    }
    MAX-ACCESS  read-write
    STATUS  current
    DESCRIPTION
        "Discard Eligibility to Cell Loss Priority mapping mode.

		mode1: The Discard Eligibility (DE) field in the Q.922 core frame
		shall be copied unchanged into the DE field in the FR-SSCS PDU header
		and mapped to the ATM Cell Loss Priority (CLP) of every ATM cell
		generated by the segmentation process of that frame.

		mode2Const0: The DE field in the Q.922 core frame shall be copied
		unchanged into the DE field in the FR-SSCS PDU header and the
		ATM Cell Loss Priority of every ATM cell generated by the segmentation
		process of that frame shall be set to the constant value 0.
		
		mode2Const1: The DE field in the Q.922 core frame shall be copied
		unchanged into the DE field in the FR-SSCS PDU header and the
		ATM Cell Loss Priority of every ATM cell generated by the segmentation
		process of that frame shall be set to the constant value 1."
    ::= { ipadAtmFrf5SvcTableEntry 4 }

ipadAtmFrf5SvcClpToDeMappingMode    OBJECT-TYPE
    SYNTAX  INTEGER
    {
    mode1(1),
    mode2(2)
    }
    MAX-ACCESS  read-write
    STATUS  current
    DESCRIPTION
        "Cell Loss Priority to Discard Eligibility mapping mode.

		mode1: If one or more ATM cells belonging to a frame has its CLP
		field set to one or if the DE field of the FR-SSCS PDU is set to one,
		the IWF shall set the DE field of the Q.922 core frame.

		mode2: No mapping is performed from the ATM layer to Q.922 core layer.
		The FR-SSCS PDU DE field is copied unchanged to the Q.922 core frame
		DE field, independent of CLP indications(s) received at the ATM layer."
    ::= { ipadAtmFrf5SvcTableEntry 5 }

ipadAtmFrf5SvcN1    OBJECT-TYPE
    SYNTAX  INTEGER(1..255)
    MAX-ACCESS  read-write
    STATUS  current
    DESCRIPTION
        "Number of keep alive requests between full status requests."
    ::= { ipadAtmFrf5SvcTableEntry 6 }

ipadAtmFrf5SvcN2    OBJECT-TYPE
    SYNTAX  INTEGER(1..10)
    MAX-ACCESS  read-write
    STATUS  current
    DESCRIPTION
        "Number of errors before alarm."
    ::= { ipadAtmFrf5SvcTableEntry 7 }

ipadAtmFrf5SvcN3    OBJECT-TYPE
    SYNTAX  INTEGER(1..10)
    MAX-ACCESS  read-write
    STATUS  current
    DESCRIPTION
        "Number of events to sample N2."
    ::= { ipadAtmFrf5SvcTableEntry 8 }

ipadAtmFrf5SvcT1    OBJECT-TYPE
    SYNTAX  INTEGER(5..240)
    MAX-ACCESS  read-write
    STATUS  current
    DESCRIPTION
        "Delay before issuing a poll sequence."
    ::= { ipadAtmFrf5SvcTableEntry 9 }

ipadAtmFrf5SvcT2    OBJECT-TYPE
    SYNTAX  INTEGER(5..245)
    MAX-ACCESS  read-write
    STATUS  current
    DESCRIPTION
        "T2 timer"
    ::= { ipadAtmFrf5SvcTableEntry 10 }

ipadAtmFrf5SvcActive    OBJECT-TYPE
    SYNTAX  INTEGER
        {
        other(1),
        no(2),
        yes(3)
        }
    MAX-ACCESS  read-only
    STATUS  current
    DESCRIPTION
        "Specifies if the frf5 service is active."
    ::= { ipadAtmFrf5SvcTableEntry 11 }

ipadAtmFrf5SvcAddDLCI        OBJECT-TYPE
    SYNTAX  INTEGER
    MAX-ACCESS  read-write
    STATUS  current
    DESCRIPTION
        "Identifies a DLCI number to be added."
    ::= { ipadAtmFrf5SvcTableEntry 12 }

ipadAtmFrf5SvcDeleteDLCI        OBJECT-TYPE
    SYNTAX  INTEGER
    MAX-ACCESS  read-write
    STATUS  current
    DESCRIPTION
        "Identifies a DLCI number to be deleted."
    ::= { ipadAtmFrf5SvcTableEntry 13 }


-- ATM FRF5 DLCI Table

-- This table is used to configure the switched and local DLCIs that
-- are attached to the Frame Relay service used for FRF5 interworking.

ipadAtmFrf5DlciTable OBJECT-TYPE
    SYNTAX    SEQUENCE OF IpadAtmFrf5DlciTableEntry
    MAX-ACCESS  not-accessible
    STATUS    current
    DESCRIPTION
        "Table of Mapped DLCIs for VCCs.
		This table is used for FRF5 to map one or more DLCIs
		to a VCC. When only one DLCI is mapped, a one-to-one relationship
		exists between the DLCI and the VCC.  When more than one DLCI
		is mapped, a many-to-one DLCI/VCC relationship exists."
    ::= { ipadAtmFrParms 2 }

ipadAtmFrf5DlciTableEntry OBJECT-TYPE
    SYNTAX  IpadAtmFrf5DlciTableEntry
    MAX-ACCESS  not-accessible
    STATUS  current
    DESCRIPTION
        "An entry in the ipad ATM Vcc parameter table."
    INDEX   { ipadAtmFrf5DlciIfIndex, ipadAtmFrf5DlciVpiIndex, ipadAtmFrf5DlciVciIndex, ipadAtmFrf5DlciIndex }
    ::= { ipadAtmFrf5DlciTable 1 }

IpadAtmFrf5DlciTableEntry ::=
    SEQUENCE
    {
    ipadAtmFrf5DlciIfIndex              INTEGER,
    ipadAtmFrf5DlciVpiIndex      	INTEGER,
    ipadAtmFrf5DlciVciIndex             INTEGER,
    ipadAtmFrf5DlciIndex                INTEGER,
    ipadAtmFrf5DlciEndpointName         DisplayString,
    ipadAtmFrf5DlciStatus               INTEGER,
    ipadAtmFrf5DlciCongestion    	INTEGER
    }

ipadAtmFrf5DlciIfIndex       OBJECT-TYPE
    SYNTAX  INTEGER
    MAX-ACCESS  read-only
    STATUS  current
    DESCRIPTION
        "The index into the ATM FRF5 DLCI table, corresponding to ifIndex."
    ::= { ipadAtmFrf5DlciTableEntry 1 }

ipadAtmFrf5DlciVpiIndex    OBJECT-TYPE
    SYNTAX  INTEGER
    MAX-ACCESS  read-only
    STATUS  current
    DESCRIPTION
        "The VPI index into the ATM FRF5 DLCI table."
    ::= { ipadAtmFrf5DlciTableEntry 2 }

ipadAtmFrf5DlciVciIndex    OBJECT-TYPE
    SYNTAX  INTEGER
    MAX-ACCESS  read-only
    STATUS  current
    DESCRIPTION
        "The VCI index into the ATM FRF5 DLCI table."
    ::= { ipadAtmFrf5DlciTableEntry 3 }

ipadAtmFrf5DlciIndex    OBJECT-TYPE
    SYNTAX  INTEGER
    MAX-ACCESS  read-only
    STATUS  current
    DESCRIPTION
        "The DLCI index into the ATM FRF5 DLCI table."
    ::= { ipadAtmFrf5DlciTableEntry 4 }

ipadAtmFrf5DlciEndpointName OBJECT-TYPE
    SYNTAX		DisplayString(SIZE(0..11))
    MAX-ACCESS  read-write
    STATUS  	current
    DESCRIPTION
        "Identifies the attached endpoint for this FRF5 DLCI."
    ::= { ipadAtmFrf5DlciTableEntry 5 }

ipadAtmFrf5DlciStatus OBJECT-TYPE
    SYNTAX  INTEGER {
			inactive(1),
			inactiveLearned(2),
			active(3),
			activeLearned(4)
		    }
    MAX-ACCESS  read-only
    STATUS  current
    DESCRIPTION
        "The current status of this mapped entry."
    ::= { ipadAtmFrf5DlciTableEntry 6 }

ipadAtmFrf5DlciCongestion    OBJECT-TYPE
    SYNTAX  INTEGER
    {
    other(1),
    no(2),
    yes(3)
    }
    MAX-ACCESS  read-only
    STATUS  current
    DESCRIPTION
        "Specifies if the dlci is receiving frames 
        with FECN or BECN bit set."
    ::= { ipadAtmFrf5DlciTableEntry 7 }


-- ATM FRF8 Service Table

-- This table contains a set of parameters used
-- to select FRF8 Interworking Function Modes 

ipadAtmFrf8SvcTable OBJECT-TYPE
    SYNTAX    SEQUENCE OF IpadAtmFrf8SvcTableEntry
    MAX-ACCESS  not-accessible
    STATUS    current
    DESCRIPTION
        "Table of ATM FRF8 profile parameters."
    ::= { ipadAtmFrParms 3 }

ipadAtmFrf8SvcTableEntry OBJECT-TYPE
    SYNTAX  IpadAtmFrf8SvcTableEntry
    MAX-ACCESS  not-accessible
    STATUS  current
    DESCRIPTION
        "An entry in the ipad ATM FRF8 service table."
    INDEX   { ipadAtmFrf8SvcIfIndex, ipadAtmFrf8SvcVpiIndex, ipadAtmFrf8SvcVciIndex }
    ::= { ipadAtmFrf8SvcTable 1 }

IpadAtmFrf8SvcTableEntry ::=
    SEQUENCE
    {
	ipadAtmFrf8SvcIfIndex                INTEGER,
	ipadAtmFrf8SvcVpiIndex               INTEGER,
	ipadAtmFrf8SvcVciIndex               INTEGER,
	ipadAtmFrf8SvcDeToClpMappingMode     INTEGER,
	ipadAtmFrf8SvcClpToDeMappingMode     INTEGER,
	ipadAtmFrf8SvcCongestionMappingMode  INTEGER,
	ipadAtmFrf8SvcEncapsulationMappingMode INTEGER,
	ipadAtmFrf8SvcEndpointName           DisplayString
    }

ipadAtmFrf8SvcIfIndex       	OBJECT-TYPE
    SYNTAX  INTEGER
    MAX-ACCESS  read-only
    STATUS  current
    DESCRIPTION
        "The index representing the ATM interface."
    ::= { ipadAtmFrf8SvcTableEntry 1 }

ipadAtmFrf8SvcVpiIndex       	OBJECT-TYPE
    SYNTAX  INTEGER
    MAX-ACCESS  read-only
    STATUS  current
    DESCRIPTION
        "The index representing the VPI of the VCC."
    ::= { ipadAtmFrf8SvcTableEntry 2 }

ipadAtmFrf8SvcVciIndex       	OBJECT-TYPE
    SYNTAX  INTEGER
    MAX-ACCESS  read-only
    STATUS  current
    DESCRIPTION
        "The index representing the VCI of the VCC."
    ::= { ipadAtmFrf8SvcTableEntry 3 }

ipadAtmFrf8SvcDeToClpMappingMode  OBJECT-TYPE
    SYNTAX  INTEGER {
                        mode1(1),
                        mode2Const0(2),
                        mode2Const1(3)
                    }
    MAX-ACCESS  read-write
    STATUS  current
    DESCRIPTION
    	"This object describes which mode of translation
    	is in use for loss priority mapping in the frame
    	relay to ATM direction.

    	mode1(1)        = the DE field in the Q.922 core
                          frame shall be mapped to the ATM
                          CLP field of every cell
                          generated by the segmentation
                          process of the AAL5 PDU
                          containing the information of
                          that frame.

        mode2Contst0(2) = the ATM CLP field of every cell
                          generated by the segmentation
                          process of the AAL5 PDU
                          containing the information of
                          that frame shall be set to
                          constant 0.

        mode2Contst1(3) = the ATM CLP field of every cell
                          generated by the segmentation
                          process of the AAL5 PDU
                          containing the information of
                          that frame shall be set to
                          constant 1."

    ::= { ipadAtmFrf8SvcTableEntry 4 }

ipadAtmFrf8SvcClpToDeMappingMode  OBJECT-TYPE
    SYNTAX  INTEGER {
                        mode1(1),
                        mode2Const0(2),
                        mode2Const1(3)
                    }
    MAX-ACCESS  read-write
    STATUS  current
    DESCRIPTION
        "This object describes which mode of translation
        is in use for loss priority mapping in the ATM to
        frame relay direction.

        mode1(1)       = if one or more cells in a frame
                         has its CLP field set, the DE
                         field of the Q.922 core frame
                         should be set.

        mode2Const0(2) = the DE field of the Q.922 core
                         frame should be set to the

                         constant 0.

        mode2Const1(3) = the DE field of the Q.922 core
                         frame should be set to the
                         constant 1."
    ::= { ipadAtmFrf8SvcTableEntry 5 }

ipadAtmFrf8SvcCongestionMappingMode  OBJECT-TYPE
    SYNTAX  INTEGER {
                        mode1(1),
                        mode2(2)
                    }
    MAX-ACCESS  read-write
    STATUS  current
    DESCRIPTION
        "This object describes which mode of translation
        is in use for forward congestion indication
        mapping in the frame relay to ATM direction.

        mode1(1) = The FECN field in the Q.922 core frame
                   shall be mapped to the ATM EFCI field
                   of every cell generated by the
                   segmentation process of the AAL5 PDU
                   containing the information of that
                   frame.

        mode2(2) = The FECN field in the Q.922 core frame
                   shall not be mapped to the ATM EFCI
                   field of cells generated by the
                   segmentation process of the AAL5 PDU
                   containing the information of that
                   frame. The EFCI field is always set to
                   'congestion not experienced'.

        In both of the modes above, if there is congestion
        in the forward direction in the ATM layer within
        the IWF, then the IWF can set the EFCI field to
        'congestion experienced'."
    ::= { ipadAtmFrf8SvcTableEntry 6 }

ipadAtmFrf8SvcEncapsulationMappingMode  OBJECT-TYPE
    SYNTAX  INTEGER {
                        transparentMode(1),
                        translationMode(2)
                    }
    MAX-ACCESS  read-write
    STATUS  current
    DESCRIPTION
        "This object indicates whether the mapping of
        upper layer protocol encapsulation is enabled on
        this interworking connection.

        transparentMode(1) = Forward the encapsulations unaltered.

        translationMode(2) = Perform mapping between the
                             two encapsulations due to the
                             incompatibilities of the two
                             methods."

    ::= { ipadAtmFrf8SvcTableEntry 7 }

ipadAtmFrf8SvcEndpointName OBJECT-TYPE
    SYNTAX	DisplayString(SIZE(0..11))
    MAX-ACCESS  read-write
    STATUS  	current
    DESCRIPTION
        "Identifies the Frame Relay endpoint for this FRF8 Service."
    ::= { ipadAtmFrf8SvcTableEntry 8 }

END

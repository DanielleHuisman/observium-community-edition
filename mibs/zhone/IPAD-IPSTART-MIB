-- $Header:   K:/WanSuite/archives/include/pvcs/ipstart.mib,v   1.2   Nov 07 2000 13:31:52   bobr  $

IPAD-IPSTART-MIB DEFINITIONS ::= BEGIN

IMPORTS IpAddress, OBJECT-TYPE, MODULE-IDENTITY, 
        NOTIFICATION-TYPE                              FROM SNMPv2-SMI
	DisplayString                                  FROM SNMPv2-TC
	ipadPPP, ipadServiceIndex, 
        ipadTrapsPrefix                                FROM IPADv2-MIB;

ipadIPStart MODULE-IDENTITY
         LAST-UPDATED "0008180000Z"
         ORGANIZATION "Verilink Corporation"
         CONTACT-INFO
            "Bob Ray
             bray@verilink.com
             1-256-774-2380"
         DESCRIPTION
            "The IPAD IP Start MIB modified for SNMPv2."
         ::= { ipadPPP 4 }

-- This MIB, which resides under ipadPPP

ipadPPPStartTable    OBJECT-TYPE
    SYNTAX    SEQUENCE OF IpadPPPStartTableEntry
    MAX-ACCESS    not-accessible
    STATUS    current
    DESCRIPTION
        "The ipad PPP Start table."
    ::= { ipadIPStart 1 }

ipadPPPStartTableEntry    OBJECT-TYPE
    SYNTAX    IpadPPPStartTableEntry
    MAX-ACCESS    not-accessible
    STATUS    current
    DESCRIPTION
        "An entry in the ipad PPP Start table."
    INDEX { ipadPPPStartService }
    ::= { ipadPPPStartTable 1 }

IpadPPPStartTableEntry ::=
    SEQUENCE
    {    
    ipadPPPStartService                     INTEGER,
    ipadPPPStartLCPState                    INTEGER,
    ipadPPPStartLCPStateTime                INTEGER,
    ipadPPPStartLCPStateChanges             INTEGER,
    ipadPPPStartLCPMRU                      INTEGER,
    ipadPPPStartLCPAsyncCCM                 DisplayString,
    ipadPPPStartLCPAuthProtocol             INTEGER,
    ipadPPPStartLCPQualityProtocol          INTEGER,
    ipadPPPStartLCPMagicNumber              DisplayString,
    ipadPPPStartLCPPFC                      INTEGER,
    ipadPPPStartLCPACFC                     INTEGER,
    ipadPPPStartLCPFCSAlternatives          INTEGER,
    ipadPPPStartLCPSDP                      INTEGER,
    ipadPPPStartLCPCompoundFrames           INTEGER,
    ipadPPPStartAuthState                   INTEGER,
    ipadPPPStartAuthStateTime               INTEGER,
    ipadPPPStartAuthStateChanges            INTEGER,
    ipadPPPStartAuthFailureCount            INTEGER,
    ipadPPPStartAuthFailureTrapEnable       INTEGER,
    ipadPPPStartIPCPState                   INTEGER,
    ipadPPPStartIPCPStateTime               INTEGER,
    ipadPPPStartIPCPStateChanges            INTEGER,
    ipadPPPStartIPCPIPSource                IpAddress,
    ipadPPPStartIPCPIPDestAddress           IpAddress,
    ipadPPPStartIPCPCompressionProtocol     INTEGER
    }

ipadPPPStartService  OBJECT-TYPE
    SYNTAX    INTEGER
    MAX-ACCESS    read-only
    STATUS    current
    DESCRIPTION
        ""
    ::= { ipadPPPStartTableEntry 1 }

ipadPPPStartLCPState  OBJECT-TYPE
    SYNTAX    INTEGER
              {
              initial(1),
              starting(2),
              closed(3),
              stopped(4),
              closing(5),
              stopping(6),
              reqSent(7),
              ackRcvd(8),
              ackSent(9),
              opened(10)
              }
    MAX-ACCESS    read-only
    STATUS    current
    DESCRIPTION
        ""
    ::= { ipadPPPStartTableEntry 2 }

ipadPPPStartLCPStateTime  OBJECT-TYPE
    SYNTAX    INTEGER
    MAX-ACCESS    read-only
    STATUS    current
    DESCRIPTION
        ""
    ::= { ipadPPPStartTableEntry 3 }

ipadPPPStartLCPStateChanges  OBJECT-TYPE
    SYNTAX    INTEGER
    MAX-ACCESS    read-only
    STATUS    current
    DESCRIPTION
        ""
    ::= { ipadPPPStartTableEntry 4 }

ipadPPPStartLCPMRU  OBJECT-TYPE
    SYNTAX    INTEGER
    MAX-ACCESS    read-only
    STATUS    current
    DESCRIPTION
        ""
    ::= { ipadPPPStartTableEntry 5 }

ipadPPPStartLCPAsyncCCM  OBJECT-TYPE
    SYNTAX    DisplayString(SIZE(4))
    MAX-ACCESS    read-only
    STATUS    current
    DESCRIPTION
        ""
    ::= { ipadPPPStartTableEntry 6 }

ipadPPPStartLCPAuthProtocol  OBJECT-TYPE
    SYNTAX    INTEGER
              {
              unknown(1),
              other(2),
              pap(3),
              chap(4),
              spap(5),
              eap(6)
              }
    MAX-ACCESS    read-only
    STATUS    current
    DESCRIPTION
        ""
    ::= { ipadPPPStartTableEntry 7 }

ipadPPPStartLCPQualityProtocol  OBJECT-TYPE
    SYNTAX    INTEGER
              {
              unknown(1),
              other(2),
              lqr(3)
              }            
    MAX-ACCESS    read-only
    STATUS    current
    DESCRIPTION
        ""
    ::= { ipadPPPStartTableEntry 8 }

ipadPPPStartLCPMagicNumber  OBJECT-TYPE
    SYNTAX    DisplayString(SIZE(4))
    MAX-ACCESS    read-only
    STATUS    current
    DESCRIPTION
        ""
    ::= { ipadPPPStartTableEntry 9 }

ipadPPPStartLCPPFC  OBJECT-TYPE
    SYNTAX    INTEGER
              {
              enabled(1),
              disabled(2)
              }
    MAX-ACCESS    read-only
    STATUS    current
    DESCRIPTION
        ""
    ::= { ipadPPPStartTableEntry 10 }

ipadPPPStartLCPACFC  OBJECT-TYPE
    SYNTAX    INTEGER
              {
              enabled(1),
              disabled(2)
              }
    MAX-ACCESS    read-only
    STATUS    current
    DESCRIPTION
        ""
    ::= { ipadPPPStartTableEntry 11 }

ipadPPPStartLCPFCSAlternatives  OBJECT-TYPE
    SYNTAX    INTEGER
              {
              unknown(1),
              other(2),
              nullFCS(3),
              ccitt16bitFCS(4),
              ccitt32bitFCS(5)
              }
    MAX-ACCESS    read-only
    STATUS    current
    DESCRIPTION
        ""
    ::= { ipadPPPStartTableEntry 12 }

ipadPPPStartLCPSDP  OBJECT-TYPE
    SYNTAX    INTEGER
    MAX-ACCESS    read-only
    STATUS    current
    DESCRIPTION
        ""
    ::= { ipadPPPStartTableEntry 13 }

ipadPPPStartLCPCompoundFrames  OBJECT-TYPE
    SYNTAX    INTEGER
              {
              enabled(1),
              disabled(2)
              }
    MAX-ACCESS    read-only
    STATUS    current
    DESCRIPTION
        ""
    ::= { ipadPPPStartTableEntry 14 }

ipadPPPStartAuthState  OBJECT-TYPE
    SYNTAX    INTEGER
              {
              initial(1),
              starting(2),
              closed(3),
              stopped(4),
              closing(5),
              stopping(6),
              reqSent(7),
              ackRcvd(8),
              ackSent(9),
              opened(10)
              }
    MAX-ACCESS    read-only
    STATUS    current
    DESCRIPTION
        ""
    ::= { ipadPPPStartTableEntry 15 }

ipadPPPStartAuthStateTime  OBJECT-TYPE
    SYNTAX    INTEGER
    MAX-ACCESS    read-only
    STATUS    current
    DESCRIPTION
        ""
    ::= { ipadPPPStartTableEntry 16 }

ipadPPPStartAuthStateChanges  OBJECT-TYPE
    SYNTAX    INTEGER
    MAX-ACCESS    read-only
    STATUS    current
    DESCRIPTION
        ""
    ::= { ipadPPPStartTableEntry 17 }

ipadPPPStartAuthFailureCount  OBJECT-TYPE
    SYNTAX    INTEGER
    MAX-ACCESS    read-only
    STATUS    current
    DESCRIPTION
        ""
    ::= { ipadPPPStartTableEntry 18 }

ipadPPPStartAuthFailureTrapEnable  OBJECT-TYPE
    SYNTAX    INTEGER
              {
              enabled(1),
              disabled(2)
              }
    MAX-ACCESS    read-write
    STATUS    current
    DESCRIPTION
        ""
    ::= { ipadPPPStartTableEntry 19 }

ipadPPPStartIPCPState  OBJECT-TYPE
    SYNTAX    INTEGER
              {
              initial(1),
              starting(2),
              closed(3),
              stopped(4),
              closing(5),
              stopping(6),
              reqSent(7),
              ackRcvd(8),
              ackSent(9),
              opened(10)
              }
    MAX-ACCESS    read-only
    STATUS    current
    DESCRIPTION
        ""
    ::= { ipadPPPStartTableEntry 20 }

ipadPPPStartIPCPStateTime  OBJECT-TYPE
    SYNTAX    INTEGER
    MAX-ACCESS    read-only
    STATUS    current
    DESCRIPTION
        ""
    ::= { ipadPPPStartTableEntry 21 }

ipadPPPStartIPCPStateChanges  OBJECT-TYPE
    SYNTAX    INTEGER
    MAX-ACCESS    read-only
    STATUS    current
    DESCRIPTION
        ""
    ::= { ipadPPPStartTableEntry 22 }

ipadPPPStartIPCPIPSource  OBJECT-TYPE
    SYNTAX    IpAddress
    MAX-ACCESS    read-only
    STATUS    current
    DESCRIPTION
        ""
    ::= { ipadPPPStartTableEntry 23 }

ipadPPPStartIPCPIPDestAddress  OBJECT-TYPE
    SYNTAX    IpAddress
    MAX-ACCESS    read-only
    STATUS    current
    DESCRIPTION
        ""
    ::= { ipadPPPStartTableEntry 24 }

ipadPPPStartIPCPCompressionProtocol  OBJECT-TYPE
    SYNTAX    INTEGER
              {
              unknown(1),
              other(2),    
              regularIPdata(3),
              compressedTCP(4),
              uncompressedTCP(5)
              }
    MAX-ACCESS    read-only
    STATUS    current
    DESCRIPTION
        ""
    ::= { ipadPPPStartTableEntry 25 }

ipadPPPStartLCPHistoryTable    OBJECT-TYPE
    SYNTAX    SEQUENCE OF IpadPPPStartLCPHistoryTableEntry
    MAX-ACCESS    not-accessible
    STATUS    current
    DESCRIPTION
        "The ipad PPPStart LCP history table."
    ::= { ipadIPStart 2 }

ipadPPPStartLCPHistoryTableEntry    OBJECT-TYPE
    SYNTAX    IpadPPPStartLCPHistoryTableEntry
    MAX-ACCESS    not-accessible
    STATUS    current
    DESCRIPTION
        "An entry in the ipad PPPStart LCP history table."
    INDEX { ipadServiceIndex, ipadPPPStartLCPHistoryIndex }
    ::= { ipadPPPStartLCPHistoryTable 1 }

IpadPPPStartLCPHistoryTableEntry ::=
    SEQUENCE 
    {
    ipadPPPStartLCPHistoryIndex       INTEGER,
    ipadPPPStartLCPHistoryState       INTEGER,
    ipadPPPStartLCPHistoryStateTime   INTEGER
    }

ipadPPPStartLCPHistoryIndex  OBJECT-TYPE
    SYNTAX    INTEGER
    MAX-ACCESS    read-only
    STATUS    current
    DESCRIPTION
        ""
    ::= { ipadPPPStartLCPHistoryTableEntry 1 }

ipadPPPStartLCPHistoryState  OBJECT-TYPE
    SYNTAX    INTEGER
              {
              initial(1),
              starting(2),
              closed(3),
              stopped(4),
              closing(5),
              stopping(6),
              reqSent(7),
              ackRcvd(8),
              ackSent(9),
              opened(10)
              }
    MAX-ACCESS    read-only
    STATUS    current
    DESCRIPTION
        ""
    ::= { ipadPPPStartLCPHistoryTableEntry 2 }

ipadPPPStartLCPHistoryStateTime  OBJECT-TYPE
    SYNTAX    INTEGER
    MAX-ACCESS    read-only
    STATUS    current
    DESCRIPTION
        ""
    ::= { ipadPPPStartLCPHistoryTableEntry 3 }

ipadPPPStartAuthHistoryTable    OBJECT-TYPE
    SYNTAX    SEQUENCE OF IpadPPPStartAuthHistoryTableEntry
    MAX-ACCESS    not-accessible
    STATUS    current
    DESCRIPTION
        "The ipad PPPStart authentication history table."
    ::= { ipadIPStart 3 }

ipadPPPStartAuthHistoryTableEntry    OBJECT-TYPE
    SYNTAX    IpadPPPStartAuthHistoryTableEntry
    MAX-ACCESS    not-accessible
    STATUS    current
    DESCRIPTION
        "An entry in the ipad PPPStart authentication 
        history table."
    INDEX { ipadServiceIndex, ipadPPPStartAuthHistoryIndex }
    ::= { ipadPPPStartAuthHistoryTable 1 }

IpadPPPStartAuthHistoryTableEntry ::=
    SEQUENCE 
    {
    ipadPPPStartAuthHistoryIndex       INTEGER,
    ipadPPPStartAuthHistoryState       INTEGER,
    ipadPPPStartAuthHistoryStateTime   INTEGER
    }

ipadPPPStartAuthHistoryIndex  OBJECT-TYPE
    SYNTAX    INTEGER
    MAX-ACCESS    read-only
    STATUS    current
    DESCRIPTION
        ""
    ::= { ipadPPPStartAuthHistoryTableEntry 1 }

ipadPPPStartAuthHistoryState  OBJECT-TYPE
    SYNTAX    INTEGER
              {
              initial(1),
              starting(2),
              closed(3),
              stopped(4),
              closing(5),
              stopping(6),
              reqSent(7),
              ackRcvd(8),
              ackSent(9),
              opened(10)
              }
    MAX-ACCESS    read-only
    STATUS    current
    DESCRIPTION
        ""
    ::= { ipadPPPStartAuthHistoryTableEntry 2 }

ipadPPPStartAuthHistoryStateTime  OBJECT-TYPE
    SYNTAX    INTEGER
    MAX-ACCESS    read-only
    STATUS    current
    DESCRIPTION
        ""
    ::= { ipadPPPStartAuthHistoryTableEntry 3 }

ipadPPPStartIPCPHistoryTable    OBJECT-TYPE
    SYNTAX    SEQUENCE OF IpadPPPStartIPCPHistoryTableEntry
    MAX-ACCESS    not-accessible
    STATUS    current
    DESCRIPTION
        "The ipad PPPStart IPCP history table."
    ::= { ipadIPStart 4 }

ipadPPPStartIPCPHistoryTableEntry    OBJECT-TYPE
    SYNTAX    IpadPPPStartIPCPHistoryTableEntry
    MAX-ACCESS    not-accessible
    STATUS    current
    DESCRIPTION
        "An entry in the ipad PPPStart IPCP history table."
    INDEX { ipadServiceIndex, ipadPPPStartIPCPHistoryIndex }
    ::= { ipadPPPStartIPCPHistoryTable 1 }

IpadPPPStartIPCPHistoryTableEntry ::=
    SEQUENCE 
    {
    ipadPPPStartIPCPHistoryIndex       INTEGER,
    ipadPPPStartIPCPHistoryState       INTEGER,
    ipadPPPStartIPCPHistoryStateTime   INTEGER
    }

ipadPPPStartIPCPHistoryIndex  OBJECT-TYPE
    SYNTAX    INTEGER
    MAX-ACCESS    read-only
    STATUS    current
    DESCRIPTION
        ""
    ::= { ipadPPPStartIPCPHistoryTableEntry 1 }

ipadPPPStartIPCPHistoryState  OBJECT-TYPE
    SYNTAX    INTEGER
              {
              initial(1),
              starting(2),
              closed(3),
              stopped(4),
              closing(5),
              stopping(6),
              reqSent(7),
              ackRcvd(8),
              ackSent(9),
              opened(10)
              }
    MAX-ACCESS    read-only
    STATUS    current
    DESCRIPTION
        ""
    ::= { ipadPPPStartIPCPHistoryTableEntry 2 }

ipadPPPStartIPCPHistoryStateTime  OBJECT-TYPE
    SYNTAX    INTEGER
    MAX-ACCESS    read-only
    STATUS    current
    DESCRIPTION
        ""
    ::= { ipadPPPStartIPCPHistoryTableEntry 3 }

ipadPPPStartAuthFailureTrap    NOTIFICATION-TYPE
    OBJECTS
        {
        ipadPPPStartAuthFailureCount        
        }
    STATUS        current
    DESCRIPTION
        ""
    ::= { ipadTrapsPrefix 25050 }
END

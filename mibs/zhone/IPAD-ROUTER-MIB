-- $Header:   K:/Wansuite/archives/include/pvcs/router.mib,v   1.3   Dec 02 2002 13:56:28   davidp  $

IPAD-ROUTER-MIB DEFINITIONS ::= BEGIN

IMPORTS IpAddress, OBJECT-TYPE, MODULE-IDENTITY        FROM SNMPv2-SMI
	DisplayString                                  FROM SNMPv2-TC
	ipad                                           FROM IPADv2-MIB;

ipadRouter MODULE-IDENTITY
         LAST-UPDATED "0010250000Z"
         ORGANIZATION "Verilink Corporation"
         CONTACT-INFO
            "Bob Ray
             bray@verilink.com
             1-256-774-2380"
         DESCRIPTION
            "The IPAD Router MIB modified for SNMPv2."
         ::= { ipad 13 }

ipadCircuitParms  OBJECT IDENTIFIER ::= { ipadRouter 1 }
ipadRIPParms      OBJECT IDENTIFIER ::= { ipadRouter 2 }
ipadOSPFParms     OBJECT IDENTIFIER ::= { ipadRouter 3 }

-- Circuit parameters

ipadCircuitTable OBJECT-TYPE
    SYNTAX    SEQUENCE OF IpadCircuitTableEntry
    MAX-ACCESS  not-accessible
    STATUS    current
    DESCRIPTION
        "Table of Circuit parameters."
    ::= { ipadCircuitParms 1 }

ipadCircuitTableEntry OBJECT-TYPE
    SYNTAX  IpadCircuitTableEntry
    MAX-ACCESS  not-accessible
    STATUS  current
    DESCRIPTION
        "An entry in the ipad Circuit parameter table."
    INDEX   { ipadCircuitIndex }
    ::= { ipadCircuitTable 1 }

IpadCircuitTableEntry ::=
    SEQUENCE
    {
    ipadCircuitIndex                  INTEGER,
    ipadCircuitEndpoint               DisplayString,
    ipadCircuitIpAddress              IpAddress,
    ipadCircuitIpMask                 IpAddress,
    ipadCircuitMaxTransmitUnit        INTEGER,
    ipadCircuitCost                   INTEGER,
    ipadCircuitEnableRIP              INTEGER,
    ipadCircuitEnableOSPF             INTEGER,
    ipadCircuitEnableMulticast        INTEGER,
    ipadCircuitOSPFArea		      INTEGER,
    ipadCircuitOSPFLSATimer	      INTEGER,
    ipadCircuitOSPFLSUDelay	      INTEGER,
    ipadCircuitOSPFRouterPriority     INTEGER,
    ipadCircuitOSPFHelloInterval      INTEGER,
    ipadCircuitOSPFDeadInterval	      INTEGER,
    ipadCircuitOSPFAuthKey	      DisplayString
    }

ipadCircuitIndex       OBJECT-TYPE
    SYNTAX  INTEGER
    MAX-ACCESS  read-only
    STATUS  current
    DESCRIPTION
        "The index into the Circuit table."
    ::= { ipadCircuitTableEntry 1 }

ipadCircuitEndpoint    OBJECT-TYPE
    SYNTAX  DisplayString
    MAX-ACCESS  read-write
    STATUS  current
    DESCRIPTION
        "An entry in the endpoint table."
    ::= { ipadCircuitTableEntry 2 }

ipadCircuitIpAddress    OBJECT-TYPE
    SYNTAX  IpAddress
    MAX-ACCESS  read-write
    STATUS  current
    DESCRIPTION
        "The IP Address of the Circuit."
    ::= { ipadCircuitTableEntry 3 }

ipadCircuitIpMask    OBJECT-TYPE
    SYNTAX  IpAddress
    MAX-ACCESS  read-write
    STATUS  current
    DESCRIPTION
        "The IP Mask of this Circuit IP address."
    ::= { ipadCircuitTableEntry 4 }

ipadCircuitMaxTransmitUnit    OBJECT-TYPE
    SYNTAX  INTEGER(0..65535)
    MAX-ACCESS  read-write
    STATUS  current
    DESCRIPTION
        "The Maximum packet size carried by this Circuit."
    ::= { ipadCircuitTableEntry 5 }

ipadCircuitCost    OBJECT-TYPE
    SYNTAX  INTEGER(0..65535)
    MAX-ACCESS  read-write
    STATUS  current
    DESCRIPTION
        "The cost (delay) of this Circuit."
    ::= { ipadCircuitTableEntry 6 }

ipadCircuitEnableRIP    OBJECT-TYPE
    SYNTAX  INTEGER
            {
            other(1),
            disabled(2),
            enabled(3),
            talkOnly(4),
            listenOnly(5)
            }
    MAX-ACCESS  read-write
    STATUS  current
    DESCRIPTION
        "To enable or disable RIP for this Circuit."
    ::= { ipadCircuitTableEntry 7 }

ipadCircuitEnableOSPF    OBJECT-TYPE
    SYNTAX  INTEGER
            {
            other(1),
            disabled(2),
            enabled(3)
            }
    MAX-ACCESS  read-write
    STATUS  current
    DESCRIPTION
        "To enable or disable OSPF for this Circuit."
    ::= { ipadCircuitTableEntry 8 }

ipadCircuitEnableMulticast    OBJECT-TYPE
    SYNTAX  INTEGER
            {
            other(1),
            disabled(2),
            enabled(3)
            }
    MAX-ACCESS  read-write
    STATUS  current
    DESCRIPTION
        "To allow multicast adressing for this Circuit."
    ::= { ipadCircuitTableEntry 9 }

ipadCircuitOSPFArea    OBJECT-TYPE
    SYNTAX  INTEGER(1..3600)
    MAX-ACCESS  read-write
    STATUS  current
    DESCRIPTION
        "OSPF Circuit Area ID."
    ::= { ipadCircuitTableEntry 10 }

ipadCircuitOSPFLSATimer    OBJECT-TYPE
    SYNTAX  INTEGER(1..3600)
    MAX-ACCESS  read-write
    STATUS  current
    DESCRIPTION
        "Number of seconds between LSA."
    ::= { ipadCircuitTableEntry 11 }

ipadCircuitOSPFLSUDelay    OBJECT-TYPE
    SYNTAX  INTEGER(1..3600)
    MAX-ACCESS  read-write
    STATUS  current
    DESCRIPTION
        "Transit delay for LSU packets."
    ::= { ipadCircuitTableEntry 12 }

ipadCircuitOSPFRouterPriority    OBJECT-TYPE
    SYNTAX  INTEGER(1..255)
    MAX-ACCESS  read-write
    STATUS  current
    DESCRIPTION
        "OSPF Circuit Router Priority."
    ::= { ipadCircuitTableEntry 13 }

ipadCircuitOSPFHelloInterval    OBJECT-TYPE
    SYNTAX  INTEGER(0..65535)
    MAX-ACCESS  read-write
    STATUS  current
    DESCRIPTION
        "OSPF Circuit Hello Interval."
    ::= { ipadCircuitTableEntry 14 }

ipadCircuitOSPFDeadInterval    OBJECT-TYPE
    SYNTAX  INTEGER(0..65535)
    MAX-ACCESS  read-write
    STATUS  current
    DESCRIPTION
        "OSPF Circuit Dead Interval."
    ::= { ipadCircuitTableEntry 15 }

ipadCircuitOSPFAuthKey    OBJECT-TYPE
    SYNTAX  DisplayString
    MAX-ACCESS  read-write
    STATUS  current
    DESCRIPTION
        "OSPF Circuit Authentication Key."
    ::= { ipadCircuitTableEntry 16  }

ipadCircuitAdd    OBJECT-TYPE
    SYNTAX  INTEGER
            {
            other(1),
            addnew(2)
            }
    MAX-ACCESS  read-write
    STATUS  current
    DESCRIPTION
        "Writing addnew(2) to this field causes a new (blank) 
        route to be appended to the Circuit Table."
    ::= { ipadCircuitParms 2 }

ipadCircuitDelete    OBJECT-TYPE
    SYNTAX  INTEGER
    MAX-ACCESS  read-write
    STATUS  current
    DESCRIPTION
        "Writing the index of an entry in the Circuit table
        causes that entry to be deleted."
    ::= { ipadCircuitParms 3 }

-- RIP general parameters

ipadRIPEnable OBJECT-TYPE
    SYNTAX  INTEGER
            {
            other(1),
            disabled(2),
            enabledRIP1(3),
            enabledRIP2(4)
            }
    MAX-ACCESS  read-write
    STATUS  current
    DESCRIPTION
        "Determines if RIP routing is enabled."
    ::= { ipadRIPParms 1 }

ipadRIPTrustNeighbors OBJECT-TYPE
    SYNTAX  INTEGER
            {
            other(1),
            disabled(2),
            enabled(3)
            }
    MAX-ACCESS  read-write
    STATUS  current
    DESCRIPTION
        "Determines if RIP Neighbors should be trusted."
    ::= { ipadRIPParms 2 }

ipadRIPInterval OBJECT-TYPE
    SYNTAX  INTEGER(0..65535)
    MAX-ACCESS  read-write
    STATUS  current
    DESCRIPTION
        "Specifies the RIP interval in seconds."
    ::= { ipadRIPParms 3 }

ipadRIPDomain OBJECT-TYPE
    SYNTAX  INTEGER(0..65535)
    MAX-ACCESS  read-write
    STATUS  current
    DESCRIPTION
        "Specifies the RIP Domain."
    ::= { ipadRIPParms 4 }

-- static ARP parameters

ipadRIPStaticARPTable OBJECT-TYPE
    SYNTAX    SEQUENCE OF IpadRIPStaticARPTableEntry
    MAX-ACCESS  not-accessible
    STATUS    current
    DESCRIPTION
        "Table of RIP Static ARP parameters."
    ::= { ipadRIPParms 5 }

ipadRIPStaticARPTableEntry OBJECT-TYPE
    SYNTAX  IpadRIPStaticARPTableEntry
    MAX-ACCESS  not-accessible
    STATUS  current
    DESCRIPTION
        "An entry in the ipad RIP Static ARP parameter table."
    INDEX   { ipadRIPStaticARPIndex }
    ::= { ipadRIPStaticARPTable 1 }

IpadRIPStaticARPTableEntry ::=
    SEQUENCE
    {
    ipadRIPStaticARPIndex                INTEGER,
    ipadRIPStaticARPEndpoint             DisplayString,
    ipadRIPStaticARPIpAddress            IpAddress,
    ipadRIPStaticARPMacAddress           DisplayString,
    ipadRIPStaticARPDLCIAddress          INTEGER,
    ipadRIPStaticARPEnableARP            INTEGER
    }

ipadRIPStaticARPIndex       OBJECT-TYPE
    SYNTAX  INTEGER
    MAX-ACCESS  read-only
    STATUS  current
    DESCRIPTION
        "The index into the RIP Static ARP table."
    ::= { ipadRIPStaticARPTableEntry 1 }

ipadRIPStaticARPEndpoint    OBJECT-TYPE
    SYNTAX  DisplayString
    MAX-ACCESS  read-write
    STATUS  current
    DESCRIPTION
        "An entry in the endpoint table."
    ::= { ipadRIPStaticARPTableEntry 2 }

ipadRIPStaticARPIpAddress    OBJECT-TYPE
    SYNTAX  IpAddress
    MAX-ACCESS  read-write
    STATUS  current
    DESCRIPTION
        "This is the IP address of the device we will 
        associate the MAC or DLCI address."
    ::= { ipadRIPStaticARPTableEntry 3 }

ipadRIPStaticARPMacAddress    OBJECT-TYPE
    SYNTAX  DisplayString
    MAX-ACCESS  read-write
    STATUS  current
    DESCRIPTION
        "MAC address of the device."
    ::= { ipadRIPStaticARPTableEntry 4 }

ipadRIPStaticARPDLCIAddress    OBJECT-TYPE
    SYNTAX  INTEGER
    MAX-ACCESS  read-write
    STATUS  current
    DESCRIPTION
        "DLCI address of the device."
    ::= { ipadRIPStaticARPTableEntry 5 }

ipadRIPStaticARPEnableARP    OBJECT-TYPE
    SYNTAX  INTEGER
            {
            other(1),
            disabled(2),
            enabled(3)
            }
    MAX-ACCESS  read-write
    STATUS  current
    DESCRIPTION
        "Enable that Static ARP Entry."
    ::= { ipadRIPStaticARPTableEntry 6 }

ipadRIPStaticARPAdd    OBJECT-TYPE
    SYNTAX  INTEGER
            {
            other(1),
            addnew(2)
            }
    MAX-ACCESS  read-write
    STATUS  current
    DESCRIPTION
        "Writing addnew(2) to this field causes a new (blank) 
        route to be appended to the Static ARP Table."
    ::= { ipadRIPParms 6 }

ipadRIPStaticARPDelete    OBJECT-TYPE
    SYNTAX  INTEGER
    MAX-ACCESS  read-write
    STATUS  current
    DESCRIPTION
        "Writing the index of an entry in the Static ARP table
        causes that entry to be deleted."
    ::= { ipadRIPParms 7 }

-- static Route parameters

ipadRIPStaticRouteTable OBJECT-TYPE
    SYNTAX    SEQUENCE OF IpadRIPStaticRouteTableEntry
    MAX-ACCESS  not-accessible
    STATUS    current
    DESCRIPTION
        "Table of RIP Static Route parameters."
    ::= { ipadRIPParms 8 }

ipadRIPStaticRouteTableEntry OBJECT-TYPE
    SYNTAX  IpadRIPStaticRouteTableEntry
    MAX-ACCESS  not-accessible
    STATUS  current
    DESCRIPTION
        "An entry in the ipad RIP Static Route parameter table."
    INDEX   { ipadRIPStaticRouteIndex }
    ::= { ipadRIPStaticRouteTable 1 }

IpadRIPStaticRouteTableEntry ::=
    SEQUENCE
    {
    ipadRIPStaticRouteIndex              INTEGER,
    ipadRIPStaticRouteEndpoint           DisplayString,
    ipadRIPStaticRouteTargetIpAddress    IpAddress,
    ipadRIPStaticRouteTargetIpMask       IpAddress,
    ipadRIPStaticRouteNextHopIpAddress   IpAddress,
    ipadRIPStaticRouteCost               INTEGER,
    ipadRIPStaticRouteEnableRouter       INTEGER
    }

ipadRIPStaticRouteIndex       OBJECT-TYPE
    SYNTAX  INTEGER
    MAX-ACCESS  read-only
    STATUS  current
    DESCRIPTION
        "The index into the RIP Static Route table."
    ::= { ipadRIPStaticRouteTableEntry 1 }

ipadRIPStaticRouteEndpoint    OBJECT-TYPE
    SYNTAX  DisplayString
    MAX-ACCESS  read-write
    STATUS  current
    DESCRIPTION
        "An entry in the endpoint table."
    ::= { ipadRIPStaticRouteTableEntry 2 }

ipadRIPStaticRouteTargetIpAddress    OBJECT-TYPE
    SYNTAX  IpAddress
    MAX-ACCESS  read-write
    STATUS  current
    DESCRIPTION
        ""
    ::= { ipadRIPStaticRouteTableEntry 3 }

ipadRIPStaticRouteTargetIpMask    OBJECT-TYPE
    SYNTAX  IpAddress
    MAX-ACCESS  read-write
    STATUS  current
    DESCRIPTION
        "IP Mask of the IP address."
    ::= { ipadRIPStaticRouteTableEntry 4 }

ipadRIPStaticRouteNextHopIpAddress    OBJECT-TYPE
    SYNTAX  IpAddress
    MAX-ACCESS  read-write
    STATUS  current
    DESCRIPTION
        "Next Hop IP address to reach the remote Network."
    ::= { ipadRIPStaticRouteTableEntry 5 }

ipadRIPStaticRouteCost    OBJECT-TYPE
    SYNTAX  INTEGER(0..65535)
    MAX-ACCESS  read-write
    STATUS  current
    DESCRIPTION
        "Cost to reach that remote Network."
    ::= { ipadRIPStaticRouteTableEntry 6 }

ipadRIPStaticRouteEnableRouter    OBJECT-TYPE
    SYNTAX  INTEGER
            {
            other(1),
            disable(2),
            enable(3),
            enableAndAdvertize(4)
            }
    MAX-ACCESS  read-write
    STATUS  current
    DESCRIPTION
        "Enable or Not this static route."
    ::= { ipadRIPStaticRouteTableEntry 7 }

ipadRIPStaticRouteAdd    OBJECT-TYPE
    SYNTAX  INTEGER
            {
            other(1),
            addnew(2)
            }
    MAX-ACCESS  read-write
    STATUS  current
    DESCRIPTION
        "Writing addnew(2) to this field causes a new (blank) 
        route to be appended to the Static Route Table."
    ::= { ipadRIPParms 9 }

ipadRIPStaticRouteDelete    OBJECT-TYPE
    SYNTAX  INTEGER
    MAX-ACCESS  read-write
    STATUS  current
    DESCRIPTION
        "Writing the index of an entry in the Static Route table
        causes that entry to be deleted."
    ::= { ipadRIPParms 10 }

-- trusted neighbor table

ipadRIPNeighborTable OBJECT-TYPE
    SYNTAX    SEQUENCE OF IpadRIPNeighborTableEntry
    MAX-ACCESS  not-accessible
    STATUS    current
    DESCRIPTION
        "Table of RIP trusted neighbors."
    ::= { ipadRIPParms 11 }

ipadRIPNeighborTableEntry OBJECT-TYPE
    SYNTAX  IpadRIPNeighborTableEntry
    MAX-ACCESS  not-accessible
    STATUS  current
    DESCRIPTION
        "An entry in the ipad RIP trusted neighbor table."
    INDEX   { ipadRIPNeighborIndex }
    ::= { ipadRIPNeighborTable 1 }

IpadRIPNeighborTableEntry ::=
    SEQUENCE
    {
    ipadRIPNeighborIndex   INTEGER,
    ipadRIPNeighborAddress IpAddress
    }

ipadRIPNeighborIndex    OBJECT-TYPE
    SYNTAX  INTEGER
    MAX-ACCESS  read-only
    STATUS  current
    DESCRIPTION
        "The index into the ipadRIPNeighborTable."
    ::= { ipadRIPNeighborTableEntry 1 }

ipadRIPNeighborAddress    OBJECT-TYPE
    SYNTAX  IpAddress
    MAX-ACCESS  read-only
    STATUS  current
    DESCRIPTION
        "A RIP trusted neighbor."
    ::= { ipadRIPNeighborTableEntry 2 }

ipadRIPNeighborAdd    OBJECT-TYPE
    SYNTAX  IpAddress
    MAX-ACCESS  read-write
    STATUS  current
    DESCRIPTION
        "Writing an IP address to this object adds the IP 
        address to the ipad RIP Trusted Neighbor table."
    ::= { ipadRIPParms 12 }

ipadRIPNeighborDelete    OBJECT-TYPE
    SYNTAX  IpAddress
    MAX-ACCESS  read-write
    STATUS  current
    DESCRIPTION
        "Writing an IP address to this object removes the 
        IP address from the ipad RIP Trusted Neighbor table."
    ::= { ipadRIPParms 13 }

ipadOSPFEnable    OBJECT-TYPE
    SYNTAX  INTEGER
            {
            other(1),
            disabled(2),
            enabled(3)
            }
    MAX-ACCESS  read-write
    STATUS  current
    DESCRIPTION
        "To enable or disable OSPF."
    ::= { ipadOSPFParms 1 }

ipadOSPFRouterID    OBJECT-TYPE
    SYNTAX  IpAddress
    MAX-ACCESS  read-write
    STATUS  current
    DESCRIPTION
        "Router's ID."
    ::= { ipadOSPFParms 2 }

ipadOSPFAreaTable OBJECT-TYPE
    SYNTAX    SEQUENCE OF IpadOSPFAreaTableEntry
    MAX-ACCESS  not-accessible
    STATUS  current
    DESCRIPTION
        "Table of OSPF circuits."
    ::= { ipadOSPFParms 3 }

ipadOSPFAreaTableEntry OBJECT-TYPE
    SYNTAX  IpadOSPFAreaTableEntry
    MAX-ACCESS  not-accessible
    STATUS  current
    DESCRIPTION
        "An entry in the OSPF area table."
    INDEX   { ipadOSPFAreaIndex }
    ::= { ipadOSPFAreaTable 1 }

IpadOSPFAreaTableEntry ::=
    SEQUENCE
    {
    ipadOSPFAreaIndex   		INTEGER,
    ipadOSPFAreaID  			IpAddress,
    ipadOSPFAreaEnable   		INTEGER,
    ipadOSPFAreaAuthType   		INTEGER,
    ipadOSPFAreaStub	   		INTEGER,
    ipadOSPFAreaAddrSummary  		IpAddress,
    ipadOSPFAreaMaskSummary  		IpAddress,
    ipadOSPFAreaAdvertise   		INTEGER
    }

ipadOSPFAreaIndex    OBJECT-TYPE
    SYNTAX  INTEGER
    MAX-ACCESS  read-only
    STATUS  current
    DESCRIPTION
        "The index into the ipadOSPFAreaTable."
    ::= { ipadOSPFAreaTableEntry 1 }

ipadOSPFAreaID    OBJECT-TYPE
    SYNTAX  IpAddress
    MAX-ACCESS  read-write
    STATUS  current
    DESCRIPTION
        "Area ID."
    ::= { ipadOSPFAreaTableEntry 2 }

ipadOSPFAreaEnable    OBJECT-TYPE
    SYNTAX  INTEGER
            {
            other(1),
            disabled(2),
            enabled(3)
            }
    MAX-ACCESS  read-write
    STATUS  current
    DESCRIPTION
        "To enable or disable this Area."
    ::= { ipadOSPFAreaTableEntry 3 }

ipadOSPFAreaAuthType    OBJECT-TYPE
    SYNTAX  INTEGER
            {
            none(1),
            simple(2)
            }
    MAX-ACCESS  read-write
    STATUS  current
    DESCRIPTION
        ""
    ::= { ipadOSPFAreaTableEntry 4 }

ipadOSPFAreaStub    OBJECT-TYPE
    SYNTAX  INTEGER
            {
            other(1),
            no(2),
            yes(3)
            }
    MAX-ACCESS  read-write
    STATUS  current
    DESCRIPTION
        ""
    ::= { ipadOSPFAreaTableEntry 5 }

ipadOSPFAreaAddrSummary    OBJECT-TYPE
    SYNTAX  IpAddress
    MAX-ACCESS  read-write
    STATUS  current
    DESCRIPTION
        "Address summary of Area."
    ::= { ipadOSPFAreaTableEntry 6 }

ipadOSPFAreaMaskSummary    OBJECT-TYPE
    SYNTAX  IpAddress
    MAX-ACCESS  read-write
    STATUS  current
    DESCRIPTION
        "Mask of the summary Area."
    ::= { ipadOSPFAreaTableEntry 7 }

ipadOSPFAreaAdvertise       OBJECT-TYPE
    SYNTAX  INTEGER
            {
            other(1),
            disabled(2),
            enabled(3)
            }
    MAX-ACCESS  read-write
    STATUS  current
    DESCRIPTION
        "To enable or disable this Area."
    ::= { ipadOSPFAreaTableEntry 8 }

ipadOSPFAreaAdd    OBJECT-TYPE
    SYNTAX  INTEGER
            {
            other(1),
            addnew(2)
            }
    MAX-ACCESS  read-write
    STATUS  current
    DESCRIPTION
        "Writing addnew(2) to this field causes a new (blank) 
        Area."
    ::= { ipadOSPFParms 4 }

ipadOSPFAreaDelete    OBJECT-TYPE
    SYNTAX  INTEGER
    MAX-ACCESS  read-write
    STATUS  current
    DESCRIPTION
        "Writing the index of an entry in the OSPF Area Table
        causes that entry to be deleted."
    ::= { ipadOSPFParms 5 }

ipadOSPFVlinkTable OBJECT-TYPE
    SYNTAX    SEQUENCE OF IpadOSPFVlinkTableEntry
    MAX-ACCESS    not-accessible
    STATUS    current
    DESCRIPTION
        "Table of OSPF circuits."
    ::= { ipadOSPFParms 6 }

ipadOSPFVlinkTableEntry OBJECT-TYPE
    SYNTAX  IpadOSPFVlinkTableEntry
    MAX-ACCESS  not-accessible
    STATUS  current
    DESCRIPTION
        "An entry in the OSPF circuit table."
    INDEX   { ipadOSPFVlinkIndex }
    ::= { ipadOSPFVlinkTable 1 }

IpadOSPFVlinkTableEntry ::=
    SEQUENCE
    {
    ipadOSPFVlinkIndex   			INTEGER,
    ipadOSPFVlinkEnable   			INTEGER,
    ipadOSPFVlinkTransitAreaID   		IpAddress,
    ipadOSPFVlinkAreaBorderRouterID		IpAddress
    }

ipadOSPFVlinkIndex    OBJECT-TYPE
    SYNTAX  INTEGER
    MAX-ACCESS  read-only
    STATUS  current
    DESCRIPTION
        "The index into the ipadOSPFVlinkTable."
    ::= { ipadOSPFVlinkTableEntry 1 }

ipadOSPFVlinkEnable    OBJECT-TYPE
    SYNTAX  INTEGER
            {
            other(1),
            disabled(2),
            enabled(3)
            }
    MAX-ACCESS  read-write
    STATUS  current
    DESCRIPTION
        "Enable or disable the Virtual Link."
    ::= { ipadOSPFVlinkTableEntry 2 }

ipadOSPFVlinkTransitAreaID    OBJECT-TYPE
    SYNTAX  IpAddress
    MAX-ACCESS  read-write
    STATUS  current
    DESCRIPTION
        "ID of the transit Area the virtual link will pass through."
    ::= { ipadOSPFVlinkTableEntry 3 }

ipadOSPFVlinkAreaBorderRouterID    OBJECT-TYPE
    SYNTAX  IpAddress
    MAX-ACCESS  read-write
    STATUS  current
    DESCRIPTION
        "Route ID of the area border router at end of the virtual link."
    ::= { ipadOSPFVlinkTableEntry 4 }

ipadOSPFVlinkAdd    OBJECT-TYPE
    SYNTAX  INTEGER
            {
            other(1),
            addnew(2)
            }
    MAX-ACCESS  read-write
    STATUS  current
    DESCRIPTION
        "Writing addnew(2) to this field causes a new (blank) 
        Vlink."
    ::= { ipadOSPFParms 7 }

ipadOSPFVlinkDelete    OBJECT-TYPE
    SYNTAX  INTEGER
    MAX-ACCESS  read-write
    STATUS  current
    DESCRIPTION
        "Writing the index of an entry in the OSPF Vlink Table
        causes that entry to be deleted."
    ::= { ipadOSPFParms 8 }

END

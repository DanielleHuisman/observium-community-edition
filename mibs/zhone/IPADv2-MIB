-- $Header:   K:/WanSuite/archives/include/pvcs/ipadv2.mib,v   1.69   Mar 19 2004 09:36:14   richardm  $

IPADv2-MIB DEFINITIONS ::= BEGIN

IMPORTS enterprises, 
        IpAddress, 
        TimeTicks,
        OBJECT-TYPE, 
        MODULE-IDENTITY,
        NOTIFICATION-TYPE                              FROM SNMPv2-SMI
        DisplayString                                  FROM SNMPv2-TC

        -- 
        -- import definitions for v2 traps
        -- eventually move the following to DS8200v2Traps-MIB
        -- 
        serialDteDTRAlarmStatus,
        t1e1ESCount,
        t1e1SESCount,
        t1e1LOSSCount,
        t1e1UASCount,
        t1e1CSSCount,
        t1e1BPVSCount,
        t1e1OOFSCount,
        t1e1AISCount,
        t1e1RASCount,
        ddsNetLOSCount,
        ddsNetOOFCount,
        ddsNetOOSCount,
        ddsNetFDLCount,
        ddsNetBPVCount                                FROM DS8200v2-MIB
        hbu,verilink                                  FROM DS8200v2-TC-MIB;

ipad MODULE-IDENTITY
    LAST-UPDATED "0011210000Z"
         ORGANIZATION "Verilink Corporation"
         CONTACT-INFO
            "support@verilink.com
             + 1 800 285 2755"
         DESCRIPTION
            "IPADv2.MIB updated for SNMPv2."
    ::= { hbu 1 }

-- IPAD sections

ipadFrPort      OBJECT IDENTIFIER ::= { ipad 1 }
ipadService     OBJECT IDENTIFIER ::= { ipad 2 }
ipadChannel     OBJECT IDENTIFIER ::= { ipad 3 }
ipadDLCI        OBJECT IDENTIFIER ::= { ipad 4 }
ipadEndpoint    OBJECT IDENTIFIER ::= { ipad 5 }
ipadUser        OBJECT IDENTIFIER ::= { ipad 6 }
ipadPPP         OBJECT IDENTIFIER ::= { ipad 7 }
ipadModem       OBJECT IDENTIFIER ::= { ipad 8 }
ipadSvcAware    OBJECT IDENTIFIER ::= { ipad 9 }
ipadPktSwitch   OBJECT IDENTIFIER ::= { ipad 10 }
ipadTrapDest    OBJECT IDENTIFIER ::= { ipad 11 }
ipadMisc        OBJECT IDENTIFIER ::= { ipad 12 }
ipadRouter      OBJECT IDENTIFIER ::= { ipad 13 }
ipadSoftKey     OBJECT IDENTIFIER ::= { ipad 14 }
ipadTCPServer   OBJECT IDENTIFIER ::= { ipad 15 }
ipadTraps       OBJECT IDENTIFIER ::= { ipad 999 }
ipadTrapsPrefix OBJECT IDENTIFIER ::= { ipadTraps 0 }
ipadSCADAConfig OBJECT IDENTIFIER ::= { ipad 16 }		
ipadSCADAStats  OBJECT IDENTIFIER ::= { ipad 17 }	
ipadSCADADevLst	OBJECT IDENTIFIER ::= { ipad 18 }
ipadDS0Config	OBJECT IDENTIFIER ::= { ipad 19 }
ipadDS0Hist24	OBJECT IDENTIFIER ::= { ipad 20 }
ipadDS0Hist30	OBJECT IDENTIFIER ::= { ipad 21 }
ipadHDLCConfig	OBJECT IDENTIFIER ::= { ipad 22 }
ipadHDLCHist24	OBJECT IDENTIFIER ::= { ipad 23 }
ipadHDLCHist30	OBJECT IDENTIFIER ::= { ipad 24 }
ipadAtm		OBJECT IDENTIFIER ::= { ipad 25 }
ipadNat		OBJECT IDENTIFIER ::= { ipad 26 }
ipadDhcp	OBJECT IDENTIFIER ::= { ipad 27 }	
ipadBridge	OBJECT IDENTIFIER ::= { ipad 28 }
ipadSmtp	OBJECT IDENTIFIER ::= { ipad 29 }
ipadEncryption	OBJECT IDENTIFIER ::= { ipad 30 }
ipadAutoLearnDS0	OBJECT IDENTIFIER ::= { ipad 31 }
ipadUnitAccess	OBJECT IDENTIFIER ::= { ipad 32 }
ipadTFTPDownload	OBJECT IDENTIFIER ::= { ipad 33 }
ipadDataLineMonitor     OBJECT IDENTIFIER ::= { ipad 34 }
ipadOrigPing	OBJECT IDENTIFIER ::= { ipad 35 }
 
-- Up to { ipad 998 }
 		  
 
-- ipadFrPort section
-- contains the frame relay port table

ipadFrPortTable    OBJECT-TYPE
    SYNTAX    SEQUENCE OF IpadFrPortTableEntry
    MAX-ACCESS    not-accessible
    STATUS    current
    DESCRIPTION
        "Table of frame relay port parameters."
    ::= { ipadFrPort 1 }

ipadFrPortTableEntry    OBJECT-TYPE
    SYNTAX  IpadFrPortTableEntry
    MAX-ACCESS  not-accessible
    STATUS  current
    DESCRIPTION
        "An entry in the ipad frame relay port table."
    INDEX   { ipadFrPortService }
    ::= { ipadFrPortTable 1 }

IpadFrPortTableEntry ::=
    SEQUENCE
    {
    ipadFrPortService            INTEGER,
    ipadFrPortActive             INTEGER,
    ipadFrPortLMIType            INTEGER,
    ipadFrPortLMIMode            INTEGER,
    ipadFrPortRxInvAlmThreshold  INTEGER,
    ipadFrPortRxInvAlmAlarm      INTEGER,
    ipadFrPortTxAlmThreshold     INTEGER,
    ipadFrPortTxAlmAlarm         INTEGER,
    ipadFrPortRxAlmThreshold     INTEGER,
    ipadFrPortRxAlmAlarm         INTEGER,
    ipadFrPortAlarmReset         INTEGER
    }

ipadFrPortService    OBJECT-TYPE
    SYNTAX  INTEGER
    MAX-ACCESS  read-only
    STATUS  current
    DESCRIPTION
        "Index into the ipad frame relay port table;
        an entry in the ipad service table."
    ::= { ipadFrPortTableEntry 1 }

ipadFrPortActive    OBJECT-TYPE
    SYNTAX  INTEGER
        {
        other(1),
        no(2),
        yes(3)
        }
    MAX-ACCESS  read-only
    STATUS  current
    DESCRIPTION
        "Specifies if the port is active."
    ::= { ipadFrPortTableEntry 2 }

ipadFrPortLMIType    OBJECT-TYPE
    SYNTAX  INTEGER
        {
        other(1),
        ccitt(2),
        ansi(3),
        lmi(4),
        none(5)
        }
    MAX-ACCESS  read-only
    STATUS  current
    DESCRIPTION
        "Specifies the link management information 
        type used on this port."
    ::= { ipadFrPortTableEntry 3 }

ipadFrPortLMIMode    OBJECT-TYPE
    SYNTAX  INTEGER
        {
        other(1),
        sourcing(2),
        monitoring(3)
        }
    MAX-ACCESS  read-only
    STATUS  current
    DESCRIPTION
        "Specifies the link management information 
        mode used on this port."
    ::= { ipadFrPortTableEntry 4 }

ipadFrPortRxInvAlmThreshold  OBJECT-TYPE
    SYNTAX  INTEGER
    MAX-ACCESS  read-write
    STATUS  current
    DESCRIPTION     
        "Sets the rx invalid frames alarm threshold.  
        Setting this field to 0 disables the alarm."
    ::= { ipadFrPortTableEntry 5 }

ipadFrPortRxInvAlmAlarm    OBJECT-TYPE
    SYNTAX  INTEGER
        {
        other(1),
        noAlarm(2),
        thresholdExceeded(3)
        }
    MAX-ACCESS  read-only
    STATUS  current
    DESCRIPTION
        "Reports if the invalid frames threshold has 
        been exceeded."
    ::= { ipadFrPortTableEntry 6 }

ipadFrPortTxAlmThreshold     OBJECT-TYPE
    SYNTAX  INTEGER
    MAX-ACCESS  read-write
    STATUS  current
    DESCRIPTION     
        "Sets the tx throughput alarm threshold (in bits/second).  
        Setting this field to 0 disables the alarm."
    ::= { ipadFrPortTableEntry 7 }

ipadFrPortTxAlmAlarm    OBJECT-TYPE
    SYNTAX  INTEGER
        {
        other(1),
        noAlarm(2),
        thresholdExceeded(3)
        }
    MAX-ACCESS  read-only
    STATUS  current
    DESCRIPTION
        "Reports if the tx throughput threshold has 
        been exceeded."
    ::= { ipadFrPortTableEntry 8 }

ipadFrPortRxAlmThreshold      OBJECT-TYPE
    SYNTAX  INTEGER
    MAX-ACCESS  read-write
    STATUS  current
    DESCRIPTION     
        "Sets the rx throughput alarm threshold (in bits/second).  
        Setting this field to 0 disables the alarm."
    ::= { ipadFrPortTableEntry 9 }

ipadFrPortRxAlmAlarm        OBJECT-TYPE
    SYNTAX  INTEGER
        {
        other(1),
        noAlarm(2),
        thresholdExceeded(3)
        }
    MAX-ACCESS  read-only
    STATUS  current
    DESCRIPTION
        "Reports if the rx throughput threshold has 
        been exceeded."
    ::= { ipadFrPortTableEntry 10 }

ipadFrPortAlarmReset OBJECT-TYPE
	SYNTAX  INTEGER
		{
		frPortAlarmResetOther(1),
		frPortAlarmResetClearAlarms(2),
		frPortAlarmResetClearStats(3)
		}
	MAX-ACCESS  read-write
	STATUS  current
	DESCRIPTION     
		"This is used to clear the current alarm counts."
	::= { ipadFrPortTableEntry 11 }

-- ipadService section
-- contains the service table

ipadServiceTable    OBJECT-TYPE
    SYNTAX  SEQUENCE OF IpadServiceTableEntry
    MAX-ACCESS  not-accessible
    STATUS  current
    DESCRIPTION
        "The ipad service table."
    ::= { ipadService 1 }

ipadServiceTableEntry    OBJECT-TYPE
    SYNTAX  IpadServiceTableEntry
    MAX-ACCESS  not-accessible
    STATUS  current
    DESCRIPTION
        "An entry in the ipad service table."
    INDEX    { ipadServiceIndex }
    ::= { ipadServiceTable 1 }

IpadServiceTableEntry ::=
    SEQUENCE
    {
    ipadServiceIndex        INTEGER,
    ipadServiceifIndex      INTEGER,
    ipadServiceType         INTEGER,
    ipadServicePair         INTEGER,
    ipadServiceStatus       INTEGER
    }

ipadServiceIndex    OBJECT-TYPE
    SYNTAX  INTEGER
    MAX-ACCESS  read-only
    STATUS  current
    DESCRIPTION
        "The index for the ipad service table."
    ::= { ipadServiceTableEntry 1 }

ipadServiceifIndex    OBJECT-TYPE
	SYNTAX  INTEGER
	{
		disabled(0),
		supervisor(1),
		network1(2),
		network2(3),
		user1(4),
		user2(5),
		ethernet(6),
		auxiliary(7),
		network3(8),
		atmCES(9),
		modem(10),
		virtual(100)
	}
	MAX-ACCESS  read-write
	STATUS  current
	DESCRIPTION
		"The MIB-II ifIndex for this service."
	::= { ipadServiceTableEntry 2 }

ipadServiceType        OBJECT-TYPE
    SYNTAX  INTEGER
        {
        other(1),
        tdm(2),
        ppp(3),
        pppMonitor(4),
        frameRelay(5),
        frameRelayMonitor(6),
        ip(7),
        serial(8),
        tty(9),
	scada(10),
	parallelIO(11),
	atm(12),
	hdlcPPP(13),
	atmCES(14),
	modem(15)
        }
    MAX-ACCESS  read-write
    STATUS  current
    DESCRIPTION
        "The type of this service."
    ::= { ipadServiceTableEntry 3 }

ipadServicePair        OBJECT-TYPE
    SYNTAX  INTEGER
    MAX-ACCESS  read-write
    STATUS  current
    DESCRIPTION
        "An entry in this table, which establishes a service pairing."
    ::= { ipadServiceTableEntry 4 }
    
ipadServiceStatus	OBJECT-TYPE
	SYNTAX  INTEGER
	{
		other(1),
		idle(2),
		down(3),
		physicalUp(4),
		protocolUp(5),
		dead(6),
		changed(7),
		training(8),
		connecting(9)
	}
	MAX-ACCESS  read-only
	STATUS  current
	DESCRIPTION
		"This parameter indicates the status of the service.
		idle - The service is not doing anything or has not been configured for use.
		down - The physical layer for the service is not ready.
		training - The physical layer is not ready but is attempting to come up.
		connecting - The physical layer is not ready but is attempting to come up.
		physicalUp - The physical layer is ready the service is not ready.
		protocolUp - The service is able to pass data.
		dead - The service is inactive because no resources are available to support it.
		changed - Service parameters were changed and require a save and restart to take effect."
	::= { ipadServiceTableEntry 5 }
 
ipadServiceAddService OBJECT-TYPE
    SYNTAX  INTEGER
        {
        addService(1)
        }
    MAX-ACCESS  read-write
    STATUS  current
    DESCRIPTION
        "Adds a row to the Service Table."
    ::= { ipadService 2 }

ipadServiceDeleteService OBJECT-TYPE
    SYNTAX  INTEGER
    MAX-ACCESS  read-write
    STATUS  current
    DESCRIPTION
        "Identifies a Service to be deleted; an index into the Service Table."
    ::= { ipadService 3 }

-- ipadChannel section
-- contains the channel table

ipadChannelTable    OBJECT-TYPE
    SYNTAX  SEQUENCE OF IpadChannelTableEntry
    MAX-ACCESS  not-accessible
    STATUS  current
    DESCRIPTION
        "The ipad channel table."
    ::= { ipadChannel 1 }

ipadChannelTableEntry    OBJECT-TYPE
    SYNTAX  IpadChannelTableEntry
    MAX-ACCESS  not-accessible
    STATUS  current
    DESCRIPTION
        "An entry in the ipad channel table."
    INDEX    { ipadChannelifIndex, ipadChannelIndex }
    ::= { ipadChannelTable 1 }

IpadChannelTableEntry ::=
    SEQUENCE
    {
    ipadChannelifIndex      INTEGER,
    ipadChannelIndex        INTEGER,
    ipadChannelService      INTEGER,
    ipadChannelPair         INTEGER,
    ipadChannelRate         INTEGER,
    ipadChannelIdlePattern  INTEGER
    }

ipadChannelifIndex    OBJECT-TYPE
    SYNTAX  INTEGER
    MAX-ACCESS  read-only
    STATUS  current
    DESCRIPTION
        "Primary index into ipad channel table, MIB-II ifIndex."
    ::= { ipadChannelTableEntry 1 }

ipadChannelIndex    OBJECT-TYPE
    SYNTAX  INTEGER
    MAX-ACCESS  read-only
    STATUS  current
    DESCRIPTION
        "Channel index for the physical interface."
    ::= { ipadChannelTableEntry 2 }

ipadChannelService    OBJECT-TYPE
    SYNTAX  INTEGER
    MAX-ACCESS  read-write
    STATUS  current
    DESCRIPTION
        "Index into service table for this channel."
    ::= { ipadChannelTableEntry 3 }

ipadChannelPair        OBJECT-TYPE
    SYNTAX  INTEGER
    MAX-ACCESS  read-write
    STATUS  current
    DESCRIPTION    
        "Pair for this channel; an entry in the channel 
        table.  Use service pair in service table to 
        determine which service contains this channel."
    ::= { ipadChannelTableEntry 4 }

ipadChannelRate        OBJECT-TYPE
    SYNTAX  INTEGER
    {
    other(1),
    rate56(2),
    rate64(3),
    rate8(4)
    }
    MAX-ACCESS  read-write
    STATUS  current
    DESCRIPTION    
        "Rate for this channel."
    ::= { ipadChannelTableEntry 5 }

ipadChannelIdlePattern   OBJECT-TYPE
    SYNTAX  INTEGER
    MAX-ACCESS  read-only
    STATUS  current
    DESCRIPTION
        "Idle pattern for this channel."
    ::= { ipadChannelTableEntry 6 }
 
-- ipadDLCI section
-- contains the DLCI table

ipadDLCITable    OBJECT-TYPE
    SYNTAX  SEQUENCE OF IpadDLCITableEntry
    MAX-ACCESS  not-accessible
    STATUS  current
    DESCRIPTION
        "The ipad DLCI table."
    ::= { ipadDLCI 1 }

ipadDLCITableEntry    OBJECT-TYPE
    SYNTAX  IpadDLCITableEntry
    MAX-ACCESS  not-accessible
    STATUS  current
    DESCRIPTION
        "An entry in the ipad DLCI table."
    INDEX    { ipadDLCIservice,ipadDLCInumber }
    ::= { ipadDLCITable 1 }

IpadDLCITableEntry ::=
    SEQUENCE
    {
    ipadDLCIservice           INTEGER,
    ipadDLCInumber            INTEGER,
    ipadDLCIactive            INTEGER,
    ipadDLCIcongestion        INTEGER,
    ipadDLCIremote            INTEGER,
    ipadDLCIremoteUnit        DisplayString,
    ipadDLCIremoteEquipActive INTEGER,
    ipadDLCIencapsulation     INTEGER,
    ipadDLCIproprietary       INTEGER,
    ipadDLCIpropOffset        INTEGER,
    ipadDLCIinBand            INTEGER,
    ipadDLCICIR               INTEGER,
    ipadDLCIBe                INTEGER,
    ipadDLCIminBC             INTEGER,
    ipadDLCIrxMon             INTEGER,
    ipadDLCIdEctrl            INTEGER,
    ipadDLCIenableDelay       INTEGER,
    ipadDLCItxExCIRThreshold  INTEGER,
    ipadDLCItxExCIRAlarm      INTEGER,
    ipadDLCItxExBeThreshold   INTEGER,
    ipadDLCItxExBeAlarm       INTEGER,
    ipadDLCIrxCongThreshold   INTEGER,
    ipadDLCIrxCongAlarm       INTEGER,
    ipadDLCIrxBECNinCIR       INTEGER,
    ipadDLCIUASThreshold      INTEGER,
    ipadDLCIUASAlarm          INTEGER,
    ipadDLCIAlarmReset        INTEGER,
    ipadDLCIRoundTripDelaySize	  		INTEGER,
    ipadDLCIRoundTripDelayRate	  		INTEGER,
    ipadDLCIRemoteFramesOfferedWithinCIR	INTEGER,
    ipadDLCIRemoteFramesOfferedWithinBE		INTEGER,
    ipadDLCIFramesReceived	  		INTEGER,
    ipadDLCIRemoteDataOfferedWithinCIR		INTEGER,
    ipadDLCIRemoteDataOfferedWithinBE		INTEGER,
    ipadDLCIDataReceived	  		INTEGER,
    ipadDLCIRemoteIPAddress	  		IpAddress,
    ipadDLCICompressionStatus			INTEGER,
    ipadDLCICompressionTxOctetsIn		INTEGER,
    ipadDLCICompressionTxOctetsOut		INTEGER,
    ipadDLCICompressionRxOctetsIn		INTEGER,
    ipadDLCICompressionRxOctetsOut		INTEGER
    }

ipadDLCIservice    OBJECT-TYPE
    SYNTAX  INTEGER
    MAX-ACCESS  read-only
    STATUS  current
    DESCRIPTION
        "An index into the ipad service table."
    ::= { ipadDLCITableEntry 1 }

ipadDLCInumber    OBJECT-TYPE
    SYNTAX  INTEGER
    MAX-ACCESS  read-only
    STATUS  current
    DESCRIPTION
        "The DLCI number for this entry."
    ::= { ipadDLCITableEntry 2 }

ipadDLCIactive    OBJECT-TYPE
    SYNTAX  INTEGER
        {
        other(1),
        no(2),
        yes(3),
        pending(4)
        }
    MAX-ACCESS  read-only
    STATUS  current
    DESCRIPTION
        "Specifies if the DLCI is active."
    ::= { ipadDLCITableEntry 3 }

ipadDLCIcongestion    OBJECT-TYPE
    SYNTAX  INTEGER
    {
    other(1),
    no(2),
    yes(3)
    }
    MAX-ACCESS  read-only
    STATUS  current
    DESCRIPTION
        "Specifies if the dlci is receiving frames 
        with FECN or BECN bit set."
    ::= { ipadDLCITableEntry 4 }

ipadDLCIremote    OBJECT-TYPE
    SYNTAX  INTEGER
    MAX-ACCESS  read-only
    STATUS  current
    DESCRIPTION
        "Remote DLCI number."
    ::= { ipadDLCITableEntry 5 }

ipadDLCIremoteUnit    OBJECT-TYPE
    SYNTAX  DisplayString( SIZE(0..11))
    MAX-ACCESS  read-only
    STATUS  current
    DESCRIPTION
        "Name of the remote DLCI."
    ::= { ipadDLCITableEntry 6 }

ipadDLCIremoteEquipActive    OBJECT-TYPE
    SYNTAX  INTEGER
    {
    other(1),
    inactive(2),
    active(3),
    sosAlarm(4)
    }
    MAX-ACCESS  read-only
    STATUS  current
    DESCRIPTION
        "Reports if the equipment attached to the
        remote unit is active."
    ::= { ipadDLCITableEntry 7 }

ipadDLCIencapsulation    OBJECT-TYPE
    SYNTAX  INTEGER
    {
    other(1),
    rfc1490(2),
    proprietary(3),
    rfc1490withEncryption(4),
    rfc1490withCompression(5)
    }
    MAX-ACCESS  read-write
    STATUS  current
    DESCRIPTION
        "Type of protocol encapsulation used on this DLCI."
    ::= { ipadDLCITableEntry 8 }

ipadDLCIproprietary    OBJECT-TYPE
    SYNTAX  INTEGER
    {
    other(1),
    ip(2),
    ipx(3),
    ethertype(4),
    none(5)
    }
    MAX-ACCESS  read-write
    STATUS  current
    DESCRIPTION
        "When the encapsulation is proprietary, the traffic type must be
        configured to gather protocol specific statistics."
    ::= { ipadDLCITableEntry 9 }

ipadDLCIpropOffset    OBJECT-TYPE
    SYNTAX  INTEGER
    MAX-ACCESS  read-write
    STATUS  current
    DESCRIPTION
        "When the encapsulation is proprietary, this is the number of bytes
        after the frame relay header to look for the specified protocol
        decode."
    ::= { ipadDLCITableEntry 10 }

ipadDLCIinBand    OBJECT-TYPE
    SYNTAX  INTEGER
    {
    other(1),
    no(2),
    yes(3)
    }
    MAX-ACCESS  read-write
    STATUS  current
    DESCRIPTION
        "Determines if frames on this DLCI will be parsed to look
        for management frames destined for the unit itself."
    ::= { ipadDLCITableEntry 11 }

ipadDLCICIR    OBJECT-TYPE
    SYNTAX  INTEGER
    MAX-ACCESS  read-write
    STATUS  current
    DESCRIPTION
        "Default committed information rate in bits per second."
    ::= { ipadDLCITableEntry 12 }

ipadDLCIBe    OBJECT-TYPE
    SYNTAX  INTEGER
    MAX-ACCESS  read-write
    STATUS  current
    DESCRIPTION
        "Default excess burst rate in bits per second."
    ::= { ipadDLCITableEntry 13 }

ipadDLCIminBC    OBJECT-TYPE
    SYNTAX  INTEGER
    MAX-ACCESS  read-write
    STATUS  current
    DESCRIPTION
        "If the corresponding interface is configured to enable
        congestion management, the minimum transfer rate at which
        the unit will throttle back offering data to the network."
    ::= { ipadDLCITableEntry 14 }

ipadDLCIrxMon    OBJECT-TYPE
    SYNTAX  INTEGER
    {
    other(1),
    no(2),
    yes(3)
    }
    MAX-ACCESS  read-write
    STATUS  current
    DESCRIPTION
        "Determines if the SLA parameters will be monitored for received
        frames."
    ::= { ipadDLCITableEntry 15 }

ipadDLCIdEctrl    OBJECT-TYPE
    SYNTAX  INTEGER
    {
    other(1),
    no(2),
    yes(3)
    }
    MAX-ACCESS  read-write
    STATUS  current
    DESCRIPTION
        "Determines if the Rx monitor will set the DE bit on all frames
        received in excess of the CIR before they are switched to their
        destination port."
    ::= { ipadDLCITableEntry 16 }

ipadDLCIenableDelay    OBJECT-TYPE
    SYNTAX  INTEGER
    {
    other(1),
    disable(2),
    enable(3)
    }
    MAX-ACCESS  read-write
    STATUS  current
    DESCRIPTION
        "Enable or disable delay."
    ::= { ipadDLCITableEntry 17 }

ipadDLCItxExCIRThreshold    OBJECT-TYPE
    SYNTAX  INTEGER
    MAX-ACCESS  read-write
    STATUS  current
    DESCRIPTION     
        "Sets the Tx over CIR alarm threshold.  This threshold 
        is the number of bits per second in excess of CIR.  Setting 
        this field to 0 disables the alarm."
    ::= { ipadDLCITableEntry 18 }

ipadDLCItxExCIRAlarm    OBJECT-TYPE
    SYNTAX  INTEGER
    {
    other(1),
    noAlarm(2),
    thresholdExceeded(3)
    }
    MAX-ACCESS  read-only
    STATUS  current
    DESCRIPTION
        "Reports if the Tx over CIR threshold has been exceeded."
    ::= { ipadDLCITableEntry 19 }

ipadDLCItxExBeThreshold    OBJECT-TYPE
    SYNTAX  INTEGER
    MAX-ACCESS  read-write
    STATUS  current
    DESCRIPTION     
        "Sets the Tx over Be alarm threshold.  This threshold is the 
        number of bits per second in excess of Be.  Setting this 
		field to 0 disables the alarm."
    ::= { ipadDLCITableEntry 20 }

ipadDLCItxExBeAlarm    OBJECT-TYPE
    SYNTAX  INTEGER
    {
    other(1),
    noAlarm(2),
    thresholdExceeded(3)
    }
    MAX-ACCESS  read-only
    STATUS  current
    DESCRIPTION
        "Reports if the Tx over Be threshold has been exceeded."
    ::= { ipadDLCITableEntry 21 }

ipadDLCIrxCongThreshold    OBJECT-TYPE
    SYNTAX  INTEGER
    MAX-ACCESS  read-write
    STATUS  current
    DESCRIPTION     
        "Sets the Rx congestion alarm threshold.  This threshold 
        is the number of frames received with BECN/FECN.  Setting 
        this field to 0 disables the alarm."
    ::= { ipadDLCITableEntry 22 }

ipadDLCIrxCongAlarm    OBJECT-TYPE
    SYNTAX  INTEGER
    {
    other(1),
    noAlarm(2),
    thresholdExceeded(3)
    }
    MAX-ACCESS  read-only
    STATUS  current
    DESCRIPTION
        "Reports if the Rx congestion threshold has been exceeded."
    ::= { ipadDLCITableEntry 23 }

ipadDLCIrxBECNinCIR    OBJECT-TYPE
    SYNTAX  INTEGER
    {
    other(1),
    noAlarm(2),
    alarmCondition(3)
    }
    MAX-ACCESS  read-only
    STATUS  current
    DESCRIPTION
        "Reports if BECN has been received within CIR."
    ::= { ipadDLCITableEntry 24 }

ipadDLCIUASThreshold    OBJECT-TYPE
    SYNTAX  INTEGER
    MAX-ACCESS  read-write
    STATUS  current
    DESCRIPTION     
        "Sets the UAS (unavailable seconds) alarm threshold.  This
        threshold is the number of seconds passed that the DLCI is
        unavailable.  Setting this field to 0 disables the alarm."
    ::= { ipadDLCITableEntry 25 }

ipadDLCIUASAlarm    OBJECT-TYPE
    SYNTAX  INTEGER
    {
    other(1),
    noAlarm(2),
    thresholdExceeded(3)
    }
    MAX-ACCESS  read-only
    STATUS  current
    DESCRIPTION
        "Reports if the UAS threshold has been exceeded."
    ::= { ipadDLCITableEntry 26 }

ipadDLCIAlarmReset OBJECT-TYPE
	SYNTAX  INTEGER
		{
		dlciAlarmResetOther(1),
		dlciAlarmResetClearAlarms(2),
		dlciAlarmResetClearStats(3)
		}
	MAX-ACCESS  read-write
	STATUS  current
	DESCRIPTION     
		"This is used to clear the current alarm counts."
	::= { ipadDLCITableEntry 27 }

ipadDLCIRoundTripDelaySize OBJECT-TYPE
	SYNTAX  INTEGER(16..1500)
	MAX-ACCESS  read-write
	STATUS  current
	DESCRIPTION     
		"Specifies the packet size in octets used to calculate 
		round trip delay."
	::= { ipadDLCITableEntry 28 }

ipadDLCIRoundTripDelayRate OBJECT-TYPE
	SYNTAX  INTEGER(1..900)
	MAX-ACCESS  read-write
	STATUS  current
	DESCRIPTION     
		"Specifies the packet rate in seconds used to calculate 
		round trip delay."
	::= { ipadDLCITableEntry 29 }

ipadDLCIRemoteFramesOfferedWithinCIR    OBJECT-TYPE
    SYNTAX  INTEGER
    MAX-ACCESS  read-only
    STATUS  current
    DESCRIPTION     
        "Count of frames sent within CIR from the remote end of the DLCI."
    ::= { ipadDLCITableEntry 30 }

ipadDLCIRemoteFramesOfferedWithinBE    OBJECT-TYPE
    SYNTAX  INTEGER
    MAX-ACCESS  read-only
    STATUS  current
    DESCRIPTION     
        "Count of frames sent within BE, but over CIR, from the remote end of the DLCI."
    ::= { ipadDLCITableEntry 31 }

ipadDLCIFramesReceived    OBJECT-TYPE
    SYNTAX  INTEGER
    MAX-ACCESS  read-only
    STATUS  current
    DESCRIPTION     
        "Count of frames received by the local device on this DLCI."
    ::= { ipadDLCITableEntry 32 }

ipadDLCIRemoteDataOfferedWithinCIR    OBJECT-TYPE
    SYNTAX  INTEGER
    MAX-ACCESS  read-only
    STATUS  current
    DESCRIPTION     
        "Count of data octets sent within CIR from the remote end of the DLCI."
    ::= { ipadDLCITableEntry 33 }

ipadDLCIRemoteDataOfferedWithinBE    OBJECT-TYPE
    SYNTAX  INTEGER
    MAX-ACCESS  read-only
    STATUS  current
    DESCRIPTION     
        "Count of data octets sent within BE, but over CIR, from the remote 
        end of the DLCI."
    ::= { ipadDLCITableEntry 34 }

ipadDLCIDataReceived    OBJECT-TYPE
    SYNTAX  INTEGER
    MAX-ACCESS  read-only
    STATUS  current
    DESCRIPTION     
        "Count of data octets received by the local device on this DLCI."
    ::= { ipadDLCITableEntry 35 }

ipadDLCIRemoteIPAddress    OBJECT-TYPE
    SYNTAX  IpAddress
    MAX-ACCESS  read-only
    STATUS  current
    DESCRIPTION     
        "The IP Address of the device on the remote end of this DLCI.  This information
        is only valid when the remote device supports Verilink's proprietary message
        exchange."
    ::= { ipadDLCITableEntry 36 }

ipadDLCICompressionStatus    OBJECT-TYPE
    SYNTAX  INTEGER
		{
		other(1),
		disabled(2),
		enabledAndNegotiated(3),
		enabledButNotNegotiated(4)
		}
    MAX-ACCESS  read-only
    STATUS  current
    DESCRIPTION     
        "This is the current status of the compression engine for this DLCI.  
        disabled(2) indicates that the compression engine is disabled.
        enabledAndNegotiated(3) indicates that compression is enabled, and has
        	been successfully negotiated with the device at the other end.
        enabledButNotNegotiated(4) indicated that compression is enabled, but has
		not been successfully negotiated with the device at the other end.
		This may be due to the DLCI being down, the other device not having
		compression enabled or other factors which would inhibit communication."
    ::= { ipadDLCITableEntry 37 }

ipadDLCICompressionTxOctetsIn    OBJECT-TYPE
    SYNTAX  INTEGER
    MAX-ACCESS  read-only
    STATUS  current
    DESCRIPTION     
        "This is a rolling counter of the number of octets given to the compression 
        engine."
    ::= { ipadDLCITableEntry 38 }

ipadDLCICompressionTxOctetsOut    OBJECT-TYPE
    SYNTAX  INTEGER
    MAX-ACCESS  read-only
    STATUS  current
    DESCRIPTION     
        "This is a rolling counter of the number of octets output from the compression 
        engine."
    ::= { ipadDLCITableEntry 39 }

ipadDLCICompressionRxOctetsIn    OBJECT-TYPE
    SYNTAX  INTEGER
    MAX-ACCESS  read-only
    STATUS  current
    DESCRIPTION     
        "This is a rolling counter of the number of octets given to the compression 
        engine."
    ::= { ipadDLCITableEntry 40 }

ipadDLCICompressionRxOctetsOut    OBJECT-TYPE
    SYNTAX  INTEGER
    MAX-ACCESS  read-only
    STATUS  current
    DESCRIPTION     
        "This is a rolling counter of the number of octets given to the compression 
        engine."
    ::= { ipadDLCITableEntry 41 }


ipadDLCILastChange OBJECT-TYPE
    SYNTAX  TimeTicks
    MAX-ACCESS  read-only
    STATUS  current
    DESCRIPTION
        "Time of the last change in the DLCI table."
    ::= { ipadDLCI 2 }
    
-- ipadEndpoint section
-- endpoint table

ipadEndpointTable    OBJECT-TYPE
    SYNTAX  SEQUENCE OF IpadEndpointTableEntry
    MAX-ACCESS  not-accessible
    STATUS  current
    DESCRIPTION
        "The ipad endpoint table."
    ::= { ipadEndpoint 1 }

ipadEndpointTableEntry    OBJECT-TYPE
    SYNTAX    IpadEndpointTableEntry
    MAX-ACCESS  not-accessible
    STATUS  current
    DESCRIPTION
        "An entry in the ipad endpoint table."
    INDEX   { ipadEndpointIndex }
    ::= { ipadEndpointTable 1 }

IpadEndpointTableEntry ::=
    SEQUENCE
    {
    ipadEndpointIndex        INTEGER,
    ipadEndpointName         DisplayString,
    ipadEndpointService      INTEGER,
    ipadEndpointDLCInumber   INTEGER,
    ipadEndpointType         INTEGER,
    ipadEndpointForward      INTEGER,
    ipadEndpointBackup       INTEGER,
    ipadEndpointRefSLP       INTEGER,
    ipadEndpointRemoteIpAddr IpAddress,
    ipadEndpointRemoteIpMask IpAddress
    }

ipadEndpointIndex    OBJECT-TYPE
    SYNTAX  INTEGER
    MAX-ACCESS  read-only
    STATUS  current
    DESCRIPTION
        "The index into the ipad endpoint table."
    ::= { ipadEndpointTableEntry 1 }

ipadEndpointName    OBJECT-TYPE
    SYNTAX  DisplayString ( SIZE(0..11) )
    MAX-ACCESS  read-write
    STATUS  current
    DESCRIPTION
        "The name for the endpoint."
    ::= { ipadEndpointTableEntry 2 }

ipadEndpointService    OBJECT-TYPE
    SYNTAX  INTEGER
    MAX-ACCESS  read-write
    STATUS  current
    DESCRIPTION
        "An index into the ipad service table."
    ::= { ipadEndpointTableEntry 3 }

ipadEndpointDLCInumber    OBJECT-TYPE
    SYNTAX  INTEGER
    MAX-ACCESS  read-write
    STATUS  current
    DESCRIPTION
        "Data link connection identifier for this endpoint;
            The DLCI number for this entry."
    ::= { ipadEndpointTableEntry 4 }

ipadEndpointType    OBJECT-TYPE
    SYNTAX  INTEGER
    {
    other(1),
    frLocal(2),
    frSwitched(3),
    ipRoute(4)
    }
    MAX-ACCESS  read-write
    STATUS  current
    DESCRIPTION
        "Endpoint type."
    ::= { ipadEndpointTableEntry 5 }

ipadEndpointForward    OBJECT-TYPE
    SYNTAX  INTEGER
    MAX-ACCESS  read-write
    STATUS  current
    DESCRIPTION
        "Index into the endpoint names table.  This is the endpoint
        on which data should be forwarded for switched endpoints." 
    ::= { ipadEndpointTableEntry 6 }

ipadEndpointBackup    OBJECT-TYPE
    SYNTAX  INTEGER
    MAX-ACCESS  read-write
    STATUS  current
    DESCRIPTION
        "Index into the endpoint table.  This is the endpoint
        on which data should be forwarded in the case where the
        endpoint becomes inactive."
    ::= { ipadEndpointTableEntry 7 }

ipadEndpointRefSLP    OBJECT-TYPE
    SYNTAX  INTEGER
    MAX-ACCESS  read-write
    STATUS  current
    DESCRIPTION
        "Index into the endpoint table.  The service level parameters
        can be copied from another configured endpoint."
    ::= { ipadEndpointTableEntry 8 }

ipadEndpointRemoteIpAddr    OBJECT-TYPE
    SYNTAX  IpAddress
    MAX-ACCESS  read-write
    STATUS  current
    DESCRIPTION
        "IP address for remote."
    ::= { ipadEndpointTableEntry 9 }

ipadEndpointRemoteIpMask    OBJECT-TYPE
    SYNTAX  IpAddress
    MAX-ACCESS  read-write
    STATUS  current
    DESCRIPTION
        "IP address mask for remote."
    ::= { ipadEndpointTableEntry 10 }

ipadEndpointAddEndpoint OBJECT-TYPE
    SYNTAX  DisplayString( SIZE(0..11) )
    MAX-ACCESS  read-write
    STATUS  current
    DESCRIPTION
        "Identifies an Endpoint to be added."
    ::= { ipadEndpoint 2 }

ipadEndpointDeleteEndpoint OBJECT-TYPE
    SYNTAX  DisplayString( SIZE(0..11) )
    MAX-ACCESS  read-write
    STATUS  current
    DESCRIPTION
        "Identifies an Endpoint to be deleted."
    ::= { ipadEndpoint 3 }

ipadEndpointLastChange OBJECT-TYPE
    SYNTAX  TimeTicks
    MAX-ACCESS  read-only
    STATUS  current
    DESCRIPTION
        "Time of the last change in the Endpoint table."
    ::= { ipadEndpoint 4 }

-- ipadUser section
-- contains the User table

ipadUserTable    OBJECT-TYPE
    SYNTAX  SEQUENCE OF IpadUserTableEntry
    MAX-ACCESS  not-accessible
    STATUS  current
    DESCRIPTION
        "Table of user selected parameters."
    ::= { ipadUser 1 }

ipadUserTableEntry    OBJECT-TYPE
    SYNTAX  IpadUserTableEntry
    MAX-ACCESS  not-accessible
    STATUS  current
    DESCRIPTION
        "An entry in the ipad user table."
    INDEX   { ipadUserIndex }
    ::= { ipadUserTable 1 }

IpadUserTableEntry ::=
    SEQUENCE
    {
    ipadUserIndex               INTEGER,
    ipadUserFilterByDLCI        INTEGER,
    ipadUserService             INTEGER,
    ipadUserDLCI                INTEGER,
    ipadUserFilterByIPAddress   INTEGER,
    ipadUserIPAddress           IpAddress,
    ipadUserIPMask              IpAddress,
    ipadUserFilterByIPPort      INTEGER,
    ipadUserIPPort              INTEGER,
    ipadUserTxAlmThreshold      INTEGER,
    ipadUserTxAlmAlarm          INTEGER,
    ipadUserAlarmReset          INTEGER,
    ipadUserVpi			INTEGER,
    ipadUserVci			INTEGER,
    ipadUserFilterByVpiVci	INTEGER
    }

ipadUserIndex    OBJECT-TYPE
    SYNTAX  INTEGER
    MAX-ACCESS  read-only
    STATUS  current
    DESCRIPTION
        "Index into the ipad user table."
    ::= { ipadUserTableEntry 1 }

ipadUserFilterByDLCI    OBJECT-TYPE
    SYNTAX  INTEGER
    {
    disabled(1),
    enabled(2)
    }
    MAX-ACCESS  read-write
    STATUS  current
    DESCRIPTION
        "Enables Service+DLCI filtering for this user statistic."
    ::= { ipadUserTableEntry 2 }

ipadUserService    OBJECT-TYPE
    SYNTAX  INTEGER
    MAX-ACCESS  read-write
    STATUS  current
    DESCRIPTION
        "Specifies the service for this user type; identifies an entry in the
        ipad DLCI table when combined with ipadUserDLCI.  Meaningful when 
        ipadUserFilterByDLCI is enabled.  Meaningless when collecting
        PPP statistics."
    ::= { ipadUserTableEntry 3 }
    
ipadUserDLCI    OBJECT-TYPE
    SYNTAX  INTEGER
    MAX-ACCESS  read-write
    STATUS  current
    DESCRIPTION
        "Specifies the DLCI for this user type; identifies an entry in the
        ipad DLCI table when combined with ipadUserService.   Meaningful when 
        ipadUserFilterByDLCI is enabled.  Meaningless when collecting
        PPP statistics."
    ::= { ipadUserTableEntry 4 }

ipadUserFilterByIPAddress   OBJECT-TYPE
    SYNTAX  INTEGER
    {
    disabled(1),
    enabled(2)
    }
    MAX-ACCESS  read-write
    STATUS  current
    DESCRIPTION
        "Enables IP address filtering for this user statistic.  A
        packet is counted towards the user statistics if the
        result of a bitwise-and of an IP address in a transmitted
        packet with ipadUserIPMask equals ipadUserIPAddress."
    ::= { ipadUserTableEntry 5 }

ipadUserIPAddress    OBJECT-TYPE
    SYNTAX  IpAddress
    MAX-ACCESS  read-write
    STATUS  current
    DESCRIPTION
        "Specifies the IP address for this user type." 
    ::= { ipadUserTableEntry 6 }
    
ipadUserIPMask          OBJECT-TYPE
    SYNTAX  IpAddress
    MAX-ACCESS  read-write
    STATUS  current
    DESCRIPTION
        "Specifies the IP address mask for this user type."
    ::= { ipadUserTableEntry 7 }

ipadUserFilterByIPPort    OBJECT-TYPE
    SYNTAX  INTEGER
    {
    disabled(1),
    enabled(2)
    }
    MAX-ACCESS  read-write
    STATUS  current
    DESCRIPTION
        "Enables IP Port filtering for this user statistic."
    ::= { ipadUserTableEntry 8 }

ipadUserIPPort          OBJECT-TYPE
    SYNTAX  INTEGER
    {
    rje(5),
    echo(7),
    systat(11),
    qotd(17),
    ftpdata(20),
    ftp(21),
    telnet(23),
    smtp(25),
    msgauth(31),
    time(37),
    nameserver(42),
    domain(53),
    sqlnet(66),
    tftp(69),
    gopher(70),
    finger(79),
    http(80),
    kerberos(88),
    npp(92),
    hostname(101),
    rtelnet(107),
    pop2(109),
    pop3(110),
    sunrpc(111),
    auth(113),
    nntp(119),
    netbiosns(137),
    netbiosdgm(138),
    netbiosssn(139),
    sgmp(153),
    snmp(161),
    snmptrap(162),
    cmipman(163),
    cmipagent(164),
    send(169),
    bgp(179),
    irc(194),
    atrtmp(201),
    atnbp(202),
    atecho(204),
    atzis(206),
    ipx(213),
    netcp(395),
    netwareip(396),
    snpp(444),
    povray(494),
    netwall(533),
    uucp(540),
    uucprlogin(541),
    ipcserver(600),
    kerberosadm(749)
    }
    MAX-ACCESS  read-write
    STATUS  current
    DESCRIPTION
        "Specifies the IP port for this user type."
    ::= { ipadUserTableEntry 9 }
    
ipadUserTxAlmThreshold    OBJECT-TYPE
    SYNTAX  INTEGER
    MAX-ACCESS  read-write
    STATUS  current
    DESCRIPTION     
        "Sets the tx throughput alarm threshold in 
        bits per second.  Setting this field to 0 
        disables the alarm."
    ::= { ipadUserTableEntry 10 }

ipadUserTxAlmAlarm    OBJECT-TYPE
    SYNTAX  INTEGER
    {
    other(1),
    noAlarm(2),
    thresholdExceeded(3)
    }
    MAX-ACCESS  read-only
    STATUS  current
    DESCRIPTION
        "Reports if the tx throughput threshold has been exceeded."
    ::= { ipadUserTableEntry 11 }

ipadUserAlarmReset OBJECT-TYPE
	SYNTAX  INTEGER
		{
		userAlarmResetOther(1),
		userAlarmResetClearAlarms(2),
		userAlarmResetClearStats(3)
		}
	MAX-ACCESS  read-write
	STATUS  current
	DESCRIPTION     
		"This is used to clear the current alarm counts."
	::= { ipadUserTableEntry 12 }

ipadUserVpi    OBJECT-TYPE
    SYNTAX  INTEGER
    MAX-ACCESS  read-write
    STATUS  current
    DESCRIPTION
        "Specifies the Vpi for this user type; identifies a VC when combined
        with the ipadUserService and ipadUserVci objects.  Meaningful when 
        ipadUserFilterByVpiVci is enabled.  Meaningless when collecting
        PPP or Frame Relay statistics."
    ::= { ipadUserTableEntry 13 }
    
ipadUserVci    OBJECT-TYPE
    SYNTAX  INTEGER
    MAX-ACCESS  read-write
    STATUS  current
    DESCRIPTION
        "Specifies the Vci for this user type; identifies a VC when combined
        with the ipadUserService and ipadUserVpi objects.  Meaningful when 
        ipadUserFilterByVpiVci is enabled.  Meaningless when collecting
        PPP or Frame Relay statistics."
    ::= { ipadUserTableEntry 14 }

ipadUserFilterByVpiVci   OBJECT-TYPE
    SYNTAX  INTEGER
    {
    disabled(1),
    enabled(2)
    }
    MAX-ACCESS  read-write
    STATUS  current
    DESCRIPTION
        "Enables Vpi/Vci filtering for this user statistic.  A
        packet is counted towards the user statistics if the packet
        is transmitted on the service/Vpi/Vci combindation specified by
        ipadUserService, ipadUserVpi, and ipadUserVci."
    ::= { ipadUserTableEntry 15 }


ipadUserIPStatTimeRemaining OBJECT-TYPE
    SYNTAX  INTEGER
    MAX-ACCESS  read-write
    STATUS  current
    DESCRIPTION
        "Specifies seconds until the next IP TopN report is generated."
    ::= { ipadUser 2 }

ipadUserIPStatTimeDuration OBJECT-TYPE
    SYNTAX  INTEGER
    MAX-ACCESS  read-only
    STATUS  current
    DESCRIPTION
        "The value of TimeRemaining when TimeRemaining was last set.  Indicates
         the number of seconds that the next IP TopN report will cover."
    ::= { ipadUser 3 }
    
ipadUserIPStatStartTime OBJECT-TYPE
    SYNTAX   TimeTicks
    MAX-ACCESS   read-only
    STATUS   current
    DESCRIPTION
        "The value of SysUpTime when TimeRemaining was last set."
    ::= { ipadUser 4 }
    
ipadUserIPStatRequestedReportSize OBJECT-TYPE
    SYNTAX  INTEGER
    MAX-ACCESS  read-write
    STATUS  current
    DESCRIPTION
        "Determines the requested maximum number of entries in the 
        topN report." 
    ::= { ipadUser 5 }

ipadUserIPStatGrantedReportSize OBJECT-TYPE
    SYNTAX  INTEGER
    MAX-ACCESS  read-only
    STATUS  current
    DESCRIPTION
        "Determines the granted number of entries in the 
        topN report.  This is by definition less than or equal
        to requested report size." 
    ::= { ipadUser 6 }

ipadUserIPStatReportNumber OBJECT-TYPE
    SYNTAX  INTEGER
    MAX-ACCESS  read-only
    STATUS  current
    DESCRIPTION
        "Specifies the number of reports that have been generated.
        This value resets to zero when the unit is restarted."
    ::= { ipadUser 7 }    

ipadUserIPStatDiscardType OBJECT-TYPE
    SYNTAX  INTEGER
    {
    byTime(1),
    byFrames(2),
    byOctets(3)
    }
    MAX-ACCESS  read-write
    STATUS  current
    DESCRIPTION
        "The internal table used to track TopN statistics is
        finite in size.  On the condition when the internal table
        is full and a new IP address is encountered, an element
        already existing in the table must be removed.  This
        variable determines the manner of selection.  Writing
        byTime(1) will cause the entry with the least recent
        frame to be discarded.  That is, all other entries in the
        table will have transmitted or received at least one packet
        more recently.  Writing byFrames(2) will select the entry
        with the fewest transmitted or received frames.  Writing
        byOctets(3) will select the entry with the fewest transmitted
        or received octets.  The default is byTime(1)."
    ::= { ipadUser 8 }

-- ipadPPP section
-- This section contains the IPAD PPP configuration and statistics tables

ipadPPPCfgTable    OBJECT-TYPE
    SYNTAX  SEQUENCE OF IpadPPPCfgTableEntry
    MAX-ACCESS  not-accessible
    STATUS  current
    DESCRIPTION
        "The ipad PPP configuration table."
    ::= { ipadPPP 1 }

ipadPPPCfgTableEntry    OBJECT-TYPE
    SYNTAX  IpadPPPCfgTableEntry
    MAX-ACCESS  not-accessible
    STATUS  current
    DESCRIPTION
        "An entry in the ipad PPP configuration table."
    INDEX   { ipadPPPCfgService }
    ::= { ipadPPPCfgTable 1 }

IpadPPPCfgTableEntry ::=
    SEQUENCE
    {
    ipadPPPCfgService               INTEGER,
    ipadPPPCfgDialMode              INTEGER,
    ipadPPPCfgInactivityTimer       INTEGER,
    ipadPPPCfgNegotiationInit       INTEGER,
    ipadPPPCfgMRU                   INTEGER,
    ipadPPPCfgACCM                  INTEGER,
    ipadPPPCfgNegMRU                INTEGER,
    ipadPPPCfgNegACCM               INTEGER,
    ipadPPPCfgNegMagic              INTEGER,
    ipadPPPCfgNegCompression        INTEGER,
    ipadPPPCfgNegAddress            INTEGER,
    ipadPPPCfgNegPAP                INTEGER,
    ipadPPPCfgNegCHAP               INTEGER,
    ipadPPPCfgAllowPAP              INTEGER,
    ipadPPPCfgAllowCHAP             INTEGER,
    ipadPPPCfgPAPUsername           DisplayString,
    ipadPPPCfgPAPPassword           DisplayString,
    ipadPPPCfgCHAPUsername          DisplayString,
    ipadPPPCfgCHAPSecret            DisplayString,
    ipadPPPCfgPortIpAddress         IpAddress,
    ipadPPPCfgPeerIpAddress         IpAddress,
    ipadPPPCfgNegIpAddress          INTEGER,
    ipadPPPCfgNegIPCPCompression    INTEGER,
    ipadPPPCfgSubnetMask            IpAddress,
    ipadPPPCfgAuthChallengeInterval INTEGER,
    ipadPPPCfgEndpoint              DisplayString,
    ipadPPPCfgNegIpMask             INTEGER,
    ipadPPPCfgNegDNSAddress         INTEGER
    }

ipadPPPCfgService     OBJECT-TYPE
    SYNTAX  INTEGER
    MAX-ACCESS  read-only
    STATUS  current
    DESCRIPTION
        "The index into the PPP configuration table;
        an entry in the ipad service table."
    ::= { ipadPPPCfgTableEntry 1 }

ipadPPPCfgDialMode    OBJECT-TYPE
    SYNTAX  INTEGER
    {
    other(1),
    direct(2),
    dialup(3),
    demanddial(4)
    }
    MAX-ACCESS  read-write
    STATUS  current
    DESCRIPTION
        "Determines the permancency of a communications connection."
    ::= { ipadPPPCfgTableEntry 2 }

ipadPPPCfgInactivityTimer    OBJECT-TYPE
    SYNTAX  INTEGER
    MAX-ACCESS  read-write
    STATUS  current
    DESCRIPTION
        "Determines when a dial-up or demand-dial connection will be
        disconnected due to inactivity in both directions.  When this
        parameter is set to zero then the timer is disabled."
    ::= { ipadPPPCfgTableEntry 3 }

ipadPPPCfgNegotiationInit    OBJECT-TYPE
    SYNTAX  INTEGER
    {
    other(1),
    no(2),
    yes(3)
    }
    MAX-ACCESS  read-write
    STATUS  current
    DESCRIPTION
        "Determines if the port waits for the other end to initiate
        parameter negotiations."
    ::= { ipadPPPCfgTableEntry 4 }

ipadPPPCfgMRU    OBJECT-TYPE
    SYNTAX  INTEGER
    MAX-ACCESS  read-write
    STATUS  current
    DESCRIPTION
        "The maximum receive unit the interface will accept.  Valid values
        are in the range 128 - 4096, default is 1500."
    ::= { ipadPPPCfgTableEntry 5 }

ipadPPPCfgACCM    OBJECT-TYPE
    SYNTAX  INTEGER
    MAX-ACCESS  read-write
    STATUS  current
    DESCRIPTION
        "Sets the async control character map used when generating
        async HDLC frames.  Setting a bit in the map causes the
        corresponding character to be mapped for transparency."
    ::= { ipadPPPCfgTableEntry 6 }

ipadPPPCfgNegMRU    OBJECT-TYPE
    SYNTAX  INTEGER
    {
    other(1),
    no(2),
    yes(3)
    }
    MAX-ACCESS  read-write
    STATUS  current
    DESCRIPTION
        "Determines if MRU size is negotiated."
    ::= { ipadPPPCfgTableEntry 7 }

ipadPPPCfgNegACCM    OBJECT-TYPE
    SYNTAX  INTEGER
    {
    other(1),
    no(2),
    yes(3)
    }
    MAX-ACCESS  read-write
    STATUS  current
    DESCRIPTION
        "Determines if ACCM is negotiated."
    ::= { ipadPPPCfgTableEntry 8 }

ipadPPPCfgNegMagic    OBJECT-TYPE
    SYNTAX  INTEGER
    {
    other(1),
    no(2),
    yes(3)
    }
    MAX-ACCESS  read-write
    STATUS  current
    DESCRIPTION
        "Determines if the magic number is negotiated."
    ::= { ipadPPPCfgTableEntry 9 }

ipadPPPCfgNegCompression    OBJECT-TYPE
    SYNTAX  INTEGER
    {
    other(1),
    no(2),
    yes(3)
    }
    MAX-ACCESS  read-write
    STATUS  current
    DESCRIPTION
        "Determines if the PPP protocol header compression is negotiated."
    ::= { ipadPPPCfgTableEntry 10 }

ipadPPPCfgNegAddress    OBJECT-TYPE
    SYNTAX  INTEGER
    {
    other(1),
    no(2),
    yes(3)
    }
    MAX-ACCESS  read-write
    STATUS  current
    DESCRIPTION
        "Determines if the PPP HDLC header compression is negotiated."
    ::= { ipadPPPCfgTableEntry 11 }

ipadPPPCfgNegPAP    OBJECT-TYPE
    SYNTAX  INTEGER
    {
    other(1),
    no(2),
    yes(3)
    }
    MAX-ACCESS  read-write
    STATUS  current
    DESCRIPTION
        "Determines if PAP is negotiated with the peer when a more secure
        authentication protocol is rejected."
    ::= { ipadPPPCfgTableEntry 12 }

ipadPPPCfgNegCHAP    OBJECT-TYPE
    SYNTAX  INTEGER
    {
    other(1),
    no(2),
    yes(3)
    }
    MAX-ACCESS  read-write
    STATUS  current
    DESCRIPTION
        "Determines if CHAP is negotiated with the peer when a more secure
        authentication protocol is rejected."
    ::= { ipadPPPCfgTableEntry 13 }

ipadPPPCfgAllowPAP    OBJECT-TYPE
    SYNTAX  INTEGER
    {
    other(1),
    no(2),
    yes(3)
    }
    MAX-ACCESS  read-write
    STATUS  current
    DESCRIPTION
        "Determines if PAP is allowed to be negotiated by the peer."
    ::= { ipadPPPCfgTableEntry 14 }

ipadPPPCfgAllowCHAP    OBJECT-TYPE
    SYNTAX  INTEGER
    {
    other(1),
    no(2),
    yes(3)
    }
    MAX-ACCESS  read-write
    STATUS  current
    DESCRIPTION
        "Determines if CHAP is allowed to be negotiated by the peer."
    ::= { ipadPPPCfgTableEntry 15 }

ipadPPPCfgPAPUsername    OBJECT-TYPE
    SYNTAX  DisplayString ( SIZE(0..30) )
    MAX-ACCESS  read-write
    STATUS  current
    DESCRIPTION
        "Identification string to determine the user identity."
    ::= { ipadPPPCfgTableEntry 16 }

ipadPPPCfgPAPPassword    OBJECT-TYPE
    SYNTAX  DisplayString ( SIZE(0..30) )
    MAX-ACCESS  read-write
    STATUS  current
    DESCRIPTION
        "Password string to validate the user identity."
    ::= { ipadPPPCfgTableEntry 17 }

ipadPPPCfgCHAPUsername    OBJECT-TYPE
    SYNTAX  DisplayString ( SIZE(0..30) )
    MAX-ACCESS  read-write
    STATUS  current
    DESCRIPTION
        "Identification string to determine the user identity."
    ::= { ipadPPPCfgTableEntry 18 }

ipadPPPCfgCHAPSecret    OBJECT-TYPE
    SYNTAX  DisplayString ( SIZE(0..30) )
    MAX-ACCESS  read-write
    STATUS  current
    DESCRIPTION
        "Password string to validate the user identity."
    ::= { ipadPPPCfgTableEntry 19 }

ipadPPPCfgPortIpAddress    OBJECT-TYPE
    SYNTAX  IpAddress
    MAX-ACCESS  read-write
    STATUS  current
    DESCRIPTION
        "Sets the IP address of the unit's port."
    ::= { ipadPPPCfgTableEntry 20 }

ipadPPPCfgPeerIpAddress    OBJECT-TYPE
    SYNTAX  IpAddress
    MAX-ACCESS  read-write
    STATUS  current
    DESCRIPTION
        "Sets the IP address of the unit's peer."
    ::= { ipadPPPCfgTableEntry 21 }

ipadPPPCfgNegIpAddress    OBJECT-TYPE
    SYNTAX  INTEGER
    {
    other(1),
    no(2),
    yes(3)
    }
    MAX-ACCESS  read-write
    STATUS  current
    DESCRIPTION
        "Determines if IP addresses are dynamically negotiated."
    ::= { ipadPPPCfgTableEntry 22 }

ipadPPPCfgNegIPCPCompression    OBJECT-TYPE
    SYNTAX  INTEGER
    {
    other(1),
    no(2),
    yes(3)
    }
    MAX-ACCESS  read-write
    STATUS  current
    DESCRIPTION
        "Determines if Van Jacobson TCPIP header compression is negotiated."
    ::= { ipadPPPCfgTableEntry 23 }
    
ipadPPPCfgSubnetMask    OBJECT-TYPE
    SYNTAX  IpAddress
    MAX-ACCESS  read-write
    STATUS  current
    DESCRIPTION
        "Specifies the subnet mask."
    ::= { ipadPPPCfgTableEntry 24 }

ipadPPPCfgAuthChallengeInterval    OBJECT-TYPE
    SYNTAX  INTEGER
    MAX-ACCESS  read-write
    STATUS  current
    DESCRIPTION
        "Specifies the authentication challenge interval."
    ::= { ipadPPPCfgTableEntry 25 }

ipadPPPCfgEndpoint    OBJECT-TYPE
    SYNTAX  DisplayString ( SIZE(0..11) )
    MAX-ACCESS  read-write
    STATUS  current
    DESCRIPTION
        "Endpoint name to run PPP over another protocol."
    ::= { ipadPPPCfgTableEntry 26 }

ipadPPPCfgNegIpMask   OBJECT-TYPE
    SYNTAX  INTEGER
    {
    other(1),
    no(2),
    yes(3)
    }
    MAX-ACCESS  read-write
    STATUS  current
    DESCRIPTION
        "Determines if the subnet Mask is negotiated."
    ::= { ipadPPPCfgTableEntry 27 }

ipadPPPCfgNegDNSAddress OBJECT-TYPE
    SYNTAX  INTEGER
    {
    other(1),
    no(2),
    yes(3)
    }
    MAX-ACCESS  read-write
    STATUS  current
    DESCRIPTION
        "Determines if the DNS address is negotiated."
    ::= { ipadPPPCfgTableEntry 28 }

-- PPP PAP association table
-- common to all PPP interfaces

ipadPPPPAPTable    OBJECT-TYPE
    SYNTAX  SEQUENCE OF IpadPPPPAPTableEntry
    MAX-ACCESS  not-accessible
    STATUS  current
    DESCRIPTION
        "Table of PAP authentication parameters."
    ::= { ipadPPP 2 }

ipadPPPPAPTableEntry    OBJECT-TYPE
    SYNTAX  IpadPPPPAPTableEntry
    MAX-ACCESS  not-accessible
    STATUS  current
    DESCRIPTION
        "An entry in the ipad PPP PAP table."
    INDEX   { ipadPPPPAPTableIndex }
    ::= { ipadPPPPAPTable 1 }

IpadPPPPAPTableEntry ::=
    SEQUENCE
    {
    ipadPPPPAPTableIndex        INTEGER,
    ipadPPPPAPTableUsername     DisplayString,
    ipadPPPPAPTablePassword     DisplayString
    }

ipadPPPPAPTableIndex    OBJECT-TYPE
    SYNTAX  INTEGER
    MAX-ACCESS  read-only
    STATUS  current
    DESCRIPTION
        "The index into the PPP PAP association table."
    ::= { ipadPPPPAPTableEntry 1 }

ipadPPPPAPTableUsername    OBJECT-TYPE
    SYNTAX  DisplayString ( SIZE(0..30) )
    MAX-ACCESS  read-write
    STATUS  current
    DESCRIPTION
        "Identification string to identify the user."
    ::= { ipadPPPPAPTableEntry 2 }

ipadPPPPAPTablePassword    OBJECT-TYPE
    SYNTAX  DisplayString ( SIZE(0..30) )
    MAX-ACCESS  read-write
    STATUS  current
    DESCRIPTION
        "Password string to validate the user identity."
    ::= { ipadPPPPAPTableEntry 3 }

-- PPP CHAP association table
-- common to all PPP interfaces

ipadPPPCHAPTable    OBJECT-TYPE
    SYNTAX  SEQUENCE OF IpadPPPCHAPTableEntry
    MAX-ACCESS  not-accessible
    STATUS  current
    DESCRIPTION
        "Table of CHAP authentication parameters."
    ::= { ipadPPP 3 }

ipadPPPCHAPTableEntry    OBJECT-TYPE
    SYNTAX  IpadPPPCHAPTableEntry
    MAX-ACCESS  not-accessible
    STATUS  current
    DESCRIPTION
        "An entry in the ipad PPP CHAP table."
    INDEX   { ipadPPPCHAPTableIndex }
    ::= { ipadPPPCHAPTable 1 }

IpadPPPCHAPTableEntry ::=
    SEQUENCE
    {
    ipadPPPCHAPTableIndex       INTEGER,
    ipadPPPCHAPTableUsername    DisplayString,
    ipadPPPCHAPTableSecret      DisplayString
    }

ipadPPPCHAPTableIndex    OBJECT-TYPE
    SYNTAX  INTEGER
    MAX-ACCESS  read-only
    STATUS  current
    DESCRIPTION
        "The index into the PPP CHAP association table."
    ::= { ipadPPPCHAPTableEntry 1 }

ipadPPPCHAPTableUsername    OBJECT-TYPE
    SYNTAX  DisplayString ( SIZE(0..30) )
    MAX-ACCESS  read-write
    STATUS  current
    DESCRIPTION
        "Identification string to identify the user."
    ::= { ipadPPPCHAPTableEntry 2 }

ipadPPPCHAPTableSecret    OBJECT-TYPE
    SYNTAX  DisplayString ( SIZE(0..30) )
    MAX-ACCESS  read-write
    STATUS  current
    DESCRIPTION
        "Password string to validate the user identity."
    ::= { ipadPPPCHAPTableEntry 3 }




-- ----------------------------------------------------------------------
-- ipadModem Dialing parameters
-- parameters needed by a port that can connect to a modem
-- ----------------------------------------------------------------------




ipadModemDialTable	OBJECT-TYPE
	SYNTAX  SEQUENCE OF IpadModemDialTableEntry
	MAX-ACCESS  not-accessible
	STATUS  current
	DESCRIPTION
		"Table of modem dialing parameters."
	::= { ipadModem 1 }

ipadModemDialTableEntry	OBJECT-TYPE
	SYNTAX  IpadModemDialTableEntry
	MAX-ACCESS  not-accessible
	STATUS  current
	DESCRIPTION
		"An entry in the ipad modem dialing parameters table."
	INDEX   { ipadModemDialTableIndex }
	::= { ipadModemDialTable 1 }

IpadModemDialTableEntry ::=
	SEQUENCE
	{
		ipadModemDialTableIndex			INTEGER,
		ipadModemDialDataIndex			INTEGER,
		ipadModemDialNumber			DisplayString,
		ipadModemDialAbortTimer			INTEGER,
		ipadModemDialRedialAttempts		INTEGER,
		ipadModemDialDelayBeforeRedial		INTEGER,
		ipadModemDialLoginScript		DisplayString,
		ipadModemDialUsername			DisplayString,
		ipadModemDialPassword			DisplayString,
		ipadModemDialChallengeScript		DisplayString,
		ipadModemDialAnswerRings		INTEGER,
		ipadModemDialCommand			INTEGER,
		ipadModemDialStatus			INTEGER,
		ipadModemDialSecurity			INTEGER,
		ipadModemDialCallbackRedialDelay	INTEGER,
		ipadModemDialCallbackTimeout		INTEGER,
		ipadModemDialCallbackChalScript		DisplayString,
		ipadModemDialCallbackRspScript		DisplayString
	}

ipadModemDialTableIndex	OBJECT-TYPE
	SYNTAX  INTEGER
	MAX-ACCESS  read-only
	STATUS  current
	DESCRIPTION
		"The index into the ipad modem dialing parameters table.
		Equivalent to MIB-II ifIndex."
	::= { ipadModemDialTableEntry 1 }

ipadModemDialDataIndex	OBJECT-TYPE
	SYNTAX  INTEGER
	MAX-ACCESS  read-write
	STATUS  current
	DESCRIPTION
		"An index into the Modem Data Table, which selects a modem."
	::= { ipadModemDialTableEntry 2 }

ipadModemDialNumber	OBJECT-TYPE
	SYNTAX  DisplayString ( SIZE(0..60) )
	MAX-ACCESS  read-write
	STATUS  current
	DESCRIPTION
		"Specifies the telephone number to dial."
	::= { ipadModemDialTableEntry 3 }

ipadModemDialAbortTimer	OBJECT-TYPE
	SYNTAX  INTEGER
	MAX-ACCESS  read-write
	STATUS  current
	DESCRIPTION
		"Aborts a connection attempt if a dial-up connection has failed to connect within the specified number of seconds.
		Range is 1..255."
	::= { ipadModemDialTableEntry 4 }

ipadModemDialRedialAttempts	OBJECT-TYPE
	SYNTAX  INTEGER
	MAX-ACCESS  read-write
	STATUS  current
	DESCRIPTION
		"Determines how many attempts to initiate a dial-up connection after the initial failure.
		Range is 0..10."
	::= { ipadModemDialTableEntry 5 }

ipadModemDialDelayBeforeRedial	OBJECT-TYPE
	SYNTAX  INTEGER
	MAX-ACCESS  read-write
	STATUS  current
	DESCRIPTION
		"Specifies the number of seconds to wait before redialing.
		Range is 1..255."
	::= { ipadModemDialTableEntry 6 }

ipadModemDialLoginScript	OBJECT-TYPE
	SYNTAX  DisplayString ( SIZE(0..60) )
	MAX-ACCESS  read-write
	STATUS  current
	DESCRIPTION
		"Script string interpreted after an originated dial-up connection is first established."
	::= { ipadModemDialTableEntry 7 }

ipadModemDialUsername	OBJECT-TYPE
	SYNTAX  DisplayString ( SIZE(0..30) )
	MAX-ACCESS  read-write
	STATUS  current
	DESCRIPTION
		"Identification string to determine the user identity."
	::= { ipadModemDialTableEntry 8 }

ipadModemDialPassword	OBJECT-TYPE
	SYNTAX  DisplayString ( SIZE(0..30) )
	MAX-ACCESS  read-write
	STATUS  current
	DESCRIPTION
		"Password string to validate the user identity."
	::= { ipadModemDialTableEntry 9 }

ipadModemDialChallengeScript	OBJECT-TYPE
	SYNTAX  DisplayString ( SIZE(0..60) )
	MAX-ACCESS  read-write
	STATUS  current
	DESCRIPTION
		"Script string interpreted after an answered dial-up connection is first established."
	::= { ipadModemDialTableEntry 10 }

ipadModemDialAnswerRings	OBJECT-TYPE
	SYNTAX  INTEGER
	MAX-ACCESS  read-write
	STATUS  current
	DESCRIPTION
		"Answers an incoming call on the given number of rings.
		A value of zero disables answering.
		Range is 0..255."
	::= { ipadModemDialTableEntry 11 }

ipadModemDialCommand	OBJECT-TYPE
	SYNTAX  INTEGER
	{
		other(1),
		setupNow(2),
		dialNow(3),
		answerNow(4),
		disconnectNow(5)
	}
	MAX-ACCESS  read-write
	STATUS  current
	DESCRIPTION
		"The set values perform the following actions:
		setupNow - Execute the modem setup scripts
		dialNow - Initiate dialing procedures
		answerNow - Initiate answering procedures
		disconnectNow - Initiate disconnect procedures"
	::= { ipadModemDialTableEntry 12 }

ipadModemDialStatus	OBJECT-TYPE
	SYNTAX  INTEGER
	{
		other(1),
		disabled(2),
		idle(3),
		dialing(4),
		answering(5),
		negotiating(6),
		online(7),
		disconnecting(8),
		error(9),
		setup(10),
		awaitingCallback(11),
		dialWait(12),
		ringing(13)
	}
	MAX-ACCESS  read-only
	STATUS  current
	DESCRIPTION
		"This object reports the current activity of the modem control feature

		disabled - The feature is not enabled
		setup - The feature is configuring the modem
		error - The feature could not setup the modem
		idle - The feature is ready to operate
		dialing - The feature is placing a call
		dialWait - The feature is between call attempts
		ringing - The feature is waiting for an incoming call to connect or go away
		answering - The feature is answering a call
		negotiating - The feature is negotiating the login security
		online - The feature data path is connected
		disconnecting - The feature is disconnecting a call
		awaitingCallback - The feature is waiting for a security callback"
	::= { ipadModemDialTableEntry 13 }

ipadModemDialSecurity	OBJECT-TYPE
	SYNTAX  INTEGER
	{
		other(1),
		disable(2),
		password(3),
		callback(4),
		callbackVerify(5)
	}
	MAX-ACCESS  read-write
	STATUS  current
	DESCRIPTION
		"disable - Dial-up security not enabled
		password - Challenge/Login password scripts used
		callback - Password security followed by answerer calling back
		callbackVerify - Callback and verify using the callback challenge/response scripts"
	::= { ipadModemDialTableEntry 14 }

ipadModemDialCallbackRedialDelay	OBJECT-TYPE
	SYNTAX  INTEGER
	MAX-ACCESS  read-write
	STATUS  current
	DESCRIPTION
		"Specifies the number of seconds to wait before redialing.
		Range is 1..255."
	::= { ipadModemDialTableEntry 15 }

ipadModemDialCallbackTimeout	OBJECT-TYPE
	SYNTAX  INTEGER
	MAX-ACCESS  read-write
	STATUS  current
	DESCRIPTION
		"This object sets the number of seconds to wait for a security callback before failing the connection attempt."
	::= { ipadModemDialTableEntry 16 }

ipadModemDialCallbackChalScript	OBJECT-TYPE
	SYNTAX  DisplayString ( SIZE(0..60) )
	MAX-ACCESS  read-write
	STATUS  current
	DESCRIPTION
		"Callback security challenge script interpreted after originating a callback dial-up connection."
	::= { ipadModemDialTableEntry 17 }

ipadModemDialCallbackRspScript	OBJECT-TYPE
	SYNTAX  DisplayString ( SIZE(0..60) )
	MAX-ACCESS  read-write
	STATUS  current
	DESCRIPTION
		"Callback security challenge response script interpreted after answering a callback dial-up connection."
	::= { ipadModemDialTableEntry 18 }




-- ----------------------------------------------------------------------
-- Modem Database parameters
-- modem characterization parameters, global to all modem interfaces.
-- ----------------------------------------------------------------------




ipadModemDataTable	OBJECT-TYPE
	SYNTAX  SEQUENCE OF IpadModemDataTableEntry
	MAX-ACCESS  not-accessible
	STATUS  current
	DESCRIPTION
		"Table of modem database parameters."
	::= { ipadModem 2 }

ipadModemDataTableEntry	OBJECT-TYPE
	SYNTAX  IpadModemDataTableEntry
	MAX-ACCESS  not-accessible
	STATUS  current
	DESCRIPTION
		"An entry in the ipad modem database parameters table."
	INDEX   { ipadModemDataTableIndex }
	::= { ipadModemDataTable 1 }

IpadModemDataTableEntry ::=
	SEQUENCE
	{
		ipadModemDataTableIndex		INTEGER,
		ipadModemDataModemName		DisplayString,
		ipadModemDataSetupScript	DisplayString,
		ipadModemDataDialingScript	DisplayString,
		ipadModemDataAnswerScript	DisplayString,
		ipadModemDataHangupScript	DisplayString,
		ipadModemDataSyncScript		DisplayString,
		ipadModemDataSyncMethod		INTEGER,
		ipadModemDataSetupScript2	DisplayString,
		ipadModemDataSetupScript3	DisplayString,
		ipadModemDataSetupScript4	DisplayString,
		ipadModemDataSetupScript5	DisplayString
	}

ipadModemDataTableIndex	OBJECT-TYPE
	SYNTAX  INTEGER
	MAX-ACCESS  read-only
	STATUS  current
	DESCRIPTION
		"The index into the ipad modem database parameters table."
	::= { ipadModemDataTableEntry 1 }

ipadModemDataModemName	OBJECT-TYPE
	SYNTAX  DisplayString ( SIZE(0..10) )
	MAX-ACCESS  read-write
	STATUS  current
	DESCRIPTION
		"Identification string for the modem database."
	::= { ipadModemDataTableEntry 2 }

ipadModemDataSetupScript	OBJECT-TYPE
	SYNTAX  DisplayString ( SIZE(0..60) )
	MAX-ACCESS  read-write
	STATUS  current
	DESCRIPTION
		"First script interpreted when a modem port is initialized."
	::= { ipadModemDataTableEntry 3 }

ipadModemDataDialingScript	OBJECT-TYPE
	SYNTAX  DisplayString ( SIZE(0..60) )
	MAX-ACCESS  read-write
	STATUS  current
	DESCRIPTION
		"Script interpreted when a dial-up connection is initiated."
	::= { ipadModemDataTableEntry 4 }

ipadModemDataAnswerScript	OBJECT-TYPE
	SYNTAX  DisplayString ( SIZE(0..60) )
	MAX-ACCESS  read-write
	STATUS  current
	DESCRIPTION
		"Script interpreted when a modem port decides to answer an incoming call."
	::= { ipadModemDataTableEntry 5 }

ipadModemDataHangupScript	OBJECT-TYPE
	SYNTAX  DisplayString ( SIZE(0..60) )
	MAX-ACCESS  read-write
	STATUS  current
	DESCRIPTION
		"Script interpreted when a dial-up connection is no longer needed."
	::= { ipadModemDataTableEntry 6 }

ipadModemDataSyncScript	OBJECT-TYPE
	SYNTAX  DisplayString ( SIZE(0..60) )
	MAX-ACCESS  read-write
	STATUS  current
	DESCRIPTION
		"Script interpreted to configure the modem to pass synchronous data."
	::= { ipadModemDataTableEntry 7 }

ipadModemDataSyncMethod	OBJECT-TYPE
	SYNTAX  INTEGER
	{
		other(1),
		none(2),
		sync(3),
		v80(4),
		rfc1662(5),
		v80crc(6)
	}
	MAX-ACCESS  read-write
	STATUS  current
	DESCRIPTION
		"This object specifies how synchronous user data is passed to the modem.

		none - The modem does not support synchronous user data.
		sync - The modem directly supports synchronous user data.
		v80 - Synchronous user data is exchanged using ITU-T V.80 procedures without CRC.
		v80crc - Synchronous user data is exchanged using ITU-T V.80 procedures with CRC.
		rfc1662 - Synchronous user data is exchanged using the method described by RFC1662."
	::= { ipadModemDataTableEntry 8 }

ipadModemDataSetupScript2	OBJECT-TYPE
	SYNTAX  DisplayString ( SIZE(0..60) )
	MAX-ACCESS  read-write
	STATUS  current
	DESCRIPTION
		"Second script interpreted when a modem port is initialized."
	::= { ipadModemDataTableEntry 9 }

ipadModemDataSetupScript3	OBJECT-TYPE
	SYNTAX  DisplayString ( SIZE(0..60) )
	MAX-ACCESS  read-write
	STATUS  current
	DESCRIPTION
		"Third script interpreted when a modem port is initialized."
	::= { ipadModemDataTableEntry 10 }

ipadModemDataSetupScript4	OBJECT-TYPE
	SYNTAX  DisplayString ( SIZE(0..60) )
	MAX-ACCESS  read-write
	STATUS  current
	DESCRIPTION
		"Fourth script interpreted when a modem port is initialized."
	::= { ipadModemDataTableEntry 11 }

ipadModemDataSetupScript5	OBJECT-TYPE
	SYNTAX  DisplayString ( SIZE(0..60) )
	MAX-ACCESS  read-write
	STATUS  current
	DESCRIPTION
		"Fifth script interpreted when a modem port is initialized."
	::= { ipadModemDataTableEntry 12 }




-- ----------------------------------------------------------------------
-- Dial Backup Configuration Table
-- ----------------------------------------------------------------------




ipadDbuTable	OBJECT-TYPE
	SYNTAX  SEQUENCE OF IpadDbuTableEntry
	MAX-ACCESS  not-accessible
	STATUS  current
	DESCRIPTION
		"The Dial Backup configuration table."
	::= { ipadModem 3 }

ipadDbuTableEntry	OBJECT-TYPE
	SYNTAX  IpadDbuTableEntry
	MAX-ACCESS  not-accessible
	STATUS  current
	DESCRIPTION
		"An entry in the Dial Backup configuration table."
	INDEX   { ipadDbuIndex }
	::= { ipadDbuTable 1 }

IpadDbuTableEntry ::=
	SEQUENCE
	{
		ipadDbuIndex			INTEGER,
		ipadDbuOperation		INTEGER,
		ipadDbuMonitoredifIndex		INTEGER,
		ipadDbuActivator1		INTEGER,
		ipadDbuActivator2		INTEGER,
		ipadDbuRevertDelay		INTEGER,
		ipadDbuTrapDelay		INTEGER,
		ipadDbuStatus			INTEGER,
		ipadDbuTrap			INTEGER
	}

ipadDbuIndex	OBJECT-TYPE
	SYNTAX  INTEGER
	MAX-ACCESS  read-only
	STATUS  current
	DESCRIPTION
		"An index into the Dial Backup configuration table.
		Equivalent to MIB-II ifIndex."
	::= { ipadDbuTableEntry 1 }

ipadDbuOperation	OBJECT-TYPE
	SYNTAX  INTEGER
	{
		other(1),
		disable(2),
		automatic(3),
		automaticDaily(4),
		forceBackup(5),
		testOriginate(6),
		testAnswer(7)
	}
	MAX-ACCESS  read-write
	STATUS  current
	DESCRIPTION
		"This object specifes the basic operation of the Dial Backup feature.

		disable - Dial Backup is not to operate
		automatic - Dial Backup will start and end automatically
		automaticDaily - Dial Backup will operate automatically within the specified times in the Daily Dial Backup Table
		forceBackup - The unit will operate in backup mode unconditionally
		testOriginate - The unit will start backup procedures and hold the dial-up connection
		testAnswer - The unit will await a call, establish, and hold the dial-up connection"
	::= { ipadDbuTableEntry 2 }

ipadDbuMonitoredifIndex	OBJECT-TYPE
	SYNTAX  INTEGER
	MAX-ACCESS  read-write
	STATUS  current
	DESCRIPTION
		"Network MIB-II ifIndex monitored by Dial Backup."
	::= { ipadDbuTableEntry 7 }

ipadDbuActivator1	OBJECT-TYPE
	SYNTAX  INTEGER
	{
		other(1),
		disable(2),
		any(3),
		carrier(4),
		es(5),
		ses(6),
		uas(7),
		los(8),
		cs(9),
		bpv(10),
		oof(11),
		ais(12),
		ras(13),
		oos(14)
	}
	MAX-ACCESS  read-write
	STATUS  current
	DESCRIPTION
		"This object specifies what will trigger a dial backup activation.

		disable - No alarm will trigger
		any - Trigger on any active alarm listed here
		carrier - Trigger on LOS, OOF, or OOS alarms
		es - Trigger on the Errored Seconds alarm
		ses - Trigger on the Severely Errored Seconds alarm
		uas - Trigger on the Unavailable Seconds alarm
		los - Trigger on the Loss Of Signal alarm
		cs - Trigger on the Controlled Slip alarm
		bpv - Trigger on the Bipolar Violation alarm
		oof - Trigger on the Out Of Frame alarm
		ais - Trigger on the Alarm Indication Signal alarm
		ras - Trigger on the Remote Alarm Signal alarm
		oos - Trigger on the Out Of Service alarm"
	::= { ipadDbuTableEntry 8 }

ipadDbuActivator2	OBJECT-TYPE
	SYNTAX  INTEGER
	{
		other(1),
		disable(2),
		any(3),
		carrier(4),
		es(5),
		ses(6),
		uas(7),
		los(8),
		cs(9),
		bpv(10),
		oof(11),
		ais(12),
		ras(13),
		oos(14)
	}
	MAX-ACCESS  read-write
	STATUS  current
	DESCRIPTION
		"This object specifies what will trigger a dial backup activation.

		disable - No alarm will trigger
		any - Trigger on any active alarm listed here
		carrier - Trigger on LOS, OOF, or OOS alarms
		es - Trigger on the Errored Seconds alarm
		ses - Trigger on the Severely Errored Seconds alarm
		uas - Trigger on the Unavailable Seconds alarm
		los - Trigger on the Loss Of Signal alarm
		cs - Trigger on the Controlled Slip alarm
		bpv - Trigger on the Bipolar Violation alarm
		oof - Trigger on the Out Of Frame alarm
		ais - Trigger on the Alarm Indication Signal alarm
		ras - Trigger on the Remote Alarm Signal alarm
		oos - Trigger on the Out Of Service alarm"
	::= { ipadDbuTableEntry 9 }

ipadDbuRevertDelay	OBJECT-TYPE
	SYNTAX  INTEGER
	MAX-ACCESS  read-write
	STATUS  current
	DESCRIPTION
		"This object specifies the number of seconds the dial backup activators must be continuously gone before the normal connection is restored."
	::= { ipadDbuTableEntry 10 }

ipadDbuTrapDelay	OBJECT-TYPE
	SYNTAX  INTEGER
	MAX-ACCESS  read-write
	STATUS  current
	DESCRIPTION
		"This object specifies the number of seconds after entering the active state before sending the Dial Backup trap."
	::= { ipadDbuTableEntry 11 }

ipadDbuStatus	OBJECT-TYPE
	SYNTAX  INTEGER
	{
		other(1),
		disabled(2),
		standby(3),
		disallowed(4),
		dialing(5),
		answering(6),
		negotiating(7),
		awaitingCallback(8),
		active(9),
		disconnecting(10),
		testWaiting(11),
		testPassed(12),
		testFailed(13),
		error(14),
		setup(15),
		dialWait(16),
		ringing(17)
	}
	MAX-ACCESS  read-only
	STATUS  current
	DESCRIPTION
		"This object reports the current activity of the Dial Backup feature

		disabled - The feature is not enabled
		setup - The feature is configuring the modem
		error - The feature could not setup the modem
		standby - The feature is ready to operate
		disallowed - The Dial Backup Daily table prevents activation
		dialing - The feature is placing a call
		dialWait - The feature is between call attempts
		ringing - The feature is waiting for an incoming call to connect or go away
		answering - The feature is answering a call
		negotiating - The feature is negotiating the login security
		awaitingCallback - The feature is waiting for a security callback
		active - The feature backup path is connected
		disconnecting - The feature is disconnecting a call
		testWaiting - The feature is waiting for a link test call
		testPassed - The feature has successfully tested the backup link
		testFailed - The feature could not establish the backup link"
	::= { ipadDbuTableEntry 12 }

ipadDbuTrap	OBJECT-TYPE
	SYNTAX  INTEGER
	{
		other(1),
		disable(2),
		enable(3)
	}
	MAX-ACCESS  read-write
	STATUS  current
	DESCRIPTION
		"Enable or disable the Dial Backup trap."
	::= { ipadDbuTableEntry 13 }




-- ----------------------------------------------------------------------
-- Daily Dial Backup Times Table
-- ----------------------------------------------------------------------




ipadDbuDailyTable	OBJECT-TYPE
	SYNTAX  SEQUENCE OF IpadDbuDailyTableEntry
	MAX-ACCESS  not-accessible
	STATUS  current
	DESCRIPTION
		"The Daily Dial Backup Times Table."
	::= { ipadModem 4 }

ipadDbuDailyTableEntry	OBJECT-TYPE
	SYNTAX  IpadDbuDailyTableEntry
	MAX-ACCESS  not-accessible
	STATUS  current
	DESCRIPTION
		"An entry in the Daily Dial Backup Times Table."
	INDEX   { ipadDbuDailyIndex, ipadDbuDailyDayOfWeek }
	::= { ipadDbuDailyTable 1 }

IpadDbuDailyTableEntry ::=
	SEQUENCE
	{
		ipadDbuDailyIndex		INTEGER,
		ipadDbuDailyDayOfWeek		INTEGER,
		ipadDbuDailyStart		INTEGER,
		ipadDbuDailyLength		INTEGER
	}

ipadDbuDailyIndex	OBJECT-TYPE
	SYNTAX  INTEGER
	MAX-ACCESS  read-only
	STATUS  current
	DESCRIPTION
		"An index into the Daily Dial Backup Times Table.
		Equivalent to MIB-II ifIndex."
	::= { ipadDbuDailyTableEntry 1 }

ipadDbuDailyDayOfWeek	OBJECT-TYPE
	SYNTAX  INTEGER
	{
		sunday(1),
		monday(2),
		tuesday(3),
		wednesday(4),
		thursday(5),
		friday(6),
		saturday(7)
	}
	MAX-ACCESS  read-only
	STATUS  current
	DESCRIPTION
		"This is the day of the week index into the Daily Dial Backup Times Table."
	::= { ipadDbuDailyTableEntry 2 }

ipadDbuDailyStart	OBJECT-TYPE
	SYNTAX  INTEGER
	{
		hour00(1),
		hour01(2),
		hour02(3),
		hour03(4),
		hour04(5),
		hour05(6),
		hour06(7),
		hour07(8),
		hour08(9),
		hour09(10),
		hour10(11),
		hour11(12),
		hour12(13),
		hour13(14),
		hour14(15),
		hour15(16),
		hour16(17),
		hour17(18),
		hour18(19),
		hour19(20),
		hour20(21),
		hour21(22),
		hour22(23),
		hour23(24)
	}
	MAX-ACCESS  read-write
	STATUS  current
	DESCRIPTION
		"This object is the beginning of a window for Dial Backup activation."
	::= { ipadDbuDailyTableEntry 3 }

ipadDbuDailyLength	OBJECT-TYPE
	SYNTAX  INTEGER
	{
		disable(1),
		hour01(2),
		hour02(3),
		hour03(4),
		hour04(5),
		hour05(6),
		hour06(7),
		hour07(8),
		hour08(9),
		hour09(10),
		hour10(11),
		hour11(12),
		hour12(13),
		hour13(14),
		hour14(15),
		hour15(16),
		hour16(17),
		hour17(18),
		hour18(19),
		hour19(20),
		hour20(21),
		hour21(22),
		hour22(23),
		hour23(24),
		hour24(25)
	}
	MAX-ACCESS  read-write
	STATUS  current
	DESCRIPTION
		"This object is the size of a window for Dial Backup activation."
	::= { ipadDbuDailyTableEntry 4 }




-- ipadSvcAware section
-- port statistics table

ipadFrPortStatsTable	OBJECT-TYPE
	SYNTAX  SEQUENCE OF IpadFrPortStatsEntry
	MAX-ACCESS  not-accessible
	STATUS  current
	DESCRIPTION
		"Port statistics."
	::= { ipadSvcAware 1 }

ipadFrPortStatsEntry	OBJECT-TYPE
	SYNTAX  IpadFrPortStatsEntry
	MAX-ACCESS  not-accessible
	STATUS  current
	DESCRIPTION
		"An entry in the service aware ports statistics table."
	INDEX	{ ipadFrPortStatsService, ipadFrPortStatsPeriod }
	::= { ipadFrPortStatsTable 1 }

IpadFrPortStatsEntry ::=
	SEQUENCE
	{
		ipadFrPortStatsService		INTEGER,
		ipadFrPortStatsPeriod		INTEGER,
		ipadFrPortStatsTxFrames		INTEGER,
		ipadFrPortStatsRxFrames		INTEGER,
		ipadFrPortStatsTxOctets		INTEGER,
		ipadFrPortStatsRxOctets		INTEGER,
		ipadFrPortStatsTxMgmtFrames	INTEGER,
		ipadFrPortStatsRxMgmtFrames	INTEGER,
		ipadFrPortStatsTxMgmtOctets	INTEGER,
		ipadFrPortStatsRxMgmtOctets	INTEGER,
		ipadFrPortStatsRxFECN		INTEGER,
		ipadFrPortStatsRxBECN		INTEGER,
		ipadFrPortStatsRxInvalid	INTEGER,
		ipadFrPortStatsTxStatInq	INTEGER,
		ipadFrPortStatsRxStatInq	INTEGER,
		ipadFrPortStatsTxStatResp	INTEGER,
		ipadFrPortStatsRxStatResp	INTEGER,
		ipadFrPortStatsRxInvLMI		INTEGER,
		ipadFrPortStatsPeak		INTEGER,
		ipadFrPortStatsAverage		INTEGER,
		ipadFrPortStatsTimeStamp	TimeTicks,
		ipadFrPortStatsTxAvgPercent	INTEGER,
		ipadFrPortStatsTxMaxPercent	INTEGER,
		ipadFrPortStatsTxInstantPercent	INTEGER,
		ipadFrPortStatsTx20PercentSec	INTEGER,
		ipadFrPortStatsTx40PercentSec	INTEGER,
		ipadFrPortStatsTx60PercentSec	INTEGER,
		ipadFrPortStatsTx80PercentSec	INTEGER,
		ipadFrPortStatsTx100PercentSec	INTEGER,
		ipadFrPortStatsRxAvgPercent	INTEGER,
		ipadFrPortStatsRxMaxPercent	INTEGER,
		ipadFrPortStatsRxInstantPercent	INTEGER,
		ipadFrPortStatsRx20PercentSec	INTEGER,
		ipadFrPortStatsRx40PercentSec	INTEGER,
		ipadFrPortStatsRx60PercentSec	INTEGER,
		ipadFrPortStatsRx80PercentSec	INTEGER,
		ipadFrPortStatsRx100PercentSec	INTEGER,
		ipadFrPortStatsValidIntervals	INTEGER
	}

ipadFrPortStatsService	OBJECT-TYPE
	SYNTAX  INTEGER
	MAX-ACCESS  read-only
	STATUS  current
	DESCRIPTION
		"Port index in the ipadFrPortStats table;
		an entry in the ipad service table."
	::= { ipadFrPortStatsEntry 1 }

ipadFrPortStatsPeriod	OBJECT-TYPE
	SYNTAX  INTEGER
	{
		portStatsSummary(1),
		portStatsCurrent(2),

		portStatsperiod1(3),
		portStatsperiod2(4),
		portStatsperiod3(5),
		portStatsperiod4(6),
		portStatsperiod5(7),
		portStatsperiod6(8),
		portStatsperiod7(9),
		portStatsperiod8(10),
		portStatsperiod9(11),

		portStatsperiod10(12),
		portStatsperiod11(13),
		portStatsperiod12(14),
		portStatsperiod13(15),
		portStatsperiod14(16),
		portStatsperiod15(17),
		portStatsperiod16(18),
		portStatsperiod17(19),
		portStatsperiod18(20),
		portStatsperiod19(21),

		portStatsperiod20(22),
		portStatsperiod21(23),
		portStatsperiod22(24),
		portStatsperiod23(25),
		portStatsperiod24(26),
		portStatsperiod25(27),
		portStatsperiod26(28),
		portStatsperiod27(29),
		portStatsperiod28(30),
		portStatsperiod29(31),

		portStatsperiod30(32),
		portStatsperiod31(33),
		portStatsperiod32(34),
		portStatsperiod33(35),
		portStatsperiod34(36),
		portStatsperiod35(37),
		portStatsperiod36(38),
		portStatsperiod37(39),
		portStatsperiod38(40),
		portStatsperiod39(41),

		portStatsperiod40(42),
		portStatsperiod41(43),
		portStatsperiod42(44),
		portStatsperiod43(45),
		portStatsperiod44(46),
		portStatsperiod45(47),
		portStatsperiod46(48),
		portStatsperiod47(49),
		portStatsperiod48(50),
		portStatsperiod49(51),

		portStatsperiod50(52),
		portStatsperiod51(53),
		portStatsperiod52(54),
		portStatsperiod53(55),
		portStatsperiod54(56),
		portStatsperiod55(57),
		portStatsperiod56(58),
		portStatsperiod57(59),
		portStatsperiod58(60),
		portStatsperiod59(61),

		portStatsperiod60(62),
		portStatsperiod61(63),
		portStatsperiod62(64),
		portStatsperiod63(65),
		portStatsperiod64(66),
		portStatsperiod65(67),
		portStatsperiod66(68),
		portStatsperiod67(69),
		portStatsperiod68(70),
		portStatsperiod69(71),

		portStatsperiod70(72),
		portStatsperiod71(73),
		portStatsperiod72(74),
		portStatsperiod73(75),
		portStatsperiod74(76),
		portStatsperiod75(77),
		portStatsperiod76(78),
		portStatsperiod77(79),
		portStatsperiod78(80),
		portStatsperiod79(81),

		portStatsperiod80(82),
		portStatsperiod81(83),
		portStatsperiod82(84),
		portStatsperiod83(85),
		portStatsperiod84(86),
		portStatsperiod85(87),
		portStatsperiod86(88),
		portStatsperiod87(89),
		portStatsperiod88(90),
		portStatsperiod89(91),

		portStatsperiod90(92),
		portStatsperiod91(93),
		portStatsperiod92(94),
		portStatsperiod93(95),
		portStatsperiod94(96),
		portStatsperiod95(97),
		portStatsperiod96(98)
	}
	MAX-ACCESS  read-only
	STATUS  current
	DESCRIPTION
		"The index into the port stats 24-hour table."
	::= { ipadFrPortStatsEntry 2 }

ipadFrPortStatsTxFrames	OBJECT-TYPE
	SYNTAX  INTEGER
	MAX-ACCESS  read-only
	STATUS  current
	DESCRIPTION
		"Number of transmitted frames for the period."
	::= { ipadFrPortStatsEntry 3 }

ipadFrPortStatsRxFrames	OBJECT-TYPE
	SYNTAX  INTEGER
	MAX-ACCESS  read-only
	STATUS  current
	DESCRIPTION
		"Number of received frames for the period."
	::= { ipadFrPortStatsEntry 4 }

ipadFrPortStatsTxOctets	OBJECT-TYPE
	SYNTAX  INTEGER
	MAX-ACCESS  read-only
	STATUS  current
	DESCRIPTION
		"Number of transmitted octets for the period."
	::= { ipadFrPortStatsEntry 5 }

ipadFrPortStatsRxOctets	OBJECT-TYPE
	SYNTAX  INTEGER
	MAX-ACCESS  read-only
	STATUS  current
	DESCRIPTION
		"Number of received octets for the period."
	::= { ipadFrPortStatsEntry 6 }

ipadFrPortStatsTxMgmtFrames	OBJECT-TYPE
	SYNTAX  INTEGER
	MAX-ACCESS  read-only
	STATUS  current
	DESCRIPTION
		"Number of transmitted management frames for the period."
	::= { ipadFrPortStatsEntry 7 }

ipadFrPortStatsRxMgmtFrames	OBJECT-TYPE
	SYNTAX  INTEGER
	MAX-ACCESS  read-only
	STATUS  current
	DESCRIPTION
		"Number of received management frames for the period."
	::= { ipadFrPortStatsEntry 8 }

ipadFrPortStatsTxMgmtOctets	OBJECT-TYPE
	SYNTAX  INTEGER
	MAX-ACCESS  read-only
	STATUS  current
	DESCRIPTION
		"Number of transmitted management octets for the period."
	::= { ipadFrPortStatsEntry 9 }

ipadFrPortStatsRxMgmtOctets	OBJECT-TYPE
	SYNTAX  INTEGER
	MAX-ACCESS  read-only
	STATUS  current
	DESCRIPTION
		"Number of received management octets for the period."
	::= { ipadFrPortStatsEntry 10 }

ipadFrPortStatsRxFECN	OBJECT-TYPE
	SYNTAX  INTEGER
	MAX-ACCESS  read-only
	STATUS  current
	DESCRIPTION
		"Number of received frames with FECN set for the period."
	::= { ipadFrPortStatsEntry 11 }

ipadFrPortStatsRxBECN	OBJECT-TYPE
	SYNTAX  INTEGER
	MAX-ACCESS  read-only
	STATUS  current
	DESCRIPTION
		"Number of received frames with BECN set for the period."
	::= { ipadFrPortStatsEntry 12 }

ipadFrPortStatsRxInvalid	OBJECT-TYPE
	SYNTAX  INTEGER
	MAX-ACCESS  read-only
	STATUS  current
	DESCRIPTION
		"Number of invalid received frames for the period."
	::= { ipadFrPortStatsEntry 13 }

ipadFrPortStatsTxStatInq	OBJECT-TYPE
	SYNTAX  INTEGER
	MAX-ACCESS  read-only
	STATUS  current
	DESCRIPTION
		"Number of transmitted status inquiry frames for the period."
	::= { ipadFrPortStatsEntry 14 }

ipadFrPortStatsRxStatInq	OBJECT-TYPE
	SYNTAX  INTEGER
	MAX-ACCESS  read-only
	STATUS  current
	DESCRIPTION
		"Number of received status inquiry frames for the period."
	::= { ipadFrPortStatsEntry 15 }

ipadFrPortStatsTxStatResp	OBJECT-TYPE
	SYNTAX  INTEGER
	MAX-ACCESS  read-only
	STATUS  current
	DESCRIPTION
		"Number of transmitted status response frames for the period."
	::= { ipadFrPortStatsEntry 16 }

ipadFrPortStatsRxStatResp	OBJECT-TYPE
	SYNTAX  INTEGER
	MAX-ACCESS  read-only
	STATUS  current
	DESCRIPTION
		"Number of received status response frames for the period."
	::= { ipadFrPortStatsEntry 17 }

ipadFrPortStatsRxInvLMI	OBJECT-TYPE
	SYNTAX  INTEGER
	MAX-ACCESS  read-only
	STATUS  current
	DESCRIPTION
		"Number of received frames with an invalid LMI for the period."
	::= { ipadFrPortStatsEntry 18 }

ipadFrPortStatsPeak	OBJECT-TYPE
	SYNTAX  INTEGER
	MAX-ACCESS  read-only
	STATUS  current
	DESCRIPTION
		"Peak throughput rate for the period (in bits/second)."
	::= { ipadFrPortStatsEntry 19 }

ipadFrPortStatsAverage	OBJECT-TYPE
	SYNTAX  INTEGER
	MAX-ACCESS  read-only
	STATUS  current
	DESCRIPTION
		"Average throughput rate for the period (in bits/second)."
	::= { ipadFrPortStatsEntry 20 }

ipadFrPortStatsTimeStamp	OBJECT-TYPE
	SYNTAX	TimeTicks
	MAX-ACCESS	read-only
	STATUS	current
	DESCRIPTION
		"The value of sysUpTime the last time the statistics were updated."
	::= { ipadFrPortStatsEntry 21 }

ipadFrPortStatsTxAvgPercent	OBJECT-TYPE
	SYNTAX  INTEGER
	MAX-ACCESS  read-only
	STATUS  current
	DESCRIPTION
		"Average Tx throughput percent for the period."
	::= { ipadFrPortStatsEntry 22 }

ipadFrPortStatsTxMaxPercent	OBJECT-TYPE
	SYNTAX  INTEGER
	MAX-ACCESS  read-only
	STATUS  current
	DESCRIPTION
		"Maximum Tx throughput percent for the period."
	::= { ipadFrPortStatsEntry 23 }

ipadFrPortStatsTxInstantPercent	OBJECT-TYPE
	SYNTAX  INTEGER
	MAX-ACCESS  read-only
	STATUS  current
	DESCRIPTION
		"Instantaneous Tx throughput percent for the period."
	::= { ipadFrPortStatsEntry 24 }

ipadFrPortStatsTx20PercentSec	OBJECT-TYPE
	SYNTAX  INTEGER
	MAX-ACCESS  read-only
	STATUS  current
	DESCRIPTION
		"Number of seconds Tx throughput was 0-20% of bandwidth."
	::= { ipadFrPortStatsEntry 25 }

ipadFrPortStatsTx40PercentSec	OBJECT-TYPE
	SYNTAX  INTEGER
	MAX-ACCESS  read-only
	STATUS  current
	DESCRIPTION
		"Number of seconds Tx throughput was 21-40% of bandwidth."
	::= { ipadFrPortStatsEntry 26 }

ipadFrPortStatsTx60PercentSec	OBJECT-TYPE
	SYNTAX  INTEGER
	MAX-ACCESS  read-only
	STATUS  current
	DESCRIPTION
		"Number of seconds Tx throughput was 41-60% of bandwidth."
	::= { ipadFrPortStatsEntry 27 }

ipadFrPortStatsTx80PercentSec	OBJECT-TYPE
	SYNTAX  INTEGER
	MAX-ACCESS  read-only
	STATUS  current
	DESCRIPTION
		"Number of seconds Tx throughput was 61-80% of bandwidth."
	::= { ipadFrPortStatsEntry 28 }

ipadFrPortStatsTx100PercentSec	OBJECT-TYPE
	SYNTAX  INTEGER
	MAX-ACCESS  read-only
	STATUS  current
	DESCRIPTION
		"Number of seconds Tx throughput was 81-100% of bandwidth."
	::= { ipadFrPortStatsEntry 29 }

ipadFrPortStatsRxAvgPercent	OBJECT-TYPE
	SYNTAX  INTEGER
	MAX-ACCESS  read-only
	STATUS  current
	DESCRIPTION
		"Average Rx throughput percent for the period."
	::= { ipadFrPortStatsEntry 30 }

ipadFrPortStatsRxMaxPercent	OBJECT-TYPE
	SYNTAX  INTEGER
	MAX-ACCESS  read-only
	STATUS  current
	DESCRIPTION
		"Maximum Rx throughput percent for the period."
	::= { ipadFrPortStatsEntry 31 }

ipadFrPortStatsRxInstantPercent	OBJECT-TYPE
	SYNTAX  INTEGER
	MAX-ACCESS  read-only
	STATUS  current
	DESCRIPTION
		"Instantaneous Rx throughput percent for the period."
	::= { ipadFrPortStatsEntry 32 }

ipadFrPortStatsRx20PercentSec	OBJECT-TYPE
	SYNTAX  INTEGER
	MAX-ACCESS  read-only
	STATUS  current
	DESCRIPTION
		"Number of seconds Rx throughput was 0-20% of bandwidth."
	::= { ipadFrPortStatsEntry 33 }

ipadFrPortStatsRx40PercentSec	OBJECT-TYPE
	SYNTAX  INTEGER
	MAX-ACCESS  read-only
	STATUS  current
	DESCRIPTION
		"Number of seconds Rx throughput was 21-40% of bandwidth."
	::= { ipadFrPortStatsEntry 34 }

ipadFrPortStatsRx60PercentSec	OBJECT-TYPE
	SYNTAX  INTEGER
	MAX-ACCESS  read-only
	STATUS  current
	DESCRIPTION
		"Number of seconds Rx throughput was 41-60% of bandwidth."
	::= { ipadFrPortStatsEntry 35 }

ipadFrPortStatsRx80PercentSec	OBJECT-TYPE
	SYNTAX  INTEGER
	MAX-ACCESS  read-only
	STATUS  current
	DESCRIPTION
		"Number of seconds Rx throughput was 61-80% of bandwidth."
	::= { ipadFrPortStatsEntry 36 }

ipadFrPortStatsRx100PercentSec	OBJECT-TYPE
	SYNTAX  INTEGER
	MAX-ACCESS  read-only
	STATUS  current
	DESCRIPTION
		"Number of seconds Rx throughput was 81-100% of bandwidth."
	::= { ipadFrPortStatsEntry 37 }

ipadFrPortStatsValidIntervals	OBJECT-TYPE
	SYNTAX  INTEGER (0..96)
	MAX-ACCESS  read-only
	STATUS  current
	DESCRIPTION
		"Number of valid intervals in the table excluding the Summary and Current entries."
	::= { ipadFrPortStatsEntry 38 }

-- DLCI statistics table

ipadDLCIstatsTable	OBJECT-TYPE
	SYNTAX  SEQUENCE OF IpadDLCIstatsEntry
	MAX-ACCESS  not-accessible
	STATUS  current
	DESCRIPTION
		"Port statistics."
	::= { ipadSvcAware 2 }

ipadDLCIstatsEntry	OBJECT-TYPE
	SYNTAX  IpadDLCIstatsEntry
	MAX-ACCESS  not-accessible
	STATUS  current
	DESCRIPTION
		"An entry in the service aware DLCI statistics table."
	INDEX	{ ipadDLCIstatsService, ipadDLCIstatsDLCI, ipadDLCIstatsPeriod }
	::= { ipadDLCIstatsTable 1 }

IpadDLCIstatsEntry ::=
	SEQUENCE
	{
		ipadDLCIstatsService				INTEGER,
		ipadDLCIstatsDLCI				INTEGER,
		ipadDLCIstatsPeriod				INTEGER,
		ipadDLCIstatsTxFrames				INTEGER,
		ipadDLCIstatsRxFrames				INTEGER,
		ipadDLCIstatsTxOctets				INTEGER,
		ipadDLCIstatsRxOctets				INTEGER,
		ipadDLCIstatsRxFECN				INTEGER,
		ipadDLCIstatsRxBECN				INTEGER,
		ipadDLCIstatsRxDE				INTEGER,
		ipadDLCIstatsTxExcessCIR			INTEGER,
		ipadDLCIstatsTxExcessBe				INTEGER,
		ipadDLCIstatsTxMgmtFrames			INTEGER,
		ipadDLCIstatsRxMgmtFrames			INTEGER,
		ipadDLCIstatsTxMgmtOctets			INTEGER,
		ipadDLCIstatsRxMgmtOctets			INTEGER,
		ipadDLCIstatsPeak				INTEGER,
		ipadDLCIstatsAverage				INTEGER,
		ipadDLCIstatsDelayPeak				INTEGER,
		ipadDLCIstatsDelayAverage			INTEGER,
		ipadDLCIstatsRoundTripTimeouts			INTEGER,
		ipadDLCIstatsUAS				INTEGER,
		ipadDLCIstatsFdrCir				INTEGER,
		ipadDLCIstatsDdrCir				INTEGER,
		ipadDLCIstatsFdrBe				INTEGER,
		ipadDLCIstatsDdrBe				INTEGER,
		ipadDLCIstatsTimeStamp				TimeTicks,
		ipadDLCIstatsRemoteFramesOfferedWithinCIR	INTEGER,
		ipadDLCIstatsRemoteFramesOfferedWithinBE	INTEGER,
		ipadDLCIstatsFramesReceived			INTEGER,
		ipadDLCIstatsFDRCIR				DisplayString,
		ipadDLCIstatsFDRBE				DisplayString,
		ipadDLCIstatsRemoteDataOfferedWithinCIR		INTEGER,
		ipadDLCIstatsRemoteDataOfferedWithinBE		INTEGER,
		ipadDLCIstatsDataReceived			INTEGER,
		ipadDLCIstatsDDRCIR				DisplayString,
		ipadDLCIstatsDDRBE				DisplayString,
		ipadDLCIstatsAvgPercent				INTEGER,
		ipadDLCIstatsMaxPercent				INTEGER,
		ipadDLCIstatsInstantPercent			INTEGER,
		ipadDLCIstats20PercentSec			INTEGER,
		ipadDLCIstats40PercentSec			INTEGER,
		ipadDLCIstats60PercentSec			INTEGER,
		ipadDLCIstats80PercentSec			INTEGER,
		ipadDLCIstats100PercentSec			INTEGER,
		ipadDLCIstatsValidIntervals			INTEGER,
		ipadDLCIstatsCompressionTxOctetsIn		INTEGER,
		ipadDLCIstatsCompressionTxOctetsOut	  	INTEGER,
		ipadDLCIstatsCompressionRxOctetsIn    	  	INTEGER,
		ipadDLCIstatsCompressionRxOctetsOut	  	INTEGER,
		ipadDLCIstatsCompressionTxRatio			DisplayString,
		ipadDLCIstatsCompressionRxRatio			DisplayString
	}

ipadDLCIstatsService	OBJECT-TYPE
	SYNTAX  INTEGER
	MAX-ACCESS  read-only
	STATUS  current
	DESCRIPTION
		"The service index for the service aware stats table; identifies an
		entry in the ipad DLCI table when combined with ipadDLCIstatsDLCI."
	::= { ipadDLCIstatsEntry 1 }
	
ipadDLCIstatsDLCI	OBJECT-TYPE
	SYNTAX  INTEGER
	MAX-ACCESS  read-only
	STATUS  current
	DESCRIPTION
		"The DLCI index for the service aware stats table; identifies an
		entry in the ipad DLCI table when combined with ipadDLCIstatsService."
	::= { ipadDLCIstatsEntry 2 }

ipadDLCIstatsPeriod	OBJECT-TYPE
	SYNTAX  INTEGER
	{
		dlciStatsSummary(1),
		dlciStatsCurrent(2),

		dlciStatsperiod1(3),
		dlciStatsperiod2(4),
		dlciStatsperiod3(5),
		dlciStatsperiod4(6),
		dlciStatsperiod5(7),
		dlciStatsperiod6(8),
		dlciStatsperiod7(9),
		dlciStatsperiod8(10),
		dlciStatsperiod9(11),

		dlciStatsperiod10(12),
		dlciStatsperiod11(13),
		dlciStatsperiod12(14),
		dlciStatsperiod13(15),
		dlciStatsperiod14(16),
		dlciStatsperiod15(17),
		dlciStatsperiod16(18),
		dlciStatsperiod17(19),
		dlciStatsperiod18(20),
		dlciStatsperiod19(21),

		dlciStatsperiod20(22),
		dlciStatsperiod21(23),
		dlciStatsperiod22(24),
		dlciStatsperiod23(25),
		dlciStatsperiod24(26),
		dlciStatsperiod25(27),
		dlciStatsperiod26(28),
		dlciStatsperiod27(29),
		dlciStatsperiod28(30),
		dlciStatsperiod29(31),

		dlciStatsperiod30(32),
		dlciStatsperiod31(33),
		dlciStatsperiod32(34),
		dlciStatsperiod33(35),
		dlciStatsperiod34(36),
		dlciStatsperiod35(37),
		dlciStatsperiod36(38),
		dlciStatsperiod37(39),
		dlciStatsperiod38(40),
		dlciStatsperiod39(41),

		dlciStatsperiod40(42),
		dlciStatsperiod41(43),
		dlciStatsperiod42(44),
		dlciStatsperiod43(45),
		dlciStatsperiod44(46),
		dlciStatsperiod45(47),
		dlciStatsperiod46(48),
		dlciStatsperiod47(49),
		dlciStatsperiod48(50),
		dlciStatsperiod49(51),

		dlciStatsperiod50(52),
		dlciStatsperiod51(53),
		dlciStatsperiod52(54),
		dlciStatsperiod53(55),
		dlciStatsperiod54(56),
		dlciStatsperiod55(57),
		dlciStatsperiod56(58),
		dlciStatsperiod57(59),
		dlciStatsperiod58(60),
		dlciStatsperiod59(61),

		dlciStatsperiod60(62),
		dlciStatsperiod61(63),
		dlciStatsperiod62(64),
		dlciStatsperiod63(65),
		dlciStatsperiod64(66),
		dlciStatsperiod65(67),
		dlciStatsperiod66(68),
		dlciStatsperiod67(69),
		dlciStatsperiod68(70),
		dlciStatsperiod69(71),

		dlciStatsperiod70(72),
		dlciStatsperiod71(73),
		dlciStatsperiod72(74),
		dlciStatsperiod73(75),
		dlciStatsperiod74(76),
		dlciStatsperiod75(77),
		dlciStatsperiod76(78),
		dlciStatsperiod77(79),
		dlciStatsperiod78(80),
		dlciStatsperiod79(81),

		dlciStatsperiod80(82),
		dlciStatsperiod81(83),
		dlciStatsperiod82(84),
		dlciStatsperiod83(85),
		dlciStatsperiod84(86),
		dlciStatsperiod85(87),
		dlciStatsperiod86(88),
		dlciStatsperiod87(89),
		dlciStatsperiod88(90),
		dlciStatsperiod89(91),

		dlciStatsperiod90(92),
		dlciStatsperiod91(93),
		dlciStatsperiod92(94),
		dlciStatsperiod93(95),
		dlciStatsperiod94(96),
		dlciStatsperiod95(97),
		dlciStatsperiod96(98)
	}
	MAX-ACCESS  read-only
	STATUS  current
	DESCRIPTION
		"The index into the DLCI stats 24-hour table."
	::= { ipadDLCIstatsEntry 3 }

ipadDLCIstatsTxFrames	OBJECT-TYPE
	SYNTAX  INTEGER
	MAX-ACCESS  read-only
	STATUS  current
	DESCRIPTION
		"The number of transmitted frames for the period."
	::= { ipadDLCIstatsEntry 4 }

ipadDLCIstatsRxFrames	OBJECT-TYPE
	SYNTAX  INTEGER
	MAX-ACCESS  read-only
	STATUS  current
	DESCRIPTION
		"The number of received frames for the period."
	::= { ipadDLCIstatsEntry 5 }

ipadDLCIstatsTxOctets	OBJECT-TYPE
	SYNTAX  INTEGER
	MAX-ACCESS  read-only
	STATUS  current
	DESCRIPTION
		"The number of transmitted octets for the period."
	::= { ipadDLCIstatsEntry 6 }

ipadDLCIstatsRxOctets	OBJECT-TYPE
	SYNTAX  INTEGER
	MAX-ACCESS  read-only
	STATUS  current
	DESCRIPTION
		"The number of received octets for the period."
	::= { ipadDLCIstatsEntry 7 }

ipadDLCIstatsRxFECN	OBJECT-TYPE
	SYNTAX  INTEGER
	MAX-ACCESS  read-only
	STATUS  current
	DESCRIPTION
		"The number of received frames with FECN set for the period."
	::= { ipadDLCIstatsEntry 8 }

ipadDLCIstatsRxBECN	OBJECT-TYPE
	SYNTAX  INTEGER
	MAX-ACCESS  read-only
	STATUS  current
	DESCRIPTION
		"The number of received frames with BECN set for the period."
	::= { ipadDLCIstatsEntry 9 }

ipadDLCIstatsRxDE	OBJECT-TYPE
	SYNTAX  INTEGER
	MAX-ACCESS  read-only
	STATUS  current
	DESCRIPTION
		"The number of received frames with DE bit set for the period."
	::= { ipadDLCIstatsEntry 10 }

ipadDLCIstatsTxExcessCIR	OBJECT-TYPE
	SYNTAX  INTEGER
	MAX-ACCESS  read-only
	STATUS  current
	DESCRIPTION
		"The number of transmitted octets in excess of CIR for the period."
	::= { ipadDLCIstatsEntry 11 }

ipadDLCIstatsTxExcessBe	OBJECT-TYPE
	SYNTAX  INTEGER
	MAX-ACCESS  read-only
	STATUS  current
	DESCRIPTION
		"The number of transmitted octets in excess of Be for the period."
	::= { ipadDLCIstatsEntry 12 }

ipadDLCIstatsTxMgmtFrames	OBJECT-TYPE
	SYNTAX  INTEGER
	MAX-ACCESS  read-only
	STATUS  current
	DESCRIPTION
		"The number of transmitted management frames for the period."
	::= { ipadDLCIstatsEntry 13 }

ipadDLCIstatsRxMgmtFrames	OBJECT-TYPE
	SYNTAX  INTEGER
	MAX-ACCESS  read-only
	STATUS  current
	DESCRIPTION
		"The number of received management frames for the period."
	::= { ipadDLCIstatsEntry 14 }

ipadDLCIstatsTxMgmtOctets	OBJECT-TYPE
	SYNTAX  INTEGER
	MAX-ACCESS  read-only
	STATUS  current
	DESCRIPTION
		"The number of transmitted management octets for the period."
	::= { ipadDLCIstatsEntry 15 }

ipadDLCIstatsRxMgmtOctets	OBJECT-TYPE
	SYNTAX  INTEGER
	MAX-ACCESS  read-only
	STATUS  current
	DESCRIPTION
		"The number of received management octets for the period."
	::= { ipadDLCIstatsEntry 16 }

ipadDLCIstatsPeak	OBJECT-TYPE
	SYNTAX  INTEGER
	MAX-ACCESS  read-only
	STATUS  current
	DESCRIPTION
		"Peak throughput rate for the period (in bits/second)."
	::= { ipadDLCIstatsEntry 17 }

ipadDLCIstatsAverage	OBJECT-TYPE
	SYNTAX  INTEGER
	MAX-ACCESS  read-only
	STATUS  current
	DESCRIPTION
		"Average throughput rate for the period (in bits/second)."
	::= { ipadDLCIstatsEntry 18 }

ipadDLCIstatsDelayPeak	OBJECT-TYPE
	SYNTAX  INTEGER
	MAX-ACCESS  read-only
	STATUS  current
	DESCRIPTION
		"Peak roundtrip delay for the period."
	::= { ipadDLCIstatsEntry 19 }

ipadDLCIstatsDelayAverage	OBJECT-TYPE
	SYNTAX  INTEGER
	MAX-ACCESS  read-only
	STATUS  current
	DESCRIPTION
		"Average roundtrip delay for the period."
	::= { ipadDLCIstatsEntry 20 }

ipadDLCIstatsRoundTripTimeouts	OBJECT-TYPE
	SYNTAX  INTEGER
	MAX-ACCESS  read-only
	STATUS  current
	DESCRIPTION
		"Number of timeouts on roundtrip delay for the period."
	::= { ipadDLCIstatsEntry 21 }

ipadDLCIstatsUAS	OBJECT-TYPE
	SYNTAX  INTEGER
	MAX-ACCESS  read-only
	STATUS  current
	DESCRIPTION
		"Number of seconds the DLCI is unavailable."
	::= { ipadDLCIstatsEntry 22 }

ipadDLCIstatsFdrCir	OBJECT-TYPE
	SYNTAX  INTEGER
	MAX-ACCESS  read-only
	STATUS  current
	DESCRIPTION
		""
	::= { ipadDLCIstatsEntry 23 }
	
ipadDLCIstatsDdrCir	OBJECT-TYPE
	SYNTAX  INTEGER
	MAX-ACCESS  read-only
	STATUS  current
	DESCRIPTION
		""
	::= { ipadDLCIstatsEntry 24 }
	
ipadDLCIstatsFdrBe	OBJECT-TYPE
	SYNTAX  INTEGER
	MAX-ACCESS  read-only
	STATUS  current
	DESCRIPTION
		""
	::= { ipadDLCIstatsEntry 25 }
	
ipadDLCIstatsDdrBe	OBJECT-TYPE
	SYNTAX  INTEGER
	MAX-ACCESS  read-only
	STATUS  current
	DESCRIPTION
		""
	::= { ipadDLCIstatsEntry 26 }

ipadDLCIstatsTimeStamp	OBJECT-TYPE
	SYNTAX	TimeTicks
	MAX-ACCESS	read-only
	STATUS	current
	DESCRIPTION
		"The value of sysUpTime the last time the statistics were updated."
	::= { ipadDLCIstatsEntry 27 }

ipadDLCIstatsRemoteFramesOfferedWithinCIR	OBJECT-TYPE
	SYNTAX  INTEGER
	MAX-ACCESS  read-only
	STATUS  current
	DESCRIPTION
		"Count of frames sent within CIR from the remote end of the DLCI."
	::= { ipadDLCIstatsEntry 28 }

ipadDLCIstatsRemoteFramesOfferedWithinBE	OBJECT-TYPE
	SYNTAX  INTEGER
	MAX-ACCESS  read-only
	STATUS  current
	DESCRIPTION
		"Count of frames sent within BE, but over CIR, from the remote end of the DLCI."
	::= { ipadDLCIstatsEntry 29 }

ipadDLCIstatsFramesReceived	OBJECT-TYPE
	SYNTAX  INTEGER
	MAX-ACCESS  read-only
	STATUS  current
	DESCRIPTION
		"Count of frames received by the local device on this DLCI."
	::= { ipadDLCIstatsEntry 30 }

ipadDLCIstatsFDRCIR	OBJECT-TYPE
	SYNTAX  DisplayString
	MAX-ACCESS  read-only
	STATUS  current
	DESCRIPTION
		"Frame Delivery Ratio calculated within CIR."
	::= { ipadDLCIstatsEntry 31 }

ipadDLCIstatsFDRBE	OBJECT-TYPE
	SYNTAX  DisplayString
	MAX-ACCESS  read-only
	STATUS  current
	DESCRIPTION
		"Frame Delivery Ratio caclulated within BE."
	::= { ipadDLCIstatsEntry 32 }

ipadDLCIstatsRemoteDataOfferedWithinCIR	OBJECT-TYPE
	SYNTAX  INTEGER
	MAX-ACCESS  read-only
	STATUS  current
	DESCRIPTION
		"Count of data octets sent within CIR from the remote end of the DLCI."
	::= { ipadDLCIstatsEntry 33 }

ipadDLCIstatsRemoteDataOfferedWithinBE	OBJECT-TYPE
	SYNTAX  INTEGER
	MAX-ACCESS  read-only
	STATUS  current
	DESCRIPTION
		"Count of data octets sent within BE, but over CIR, from the remote 
		end of the DLCI."
	::= { ipadDLCIstatsEntry 34 }

ipadDLCIstatsDataReceived	OBJECT-TYPE
	SYNTAX  INTEGER
	MAX-ACCESS  read-only
	STATUS  current
	DESCRIPTION
		"Count of data octets received by the local device on this DLCI."
	::= { ipadDLCIstatsEntry 35 }

ipadDLCIstatsDDRCIR	OBJECT-TYPE
	SYNTAX  DisplayString
	MAX-ACCESS  read-only
	STATUS  current
	DESCRIPTION
		"Data Delivery Ratio calculated within CIR."
	::= { ipadDLCIstatsEntry 36 }

ipadDLCIstatsDDRBE	OBJECT-TYPE
	SYNTAX  DisplayString
	MAX-ACCESS  read-only
	STATUS  current
	DESCRIPTION
		"Data Delivery Ratio caclulated within BE."
	::= { ipadDLCIstatsEntry 37 }

ipadDLCIstatsAvgPercent	OBJECT-TYPE
	SYNTAX  INTEGER
	MAX-ACCESS  read-only
	STATUS  current
	DESCRIPTION
		"Average throughput percent for the period."
	::= { ipadDLCIstatsEntry 38 }

ipadDLCIstatsMaxPercent	OBJECT-TYPE
	SYNTAX  INTEGER
	MAX-ACCESS  read-only
	STATUS  current
	DESCRIPTION
		"Maximum throughput percent for the period."
	::= { ipadDLCIstatsEntry 39 }

ipadDLCIstatsInstantPercent	OBJECT-TYPE
	SYNTAX  INTEGER
	MAX-ACCESS  read-only
	STATUS  current
	DESCRIPTION
		"Instantaneous throughput percent for the period."
	::= { ipadDLCIstatsEntry 40 }

ipadDLCIstats20PercentSec	OBJECT-TYPE
	SYNTAX  INTEGER
	MAX-ACCESS  read-only
	STATUS  current
	DESCRIPTION
		"Number of seconds throughput was 0-20% of bandwidth."
	::= { ipadDLCIstatsEntry 41 }

ipadDLCIstats40PercentSec	OBJECT-TYPE
	SYNTAX  INTEGER
	MAX-ACCESS  read-only
	STATUS  current
	DESCRIPTION
		"Number of seconds throughput was 21-40% of bandwidth."
	::= { ipadDLCIstatsEntry 42 }

ipadDLCIstats60PercentSec	OBJECT-TYPE
	SYNTAX  INTEGER
	MAX-ACCESS  read-only
	STATUS  current
	DESCRIPTION
		"Number of seconds throughput was 41-60% of bandwidth."
	::= { ipadDLCIstatsEntry 43 }

ipadDLCIstats80PercentSec	OBJECT-TYPE
	SYNTAX  INTEGER
	MAX-ACCESS  read-only
	STATUS  current
	DESCRIPTION
		"Number of seconds throughput was 61-80% of bandwidth."
	::= { ipadDLCIstatsEntry 44 }

ipadDLCIstats100PercentSec	OBJECT-TYPE
	SYNTAX  INTEGER
	MAX-ACCESS  read-only
	STATUS  current
	DESCRIPTION
		"Number of seconds throughput was 81-100% of bandwidth."
	::= { ipadDLCIstatsEntry 45 }

ipadDLCIstatsValidIntervals	OBJECT-TYPE
	SYNTAX  INTEGER (0..96)
	MAX-ACCESS  read-only
	STATUS  current
	DESCRIPTION
		"Number of valid intervals in the table excluding the Summary and Current entries."
	::= { ipadDLCIstatsEntry 46 }

ipadDLCIstatsCompressionTxOctetsIn	OBJECT-TYPE
	SYNTAX  INTEGER
	MAX-ACCESS  read-only
	STATUS  current
	DESCRIPTION
		"Number of octets passed into the compression engine."
	::= { ipadDLCIstatsEntry 47 }

ipadDLCIstatsCompressionTxOctetsOut	OBJECT-TYPE
	SYNTAX  INTEGER
	MAX-ACCESS  read-only
	STATUS  current
	DESCRIPTION
		"Number of octets passed out of the compression engine."
	::= { ipadDLCIstatsEntry 48 }

ipadDLCIstatsCompressionRxOctetsIn	OBJECT-TYPE
	SYNTAX  INTEGER
	MAX-ACCESS  read-only
	STATUS  current
	DESCRIPTION
		"Number of octets passed into the compression engine."
	::= { ipadDLCIstatsEntry 49 }

ipadDLCIstatsCompressionRxOctetsOut	OBJECT-TYPE
	SYNTAX  INTEGER
	MAX-ACCESS  read-only
	STATUS  current
	DESCRIPTION
		"Number of octets passed out of the compression engine."
	::= { ipadDLCIstatsEntry 50 }

ipadDLCIstatsCompressionTxRatio	OBJECT-TYPE
	SYNTAX  DisplayString
	MAX-ACCESS  read-only
	STATUS  current
	DESCRIPTION
		"Compression Ratio calculated in the transmit direction."
	::= { ipadDLCIstatsEntry 51 }

ipadDLCIstatsCompressionRxRatio	OBJECT-TYPE
	SYNTAX  DisplayString
	MAX-ACCESS  read-only
	STATUS  current
	DESCRIPTION
		"Compression Ratio calculation in the receive direction."
	::= { ipadDLCIstatsEntry 52 }


ipadUserStatsTable    OBJECT-TYPE
    SYNTAX  SEQUENCE OF IpadUserStatsEntry
    MAX-ACCESS  not-accessible
    STATUS  current
    DESCRIPTION
        "User-selected protocol statistics."
    ::= { ipadSvcAware 3 }

ipadUserStatsEntry    OBJECT-TYPE
    SYNTAX  IpadUserStatsEntry
    MAX-ACCESS  not-accessible
    STATUS  current
    DESCRIPTION
        "An entry in the user statistics table."
    INDEX    { ipadUserStatsIndex, ipadUserStatsPeriod }
    ::= { ipadUserStatsTable 1 }

IpadUserStatsEntry ::=
    SEQUENCE
    {
    ipadUserStatsIndex           INTEGER,
    ipadUserStatsPeriod          INTEGER,
    ipadUserStatsTxFrames        INTEGER,
    ipadUserStatsRxFrames        INTEGER,
    ipadUserStatsTxOctets        INTEGER,
    ipadUserStatsRxOctets        INTEGER,
    ipadUserStatsTxRatePeak      INTEGER,
    ipadUserStatsTxRateAverage   INTEGER,
    ipadUserStatsTimeStamp       TimeTicks
    }

ipadUserStatsIndex    OBJECT-TYPE
    SYNTAX  INTEGER
    MAX-ACCESS  read-only
    STATUS  current
    DESCRIPTION
        "Index into the user statistics table."
    ::= { ipadUserStatsEntry 1 }    

ipadUserStatsPeriod    OBJECT-TYPE
    SYNTAX  INTEGER
    {
    userStatsSummary(1),
    userStatsCurrent(2),

    userStatsperiod1(3),
    userStatsperiod2(4),
    userStatsperiod3(5),
    userStatsperiod4(6),
    userStatsperiod5(7),
    userStatsperiod6(8),
    userStatsperiod7(9),
    userStatsperiod8(10),
    userStatsperiod9(11),

    userStatsperiod10(12),
    userStatsperiod11(13),
    userStatsperiod12(14),
    userStatsperiod13(15),
    userStatsperiod14(16),
    userStatsperiod15(17),
    userStatsperiod16(18),
    userStatsperiod17(19),
    userStatsperiod18(20),
    userStatsperiod19(21),

    userStatsperiod20(22),
    userStatsperiod21(23),
    userStatsperiod22(24),
    userStatsperiod23(25),
    userStatsperiod24(26),
    userStatsperiod25(27),
    userStatsperiod26(28),
    userStatsperiod27(29),
    userStatsperiod28(30),
    userStatsperiod29(31),

    userStatsperiod30(32),
    userStatsperiod31(33),
    userStatsperiod32(34),
    userStatsperiod33(35),
    userStatsperiod34(36),
    userStatsperiod35(37),
    userStatsperiod36(38),
    userStatsperiod37(39),
    userStatsperiod38(40),
    userStatsperiod39(41),

    userStatsperiod40(42),
    userStatsperiod41(43),
    userStatsperiod42(44),
    userStatsperiod43(45),
    userStatsperiod44(46),
    userStatsperiod45(47),
    userStatsperiod46(48),
    userStatsperiod47(49),
    userStatsperiod48(50),
    userStatsperiod49(51),

    userStatsperiod50(52),
    userStatsperiod51(53),
    userStatsperiod52(54),
    userStatsperiod53(55),
    userStatsperiod54(56),
    userStatsperiod55(57),
    userStatsperiod56(58),
    userStatsperiod57(59),
    userStatsperiod58(60),
    userStatsperiod59(61),

    userStatsperiod60(62),
    userStatsperiod61(63),
    userStatsperiod62(64),
    userStatsperiod63(65),
    userStatsperiod64(66),
    userStatsperiod65(67),
    userStatsperiod66(68),
    userStatsperiod67(69),
    userStatsperiod68(70),
    userStatsperiod69(71),

    userStatsperiod70(72),
    userStatsperiod71(73),
    userStatsperiod72(74),
    userStatsperiod73(75),
    userStatsperiod74(76),
    userStatsperiod75(77),
    userStatsperiod76(78),
    userStatsperiod77(79),
    userStatsperiod78(80),
    userStatsperiod79(81),

    userStatsperiod80(82),
    userStatsperiod81(83),
    userStatsperiod82(84),
    userStatsperiod83(85),
    userStatsperiod84(86),
    userStatsperiod85(87),
    userStatsperiod86(88),
    userStatsperiod87(89),
    userStatsperiod88(90),
    userStatsperiod89(91),

    userStatsperiod90(92),
    userStatsperiod91(93),
    userStatsperiod92(94),
    userStatsperiod93(95),
    userStatsperiod94(96),
    userStatsperiod95(97),
    userStatsperiod96(98)
    }
    MAX-ACCESS  read-only
    STATUS  current
    DESCRIPTION
        "The index into the user stats 24-hour table."
    ::= { ipadUserStatsEntry 2 }    

ipadUserStatsTxFrames    OBJECT-TYPE
    SYNTAX  INTEGER
    MAX-ACCESS  read-only
    STATUS  current
    DESCRIPTION
        "Number of transmitted frames for the period."
    ::= { ipadUserStatsEntry 3 }    

ipadUserStatsRxFrames    OBJECT-TYPE
    SYNTAX  INTEGER
    MAX-ACCESS  read-only
    STATUS  current
    DESCRIPTION
        "Number of received frames for the period."
    ::= { ipadUserStatsEntry 4 }    

ipadUserStatsTxOctets    OBJECT-TYPE
    SYNTAX  INTEGER
    MAX-ACCESS  read-only
    STATUS  current
    DESCRIPTION
        "Number of transmitted octets for the period."
    ::= { ipadUserStatsEntry 5 }    

ipadUserStatsRxOctets    OBJECT-TYPE
    SYNTAX  INTEGER
    MAX-ACCESS  read-only
    STATUS  current
    DESCRIPTION
        "Number of received octets for the period."
    ::= { ipadUserStatsEntry 6 }    

ipadUserStatsTxRatePeak    OBJECT-TYPE
    SYNTAX  INTEGER
    MAX-ACCESS  read-only
    STATUS  current
    DESCRIPTION
        "Peak throughput rate for the period (in bits/second)."
    ::= { ipadUserStatsEntry 7 }

ipadUserStatsTxRateAverage    OBJECT-TYPE
    SYNTAX  INTEGER
    MAX-ACCESS  read-only
    STATUS  current
    DESCRIPTION
        "Average throughput rate for the period (in bits/second)."    
    ::= { ipadUserStatsEntry 8 }

ipadUserStatsTimeStamp	OBJECT-TYPE
	SYNTAX	TimeTicks
	MAX-ACCESS	read-only
	STATUS	current
	DESCRIPTION
		"The value of sysUpTime the last time the statistics were updated."
	::= { ipadUserStatsEntry 9 }

-- IPTopN stats section

ipadIPTopNStatsTable    OBJECT-TYPE
    SYNTAX  SEQUENCE OF IpadIPTopNStatsEntry
    MAX-ACCESS  not-accessible
    STATUS  current
    DESCRIPTION
        "IP TopN statistics."
    ::= { ipadSvcAware 4 }

ipadIPTopNStatsEntry    OBJECT-TYPE
    SYNTAX  IpadIPTopNStatsEntry
    MAX-ACCESS  not-accessible
    STATUS  current
    DESCRIPTION
        "An entry in the user statistics table."
    INDEX    { ipadIPTopNStatsIndex }
    ::= { ipadIPTopNStatsTable 1 }

IpadIPTopNStatsEntry ::=
    SEQUENCE
    {
    ipadIPTopNStatsIndex            INTEGER,
    ipadIPTopNStatsAddress          OCTET STRING,
    ipadIPTopNStatsTimestamp        TimeTicks,
    ipadIPTopNStatsRxFrames         INTEGER,
    ipadIPTopNStatsRxOctets         INTEGER,
    ipadIPTopNStatsTxFrames         INTEGER,
    ipadIPTopNStatsTxOctets         INTEGER
    }

ipadIPTopNStatsIndex    OBJECT-TYPE
    SYNTAX  INTEGER
    MAX-ACCESS  read-only
    STATUS  current
    DESCRIPTION
        "Index into the IP TopN statistics table."
    ::= { ipadIPTopNStatsEntry 1 }    

ipadIPTopNStatsAddress    OBJECT-TYPE
    SYNTAX  OCTET STRING (SIZE(1..16))
    MAX-ACCESS  read-only
    STATUS  current
    DESCRIPTION
        "IP address of this entry."
    ::= { ipadIPTopNStatsEntry 2 }

ipadIPTopNStatsTimestamp    OBJECT-TYPE
    SYNTAX  TimeTicks
    MAX-ACCESS  read-only
    STATUS  current
    DESCRIPTION
        "Time of last IP frame for this entry."
    ::= { ipadIPTopNStatsEntry 3 }

ipadIPTopNStatsRxFrames    OBJECT-TYPE
    SYNTAX  INTEGER
    MAX-ACCESS  read-only
    STATUS  current
    DESCRIPTION
        "Number of received IP frames for this entry."
    ::= { ipadIPTopNStatsEntry 4 }    

ipadIPTopNStatsRxOctets    OBJECT-TYPE
    SYNTAX  INTEGER
    MAX-ACCESS  read-only
    STATUS  current
    DESCRIPTION
        "Number of received IP octets for this entry."
    ::= { ipadIPTopNStatsEntry 5 }    

ipadIPTopNStatsTxFrames    OBJECT-TYPE
    SYNTAX  INTEGER
    MAX-ACCESS  read-only
    STATUS  current
    DESCRIPTION
        "Number of transmitted IP frames for this entry."
    ::= { ipadIPTopNStatsEntry 6 }    

ipadIPTopNStatsTxOctets    OBJECT-TYPE
    SYNTAX  INTEGER
    MAX-ACCESS  read-only
    STATUS  current
    DESCRIPTION
        "Number of transmitted IP octets for this entry."
    ::= { ipadIPTopNStatsEntry 7 }    

-- ipadPktSwitch section
-- packet switch parameters

ipadPktSwOperatingMode    OBJECT-TYPE
    SYNTAX  INTEGER
    {
	other(1),
	tdm(2),
	monitor(3),
	packet(4),
	remoteConfig(5),
	profile2(6),
	profile3(7),
	profile4(8),
	profile5(9),
	profile6(10),
	profile7(11),
	profile8(12),
	profile9(13),
	profile10(14),
	profile11(15),
	profile12(16),
	profile13(17),
	profile14(18),
	profile15(19),
	profile16(20),
	profile17(21),
	profile18(22),
	profile19(23),
	profile20(24),
	profile21(25)
    }
    MAX-ACCESS  read-write
    STATUS  current
    DESCRIPTION
        "Selects overall mode of operation."
    ::= { ipadPktSwitch 1 }

ipadPktSwCfgTable    OBJECT-TYPE
    SYNTAX  SEQUENCE OF IpadPktSwCfgTableEntry
    MAX-ACCESS  not-accessible
    STATUS  current
    DESCRIPTION
        "The ipad packet switch configuration table."
    ::= { ipadPktSwitch 2 }

ipadPktSwCfgTableEntry    OBJECT-TYPE
    SYNTAX  IpadPktSwCfgTableEntry
    MAX-ACCESS  not-accessible
    STATUS  current
    DESCRIPTION
        "An entry in the ipad packet switch configuration table."
    INDEX   { ipadPktSwCfgService }
    ::= { ipadPktSwCfgTable 1 }

IpadPktSwCfgTableEntry ::=
    SEQUENCE
    {
    ipadPktSwCfgService        INTEGER,
    ipadPktSwCfgInterfaceType  INTEGER,
    ipadPktSwCfgLnkMgmtType    INTEGER,
    ipadPktSwCfgMaxFrameSize   INTEGER,
    ipadPktSwCfgnN1            INTEGER,
    ipadPktSwCfgnN2            INTEGER,
    ipadPktSwCfgnN3            INTEGER,
    ipadPktSwCfgnT1            INTEGER,
    ipadPktSwCfgDefCIR         INTEGER,
    ipadPktSwCfgDefExBurst     INTEGER,
    ipadPktSwCfgCIREE          INTEGER,
    ipadPktSwCfgLinkInjection  INTEGER,
    ipadPktSwCfgAutoDiagnostic INTEGER,
    ipadPktSwCfgAutoDiscovery  INTEGER,
    ipadPktSwCfgMgmtDLCI       INTEGER,
    ipadPktSwCfgRoundTripDelaySize INTEGER,
    ipadPktSwCfgRoundTripDelayRate INTEGER,
    ipadPktSwCfgAutoIPMgmtAddr	   INTEGER,
    ipadPktSwCfgNormalTxQueueSize  INTEGER,
    ipadPktSwCfgAddDLCI        INTEGER,
    ipadPktSwCfgDeleteDLCI     INTEGER
    }

ipadPktSwCfgService        OBJECT-TYPE
    SYNTAX  INTEGER
    MAX-ACCESS  read-only
    STATUS  current
    DESCRIPTION
        "The index into the packet switch configuration table;
        an entry in the ipad Service table."
    ::= { ipadPktSwCfgTableEntry 1 }

ipadPktSwCfgInterfaceType    OBJECT-TYPE
    SYNTAX  INTEGER
    {
    uni(1),
    ni(2),
    nni(3)
    }
    MAX-ACCESS  read-write
    STATUS  current
    DESCRIPTION
        "Network ports should be set to User Network Interface (uni) 
        and user ports should be set to Network Interface (ni)."
    ::= { ipadPktSwCfgTableEntry 2 }

ipadPktSwCfgLnkMgmtType        OBJECT-TYPE
    SYNTAX  INTEGER
    {
    other(1),
    auto(2),
    ccitt(3),
    ansi(4),
    lmi(5),
    none(6)
    }
    MAX-ACCESS  read-write
    STATUS  current
    DESCRIPTION
        "If set to auto, the frame relay LMI type will 
        be learned from the network side.  If set to 
        none, all DLCI must be configured."
    ::= { ipadPktSwCfgTableEntry 3 }

ipadPktSwCfgMaxFrameSize    OBJECT-TYPE
    SYNTAX  INTEGER
    MAX-ACCESS  read-write
    STATUS  current
    DESCRIPTION
        "This is the maximum frame size configured in the frame relay network."
    ::= { ipadPktSwCfgTableEntry 4 }

ipadPktSwCfgnN1            OBJECT-TYPE
    SYNTAX  INTEGER
    MAX-ACCESS  read-write
    STATUS  current
    DESCRIPTION
        "Number of keep alive requests between full status request."
    ::= { ipadPktSwCfgTableEntry 5 }

ipadPktSwCfgnN2            OBJECT-TYPE
    SYNTAX  INTEGER
    MAX-ACCESS  read-write
    STATUS  current
    DESCRIPTION
        "Number of errors from FRAD before alarm."
    ::= { ipadPktSwCfgTableEntry 6 }

ipadPktSwCfgnN3            OBJECT-TYPE
    SYNTAX  INTEGER
    MAX-ACCESS  read-write
    STATUS  current
    DESCRIPTION
        "Number of events to sample nN2."
    ::= { ipadPktSwCfgTableEntry 7 }

ipadPktSwCfgnT1            OBJECT-TYPE
    SYNTAX  INTEGER
    MAX-ACCESS  read-write
    STATUS  current
    DESCRIPTION
        "Delay before issuing a poll sequence."
    ::= { ipadPktSwCfgTableEntry 8 }

ipadPktSwCfgDefCIR        OBJECT-TYPE
    SYNTAX  INTEGER
    MAX-ACCESS  read-write
    STATUS  current
    DESCRIPTION
        "Default committed information rate in bits per second."
    ::= { ipadPktSwCfgTableEntry 9 }

ipadPktSwCfgDefExBurst        OBJECT-TYPE
    SYNTAX  INTEGER
    MAX-ACCESS  read-write
    STATUS  current
    DESCRIPTION
        "Default excess burst rate in bits per second."
    ::= { ipadPktSwCfgTableEntry 10 }

ipadPktSwCfgCIREE        OBJECT-TYPE
    SYNTAX  INTEGER
    {
    other(1),
    no(2),
    yes(3)
    }
    MAX-ACCESS  read-write
    STATUS  current
    DESCRIPTION
        "Determines if the interface will enforce CIR and 
        excess burst configured values."
    ::= { ipadPktSwCfgTableEntry 11 }

ipadPktSwCfgLinkInjection    OBJECT-TYPE
    SYNTAX  INTEGER
    {
    other(1),
    standard(2),
    buffered(3),
    forced(4)
    }
    MAX-ACCESS  read-write
    STATUS  current
    DESCRIPTION
        "Indicates how to process frames in excess 
        of the CIR when congestion exists."
    ::= { ipadPktSwCfgTableEntry 12 }

ipadPktSwCfgAutoDiagnostic    OBJECT-TYPE
    SYNTAX  INTEGER
    {
    other(1),
    no(2),
    yes(3)
    }
    MAX-ACCESS  read-write
    STATUS  current
    DESCRIPTION
        "Determines if the unit will put itself into 
        diagnostic mode everytime it determines that
        there are no LMI received on a network service."
    ::= { ipadPktSwCfgTableEntry 13 }

ipadPktSwCfgAutoDiscovery    OBJECT-TYPE
    SYNTAX  INTEGER
    {
    other(1),
    no(2),
    yes(3)
    }
    MAX-ACCESS  read-write
    STATUS  current
    DESCRIPTION
        "Determines if the unit will learn the DLCIs 
        from the LMMI received on this service."
    ::= { ipadPktSwCfgTableEntry 14 }

ipadPktSwCfgMgmtDLCI	OBJECT-TYPE
	SYNTAX  INTEGER(0..4096)
    MAX-ACCESS  read-write
    STATUS  current
    DESCRIPTION
        "Specifies the DLCI that will be used by the unit
		for management information.  Specifying a 0 disables
		this feature."
    ::= { ipadPktSwCfgTableEntry 15 }

ipadPktSwCfgRoundTripDelaySize OBJECT-TYPE
	SYNTAX  INTEGER(16..1500)
	MAX-ACCESS  read-write
	STATUS  current
	DESCRIPTION     
		"Specifies the packet size in octets used to calculate 
		round trip delay."
	::= { ipadPktSwCfgTableEntry 16 }

ipadPktSwCfgRoundTripDelayRate OBJECT-TYPE
	SYNTAX  INTEGER(1..900)
	MAX-ACCESS  read-write
	STATUS  current
	DESCRIPTION     
		"Specifies the packet rate in seconds used to calculate 
		round trip delay."
	::= { ipadPktSwCfgTableEntry 17 }

ipadPktSwCfgAutoIPMgmtAddr	OBJECT-TYPE
    SYNTAX  INTEGER
    {
    other(1),
    no(2),
    yes(3)
    }
    MAX-ACCESS  read-write
    STATUS  current
    DESCRIPTION
        "Look for DLCI (980-995) and uses its IP address."
    ::= { ipadPktSwCfgTableEntry 18 }

ipadPktSwCfgNormalTxQueueSize	OBJECT-TYPE
    SYNTAX  INTEGER(1..32)
    MAX-ACCESS  read-write
    STATUS  current
    DESCRIPTION
        "The depth of the normal priority tx queue.  This size determines the
        max number of low priority packets that can be queued in front of high
        priority traffic."
    ::= { ipadPktSwCfgTableEntry 19 }
 
ipadPktSwCfgAddDLCI        OBJECT-TYPE
    SYNTAX  INTEGER
    MAX-ACCESS  read-write
    STATUS  current
    DESCRIPTION
        "Identifies a DLCI number to be added."
    ::= { ipadPktSwCfgTableEntry 20 }

ipadPktSwCfgDeleteDLCI        OBJECT-TYPE
    SYNTAX  INTEGER
    MAX-ACCESS  read-write
    STATUS  current
    DESCRIPTION
        "Identifies a DLCI number to be deleted."
    ::= { ipadPktSwCfgTableEntry 21 }

-- ipadTrapDest    section
-- ipadTrapDestTable contains trap destinations

ipadTrapDestTable    OBJECT-TYPE
    SYNTAX  SEQUENCE OF IpadTrapDestTableEntry
    MAX-ACCESS  not-accessible
    STATUS  current
    DESCRIPTION
        "The ipad trap destination table."
    ::= { ipadTrapDest 1 }

ipadTrapDestTableEntry    OBJECT-TYPE
    SYNTAX  IpadTrapDestTableEntry
    MAX-ACCESS  not-accessible
    STATUS  current
    DESCRIPTION
        "An entry in the ipad trap destination table."
    INDEX    { ipadTrapDestIndex }
    ::= { ipadTrapDestTable 1 }

IpadTrapDestTableEntry ::=
    SEQUENCE
    {
    ipadTrapDestIndex        INTEGER,
    ipadTrapDestination      IpAddress
    }

ipadTrapDestIndex    OBJECT-TYPE
    SYNTAX  INTEGER
    MAX-ACCESS  read-only
    STATUS  current
    DESCRIPTION
        "Index into the ipad trap destination table."
    ::= { ipadTrapDestTableEntry 1 }

ipadTrapDestination    OBJECT-TYPE
    SYNTAX  IpAddress
    MAX-ACCESS  read-write
    STATUS  current
    DESCRIPTION
        "Trap destination."
    ::= { ipadTrapDestTableEntry 2 }

-- ipad-specific Service Aware trap definitions

ipadFrPortRxInvalidFramesExceeded    NOTIFICATION-TYPE
    OBJECTS
        {
        ipadFrPortRxInvAlmAlarm
        }
    STATUS        current
    DESCRIPTION
        "This trap is sent out when an ipad frame relay
        port receive invalid frames alarm threshold has 
        been exceeded."
    ::= { ipadTrapsPrefix 25000 }

ipadFrPortRxThroughputExceeded    NOTIFICATION-TYPE
    OBJECTS
        {
        ipadFrPortRxAlmAlarm
        }
    STATUS        current
    DESCRIPTION
        "This trap is sent out when an ipad frame relay
        port receive throughput threshold has been exceeded."
    ::= { ipadTrapsPrefix 25001 }

ipadFrPortTxThroughputExceeded    NOTIFICATION-TYPE
    OBJECTS
        {
        ipadFrPortTxAlmAlarm
        }
    STATUS        current
    DESCRIPTION
        "This trap is sent out when an ipad frame relay
        port transmit throughput threshold has been exceeded."
    ::= { ipadTrapsPrefix 25002 }

ipadDLCItxCIRexceeded    NOTIFICATION-TYPE
    OBJECTS
        {
        ipadDLCItxExCIRAlarm
        }
    STATUS        current
    DESCRIPTION
        "This trap is sent out when the Tx over CIR threshold
        has been exceeded.  This threshold is the number of
        frames in excess of CIR."
    ::= { ipadTrapsPrefix 25003 }

ipadDLCItxBEexceeded    NOTIFICATION-TYPE
    OBJECTS
        {
        ipadDLCItxExBeAlarm
        }
    STATUS        current
    DESCRIPTION
        "This trap is sent out when the Tx over Be threshold
        has been exceeded.  This threshold is the number of
        frames in excess of Be."
    ::= { ipadTrapsPrefix 25004 }

ipadDLCIRxCongestionExceeded    NOTIFICATION-TYPE
    OBJECTS
        {
        ipadDLCIrxCongAlarm
        }
    STATUS        current
    DESCRIPTION
        "This trap is sent out when the Rx congestion threshold
        has been exceeded.  This threshold is the number of
        frames received with BECN/FECN."
    ::= { ipadTrapsPrefix 25005 }

ipadUserTxExceeded    NOTIFICATION-TYPE
    OBJECTS
        {
        ipadUserTxAlmAlarm
        }
    STATUS        current
    DESCRIPTION
        "This trap is sent out when the Tx throughput threshold
        in bits per second has been exceeded.  This threshold
        represents the number of bits for the user-selected
        protocol."
    ::= { ipadTrapsPrefix 25006 }

ipadDlciRxBECNinCIRAlarm    NOTIFICATION-TYPE
    OBJECTS
        {
        ipadDLCIrxBECNinCIR
        }
    STATUS        current
    DESCRIPTION
        "This trap is sent out when a frame with BECN set has
        been received within CIR."
    ::= { ipadTrapsPrefix 25007 }
    
ipadDlciUASExceeded    NOTIFICATION-TYPE
    OBJECTS
        {
        ipadDLCIUASAlarm
        }
    STATUS        current
    DESCRIPTION
        "This trap is sent out when the UAS (unavailable seconds)
        threshold for the DLCI has been exceeded."
    ::= { ipadTrapsPrefix 25008 }

-- ipad-specific Serial DTE alarm trap definitions

ipadserialDteDTRAlarmExists    NOTIFICATION-TYPE
    OBJECTS
        {
        serialDteDTRAlarmStatus
        }
    STATUS        current
    DESCRIPTION
        "This trap is sent out when a DTR Loss alarm is declared."
    ::= { ipadTrapsPrefix 25009 }


-- ipad-specific T1E1 alarm trap definitions

ipadt1e1ESAlarmDeclared        NOTIFICATION-TYPE
    OBJECTS
        {
        t1e1ESCount
        }
    STATUS        current
    DESCRIPTION
        "This trap is sent out when an Errored Seconds
        alarm is declared."
    ::= { ipadTrapsPrefix 25010 }

ipadt1e1SESAlarmDeclared    NOTIFICATION-TYPE
    OBJECTS
        {
        t1e1SESCount
        }
    STATUS        current
    DESCRIPTION
        "This trap is sent out when a Severely Errored Seconds
        alarm is declared."
    ::= { ipadTrapsPrefix 25011 }

ipadt1e1LOSSAlarmDeclared    NOTIFICATION-TYPE
    OBJECTS
        {
        t1e1LOSSCount
        }
    STATUS        current
    DESCRIPTION
        "This trap is sent out when a Loss of Signal Seconds
        alarm is declared."
    ::= { ipadTrapsPrefix 25012 }

ipadt1e1UASAlarmDeclared    NOTIFICATION-TYPE
    OBJECTS
        {
        t1e1UASCount
        }
    STATUS        current
    DESCRIPTION
        "This trap is sent out when an Unavailable Seconds
        alarm is declared."
    ::= { ipadTrapsPrefix 25013 }

ipadt1e1CSSAlarmDeclared    NOTIFICATION-TYPE
    OBJECTS
        {
        t1e1CSSCount
        }
    STATUS        current
    DESCRIPTION
        "This trap is sent out when a Controlled Slip Seconds
        alarm is declared."
    ::= { ipadTrapsPrefix 25014 }

ipadt1e1BPVSAlarmDeclared    NOTIFICATION-TYPE
    OBJECTS
        {
        t1e1BPVSCount
        }
    STATUS        current
    DESCRIPTION
        "This trap is sent out when a Bipolar Violation Seconds
        alarm is declared."
    ::= { ipadTrapsPrefix 25015 }

ipadt1e1OOFSAlarmDeclared    NOTIFICATION-TYPE
    OBJECTS
        {
        t1e1OOFSCount
        }
    STATUS        current
    DESCRIPTION
        "This trap is sent out when an Out of Frame Seconds
        alarm is declared."
    ::= { ipadTrapsPrefix 25016 }

ipadt1e1AISAlarmExists    NOTIFICATION-TYPE
    OBJECTS
        {
        t1e1AISCount
        }
    STATUS        current
    DESCRIPTION
        "This trap is sent out when an Alarm Indication Signal
        alarm is declared."
    ::= { ipadTrapsPrefix 25017 }

ipadt1e1RASAlarmExists    NOTIFICATION-TYPE
    OBJECTS
        {
        t1e1RASCount
        }
    STATUS        current
    DESCRIPTION
        "This trap is sent out when a Remote Alarm Signal
        alarm is declared."
    ::= { ipadTrapsPrefix 25018 }

-- ipad specific remote SOS alarm

ipadDLCIremoteSOSAlarm NOTIFICATION-TYPE
    OBJECTS
        {
        ipadDLCIremoteEquipActive
        }
    STATUS        current
    DESCRIPTION
        "This trap is sent when the remote unit for a
        DLCI senses and reports an SOS condition."
    ::= { ipadTrapsPrefix 25019 }

-- ipad-specific DDS alarm trap definitions

ipadDdsLOSSAlarmDeclared    NOTIFICATION-TYPE
    OBJECTS
        {
        ddsNetLOSCount
        }
    STATUS        current
    DESCRIPTION
        "This trap is sent out when a Loss of Signal Seconds
        alarm is declared."
    ::= { ipadTrapsPrefix 25020 }

ipadDdsOOFSAlarmDeclared    NOTIFICATION-TYPE
    OBJECTS
        {
        ddsNetOOFCount
        }
    STATUS        current
    DESCRIPTION
        "This trap is sent out when an Out of Frame Seconds
        alarm is declared."
    ::= { ipadTrapsPrefix 25021 }

ipadDdsOOSSAlarmDeclared    NOTIFICATION-TYPE
    OBJECTS
        {
        ddsNetOOSCount
        }
    STATUS        current
    DESCRIPTION
        "This trap is sent out when an Out of Service Seconds
        alarm is declared."
    ::= { ipadTrapsPrefix 25022 }

ipadDdsFDLSAlarmDeclared    NOTIFICATION-TYPE
    OBJECTS
        {
        ddsNetFDLCount
        }
    STATUS        current
    DESCRIPTION
        "This trap is sent out when a FDL error Seconds
        alarm is declared."
    ::= { ipadTrapsPrefix 25023 }

ipadDdsBPVSAlarmDeclared    NOTIFICATION-TYPE
    OBJECTS
        {
        ddsNetBPVCount
        }
    STATUS        current
    DESCRIPTION
        "This trap is sent out when a Bipolar Violation Seconds
        alarm is declared."
    ::= { ipadTrapsPrefix 25024 }

 
-- ipad specific DS0 Utilization Monitor trap definitions
 
ipadDS0HighAlarmDeclared	NOTIFICATION-TYPE
	OBJECTS
	{
	ipadDS0ConfigHighUtilCount
	}
	STATUS	current
	DESCRIPTION
		"This trap is sent out when a high utilization
		alarm is declared."
	::= { ipadTrapsPrefix 25025 }
 
ipadDS0LowAlarmDeclared	NOTIFICATION-TYPE
	OBJECTS
	{
	ipadDS0ConfigLowUtilAlarm
	}
	STATUS	current
	DESCRIPTION
		"This trap is sent out when a low utilization
		alarm is declared."
	::= { ipadTrapsPrefix 25026 }
 
 
-- ipad specific HDLC Utilization Monitor trap definitions
 
ipadHDLCRxHighAlarmDeclared	NOTIFICATION-TYPE
	OBJECTS
	{
	ipadHDLCConfigRxHighUtilCount
	}
	STATUS	current
	DESCRIPTION
		"This trap is sent out when a high Rx utilization
		alarm is declared."
	::= { ipadTrapsPrefix 25027 }
 
ipadHDLCRxLowAlarmDeclared	NOTIFICATION-TYPE
	OBJECTS
	{
	ipadHDLCConfigRxLowUtilAlarm
	}
	STATUS	current
	DESCRIPTION
		"This trap is sent out when a low Rx utilization
		alarm is declared."
	::= { ipadTrapsPrefix 25028 }
 
ipadHDLCTxHighAlarmDeclared	NOTIFICATION-TYPE
	OBJECTS
	{
	ipadHDLCConfigTxHighUtilCount
	}
	STATUS	current
	DESCRIPTION
		"This trap is sent out when a high Tx utilization
		alarm is declared."
	::= { ipadTrapsPrefix 25029 }
 
ipadHDLCTxLowAlarmDeclared	NOTIFICATION-TYPE
	OBJECTS
	{
	ipadHDLCConfigTxLowUtilAlarm
	}
	STATUS	current
	DESCRIPTION
		"This trap is sent out when a low Tx utilization
		alarm is declared."
	::= { ipadTrapsPrefix 25030 }

-- ipad specific Dial Backup Configuration Table trap definitions
 
ipadDbuActivated	NOTIFICATION-TYPE
	OBJECTS
	{
		ipadDbuStatus
	}
	STATUS	current
	DESCRIPTION
		"This trap is sent out when Dial Backup becomes active."
	::= { ipadTrapsPrefix 25031 }
 
 
 
-- ipadMisc section
-- ipadMiscPortSettings contains, currently, a table indicating if a
--    serial interface should be set for DTE or DCE

ipadMiscPortSettings	OBJECT-TYPE
	SYNTAX  SEQUENCE OF IpadMiscPortSettingsEntry
	MAX-ACCESS  not-accessible
	STATUS  current
	DESCRIPTION
		"The ipad miscellaneous port settings table."
	::= { ipadMisc 1 }

ipadMiscPortSettingsEntry	OBJECT-TYPE
	SYNTAX  IpadMiscPortSettingsEntry
	MAX-ACCESS  not-accessible
	STATUS  current
	DESCRIPTION
		"An entry in the ipad miscellaneous port settings table."
	INDEX	{ ipadMiscPortSettingsIndex }
	::= { ipadMiscPortSettings 1 }

IpadMiscPortSettingsEntry ::=
	SEQUENCE
	{
		ipadMiscPortSettingsIndex		INTEGER,
		ipadMiscPortSettingsSerialType		INTEGER,
		ipadMiscPortSettingsModemControl	INTEGER
	}

ipadMiscPortSettingsIndex	OBJECT-TYPE
	SYNTAX  INTEGER
	MAX-ACCESS  read-only
	STATUS  current
	DESCRIPTION
		"The MIB-II ifIndex for this port."
	::= { ipadMiscPortSettingsEntry 1 }

ipadMiscPortSettingsSerialType	OBJECT-TYPE
	SYNTAX  INTEGER
	{
		other(1),
		dce(2),
		dte(3)
	}
	MAX-ACCESS  read-write
	STATUS  current
	DESCRIPTION
		"The type of this serial port."
	::= { ipadMiscPortSettingsEntry 2 }

ipadMiscPortSettingsModemControl	OBJECT-TYPE
	SYNTAX  INTEGER
	{
		other(1),
		disable(2),
		enable(3)
	}
	MAX-ACCESS  read-write
	STATUS  current
	DESCRIPTION
		"Request the attached service to use the modem dialing control feature."
	::= { ipadMiscPortSettingsEntry 3 }

ipadMiscClearStatusCounts    OBJECT-TYPE
    SYNTAX  INTEGER
    {
    other(1),
    clearAll(2)
    }
    MAX-ACCESS  read-write
    STATUS  current
    DESCRIPTION
        "Writing a 2 to this field will clear all status counts."
    ::= { ipadMisc 2 }

ipadMiscEnableServiceAware	OBJECT-TYPE
	SYNTAX	INTEGER
	{
    other(1),
    disable(2),
    enable(3)
	}
	MAX-ACCESS	read-write
	STATUS		current
	DESCRIPTION
		"Writing a 3 to this field will enable service aware statistics
		gathering."
	::= { ipadMisc 3 }

 
ipadMiscShdslConfigTable    OBJECT-TYPE
    SYNTAX  SEQUENCE OF IpadMiscShdslConfigEntry
    MAX-ACCESS  not-accessible
    STATUS  current
    DESCRIPTION
        "The ipad miscellaneous SHDSL configuration table."
    ::= { ipadMisc 4 }
 
ipadMiscShdslConfigEntry    OBJECT-TYPE
    SYNTAX  IpadMiscShdslConfigEntry
    MAX-ACCESS  not-accessible
    STATUS  current
    DESCRIPTION
        "An entry in the ipad miscellaneous SHDSL configuration table."
    INDEX    { ipadMiscShdslConfigIndex }
    ::= { ipadMiscShdslConfigTable 1 }
 
IpadMiscShdslConfigEntry ::=
    SEQUENCE
    {
    ipadMiscShdslConfigIndex             INTEGER,
    ipadMiscShdslTerminalType            INTEGER,
    ipadMiscShdslTiming                  INTEGER,
    ipadMiscShdslStationInTiming         INTEGER,
    ipadMiscShdslStationTimingNxMultiple INTEGER,
    ipadMiscShdslAutomaticRetrain        INTEGER
    }
 
ipadMiscShdslConfigIndex   OBJECT-TYPE
	SYNTAX  INTEGER
	MAX-ACCESS  read-only
	STATUS  current
	DESCRIPTION
		"This object is the index into the SHDSL configuration table."
	::= { ipadMiscShdslConfigEntry 1 }
 
ipadMiscShdslTerminalType OBJECT-TYPE
	SYNTAX	INTEGER
			{
			other(1),
			isXtuC(2),
			isXtuR(3)
			}
	MAX-ACCESS	read-write
	STATUS		current
	DESCRIPTION
		"Selects whether the tu is a central or remote site terminal unit.
		Applicable to HDSL2/SHDSL only."
	::= { ipadMiscShdslConfigEntry 2 }
	
 
 
ipadMiscShdslTiming      OBJECT-TYPE
	SYNTAX  INTEGER
		{
		shdslTimingOther(1),
		shdslTimingInternal(2),
		shdslTimingNetwork(3),
		shdslTimingEqDTE(4),
		shdslTimingStation(5),
		shdslTimingPort1(6),
		shdslTimingPort2(7)
		}
	MAX-ACCESS  read-write
	STATUS  current
	DESCRIPTION
		"Sets the timing source to synchronize the unit's internal timing generators."
	::= { ipadMiscShdslConfigEntry 3 }
 
ipadMiscShdslStationInTiming OBJECT-TYPE
	SYNTAX  INTEGER
		{
		shdslStationInTimingOther(1),
		shdslStationInTimingNX64(2),
		shdslStationInTiming1544(3),
		shdslStationInTiming2048(4)
		}
	MAX-ACCESS  read-write
	STATUS  current
	DESCRIPTION
		"Selects the input timing if SHDSLTiming is set to Station."
	::= { ipadMiscShdslConfigEntry 4 }
 
ipadMiscShdslStationTimingNxMultiple OBJECT-TYPE
	SYNTAX  INTEGER
	MAX-ACCESS  read-write
	STATUS  current
	DESCRIPTION
		"Selects the N-multiple when Station Input Timing is set to either NX56 or NX65."
	::= { ipadMiscShdslConfigEntry 5 }
 
 
ipadMiscShdslAutomaticRetrain OBJECT-TYPE
    SYNTAX  INTEGER
			{
			other(1),
			disable(2),
			enable(3)
			}
    MAX-ACCESS  read-write
    STATUS  current
    DESCRIPTION
        "Enable or disable automatic line retraining when needed.
		Enable is the default. Disable is used for PSD measurement."
	::= { ipadMiscShdslConfigEntry 6 }
 
ipadMiscShdslStatusTable    OBJECT-TYPE
    SYNTAX  SEQUENCE OF IpadMiscShdslStatusEntry
    MAX-ACCESS  not-accessible
    STATUS  current
    DESCRIPTION
        "The ipad miscellaneous SHDSL status table."
    ::= { ipadMisc 5 }
 
ipadMiscShdslStatusEntry    OBJECT-TYPE
    SYNTAX  IpadMiscShdslStatusEntry
    MAX-ACCESS  not-accessible
    STATUS  current
    DESCRIPTION
        "An entry in the ipad miscellaneous SHDSL status table."
    INDEX    { ipadMiscShdslStatusIndex }
    ::= { ipadMiscShdslStatusTable 1 }
 
IpadMiscShdslStatusEntry ::=
    SEQUENCE
    {
    ipadMiscShdslStatusIndex              INTEGER,
    ipadMiscShdslConnectionStatus         INTEGER,
    ipadMiscShdslDetailedConnectionStatus DisplayString,
    ipadMiscShdslEOCInMessages            INTEGER,
    ipadMiscShdslEOCOutMessages           INTEGER,
    ipadMiscShdslConnectionStatusPair2    INTEGER,
    ipadMiscShdslDetailedConnectionStatusPair2 DisplayString
    }
 
ipadMiscShdslStatusIndex   OBJECT-TYPE
	SYNTAX  INTEGER
	MAX-ACCESS  read-only
	STATUS  current
	DESCRIPTION
		"This object is the index into the SHDSL configuration table."
	::= { ipadMiscShdslStatusEntry 1 }
 
ipadMiscShdslConnectionStatus   OBJECT-TYPE
	SYNTAX  INTEGER
		{
		idle(1),
		handshake(2),
		training(3),
		data(4)
		}
	MAX-ACCESS  read-only
	STATUS  current
	DESCRIPTION
		"This object displays the connection status of Wire Pair 1 of an SHDSL connection."
	::= { ipadMiscShdslStatusEntry 2 }
 
ipadMiscShdslDetailedConnectionStatus   OBJECT-TYPE
        SYNTAX  DisplayString(SIZE(0..20))
	MAX-ACCESS  read-only
	STATUS  current
	DESCRIPTION
		"This object displays the detailed connection status of Wire Pair 1 of an SHDSL connection."
	::= { ipadMiscShdslStatusEntry 3 }
 
ipadMiscShdslEOCInMessages   OBJECT-TYPE
	SYNTAX  INTEGER
	MAX-ACCESS  read-only
	STATUS  current
	DESCRIPTION
		"This object displays the number of EOC messages received."
	::= { ipadMiscShdslStatusEntry 4 }
 
ipadMiscShdslEOCOutMessages   OBJECT-TYPE
	SYNTAX  INTEGER
	MAX-ACCESS  read-only
	STATUS  current
	DESCRIPTION
		"This object displays the number of EOC messages transmitted."
	::= { ipadMiscShdslStatusEntry 5 }
 
ipadMiscShdslConnectionStatusPair2   OBJECT-TYPE
	SYNTAX  INTEGER
		{
		idle(1),
		handshake(2),
		training(3),
		data(4)
		}
	MAX-ACCESS  read-only
	STATUS  current
	DESCRIPTION
		"This object displays the connection status of Wire Pair 2 of an SHDSL connection."
	::= { ipadMiscShdslStatusEntry 6 }
 
ipadMiscShdslDetailedConnectionStatusPair2   OBJECT-TYPE
        SYNTAX  DisplayString(SIZE(0..20))
	MAX-ACCESS  read-only
	STATUS  current
	DESCRIPTION
		"This object displays the detailed connection status of Wire Pair 2 of an SHDSL connection."
	::= { ipadMiscShdslStatusEntry 7 }

ipadMiscEnableSupervisoryPort	OBJECT-TYPE
	SYNTAX	INTEGER
	{
    other(1),
    disable(2),
    enable(3)
	}
	MAX-ACCESS	read-write
	STATUS		current
	DESCRIPTION
		"Writing a 2 to this field will disable VT100 and telnet.
		Writing a 3 to this field will enable VT100 and telnet."
	::= { ipadMisc 6 }
	
ipadMiscEnableButtons	OBJECT-TYPE
	SYNTAX	INTEGER
	{
    other(1),
    disable(2),
    enable(3)
	}
	MAX-ACCESS	read-write
	STATUS		current
	DESCRIPTION
		"Writing a 2 to this field will disable the buttons.
		Writing a 3 to this field will enable the buttons."
	::= { ipadMisc 7 }
 
ipadMiscBootupConsoleAvail	OBJECT-TYPE
	SYNTAX	INTEGER
	{
    other(1),
    disable(2),
    enable(3)
	}
	MAX-ACCESS	read-write
	STATUS		current
	DESCRIPTION
		"Writing a 2 to this field will disable the console 
		port for diagnostic messages.
		Writing a 3 to this field will enable these messages."
	::= { ipadMisc 8 }
	
ipadMiscEnableLEDs      	OBJECT-TYPE
	SYNTAX	INTEGER
	{
    other(1),
    disable(2),
    enable(3)
	}
	MAX-ACCESS	read-write
	STATUS		current
	DESCRIPTION
		"Writing a 2 to this field will disable the LEDs.
		Writing a 3 to this field will enable the LEDs."
	::= { ipadMisc 9 }

ipadMiscDisableLAN      	OBJECT-TYPE
	SYNTAX	INTEGER
	{
		other(1),
		disable(2),
		enable(3),
		half10(4),
		full10(5),
		half100(6),
		full100(7)
	}
	MAX-ACCESS	read-write
	STATUS		current
	DESCRIPTION
		"This parameter defines the setup of the Ethernet LAN port.
		 disable(2) - Disable the Ethernet LAN Port.
		 enable(3)  - Enable the Ethernet LAN port and auto-negotiate speed and duplex.
		 half10(4)  - Enable the Ethernet LAN port and manually set to 10 Mbps and half-duplex.
		 full10(5)  - Enable the Ethernet LAN port and manually set to 10 Mbps and full-duplex.
		 half100(6) - Enable the Ethernet LAN port and manually set to 100 Mbps and half-duplex.
		 full100(7) - Enable the Ethernet LAN port and manually set to 100 Mbps and full-duplex."
	::= { ipadMisc 10 }

ipadMiscLANStatus	      	OBJECT-TYPE
	SYNTAX	INTEGER
	{
		down(1),
		half10(2),
		full10(3),
		half100(4),
		full100(5),
		na(6)
	}
	MAX-ACCESS	read-only
	STATUS		current
	DESCRIPTION
		"This parameter defines the setup of the Ethernet LAN port.
		 down(1)    - Port has not negotiated.
		 half10(2)  - Port negotiated 10 Mbps and half-duplex.
		 full10(3)  - Port negotiated 10 Mbps and full-duplex.
		 half100(4) - Port negotiated 100 Mbps and half-duplex.
		 full100(5) - Port negotiated 100 Mbps and full-duplex.
		 na(6)      - Not Applicable (speed/duplex manually set)."
	::= { ipadMisc 11 }
 
-- ipadSoftKey section
-- contains software key table

ipadSoftKeyTable OBJECT-TYPE
    SYNTAX    SEQUENCE OF IpadSoftKeyTableEntry
    MAX-ACCESS    not-accessible
    STATUS    current
    DESCRIPTION
        "Table of software keys."
    ::= { ipadSoftKey 1 }

ipadSoftKeyTableEntry OBJECT-TYPE
    SYNTAX  IpadSoftKeyTableEntry
    MAX-ACCESS  not-accessible
    STATUS  current
    DESCRIPTION
        "An entry in the software key table."
    INDEX   { ipadSoftKeyIndex }
    ::= { ipadSoftKeyTable 1 }

IpadSoftKeyTableEntry ::=
    SEQUENCE
    {
    ipadSoftKeyIndex             INTEGER,
    ipadSoftKeyAcronym           DisplayString,
    ipadSoftKeyDescription       DisplayString,
    ipadSoftKeyExpirationDate    DisplayString
    }

ipadSoftKeyIndex OBJECT-TYPE
    SYNTAX  INTEGER
    MAX-ACCESS  read-only
    STATUS  current
    DESCRIPTION
        "Index into the ipad software key table."
    ::= { ipadSoftKeyTableEntry 1 }

ipadSoftKeyAcronym OBJECT-TYPE
    SYNTAX  DisplayString(SIZE(0..3))
    MAX-ACCESS  read-only
    STATUS  current
    DESCRIPTION
        "Three-letter acronym for software key."
    ::= { ipadSoftKeyTableEntry 2 }

ipadSoftKeyDescription OBJECT-TYPE
    SYNTAX  DisplayString(SIZE(0..80))
    MAX-ACCESS  read-only
    STATUS  current
    DESCRIPTION
        "Description, if available, of this software key."
    ::= { ipadSoftKeyTableEntry 3 }

ipadSoftKeyExpirationDate OBJECT-TYPE
    SYNTAX  DisplayString(SIZE(0..8))
    MAX-ACCESS  read-only
    STATUS  current
    DESCRIPTION
        "Expiration date of this software key in the format YY/MM/DD."
    ::= { ipadSoftKeyTableEntry 4 }

ipadSoftKeyEntry OBJECT-TYPE
    SYNTAX    DisplayString(SIZE(0..80))
    MAX-ACCESS    read-write
    STATUS    current
    DESCRIPTION
        "Writing a software key will enable that feature (assuming
        a correct and valid key is entered)."
    ::= { ipadSoftKey 2 }

-- TCP Server section
--

ipadTCPServerEnable OBJECT-TYPE
    SYNTAX    	INTEGER
			    {
				other(1),
			    disable(2),
				enable(3)
				}
	MAX-ACCESS  read-write
    STATUS      current
    DESCRIPTION
        "Enables/disables the TCP Server."
    ::= { ipadTCPServer 1 }

ipadTCPServerConnTable OBJECT-TYPE
    SYNTAX    	SEQUENCE OF IpadTCPServerConnTableEntry
    MAX-ACCESS  not-accessible
    STATUS    	current
    DESCRIPTION
        "Table of TCP Server connections."
    ::= { ipadTCPServer 2 }

ipadTCPServerConnTableEntry OBJECT-TYPE
    SYNTAX  	IpadTCPServerConnTableEntry
    MAX-ACCESS  not-accessible
    STATUS  	current
    DESCRIPTION
        "An entry in the TCP Server connection table."
    INDEX   { ipadTCPServerConnIndex }
    ::= { ipadTCPServerConnTable 1 }

IpadTCPServerConnTableEntry ::=
    SEQUENCE
    {
    ipadTCPServerConnIndex				INTEGER,
	ipadTCPServerConnEndpoint			DisplayString,
	ipadTCPServerConnLocalPort			INTEGER,
	ipadTCPServerConnEnableEntry		INTEGER
    }

ipadTCPServerConnIndex OBJECT-TYPE
    SYNTAX  	INTEGER
    MAX-ACCESS  read-only
    STATUS  	current
    DESCRIPTION
        "Index into the ipad TCP Server Connection table."
    ::= { ipadTCPServerConnTableEntry 1 }

ipadTCPServerConnEndpoint OBJECT-TYPE
	SYNTAX		DisplayString(SIZE(0..11))
    MAX-ACCESS  read-write
    STATUS  	current
    DESCRIPTION
        "Identifies the endpoint for this connection."
    ::= { ipadTCPServerConnTableEntry 2 }

ipadTCPServerConnLocalPort OBJECT-TYPE
	SYNTAX		INTEGER(1..65535)
    MAX-ACCESS  read-write
    STATUS  	current
    DESCRIPTION
        "Identifies the TCP port for this connection (default: 2000)."
    ::= { ipadTCPServerConnTableEntry 3 }

ipadTCPServerConnEnableEntry OBJECT-TYPE
	SYNTAX		INTEGER
			    {
				other(1),
			    disable(2),
				enable(3)
				}
    MAX-ACCESS  read-write
    STATUS  	current
    DESCRIPTION
        "Enables or disables this entry."
    ::= { ipadTCPServerConnTableEntry 4 }

ipadTCPServerAddConnEntry OBJECT-TYPE
    SYNTAX 		INTEGER 
    			{  
    			other(1),
    			addnew(2)
    			} 
    MAX-ACCESS  read-write
    STATUS  	current
    DESCRIPTION
        "Writing addnew(2) to this field causes a new (blank) 
        connection to be appended to the TCP Server Table."
    ::= { ipadTCPServer 3 }

ipadTCPServerDeleteConnEntry OBJECT-TYPE
    SYNTAX  	INTEGER
    MAX-ACCESS  read-write
    STATUS  	current
    DESCRIPTION
        "Identifies a connection table entry to be deleted."
    ::= { ipadTCPServer 4 }
 
 
ipadTCPServerHostAccessTable	OBJECT-TYPE
	SYNTAX		SEQUENCE OF IpadTCPServerHostAccessTableEntry
	MAX-ACCESS	not-accessible
	STATUS		current
	DESCRIPTION
		"Table of TCP Server IP Host Access List."
	::= { ipadTCPServer 5 }
 
ipadTCPServerHostAccessTableEntry	OBJECT-TYPE
	SYNTAX		IpadTCPServerHostAccessTableEntry
	MAX-ACCESS	not-accessible
	STATUS		current
	DESCRIPTION
		"An entry in the TCP Server Host Access List table."
	INDEX	{ ipadTCPServerHostAccessIndex }
	::= { ipadTCPServerHostAccessTable 1 }
 
IpadTCPServerHostAccessTableEntry ::=
	SEQUENCE
	{
	ipadTCPServerHostAccessIndex	INTEGER,
	ipadTCPServerHostAccessIPAddr	IpAddress
	}
 
ipadTCPServerHostAccessIndex	OBJECT-TYPE
	SYNTAX  INTEGER
	MAX-ACCESS  read-only
	STATUS  current
	DESCRIPTION
		"Index into the ipad trap destination table."
	::= { ipadTCPServerHostAccessTableEntry 1 }
 
ipadTCPServerHostAccessIPAddr	OBJECT-TYPE
	SYNTAX  IpAddress
	MAX-ACCESS  read-write
	STATUS  current
	DESCRIPTION
	"Trap destination."
	::= { ipadTCPServerHostAccessTableEntry 2 }
 
-- ipadSCADAConfig section
 
ipadSCADAConfigTable    OBJECT-TYPE
	SYNTAX  SEQUENCE OF IpadSCADAConfigTableEntry
	MAX-ACCESS  not-accessible
	STATUS  current
	DESCRIPTION
		"The SCADA config table."
	::= { ipadSCADAConfig 1 }
 
ipadSCADAConfigTableEntry       OBJECT-TYPE
	SYNTAX  IpadSCADAConfigTableEntry
	MAX-ACCESS  not-accessible
	STATUS  current
	DESCRIPTION
		"An entry in the SCADA config table."
	INDEX   { ipadSCADACfgIndex }
	::= { ipadSCADAConfigTable 1 }
 
IpadSCADAConfigTableEntry ::=
	SEQUENCE
	{
	ipadSCADACfgIndex			INTEGER,
	ipadSCADACfgMessageSize			INTEGER,
	ipadSCADACfgIdleCharDelay		INTEGER,
	ipadSCADACfgInputTerminator  		INTEGER,
	ipadSCADACfgAddDevLst			INTEGER,
	ipadSCADACfgDeleteDevLst	 	INTEGER,
	ipadSCADACfgDataDirection		INTEGER,
	ipadSCADACfgProtocol			INTEGER,
	ipadSCADACfgLoopback			INTEGER
	}
 
ipadSCADACfgIndex	OBJECT-TYPE
	SYNTAX  INTEGER
	MAX-ACCESS  read-only
	STATUS  current
	DESCRIPTION
		"The index for SCADA config table."
	::= { ipadSCADAConfigTableEntry 1 }
 
ipadSCADACfgMessageSize  OBJECT-TYPE
	SYNTAX  INTEGER
	MAX-ACCESS  read-write
	STATUS  current
	DESCRIPTION
		"The SCADA message size."
	::= { ipadSCADAConfigTableEntry 2 }
 
ipadSCADACfgIdleCharDelay  OBJECT-TYPE
	SYNTAX  INTEGER
	MAX-ACCESS  read-write
	STATUS  current
	DESCRIPTION
		"The SCADA idle character delay."
	::= { ipadSCADAConfigTableEntry 3 }
 
ipadSCADACfgInputTerminator  OBJECT-TYPE
	SYNTAX  INTEGER
	MAX-ACCESS  read-write
	STATUS  current
	DESCRIPTION
		"The SCADA input message terminator."
	::= { ipadSCADAConfigTableEntry 4 }
 
ipadSCADACfgAddDevLst OBJECT-TYPE
    SYNTAX 		INTEGER
    			{  
    			other(1),
    			addnew(2)
    			} 
    MAX-ACCESS  read-write
    STATUS  	current
    DESCRIPTION
        "Appends an entry to the SCADA device list table."
    ::= { ipadSCADAConfigTableEntry 5 }
 
ipadSCADACfgDeleteDevLst OBJECT-TYPE
    SYNTAX  	INTEGER
    MAX-ACCESS  read-write
    STATUS  	current
    DESCRIPTION
        "Deletes an entry in the SCADA device list table."
    ::= { ipadSCADAConfigTableEntry 6 }
 
ipadSCADACfgDataDirection OBJECT-TYPE
    SYNTAX 		INTEGER
    			{  
    			other(1),
    			both(2),
    			output(3),
				input(4)
    			} 
    MAX-ACCESS  read-write
    STATUS  	current
    DESCRIPTION
        "Data Direction enables for SCADA configuration."
    ::= { ipadSCADAConfigTableEntry 7 }
 
ipadSCADACfgProtocol OBJECT-TYPE
    SYNTAX      INTEGER
                {  
                other(1),
                async(2),
                syncVancommHost(3),
                syncVancommRTU(4)
                } 
    MAX-ACCESS  read-write
    STATUS      current
    DESCRIPTION
        "Configured SCADA Protocol."
    ::= { ipadSCADAConfigTableEntry 8 }
 
 
ipadSCADACfgLoopback OBJECT-TYPE
    SYNTAX	INTEGER
    		{  
    		none(1),
		network(2),
		port(3),
		both(4)
    		} 
    MAX-ACCESS  read-write
    STATUS  	current
    DESCRIPTION
        "Loopback allows user to loop data to either Network, Serial Port or both."
    ::= { ipadSCADAConfigTableEntry 9 }
 
 
-- ipadSCADAStats section
 
ipadSCADAStatsTable    OBJECT-TYPE
	SYNTAX  SEQUENCE OF IpadSCADAStatsTableEntry
	MAX-ACCESS  not-accessible
	STATUS  current
	DESCRIPTION
		"The SCADA statistics table."
	::= { ipadSCADAStats 1 }
 
ipadSCADAStatsTableEntry       OBJECT-TYPE
	SYNTAX  IpadSCADAStatsTableEntry
	MAX-ACCESS  not-accessible
	STATUS  current
	DESCRIPTION
		"An entry in the SCADA statistics table."
	INDEX   { ipadSCADAStatsIndex }
	::= { ipadSCADAStatsTable 1 }
 
IpadSCADAStatsTableEntry ::=
	SEQUENCE
	{
	ipadSCADAStatsIndex				INTEGER,
	ipadSCADAStatsTxChars			INTEGER,
	ipadSCADAStatsRxChars			INTEGER,
	ipadSCADAStatsTxMsgs			INTEGER,
	ipadSCADAStatsRxMsgs			INTEGER,
	ipadSCADAStatsRxParityErrors	INTEGER,
	ipadSCADAStatsRxFramingErrors	INTEGER,
	ipadSCADAStatsClear				INTEGER
	}
 
ipadSCADAStatsIndex	OBJECT-TYPE
	SYNTAX  INTEGER
	MAX-ACCESS  read-only
	STATUS  current
	DESCRIPTION
		"The index for SCADA Statistics Table."
	::= { ipadSCADAStatsTableEntry 1 }
 
ipadSCADAStatsTxChars  OBJECT-TYPE
	SYNTAX  INTEGER
	MAX-ACCESS  read-only
	STATUS  current
	DESCRIPTION
		"The number of chracters transmitted through SCADA port."
	::= { ipadSCADAStatsTableEntry 2 }
 
ipadSCADAStatsRxChars  OBJECT-TYPE
	SYNTAX  INTEGER
	MAX-ACCESS  read-only
	STATUS  current
	DESCRIPTION
		"The number of chracters received through SCADA port."
	::= { ipadSCADAStatsTableEntry 3 }
 
ipadSCADAStatsTxMsgs  OBJECT-TYPE
	SYNTAX  INTEGER
	MAX-ACCESS  read-only
	STATUS  current
	DESCRIPTION
		"The number of messages transmitted through SCADA port."
	::= { ipadSCADAStatsTableEntry 4 }
 
ipadSCADAStatsRxMsgs  OBJECT-TYPE
	SYNTAX  INTEGER
	MAX-ACCESS  read-only
	STATUS  current
	DESCRIPTION
		"The number of messages received through SCADA port."
	::= { ipadSCADAStatsTableEntry 5 }
 
ipadSCADAStatsRxParityErrors  OBJECT-TYPE
	SYNTAX  INTEGER
	MAX-ACCESS  read-only
	STATUS  current
	DESCRIPTION
		"The number of parity errors received from SCADA port."
	::= { ipadSCADAStatsTableEntry 6 }
 
ipadSCADAStatsRxFramingErrors  OBJECT-TYPE
	SYNTAX  INTEGER
	MAX-ACCESS  read-only
	STATUS  current
	DESCRIPTION
		"The number of framming errors received from SCADA port."
	::= { ipadSCADAStatsTableEntry 7 }
 
ipadSCADAStatsClear	OBJECT-TYPE
	SYNTAX	INTEGER
		{
		ipadSCADAStatsClearOther(1),
		ipadSCADAStatsClearNow(2)
		}
	MAX-ACCESS	read-write
	STATUS	current
	DESCRIPTION
	"Writing a value of ipadSCADAStatsClearNow(2) to this field causes all existing stats to be cleared immediately."
	::= { ipadSCADAStatsTableEntry 8 }
 
 
-- ipadSCADADevLst section
 
ipadSCADADevLstTable    OBJECT-TYPE
	SYNTAX  SEQUENCE OF IpadSCADADevLstTableEntry
	MAX-ACCESS  not-accessible
	STATUS  current
	DESCRIPTION
		"The SCADA device list table."
	::= { ipadSCADADevLst 1 }
 
ipadSCADADevLstTableEntry       OBJECT-TYPE
	SYNTAX  IpadSCADADevLstTableEntry
	MAX-ACCESS  not-accessible
	STATUS  current
	DESCRIPTION
		"An entry in the SCADA device list table."
	INDEX   { ipadSCADADevLstIndex, ipadSCADADevLstDevIndex }
	::= { ipadSCADADevLstTable 1 }
 
IpadSCADADevLstTableEntry ::=
	SEQUENCE
	{
	ipadSCADADevLstIndex				INTEGER,
	ipadSCADADevLstDevIndex				INTEGER,
	ipadSCADADevLstEndpointName			DisplayString,
	ipadSCADADevLstEntryStatus			INTEGER
	}
 
ipadSCADADevLstIndex	OBJECT-TYPE
	SYNTAX  INTEGER
	MAX-ACCESS  read-only
	STATUS  current
	DESCRIPTION
		"The index for SCADA device list table."
	::= { ipadSCADADevLstTableEntry 1 }
 
ipadSCADADevLstDevIndex  OBJECT-TYPE
	SYNTAX  INTEGER
	MAX-ACCESS  read-only
	STATUS  current
	DESCRIPTION
		"The index of device."
	::= { ipadSCADADevLstTableEntry 2 }
 
 
ipadSCADADevLstEndpointName  OBJECT-TYPE
	SYNTAX  DisplayString(SIZE(0..11))
	MAX-ACCESS  read-write
	STATUS  current
	DESCRIPTION
		"The name of the endpoint."
	::= { ipadSCADADevLstTableEntry 3 }
 
 
ipadSCADADevLstEntryStatus  OBJECT-TYPE
	SYNTAX  INTEGER
			{
			other(1),
			disable(2),
			enable(3)
			}
	MAX-ACCESS  read-write
	STATUS  current
	DESCRIPTION
		"The disabled or dnabled status of the entry."
	::= { ipadSCADADevLstTableEntry 4 }
 
 
-- ipadDS0Config section
-- contains the DS0 Utilization Monitor Config table
 
ipadDS0ConfigTable	OBJECT-TYPE
	SYNTAX SEQUENCE OF IpadDS0ConfigTableEntry
	MAX-ACCESS	not-accessible
	STATUS	current
	DESCRIPTION
		"The ipad DS0 Utilization Monitor Config table."
	::= { ipadDS0Config 1 }
 
ipadDS0ConfigTableEntry	OBJECT-TYPE
	SYNTAX IpadDS0ConfigTableEntry
	MAX-ACCESS	not-accessible
	STATUS	current
	DESCRIPTION
		"An entry in the ipad DS0 Utilization Monitor Config table."
	INDEX	{ ipadDS0ConfigIndex }
	::= { ipadDS0ConfigTable 1 }
 
IpadDS0ConfigTableEntry ::=
	SEQUENCE
	{
	ipadDS0ConfigIndex		INTEGER,
	ipadDS0ConfigNumberDS0		INTEGER,
	ipadDS0ConfigResetTimer		INTEGER,
	ipadDS0ConfigHighUtil		INTEGER,
	ipadDS0ConfigHighUtilThreshold	INTEGER,
	ipadDS0ConfigHighUtilStatus	INTEGER,
	ipadDS0ConfigHighUtilCount	INTEGER,
	ipadDS0ConfigHighUtilAlarm	INTEGER,
	ipadDS0ConfigLowUtil		INTEGER,
	ipadDS0ConfigLowUtilAlarm	INTEGER,
	ipadDS0ConfigReset		INTEGER
	}
 
ipadDS0ConfigIndex	OBJECT-TYPE
	SYNTAX INTEGER
	MAX-ACCESS	read-only
	STATUS	current
	DESCRIPTION
		"Index into the DS0 Utilization Monitor Config table."
	::= { ipadDS0ConfigTableEntry 1 }
 
ipadDS0ConfigNumberDS0	OBJECT-TYPE
	SYNTAX INTEGER
	MAX-ACCESS	read-only
	STATUS	current
	DESCRIPTION
		"Number of DS0's monitored by this table entry."
	::= { ipadDS0ConfigTableEntry 2 }
 
ipadDS0ConfigResetTimer	OBJECT-TYPE
	SYNTAX INTEGER
	MAX-ACCESS	read-write
	STATUS	current
	DESCRIPTION
		"Number of contiguous seconds a utilization alarm must not
		be present before the alarm condition is automatically reset."
	::= { ipadDS0ConfigTableEntry 3 }
 
ipadDS0ConfigHighUtil	OBJECT-TYPE
	SYNTAX INTEGER
	MAX-ACCESS	read-write
	STATUS	current
	DESCRIPTION
		"What the user considers a high DS0 utilization for this entry.
		Utilization is expressed as a percentage."
	::= { ipadDS0ConfigTableEntry 4 }
 
ipadDS0ConfigHighUtilThreshold	OBJECT-TYPE
	SYNTAX INTEGER
	MAX-ACCESS	read-write
	STATUS	current
	DESCRIPTION
		"Number of seconds a high utilization condition must be
		present within 15 minutes before an alarm condition is
		declared."
	::= { ipadDS0ConfigTableEntry 5 }
 
ipadDS0ConfigHighUtilStatus	OBJECT-TYPE
    SYNTAX 		INTEGER
    			{  
    			other(1),
		notExist(2),
		exists(3)
		}
	MAX-ACCESS	read-only
	STATUS	current
	DESCRIPTION
		"Indicates if a high utilization condition exists."
	::= { ipadDS0ConfigTableEntry 6 }
 
ipadDS0ConfigHighUtilCount	OBJECT-TYPE
	SYNTAX INTEGER
	MAX-ACCESS	read-only
	STATUS	current
	DESCRIPTION
		"The number of seconds in the past 15 minutes that have
		been greater than or equal to the high utilization parameter.
		The value is calculated from a sliding window of
		15 one-minute buckets."
	::= { ipadDS0ConfigTableEntry 7 }
 
ipadDS0ConfigHighUtilAlarm	OBJECT-TYPE
	SYNTAX INTEGER
		{
		other(1),
		noAlarm(2),
		thresholdExceeded(3)
    			} 
	MAX-ACCESS	read-only
	STATUS	current
	DESCRIPTION
		"Indicates if the high utilization alarm threshold is exceeded."
	::= { ipadDS0ConfigTableEntry 8 }
 
ipadDS0ConfigLowUtil	OBJECT-TYPE
	SYNTAX INTEGER
    MAX-ACCESS  read-write
    STATUS  	current
    DESCRIPTION
		"What the user considers an end-of-day low DS0 utilization
		for this entry.  Utilization is expressed as a percentage.
		When the utilization is set to zero the low utilization
		alarm is disabled."
	::= { ipadDS0ConfigTableEntry 9 }
 
ipadDS0ConfigLowUtilAlarm	OBJECT-TYPE
	SYNTAX INTEGER
		{
		other(1),
		noAlarm(2),
		thresholdExceeded(3)
		}
	MAX-ACCESS	read-only
	STATUS	current
	DESCRIPTION
		"Indicates if the low utilization alarm is declared."
	::= { ipadDS0ConfigTableEntry 10 }
 
ipadDS0ConfigReset	OBJECT-TYPE
    SYNTAX  	INTEGER
		{
		none(1),
		clearAlarms(2),
		clearHistory(3)
		}
    MAX-ACCESS  read-write
    STATUS  	current
    DESCRIPTION
		"The set values perform the following actions:
		clearAlarms(2) - Clears any active DS0 utilization alarms and counts
		clearHistory(3) - Clears DS0 utilization history tables."
	::= { ipadDS0ConfigTableEntry 11 }
 
-- ipadDS0Hist24 section
-- contains the DS0 Utilization Monitor 24-Hour History table
 
ipadDS0Hist24Table	OBJECT-TYPE
	SYNTAX SEQUENCE OF IpadDS0Hist24TableEntry
	MAX-ACCESS	not-accessible
	STATUS	current
	DESCRIPTION
		"The ipad DS0 Utilization Monitor 24-Hour History table."
	::= { ipadDS0Hist24 1 }
 
ipadDS0Hist24TableEntry	OBJECT-TYPE
	SYNTAX IpadDS0Hist24TableEntry
	MAX-ACCESS	not-accessible
	STATUS	current
	DESCRIPTION
		"An entry in the ipad DS0 Utilization Monitor 24-Hour History table."
	INDEX	{ ipadDS0Hist24Index, ipadDS0Hist24HistoricalIndex }
	::= { ipadDS0Hist24Table 1 }
 
IpadDS0Hist24TableEntry ::=
	SEQUENCE
	{
	ipadDS0Hist24Index		INTEGER,
	ipadDS0Hist24HistoricalIndex	INTEGER,
	ipadDS0Hist24Timestamp		TimeTicks,
	ipadDS0Hist24HighUtilSeconds	INTEGER,
	ipadDS0Hist24Utilization	INTEGER
	}
 
ipadDS0Hist24Index	OBJECT-TYPE
	SYNTAX INTEGER
	MAX-ACCESS	read-only
	STATUS	current
	DESCRIPTION
		"Index into the DS0 Utilization Monitor 24-Hour History table."
	::= { ipadDS0Hist24TableEntry 1 }
 
ipadDS0Hist24HistoricalIndex	OBJECT-TYPE
	SYNTAX INTEGER
		{
		statSummary(1),
		statCurrent(2),
 
		statPeriod1(3),
		statPeriod2(4),
		statPeriod3(5),
		statPeriod4(6),
		statPeriod5(7),
		statPeriod6(8),
		statPeriod7(9),
		statPeriod8(10),
		statPeriod9(11),
 
		statPeriod10(12),
		statPeriod11(13),
		statPeriod12(14),
		statPeriod13(15),
		statPeriod14(16),
		statPeriod15(17),
		statPeriod16(18),
		statPeriod17(19),
		statPeriod18(20),
		statPeriod19(21),
 
		statPeriod20(22),
		statPeriod21(23),
		statPeriod22(24),
		statPeriod23(25),
		statPeriod24(26),
		statPeriod25(27),
		statPeriod26(28),
		statPeriod27(29),
		statPeriod28(30),
		statPeriod29(31),
 
		statPeriod30(32),
		statPeriod31(33),
		statPeriod32(34),
		statPeriod33(35),
		statPeriod34(36),
		statPeriod35(37),
		statPeriod36(38),
		statPeriod37(39),
		statPeriod38(40),
		statPeriod39(41),
 
		statPeriod40(42),
		statPeriod41(43),
		statPeriod42(44),
		statPeriod43(45),
		statPeriod44(46),
		statPeriod45(47),
		statPeriod46(48),
		statPeriod47(49),
		statPeriod48(50),
		statPeriod49(51),
 
		statPeriod50(52),
		statPeriod51(53),
		statPeriod52(54),
		statPeriod53(55),
		statPeriod54(56),
		statPeriod55(57),
		statPeriod56(58),
		statPeriod57(59),
		statPeriod58(60),
		statPeriod59(61),
 
		statPeriod60(62),
		statPeriod61(63),
		statPeriod62(64),
		statPeriod63(65),
		statPeriod64(66),
		statPeriod65(67),
		statPeriod66(68),
		statPeriod67(69),
		statPeriod68(70),
		statPeriod69(71),
 
		statPeriod70(72),
		statPeriod71(73),
		statPeriod72(74),
		statPeriod73(75),
		statPeriod74(76),
		statPeriod75(77),
		statPeriod76(78),
		statPeriod77(79),
		statPeriod78(80),
		statPeriod79(81),
 
		statPeriod80(82),
		statPeriod81(83),
		statPeriod82(84),
		statPeriod83(85),
		statPeriod84(86),
		statPeriod85(87),
		statPeriod86(88),
		statPeriod87(89),
		statPeriod88(90),
		statPeriod89(91),
 
		statPeriod90(92),
		statPeriod91(93),
		statPeriod92(94),
		statPeriod93(95),
		statPeriod94(96),
		statPeriod95(97),
		statPeriod96(98)
		}
	MAX-ACCESS	read-only
	STATUS	current
	DESCRIPTION
		"Historical index into the DS0 Utilization Monitor 24-Hour History table."
	::= { ipadDS0Hist24TableEntry 2 }
 
ipadDS0Hist24Timestamp	OBJECT-TYPE
	SYNTAX TimeTicks
	MAX-ACCESS	read-only
	STATUS	current
	DESCRIPTION
		"SysUpTime when the utilization interval completed."
	::= { ipadDS0Hist24TableEntry 3 }
 
ipadDS0Hist24HighUtilSeconds	OBJECT-TYPE
	SYNTAX INTEGER
	MAX-ACCESS	read-only
	STATUS	current
	DESCRIPTION
		"The number of seconds in the interval that have
		been greater than or equal to the high utilization parameter."
	::= { ipadDS0Hist24TableEntry 4 }
 
ipadDS0Hist24Utilization	OBJECT-TYPE
	SYNTAX INTEGER
	MAX-ACCESS	read-only
	STATUS	current
	DESCRIPTION
		"The percent of DS0's utilized over the given interval."
	::= { ipadDS0Hist24TableEntry 5 }
 
 
-- ipadDS0Hist30 section
-- contains the DS0 Utilization Monitor 30-Day History table
 
ipadDS0Hist30Table	OBJECT-TYPE
	SYNTAX SEQUENCE OF IpadDS0Hist30TableEntry
	MAX-ACCESS	not-accessible
	STATUS	current
	DESCRIPTION
		"The ipad DS0 Utilization Monitor 30-Day History table."
	::= { ipadDS0Hist30 1 }
 
ipadDS0Hist30TableEntry	OBJECT-TYPE
	SYNTAX IpadDS0Hist30TableEntry
	MAX-ACCESS	not-accessible
	STATUS	current
	DESCRIPTION
		"An entry in the ipad DS0 Utilization Monitor 30-Day History table."
	INDEX	{ ipadDS0Hist30Index, ipadDS0Hist30HistoricalIndex }
	::= { ipadDS0Hist30Table 1 }
 
IpadDS0Hist30TableEntry ::=
	SEQUENCE
	{
	ipadDS0Hist30Index		INTEGER,
	ipadDS0Hist30HistoricalIndex	INTEGER,
	ipadDS0Hist30Timestamp		TimeTicks,
	ipadDS0Hist30HighUtilSeconds	INTEGER,
	ipadDS0Hist30Utilization	INTEGER
	}
 
ipadDS0Hist30Index	OBJECT-TYPE
	SYNTAX INTEGER
	MAX-ACCESS	read-only
	STATUS	current
	DESCRIPTION
		"Index into the DS0 Utilization Monitor 30-Day History table."
	::= { ipadDS0Hist30TableEntry 1 }
 
ipadDS0Hist30HistoricalIndex	OBJECT-TYPE
	SYNTAX INTEGER
		{
		statSummary(1),
 
		statDay1(2),
		statDay2(3),
		statDay3(4),
		statDay4(5),
		statDay5(6),
		statDay6(7),
		statDay7(8),
		statDay8(9),
		statDay9(10),
 
		statDay10(11),
		statDay11(12),
		statDay12(13),
		statDay13(14),
		statDay14(15),
		statDay15(16),
		statDay16(17),
		statDay17(18),
		statDay18(19),
		statDay19(20),
 
		statDay20(21),
		statDay21(22),
		statDay22(23),
		statDay23(24),
		statDay24(25),
		statDay25(26),
		statDay26(27),
		statDay27(28),
		statDay28(29),
		statDay29(30),
 
		statDay30(31)
		}
	MAX-ACCESS	read-only
	STATUS	current
	DESCRIPTION
		"Historical index into the DS0 Utilization Monitor 30-Day History table."
	::= { ipadDS0Hist30TableEntry 2 }
 
ipadDS0Hist30Timestamp	OBJECT-TYPE
	SYNTAX TimeTicks
	MAX-ACCESS	read-only
	STATUS	current
	DESCRIPTION
		"SysUpTime when the utilization interval completed."
	::= { ipadDS0Hist30TableEntry 3 }
 
ipadDS0Hist30HighUtilSeconds	OBJECT-TYPE
	SYNTAX INTEGER
	MAX-ACCESS	read-only
	STATUS	current
	DESCRIPTION
		"The number of seconds in the interval that have
		been greater than or equal to the high utilization parameter."
	::= { ipadDS0Hist30TableEntry 4 }
 
ipadDS0Hist30Utilization	OBJECT-TYPE
	SYNTAX INTEGER
	MAX-ACCESS	read-only
	STATUS	current
	DESCRIPTION
		"The percent of DS0's utilized over the given interval."
	::= { ipadDS0Hist30TableEntry 5 }
 
 
-- ipadHDLCConfig section
-- contains the HDLC Utilization Monitor Config table
 
ipadHDLCConfigTable	OBJECT-TYPE
	SYNTAX SEQUENCE OF IpadHDLCConfigTableEntry
	MAX-ACCESS	not-accessible
	STATUS	current
	DESCRIPTION
		"The ipad HDLC Utilization Monitor Config table."
	::= { ipadHDLCConfig 1 }
 
ipadHDLCConfigTableEntry	OBJECT-TYPE
	SYNTAX IpadHDLCConfigTableEntry
	MAX-ACCESS	not-accessible
	STATUS	current
	DESCRIPTION
		"An entry in the ipad HDLC Utilization Monitor Config table."
	INDEX	{ ipadHDLCConfigIndex }
	::= { ipadHDLCConfigTable 1 }
 
IpadHDLCConfigTableEntry ::=
	SEQUENCE
	{
	ipadHDLCConfigIndex			INTEGER,
	ipadHDLCConfigService			INTEGER,
	ipadHDLCConfigServiceBPS		INTEGER,
	ipadHDLCConfigResetTimer		INTEGER,
	ipadHDLCConfigRxHighUtil		INTEGER,
	ipadHDLCConfigRxHighUtilThreshold	INTEGER,
	ipadHDLCConfigRxHighUtilStatus		INTEGER,
	ipadHDLCConfigRxHighUtilCount		INTEGER,
	ipadHDLCConfigRxHighUtilAlarm		INTEGER,
	ipadHDLCConfigRxLowUtil			INTEGER,
	ipadHDLCConfigRxLowUtilAlarm		INTEGER,
	ipadHDLCConfigTxHighUtil		INTEGER,
	ipadHDLCConfigTxHighUtilThreshold	INTEGER,
	ipadHDLCConfigTxHighUtilStatus		INTEGER,
	ipadHDLCConfigTxHighUtilCount		INTEGER,
	ipadHDLCConfigTxHighUtilAlarm		INTEGER,
	ipadHDLCConfigTxLowUtil			INTEGER,
	ipadHDLCConfigTxLowUtilAlarm		INTEGER,
	ipadHDLCConfigReset			INTEGER
	}
 
ipadHDLCConfigIndex	OBJECT-TYPE
	SYNTAX INTEGER
	MAX-ACCESS	read-only
	STATUS	current
	DESCRIPTION
		"Index into the HDLC Utilization Monitor Config table."
	::= { ipadHDLCConfigTableEntry 1 }
 
ipadHDLCConfigService	OBJECT-TYPE
	SYNTAX INTEGER
	MAX-ACCESS	read-write
	STATUS	current
	DESCRIPTION
		"Service the HDLC utilization monitor is attached.
		0 = Disabled."
	::= { ipadHDLCConfigTableEntry 2 }
 
ipadHDLCConfigServiceBPS	OBJECT-TYPE
	SYNTAX INTEGER
	MAX-ACCESS	read-only
	STATUS	current
	DESCRIPTION
		"Service bit rate."
	::= { ipadHDLCConfigTableEntry 3 }
 
ipadHDLCConfigResetTimer	OBJECT-TYPE
	SYNTAX INTEGER
	MAX-ACCESS	read-write
	STATUS	current
	DESCRIPTION
		"Number of contiguous seconds a utilization alarm must not
		be present before the alarm condition is automatically reset."
	::= { ipadHDLCConfigTableEntry 4 }
 
ipadHDLCConfigRxHighUtil	OBJECT-TYPE
	SYNTAX INTEGER
	MAX-ACCESS	read-write
	STATUS	current
	DESCRIPTION
		"What the user considers a high Rx HDLC utilization for this entry.
		Utilization is expressed as a percentage."
	::= { ipadHDLCConfigTableEntry 5 }
 
ipadHDLCConfigRxHighUtilThreshold	OBJECT-TYPE
	SYNTAX INTEGER
	MAX-ACCESS	read-write
	STATUS	current
	DESCRIPTION
		"Number of seconds a Rx high utilization condition must be
		present within 15 minutes before an alarm condition is
		declared."
	::= { ipadHDLCConfigTableEntry 6 }
 
ipadHDLCConfigRxHighUtilStatus	OBJECT-TYPE
	SYNTAX INTEGER
		{
		other(1),
		notExist(2),
		exists(3)
		}
	MAX-ACCESS	read-only
	STATUS	current
	DESCRIPTION
		"Indicates if a Rx high utilization condition exists."
	::= { ipadHDLCConfigTableEntry 7 }
 
ipadHDLCConfigRxHighUtilCount	OBJECT-TYPE
	SYNTAX INTEGER
	MAX-ACCESS	read-only
	STATUS	current
	DESCRIPTION
		"The number of seconds in the past 15 minutes that have
		been greater than or equal to the Rx high utilization parameter.
		The value is calculated from a sliding window of
		15 one-minute buckets."
	::= { ipadHDLCConfigTableEntry 8 }
 
ipadHDLCConfigRxHighUtilAlarm	OBJECT-TYPE
	SYNTAX INTEGER
		{
		other(1),
		noAlarm(2),
		thresholdExceeded(3)
		}
	MAX-ACCESS	read-only
	STATUS	current
	DESCRIPTION
		"Indicates if the Rx high utilization alarm threshold is exceeded."
	::= { ipadHDLCConfigTableEntry 9 }
 
ipadHDLCConfigRxLowUtil	OBJECT-TYPE
	SYNTAX INTEGER
	MAX-ACCESS	read-write
	STATUS	current
	DESCRIPTION
		"What the user considers an end-of-day low Rx HDLC utilization
		for this entry.  Utilization is expressed as a percentage.
		When the utilization is set to zero the Rx low utilization
		alarm is disabled."
	::= { ipadHDLCConfigTableEntry 10 }
 
ipadHDLCConfigRxLowUtilAlarm	OBJECT-TYPE
	SYNTAX INTEGER
		{
		other(1),
		noAlarm(2),
		thresholdExceeded(3)
		}
	MAX-ACCESS	read-only
	STATUS	current
	DESCRIPTION
		"Indicates if the Rx low utilization alarm is declared."
	::= { ipadHDLCConfigTableEntry 11 }
 
ipadHDLCConfigTxHighUtil	OBJECT-TYPE
	SYNTAX INTEGER
	MAX-ACCESS	read-write
	STATUS	current
	DESCRIPTION
		"What the user considers a high Tx HDLC utilization for this entry.
		Utilization is expressed as a percentage."
	::= { ipadHDLCConfigTableEntry 12 }
 
ipadHDLCConfigTxHighUtilThreshold	OBJECT-TYPE
	SYNTAX INTEGER
	MAX-ACCESS	read-write
	STATUS	current
	DESCRIPTION
		"Number of seconds a Tx high utilization condition must be
		present within 15 minutes before an alarm condition is
		declared."
	::= { ipadHDLCConfigTableEntry 13 }
 
ipadHDLCConfigTxHighUtilStatus	OBJECT-TYPE
	SYNTAX INTEGER
		{
		other(1),
		notExist(2),
		exists(3)
		}
	MAX-ACCESS	read-only
	STATUS	current
	DESCRIPTION
		"Indicates if a Tx high utilization condition exists."
	::= { ipadHDLCConfigTableEntry 14 }
 
ipadHDLCConfigTxHighUtilCount	OBJECT-TYPE
	SYNTAX INTEGER
	MAX-ACCESS	read-only
	STATUS	current
	DESCRIPTION
		"The number of seconds in the past 15 minutes that have
		been greater than or equal to the Tx high utilization parameter.
		The value is calculated from a sliding window of
		15 one-minute buckets."
	::= { ipadHDLCConfigTableEntry 15 }
 
ipadHDLCConfigTxHighUtilAlarm	OBJECT-TYPE
	SYNTAX INTEGER
		{
		other(1),
		noAlarm(2),
		thresholdExceeded(3)
		}
	MAX-ACCESS	read-only
	STATUS	current
	DESCRIPTION
		"Indicates if the Tx high utilization alarm threshold is exceeded."
	::= { ipadHDLCConfigTableEntry 16 }
 
ipadHDLCConfigTxLowUtil	OBJECT-TYPE
	SYNTAX INTEGER
	MAX-ACCESS	read-write
	STATUS	current
	DESCRIPTION
		"What the user considers an end-of-day low Tx HDLC utilization
		for this entry.  Utilization is expressed as a percentage.
		When the utilization is set to zero the Tx low utilization
		alarm is disabled."
	::= { ipadHDLCConfigTableEntry 17 }
 
ipadHDLCConfigTxLowUtilAlarm	OBJECT-TYPE
	SYNTAX INTEGER
		{
		other(1),
		noAlarm(2),
		thresholdExceeded(3)
		}
	MAX-ACCESS	read-only
	STATUS	current
	DESCRIPTION
		"Indicates if the Tx low utilization alarm is declared."
	::= { ipadHDLCConfigTableEntry 18 }
ipadHDLCConfigReset	OBJECT-TYPE
	SYNTAX INTEGER
		{
		none(1),
		clearAlarms(2),
		clearHistory(3)
		}
	MAX-ACCESS	read-write
	STATUS	current
	DESCRIPTION
		"The set values perform the following actions:
		clearAlarms(2) - Clears any active HDLC utilization alarms and counts
		clearHistory(3) - Clears HDLC utilization history tables."
	::= { ipadHDLCConfigTableEntry 19 }
 
 
-- ipadHDLCHist24 section
-- contains the HDLC Utilization Monitor 24-Hour History table
 
ipadHDLCHist24Table	OBJECT-TYPE
	SYNTAX SEQUENCE OF IpadHDLCHist24TableEntry
	MAX-ACCESS	not-accessible
	STATUS	current
	DESCRIPTION
		"The ipad HDLC Utilization Monitor 24-Hour History table."
	::= { ipadHDLCHist24 1 }
 
ipadHDLCHist24TableEntry	OBJECT-TYPE
	SYNTAX IpadHDLCHist24TableEntry
	MAX-ACCESS	not-accessible
	STATUS	current
	DESCRIPTION
		"An entry in the ipad HDLC Utilization Monitor 24-Hour History table."
	INDEX	{ ipadHDLCHist24Index, ipadHDLCHist24HistoricalIndex }
	::= { ipadHDLCHist24Table 1 }
 
IpadHDLCHist24TableEntry ::=
	SEQUENCE
	{
	ipadHDLCHist24Index			INTEGER,
	ipadHDLCHist24HistoricalIndex		INTEGER,
	ipadHDLCHist24Timestamp			TimeTicks,
	ipadHDLCHist24RxHighUtilSeconds		INTEGER,
	ipadHDLCHist24RxUtilization		INTEGER,
	ipadHDLCHist24TxHighUtilSeconds		INTEGER,
	ipadHDLCHist24TxUtilization		INTEGER
	}
 
ipadHDLCHist24Index	OBJECT-TYPE
	SYNTAX INTEGER
	MAX-ACCESS	read-only
	STATUS	current
	DESCRIPTION
		"Index into the HDLC Utilization Monitor 24-Hour History table."
	::= { ipadHDLCHist24TableEntry 1 }
 
ipadHDLCHist24HistoricalIndex	OBJECT-TYPE
	SYNTAX INTEGER
		{
		statSummary(1),
		statCurrent(2),
 
		statPeriod1(3),
		statPeriod2(4),
		statPeriod3(5),
		statPeriod4(6),
		statPeriod5(7),
		statPeriod6(8),
		statPeriod7(9),
		statPeriod8(10),
		statPeriod9(11),
 
		statPeriod10(12),
		statPeriod11(13),
		statPeriod12(14),
		statPeriod13(15),
		statPeriod14(16),
		statPeriod15(17),
		statPeriod16(18),
		statPeriod17(19),
		statPeriod18(20),
		statPeriod19(21),
 
		statPeriod20(22),
		statPeriod21(23),
		statPeriod22(24),
		statPeriod23(25),
		statPeriod24(26),
		statPeriod25(27),
		statPeriod26(28),
		statPeriod27(29),
		statPeriod28(30),
		statPeriod29(31),
 
		statPeriod30(32),
		statPeriod31(33),
		statPeriod32(34),
		statPeriod33(35),
		statPeriod34(36),
		statPeriod35(37),
		statPeriod36(38),
		statPeriod37(39),
		statPeriod38(40),
		statPeriod39(41),
 
		statPeriod40(42),
		statPeriod41(43),
		statPeriod42(44),
		statPeriod43(45),
		statPeriod44(46),
		statPeriod45(47),
		statPeriod46(48),
		statPeriod47(49),
		statPeriod48(50),
		statPeriod49(51),
 
		statPeriod50(52),
		statPeriod51(53),
		statPeriod52(54),
		statPeriod53(55),
		statPeriod54(56),
		statPeriod55(57),
		statPeriod56(58),
		statPeriod57(59),
		statPeriod58(60),
		statPeriod59(61),
 
		statPeriod60(62),
		statPeriod61(63),
		statPeriod62(64),
		statPeriod63(65),
		statPeriod64(66),
		statPeriod65(67),
		statPeriod66(68),
		statPeriod67(69),
		statPeriod68(70),
		statPeriod69(71),
 
		statPeriod70(72),
		statPeriod71(73),
		statPeriod72(74),
		statPeriod73(75),
		statPeriod74(76),
		statPeriod75(77),
		statPeriod76(78),
		statPeriod77(79),
		statPeriod78(80),
		statPeriod79(81),
 
		statPeriod80(82),
		statPeriod81(83),
		statPeriod82(84),
		statPeriod83(85),
		statPeriod84(86),
		statPeriod85(87),
		statPeriod86(88),
		statPeriod87(89),
		statPeriod88(90),
		statPeriod89(91),
 
		statPeriod90(92),
		statPeriod91(93),
		statPeriod92(94),
		statPeriod93(95),
		statPeriod94(96),
		statPeriod95(97),
		statPeriod96(98)
		}
	MAX-ACCESS	read-only
	STATUS	current
	DESCRIPTION
		"Historical index into the HDLC Utilization Monitor 24-Hour History table."
	::= { ipadHDLCHist24TableEntry 2 }
 
ipadHDLCHist24Timestamp	OBJECT-TYPE
	SYNTAX TimeTicks
	MAX-ACCESS	read-only
	STATUS	current
	DESCRIPTION
		"SysUpTime when the utilization interval completed."
	::= { ipadHDLCHist24TableEntry 3 }
 
ipadHDLCHist24RxHighUtilSeconds	OBJECT-TYPE
	SYNTAX INTEGER
	MAX-ACCESS	read-only
	STATUS	current
	DESCRIPTION
		"The number of seconds in the interval that have been greater
		than or equal to the Rx high utilization parameter."
	::= { ipadHDLCHist24TableEntry 4 }
 
ipadHDLCHist24RxUtilization	OBJECT-TYPE
	SYNTAX INTEGER
	MAX-ACCESS	read-only
	STATUS	current
	DESCRIPTION
		"The percent of Rx HDLC bandwidth utilized over the given interval."
	::= { ipadHDLCHist24TableEntry 5 }
 
ipadHDLCHist24TxHighUtilSeconds	OBJECT-TYPE
	SYNTAX INTEGER
	MAX-ACCESS	read-only
	STATUS	current
	DESCRIPTION
		"The number of seconds in the interval that have been greater
		than or equal to the Tx high utilization parameter."
	::= { ipadHDLCHist24TableEntry 6 }
 
ipadHDLCHist24TxUtilization	OBJECT-TYPE
	SYNTAX INTEGER
	MAX-ACCESS	read-only
	STATUS	current
	DESCRIPTION
		"The percent of Tx HDLC bandwidth utilized over the given interval."
	::= { ipadHDLCHist24TableEntry 7 }
 
 
-- ipadHDLCHist30 section
-- contains the HDLC Utilization Monitor 30-Day History table
 
ipadHDLCHist30Table	OBJECT-TYPE
	SYNTAX SEQUENCE OF IpadHDLCHist30TableEntry
	MAX-ACCESS	not-accessible
	STATUS	current
	DESCRIPTION
		"The ipad HDLC Utilization Monitor 30-Day History table."
	::= { ipadHDLCHist30 1 }
 
ipadHDLCHist30TableEntry	OBJECT-TYPE
	SYNTAX IpadHDLCHist30TableEntry
	MAX-ACCESS	not-accessible
	STATUS	current
	DESCRIPTION
		"An entry in the ipad HDLC Utilization Monitor 30-Day History table."
	INDEX	{ ipadHDLCHist30Index, ipadHDLCHist30HistoricalIndex }
	::= { ipadHDLCHist30Table 1 }
 
IpadHDLCHist30TableEntry ::=
	SEQUENCE
	{
	ipadHDLCHist30Index			INTEGER,
	ipadHDLCHist30HistoricalIndex		INTEGER,
	ipadHDLCHist30Timestamp			TimeTicks,
	ipadHDLCHist30RxHighUtilSeconds		INTEGER,
	ipadHDLCHist30RxUtilization		INTEGER,
	ipadHDLCHist30TxHighUtilSeconds		INTEGER,
	ipadHDLCHist30TxUtilization		INTEGER
	}
 
ipadHDLCHist30Index	OBJECT-TYPE
	SYNTAX INTEGER
	MAX-ACCESS	read-only
	STATUS	current
	DESCRIPTION
		"Index into the HDLC Utilization Monitor 30-Day History table."
	::= { ipadHDLCHist30TableEntry 1 }
 
ipadHDLCHist30HistoricalIndex	OBJECT-TYPE
	SYNTAX INTEGER
		{
		statSummary(1),
 
		statDay1(2),
		statDay2(3),
		statDay3(4),
		statDay4(5),
		statDay5(6),
		statDay6(7),
		statDay7(8),
		statDay8(9),
		statDay9(10),
 
		statDay10(11),
		statDay11(12),
		statDay12(13),
		statDay13(14),
		statDay14(15),
		statDay15(16),
		statDay16(17),
		statDay17(18),
		statDay18(19),
		statDay19(20),
 
		statDay20(21),
		statDay21(22),
		statDay22(23),
		statDay23(24),
		statDay24(25),
		statDay25(26),
		statDay26(27),
		statDay27(28),
		statDay28(29),
		statDay29(30),
 
		statDay30(31)
		}
	MAX-ACCESS	read-only
	STATUS	current
	DESCRIPTION
		"Historical index into the HDLC Utilization Monitor 30-Day History table."
	::= { ipadHDLCHist30TableEntry 2 }
 
ipadHDLCHist30Timestamp	OBJECT-TYPE
	SYNTAX TimeTicks
	MAX-ACCESS	read-only
	STATUS	current
	DESCRIPTION
		"SysUpTime when the utilization interval completed."
	::= { ipadHDLCHist30TableEntry 3 }
 
ipadHDLCHist30RxHighUtilSeconds	OBJECT-TYPE
	SYNTAX INTEGER
	MAX-ACCESS	read-only
	STATUS	current
	DESCRIPTION
		"The number of seconds in the interval that have been greater
		than or equal to the Rx high utilization parameter."
	::= { ipadHDLCHist30TableEntry 4 }
 
ipadHDLCHist30RxUtilization	OBJECT-TYPE
	SYNTAX INTEGER
	MAX-ACCESS	read-only
	STATUS	current
	DESCRIPTION
		"The percent of Rx HDLC bandwidth utilized over the given interval."
	::= { ipadHDLCHist30TableEntry 5 }
 
ipadHDLCHist30TxHighUtilSeconds	OBJECT-TYPE
	SYNTAX INTEGER
	MAX-ACCESS	read-only
	STATUS	current
	DESCRIPTION
		"The number of seconds in the interval that have been greater
		than or equal to the Tx high utilization parameter."
	::= { ipadHDLCHist30TableEntry 6 }
 
ipadHDLCHist30TxUtilization	OBJECT-TYPE
	SYNTAX INTEGER
	MAX-ACCESS	read-only
	STATUS	current
	DESCRIPTION
		"The percent of Tx HDLC bandwidth utilized over the given interval."
	::= { ipadHDLCHist30TableEntry 7 }
 
 
 -- SMTP section - configuration for email notification

ipadSmtpMailServer    OBJECT-TYPE
    SYNTAX  IpAddress
    MAX-ACCESS  read-write
    STATUS  current
    DESCRIPTION
        "IP Address of the ."
    ::= { ipadSmtp 1 }

ipadSmtpDomainName    OBJECT-TYPE
    SYNTAX  DisplayString
    MAX-ACCESS  read-write
    STATUS  current
    DESCRIPTION
        "Domain Name of the SMTP client."
    ::= { ipadSmtp 2 }

ipadSmtpMailFrom    OBJECT-TYPE
    SYNTAX  DisplayString
    MAX-ACCESS  read-write
    STATUS  current
    DESCRIPTION
        "Name of the SMTP client, is used in the From section of the email."
    ::= { ipadSmtp 3 }

ipadSmtpRecipient1    OBJECT-TYPE
    SYNTAX  DisplayString
    MAX-ACCESS  read-write
    STATUS  current
    DESCRIPTION
        "Destination for the email."
    ::= { ipadSmtp 4 }

ipadSmtpRecipient2    OBJECT-TYPE
    SYNTAX  DisplayString
    MAX-ACCESS  read-write
    STATUS  current
    DESCRIPTION
        "Destination for the email."
    ::= { ipadSmtp 5 }

ipadSmtpRecipient3    OBJECT-TYPE
    SYNTAX  DisplayString
    MAX-ACCESS  read-write
    STATUS  current
    DESCRIPTION
        "Destination for the email."
    ::= { ipadSmtp 6 }

ipadSmtpRecipient4    OBJECT-TYPE
    SYNTAX  DisplayString
    MAX-ACCESS  read-write
    STATUS  current
    DESCRIPTION
        "Destination for the email."
    ::= { ipadSmtp 7 }

ipadSmtpRecipient5    OBJECT-TYPE
    SYNTAX  DisplayString
    MAX-ACCESS  read-write
    STATUS  current
    DESCRIPTION
        "Destination for the email."
    ::= { ipadSmtp 8 }

 -- Encryption section --

ipadEncryptionEnable	OBJECT-TYPE
	SYNTAX  INTEGER
		{
		other(1),
		disable(2),
		enable(3)
		}
	MAX-ACCESS  read-write
	STATUS  current
	DESCRIPTION
		"Allow disabling encryption."
	::= { ipadEncryption 1 }

ipadEncryptionStartupKey	OBJECT-TYPE
	SYNTAX  DisplayString(SIZE(0..56))
	MAX-ACCESS  read-write
	STATUS  current
	DESCRIPTION
		""
	::= { ipadEncryption 2 }

ipadEncryptionStartupKeyConfirm	OBJECT-TYPE
	SYNTAX  DisplayString(SIZE(0..56))
	MAX-ACCESS  read-write
	STATUS  current
	DESCRIPTION
		""
	::= { ipadEncryption 3 }

ipadEncryptionType	OBJECT-TYPE
	SYNTAX  INTEGER
		{
		blowfish(1),
		des(2),
		triple-des(3)
		}
	MAX-ACCESS  read-write
	STATUS  current
	DESCRIPTION
		""
	::= { ipadEncryption 4 }


ipadEncryptionKey1	OBJECT-TYPE
	SYNTAX  DisplayString(SIZE(0..56))
	MAX-ACCESS  read-write
	STATUS  current
	DESCRIPTION
		""
	::= { ipadEncryption 5 }

ipadEncryptionKey2	OBJECT-TYPE
	SYNTAX  DisplayString(SIZE(0..56))
	MAX-ACCESS  read-write
	STATUS  current
	DESCRIPTION
		""
	::= { ipadEncryption 6 }

ipadEncryptionKey3	OBJECT-TYPE
	SYNTAX  DisplayString(SIZE(0..56))
	MAX-ACCESS  read-write
	STATUS  current
	DESCRIPTION
		""
	::= { ipadEncryption 7 }

ipadEncryptionKey4	OBJECT-TYPE
	SYNTAX  DisplayString(SIZE(0..56))
	MAX-ACCESS  read-write
	STATUS  current
	DESCRIPTION
		""
	::= { ipadEncryption 8 }

ipadEncryptionKey5	OBJECT-TYPE
	SYNTAX  DisplayString(SIZE(0..56))
	MAX-ACCESS  read-write
	STATUS  current
	DESCRIPTION
		""
	::= { ipadEncryption 9 }

ipadEncryptionKey6	OBJECT-TYPE
	SYNTAX  DisplayString(SIZE(0..56))
	MAX-ACCESS  read-write
	STATUS  current
	DESCRIPTION
		""
	::= { ipadEncryption 10 }

ipadEncryptionKey7	OBJECT-TYPE
	SYNTAX  DisplayString(SIZE(0..56))
	MAX-ACCESS  read-write
	STATUS  current
	DESCRIPTION
		""
	::= { ipadEncryption 11 }

ipadEncryptionKey8	OBJECT-TYPE
	SYNTAX  DisplayString(SIZE(0..56))
	MAX-ACCESS  read-write
	STATUS  current
	DESCRIPTION
		""
	::= { ipadEncryption 12 }

ipadEncryptionKey9	OBJECT-TYPE
	SYNTAX  DisplayString(SIZE(0..56))
	MAX-ACCESS  read-write
	STATUS  current
	DESCRIPTION
		""
	::= { ipadEncryption 13 }

ipadEncryptionKey10	OBJECT-TYPE
	SYNTAX  DisplayString(SIZE(0..56))
	MAX-ACCESS  read-write
	STATUS  current
	DESCRIPTION
		""
	::= { ipadEncryption 14 }

ipadEncryptionKeyLife	OBJECT-TYPE
	SYNTAX  INTEGER
	MAX-ACCESS  read-write
	STATUS  current
	DESCRIPTION
		""
	::= { ipadEncryption 15 }


-- Auto Learn DS0 Section (ipadAutoLearnDS0)


ipadAutoLearnDS0Table	OBJECT-TYPE
	SYNTAX SEQUENCE OF IpadAutoLearnDS0TableEntry
	MAX-ACCESS	not-accessible
	STATUS	current
	DESCRIPTION
		"The ipad Auto Learn DS0 Config table."
	::= { ipadAutoLearnDS0 1 }

ipadAutoLearnDS0TableEntry	OBJECT-TYPE
	SYNTAX IpadAutoLearnDS0TableEntry
	MAX-ACCESS	not-accessible
	STATUS	current
	DESCRIPTION
		"An entry in the ipad Auto Learn DS0 Config table."
	INDEX	{ ipadAutoLearnDS0Index }
	::= { ipadAutoLearnDS0Table 1 }

IpadAutoLearnDS0TableEntry ::=
	SEQUENCE
	{
	ipadAutoLearnDS0Index		INTEGER,
	ipadAutoLearnDS0Boot		INTEGER,
	ipadAutoLearnDS0Rate		INTEGER,
	ipadAutoLearnDS0Command		INTEGER
	}

ipadAutoLearnDS0Index	OBJECT-TYPE
	SYNTAX INTEGER
	MAX-ACCESS	read-only
	STATUS	current
	DESCRIPTION
		"The MIB-II ifIndex into the Auto Learn DS0 Config table."
	::= { ipadAutoLearnDS0TableEntry 1 }

ipadAutoLearnDS0Boot	OBJECT-TYPE
	SYNTAX INTEGER
		{
		other(1),
		disable(2),
		enable(3),
		carrierDown(4),
		serviceDown(5)
		}
	MAX-ACCESS	read-write
	STATUS	current
	DESCRIPTION
		"Select when to automatically learn DS0 assignments:
		disable - Do not automatically learn DS0s
		enable - Learn on boot
		carrierDown - Learn on boot and while the ifIndex carrier is down
		serviceDown - Learn on boot and while the first service on ifIndex is down"
	::= { ipadAutoLearnDS0TableEntry 2 }

ipadAutoLearnDS0Rate	OBJECT-TYPE
	SYNTAX INTEGER
		{
		other(1),
		auto(2),
		learnAs56K(3),
		learnAs64K(4),
		learnAsVoice(5)
		}
	MAX-ACCESS	read-write
	STATUS	current
	DESCRIPTION
		"Select the rate of the learned DS0's."
	::= { ipadAutoLearnDS0TableEntry 3 }

ipadAutoLearnDS0Command	OBJECT-TYPE
	SYNTAX INTEGER
		{
		none(1),
		learnNow(2)
		}
	MAX-ACCESS	read-write
	STATUS	current
	DESCRIPTION
		"The set values perform the following actions:
		learnNow(2) - Attempt to learn the active DS0's now."
	::= { ipadAutoLearnDS0TableEntry 4 }


-- Unit Access Section (ipadUnitAccess)
 
 
ipadUnitAccessTable	OBJECT-TYPE
	SYNTAX SEQUENCE OF IpadUnitAccessTableEntry
	MAX-ACCESS	not-accessible
	STATUS	current
	DESCRIPTION
		"The ipad Unit Access table."
	::= { ipadUnitAccess 1 }
 
ipadUnitAccessTableEntry	OBJECT-TYPE
	SYNTAX IpadUnitAccessTableEntry
	MAX-ACCESS	not-accessible
	STATUS	current
	DESCRIPTION
		"An entry in the ipad Unit Access table."
	INDEX	{ ipadAutoLearnDS0Index }
	::= { ipadUnitAccessTable 1 }
 
IpadUnitAccessTableEntry ::=
	SEQUENCE
	{
	ipadUnitAccessIndex		INTEGER,
	ipadUnitAccessIpa		IpAddress,
	ipadUnitAccessMask		IpAddress
	}
 
ipadUnitAccessIndex	OBJECT-TYPE
	SYNTAX INTEGER
	MAX-ACCESS	read-only
	STATUS	current
	DESCRIPTION
		"The MIB-II Index into the Unit Access table."
	::= { ipadUnitAccessTableEntry 1 }
 
ipadUnitAccessIpa	OBJECT-TYPE
	SYNTAX		IpAddress
	MAX-ACCESS	read-write
	STATUS	current
	DESCRIPTION
		"IP Address of Source to allow Unit Access."
	::= { ipadUnitAccessTableEntry 2 }
 
ipadUnitAccessMask	OBJECT-TYPE
	SYNTAX		IpAddress
	MAX-ACCESS	read-write
	STATUS	current
	DESCRIPTION
		"Mask of Source to allow Unit Access."
	::= { ipadUnitAccessTableEntry 3 }


-- ipad TFTP Up/Download Section (ipadTFTPDownload)


ipadTFTPDownloadServerIpa	OBJECT-TYPE
	SYNTAX		IpAddress
	MAX-ACCESS	read-write
	STATUS	current
	DESCRIPTION
		"TFTP Server IP Address."
	::= { ipadTFTPDownload 1 }

ipadTFTPDownloadFileName	OBJECT-TYPE
	SYNTAX  DisplayString (SIZE(0..80))
	MAX-ACCESS	read-write
	STATUS	current
	DESCRIPTION
		"TFTP Filename to Download or Upload."
	::= { ipadTFTPDownload 2 }

ipadTFTPDownloadAction	OBJECT-TYPE
	SYNTAX INTEGER
		{
		getfile(1),
		putfile(2),
		abort(3),
		idle(4)
		}
	MAX-ACCESS	read-write
	STATUS	current
	DESCRIPTION
		"TFTP Action to be performed."
	::= { ipadTFTPDownload 3 }

ipadTFTPDownloadStatus	OBJECT-TYPE
	SYNTAX INTEGER
		{
		idle(1),
		gettingfile(2),
		puttingfile(3),
		aborting(4),
		successful(5),
		invalidFileName(6),
		fileAccessFailed(7),
		invalidFile(8)
		}
	MAX-ACCESS	read-only
	STATUS	current
	DESCRIPTION
		"TFTP current status of action."
	::= { ipadTFTPDownload 4 }


-- Data Link Monitor Section (ipadDataLinkMonitor)
 
ipadDLMConfig     OBJECT IDENTIFIER ::= { ipadDataLineMonitor 1 }
 
ipadDLMConfigMode    OBJECT-TYPE
    SYNTAX  INTEGER
	{
	other(1),
	analyze(2),
	live(3)
	}
    MAX-ACCESS  read-write
    STATUS  current
    DESCRIPTION
        "Data Link Monitor on/off switch.  Toggles mode from analyze (static) to
        live (capture)."
    ::= { ipadDLMConfig 1 }

ipadDLMConfigBufferManagement	OBJECT-TYPE
	SYNTAX INTEGER
		{
		other(1),
		wrap(2),
		stopOnFull(3)
		}
	MAX-ACCESS	read-write
	STATUS	current
	DESCRIPTION
		"The DLM has a buffer of n messages.  Settings this object to wrap(2)
		allows the buffer to wrap around and be a continous buffer.  
		stopOnFull(3) forces the capture of packets to stop once the 
		end of the buffer is reached."
	::= { ipadDLMConfig 2 }

ipadDLMTable	OBJECT-TYPE
	SYNTAX SEQUENCE OF IpadDLMTableEntry
	MAX-ACCESS	not-accessible
	STATUS	current
	DESCRIPTION
		"The ipad Data Line Monitor configuration table."
	::= { ipadDataLineMonitor 2 }

ipadDLMTableEntry	OBJECT-TYPE
	SYNTAX IpadDLMTableEntry
	MAX-ACCESS	not-accessible
	STATUS	current
	DESCRIPTION
		"An entry in the ipad DLM config table."
	INDEX	{ ipadDLMServiceIndex }
	::= { ipadDLMTable 1 }

IpadDLMTableEntry ::=
	SEQUENCE
	{
	ipadDLMServiceIndex		INTEGER,
	ipadDLMEnable			INTEGER,
	ipadDLMTxRxFilter		INTEGER,
	ipadDLMPatternEnable		INTEGER,
	ipadDLMPattern			INTEGER,
	ipadDLMPatternMask		INTEGER,
	ipadDLMPatternOffset		INTEGER
	}

ipadDLMServiceIndex	OBJECT-TYPE
	SYNTAX INTEGER
	MAX-ACCESS	read-only
	STATUS	current
	DESCRIPTION
		"The service index into the DLM table."
	::= { ipadDLMTableEntry 1 }
 
ipadDLMEnable	OBJECT-TYPE
	SYNTAX INTEGER
		{
		other(1),
		disable(2),
		enable(3)
		}
	MAX-ACCESS	read-write
	STATUS	current
	DESCRIPTION
		"Enable/Disable the DLM on the specified service."
	::= { ipadDLMTableEntry 2 }
 
ipadDLMTxRxFilter	OBJECT-TYPE
	SYNTAX INTEGER
		{
		other(1),
		all(2),
		transmitOnly(3),
		receiveOnly(4)
		}
	MAX-ACCESS	read-write
	STATUS	current
	DESCRIPTION
		"Allows the user to capture only received, transmit, or both."
	::= { ipadDLMTableEntry 3 }

ipadDLMPatternEnable	OBJECT-TYPE
	SYNTAX INTEGER
		{
		other(1),
		disable(2),
		enable(3)
		}
	MAX-ACCESS	read-write
	STATUS	current
	DESCRIPTION
		"Enable/Disable the search for a specific pattern."
	::= { ipadDLMTableEntry 4 }

ipadDLMPattern	OBJECT-TYPE
	SYNTAX INTEGER
	MAX-ACCESS	read-write
	STATUS	current
	DESCRIPTION
		"The pattern to search for in the captured packets."
	::= { ipadDLMTableEntry 5 }

ipadDLMPatternMask	OBJECT-TYPE
	SYNTAX INTEGER
	MAX-ACCESS	read-write
	STATUS	current
	DESCRIPTION
		"The mask to use with ipadDLMPattern to search for in 
		the captured packets."
	::= { ipadDLMTableEntry 6 }

ipadDLMPatternOffset	OBJECT-TYPE
	SYNTAX INTEGER(0..32)
	MAX-ACCESS	read-write
	STATUS	current
	DESCRIPTION
		"The offset into the packet to search for the pattern."
	::= { ipadDLMTableEntry 7 }

ipadDLMPacketTable	OBJECT-TYPE
	SYNTAX SEQUENCE OF IpadDLMPacketTableEntry
	MAX-ACCESS	not-accessible
	STATUS	current
	DESCRIPTION
		"The ipad Data Link Monitor packet table."
	::= { ipadDataLineMonitor 3 }

ipadDLMPacketTableEntry	OBJECT-TYPE
	SYNTAX IpadDLMPacketTableEntry
	MAX-ACCESS	not-accessible
	STATUS	current
	DESCRIPTION
		"An entry in the ipad DLM packet table."
	INDEX	{ ipadDLMPacketIndex }
	::= { ipadDLMPacketTable 1 }

IpadDLMPacketTableEntry ::=
	SEQUENCE
	{
	ipadDLMPacketIndex		INTEGER,
	ipadDLMPacketServiceIndex	INTEGER,
	ipadDLMPacketTimestamp		TimeTicks,
	ipadDLMPacketDataDirection	INTEGER,
	ipadDLMPacketSize		INTEGER,
	ipadDLMPacketData		OCTET STRING
	}

ipadDLMPacketIndex	OBJECT-TYPE
	SYNTAX INTEGER
	MAX-ACCESS	read-only
	STATUS	current
	DESCRIPTION
		"The service index into the DLM table."
	::= { ipadDLMPacketTableEntry 1 }

ipadDLMPacketServiceIndex	OBJECT-TYPE
	SYNTAX INTEGER
	MAX-ACCESS	read-only
	STATUS	current
	DESCRIPTION
		"The service index the packet was captured on."
	::= { ipadDLMPacketTableEntry 2 }

ipadDLMPacketTimestamp	OBJECT-TYPE
	SYNTAX TimeTicks
	MAX-ACCESS	read-only
	STATUS	current
	DESCRIPTION
		"The time that the packet was captured."
	::= { ipadDLMPacketTableEntry 3 }

ipadDLMPacketDataDirection	OBJECT-TYPE
	SYNTAX INTEGER
		{
		other(1),
		transmit(2),
		receive(3)
		}
	MAX-ACCESS	read-only
	STATUS	current
	DESCRIPTION
		"The direction the data was goin in respect to the interface."
	::= { ipadDLMPacketTableEntry 4 }

ipadDLMPacketSize	OBJECT-TYPE
	SYNTAX INTEGER
	MAX-ACCESS	read-only
	STATUS	current
	DESCRIPTION
		"The size of the captured packet."
	::= { ipadDLMPacketTableEntry 5 }
 
ipadDLMPacketData	OBJECT-TYPE
	SYNTAX      OCTET STRING( SIZE(0..32) )
	MAX-ACCESS	read-only
	STATUS	current
	DESCRIPTION
		"The contents of the first 32 bytes of the captured packet."
	::= { ipadDLMPacketTableEntry 6 }


-- ipadOrigPing:  Originate PING controller parameters.

ipadOrigPingCommand		OBJECT-TYPE
	SYNTAX  INTEGER
		{
		other(1),
		stop(2),
		start(3),
		clearStats(4)
		}
	MAX-ACCESS  read-write
	STATUS  current
	DESCRIPTION
		"Action command to start/stop sending PING messages."
	::= { ipadOrigPing 1 }

ipadOrigPingDestIPAddr		OBJECT-TYPE
	SYNTAX  IpAddress
	MAX-ACCESS  read-write
	STATUS  current
	DESCRIPTION
		"Destination IP address of sent PING request messages."
	::= { ipadOrigPing 2 }

ipadOrigPingTimeout		OBJECT-TYPE
	SYNTAX  INTEGER
	MAX-ACCESS  read-write
	STATUS  current
	DESCRIPTION
		"Number of seconds to wait for a reply to a PING request message."
	::= { ipadOrigPing 3 }

ipadOrigPingSize		OBJECT-TYPE
	SYNTAX  INTEGER
	MAX-ACCESS  read-write
	STATUS  current
	DESCRIPTION
		"Number of bytes in a PING request message data field."
	::= { ipadOrigPing 4 }

ipadOrigPingToSend		OBJECT-TYPE
	SYNTAX  INTEGER
	MAX-ACCESS  read-write
	STATUS  current
	DESCRIPTION
		"Number of PING request messages to send."
	::= { ipadOrigPing 5 }

ipadOrigPingSent		OBJECT-TYPE
	SYNTAX  INTEGER
	MAX-ACCESS  read-only
	STATUS  current
	DESCRIPTION
		"Number of PING request messages sent."
	::= { ipadOrigPing 6 }

ipadOrigPingReplies		OBJECT-TYPE
	SYNTAX  INTEGER
	MAX-ACCESS  read-only
	STATUS  current
	DESCRIPTION
		"Number of PING response messages received."
	::= { ipadOrigPing 7 }

ipadOrigPingDelayMin		OBJECT-TYPE
	SYNTAX  INTEGER
	MAX-ACCESS  read-only
	STATUS  current
	DESCRIPTION
		"Minimum PING round trip delay in milliseconds."
	::= { ipadOrigPing 8 }

ipadOrigPingDelayAvg		OBJECT-TYPE
	SYNTAX  INTEGER
	MAX-ACCESS  read-only
	STATUS  current
	DESCRIPTION
		"Average PING round trip delay in milliseconds."
	::= { ipadOrigPing 9 }

ipadOrigPingDelayMax		OBJECT-TYPE
	SYNTAX  INTEGER
	MAX-ACCESS  read-only
	STATUS  current
	DESCRIPTION
		"Maximum PING round trip delay in milliseconds."
	::= { ipadOrigPing 10 }

ipadOrigPingReport		OBJECT-TYPE
	SYNTAX  DisplayString(SIZE(0..80))
	MAX-ACCESS  read-only
	STATUS  current
	DESCRIPTION
		"ASCII status report of originate PING activity."
	::= { ipadOrigPing 11 }

ipadOrigPingExceptReport	OBJECT-TYPE
	SYNTAX  DisplayString(SIZE(0..80))
	MAX-ACCESS  read-only
	STATUS  current
	DESCRIPTION
		"ASCII status report of last originate PING exception received."
	::= { ipadOrigPing 12 }


END

NTNTECH-INTERFACE-MODULE-CONFIGURATION-MIB DEFINITIONS ::= BEGIN    

--	*****************************************************************
--  Enterprise:
--   	Paradyne Corporation    
--
--  ContactInfo:
--    	Paradyne Corporation
--     	8545 126th Avenue North
--     	phone: +1 (727) 530 2000
--     	email: support@paradyne.com 
--		www:   http://www.nettonet.com/support/
--
--  Description:
--    	ntntech-interface-module-configuration-MIB.my
--    	Revision: 1.02.02
--    	Part Number: xx-xxxx-xx
--    	Date: November 17, 2004
--    
--    	This module provides explicit definitions for the Net to
--		Net Technologies naming	tree below:
--    
--    	nettonettech { enterprises 8059 }
--    
--    	This module will be extended, as additional sub-sections
--    	of this naming tree are defined.
--
--  Disclaimer:
--	   	This is an extremely preliminary MIB module and is subject
--		to change at any time therefore, use at your own risk.
--    
-- 	Copyright (c)2000 - 2004 by Paradyne Corporation.
-- 	All rights reserved.    

-- ******************************************************************
IMPORTS  
	ntntechInterfaceModule,NtnDisplayString		FROM NTNTECH-ROOT-MIB
   	OBJECT-TYPE, MODULE-IDENTITY,IpAddress	    FROM SNMPv2-SMI
   	TEXTUAL-CONVENTION							FROM SNMPv2-TC;
-- *******************************************************************     
ntntechInterfaceModuleConfigurationMIB MODULE-IDENTITY  
    LAST-UPDATED "0411171059Z"  -- November 17, 2004 10:59 am
    ORGANIZATION "Paradyne Corporation"
    CONTACT-INFO
        "Paradyne Corporation
        8545 126th Avenue North
        Largo, FL 33773   
     	
        phone: +1 (727) 530-2000
        email: support@paradyne.com 
        www:   http://www.nettonet.com/support/"

    DESCRIPTION
         "This mib module defines an SNMP API to manage Paradyne Corporation's
          IPD12000, IPD4000, and Mini/Micro DSLAM 
         interface parameters.  The interface types are described below,
         
         AMD8000-12
         12-Port ADSL Mini DSLAMs With Full Rate and G.lite Operational Modes  
		 
         AAM8000-12
         12-Port ADSL Access Multiplexer with Full Rate and G.lite Operational
         Modes 
		 
         AAM8000-24
         24-Port ADSL Access Multiplexer with Full Rate and G.lite Operational
         Modes
		 
         EAM2000-12
         12-Port E1 Access Multiplexer 
		 
         TAM1500-12
         12-Port T1 Access Multiplexer    
         		 
         IAM144-12
         12-Port IDSL Access Multiplexer     
         
         SAM1000-12
         12-Port SDSL Access Multiplexer  
         		         
         SAM2000-12, SAM2000Q-12, and SAM2000G-12
         12-Port SDSL Access Multiplexers with CAP, 2B1Q or TC/PAM (G.SHDSL)
         encoding        
		 
         SAM2000D-12
         12-Port SDSL Access Multiplexer W/O voice daughter card, running CAP encoding 
         
         SAM2000DQ-12
         12-Port SDSL Access Multiplexer W/O voice daughter card, running 2B1Q encoding
		 
         SAM2000V-12, SAM2000QV-12, SAM2000GV-12 
         12-Port SDSL Access Multiplexers with Voice Capability running CAP, 
         2B1Q or TC/PAM (G.SHDSL) encoding   
	                    
         SIM2000-12
         12-Port SDSL Access Multiplexer with CAP, 2B1Q and TC/PAM (G.SHDSL)
         encoding
	     
         SIM2000-24
         24-Port SDSL Access Multiplexer with CAP, 2B1Q and TC/PAM (G.SHDSL)
         encoding          
         
         SMD2000-12, SMD2000Q-12, SMD2000G-12
         12-Port SDSL Mini DSLAMs: AC and DC Versions with Cap, 2B1Q and
         G.SHDSL Line encoding    
         
         SuD2011_12T, SuD2011_12E, SuD2003_12T, SuD2003_12E
         12-Port SDSL Micro DSLAMs: Cap, 2B1Q and G.SHDSL Line encoding 
         
         SuD2011_6T, SuD2011_6E, SuD2002_6T, SuD2002_6E 
         6-Port SDSL Micro DSLAMs: Cap, 2B1Q and G.SHDSL Line encoding "  
         
    REVISION	"0208061150Z"
    DESCRIPTION
        "Added to the ifCfgPortTable the OID ifCfgPortBkBoneEtherType.
        VLAN ID max limit changed from 4095 to 4085."  
      	
    REVISION	"0208281023Z"
    DESCRIPTION
        "New Release - v1.01.00"   
        
    REVISION	"0210110940Z"
    DESCRIPTION
    	"Added fixedadaptive(4) mode to the ifCfgPortAdslPortMode OID."   
    	
    REVISION	"0210220200Z"
    DESCRIPTION
        "New Release - v1.01.01"  
        
    REVISION	"0309301059Z"
    DESCRIPTION
    	"Added to the comment section of ifCfgPortT1RxTxRate and ifCfgPortE1RxTxRate
    	 the newly supported T1/E1 module types - 
    		tim1500p12(31),
			tim1500p24(32),
			eim2000p12(33),
			eim2000p24(34)" 
			 
	    
	REVISION  "0410110932Z"
	DESCRIPTION
		"Adjusted copyright and Paradyne references."        
		
		REVISION "0411171059Z"
		DESCRIPTION
			"New release version 1.02.01"
			



::= { ntntechInterfaceModule 1 }              
      
      
--	Interface Module Configuration Objects (ifModCfgObjects)                        
  
ifModCfgMIBObjects OBJECT IDENTIFIER ::= { ntntechInterfaceModuleConfigurationMIB 1 }   

--	Access Module configuration for all Net To Net Tech interface
--	types: 
--
--			ADSL,IDSL,SDSL,T1, and E1     
--                                        

ifModCfgParameterConfiguration OBJECT IDENTIFIER ::= { ifModCfgMIBObjects 1 }  

prmCfgInterface OBJECT IDENTIFIER ::= { ifModCfgParameterConfiguration 1 } 

-- Interface Module configuration for each Net To Net Tech interface type 
  
prmCfgInterfacePort OBJECT IDENTIFIER ::= { ifModCfgParameterConfiguration 2 }

--	Interface Module Port configuration for each Net To Net Tech
--  interface type

ifCfgPortTable OBJECT-TYPE
   	SYNTAX      SEQUENCE OF IfCfgPortEntry
   	MAX-ACCESS  not-accessible
   	STATUS      current
   	DESCRIPTION
    "A list of IPD12000, IPD4000 Access/Inverse module and Mini/Micro
    DSLAM entries."
    ::= { prmCfgInterfacePort 1 }

ifCfgPortEntry OBJECT-TYPE
   	SYNTAX			IfCfgPortEntry
   	MAX-ACCESS  	not-accessible
   	STATUS      	current
   	DESCRIPTION
    "An entry containing management information applicable to the IPD12000, IPD4000
    Access/Inverse module as well as the Mini/Micro DSLAM."
    INDEX   { ifCfgSlotIndex,ifCfgPortIndex }
    ::= { ifCfgPortTable 1 }

   	IfCfgPortEntry ::=
       SEQUENCE {
           ifCfgSlotIndex	 			INTEGER,
           ifCfgPortIndex				INTEGER,
           ifCfgPortCircuitID			OCTET STRING,
           ifCfgPortFltrIp1Start		IpAddress,
           ifCfgPortFltrIp1End			IpAddress,
           ifCfgPortFltrIp2Start		IpAddress,
           ifCfgPortFltrIp2End			IpAddress,   
           ifCfgPortBackboneVlan		INTEGER,   
           ifCfgPortVlanPriority		INTEGER,    
           ifCfgPortFloodMde			INTEGER,   
           ifCfgPortIpFltProtocol		INTEGER,
           ifCfgPortReset				INTEGER,
           ifCfgPortBkBoneEthType		INTEGER       
       } 
       
	ifCfgSlotIndex OBJECT-TYPE
       	SYNTAX      INTEGER (1..12)
       	MAX-ACCESS  read-only
       	STATUS      current
       	DESCRIPTION
        "The physical slot number of the IPD chassis to which the interface module resides.
        The Mini/Micro DSLAM will have a slot index value of 1."
       	::= { ifCfgPortEntry 1 }
   
   	ifCfgPortIndex OBJECT-TYPE
       	SYNTAX      INTEGER (1..48)
       	MAX-ACCESS  read-only
       	STATUS      current
       	DESCRIPTION
        "The physical port number of the interface."
       	::= { ifCfgPortEntry 2 } 
       	
    ifCfgPortCircuitID OBJECT-TYPE
       	SYNTAX      OCTET STRING (SIZE (0..15))
       	MAX-ACCESS  read-write
       	STATUS      current
       	DESCRIPTION
        "The circuit identification number assigned to a port on an interface."
       	::= { ifCfgPortEntry 3 } 
       	
    ifCfgPortFltrIp1Start OBJECT-TYPE
       	SYNTAX      IpAddress
       	MAX-ACCESS  read-write
       	STATUS      current
       	DESCRIPTION
        "The value assigned to a port which designates the start of the first
        Ip filter range."
       	::= { ifCfgPortEntry 4 } 
       	
	ifCfgPortFltrIp1End OBJECT-TYPE
       	SYNTAX      IpAddress
       	MAX-ACCESS  read-write
       	STATUS      current
       	DESCRIPTION
        "The value assigned to a port which designates the end of the first
        Ip filter range."
       	::= { ifCfgPortEntry 5 }  
       	
    ifCfgPortFltrIp2Start OBJECT-TYPE
       	SYNTAX      IpAddress
       	MAX-ACCESS  read-write
       	STATUS      current
       	DESCRIPTION
        "The value assigned to a port which designates the start of the second
        Ip filter range."
       	::= { ifCfgPortEntry 6 } 
       	
	ifCfgPortFltrIp2End OBJECT-TYPE
       	SYNTAX      IpAddress
       	MAX-ACCESS  read-write
       	STATUS      current
       	DESCRIPTION
        "The value assigned to a port which designates the end of the second
        Ip filter range."
       	::= { ifCfgPortEntry 7 }   
       	
    ifCfgPortBackboneVlan OBJECT-TYPE
       	SYNTAX      INTEGER (0..4085)
       	MAX-ACCESS  read-write
       	STATUS      current
       	DESCRIPTION
        "The Backbone VLAN tag will become the primary identifier that can be
        used by routers with backbone capabilities to direct traffic to the
        appropriate network cloud."
       	::= { ifCfgPortEntry 8 }  
     	
    ifCfgPortVlanPriority OBJECT-TYPE
       	SYNTAX      INTEGER (0..7)
       	MAX-ACCESS  read-write
       	STATUS      current
       	DESCRIPTION
        "The value assigned to a port which designates the VLAN priority."
       	::= { ifCfgPortEntry 9 }    
       	
    ifCfgPortFloodMde OBJECT-TYPE
       	SYNTAX      INTEGER {
       					uplFlood(1),
       					vlnFlood(2)
       				}
       	MAX-ACCESS  read-write
       	STATUS      current
       	DESCRIPTION
        "The value assigned to a port which designates the flood mode."
       	::= { ifCfgPortEntry 10 } 
       	
    ifCfgPortIpFltProtocol OBJECT-TYPE
       	SYNTAX      INTEGER {           
       					protocolALL(1),
       					protocolIP(2)
       				}
       	MAX-ACCESS  read-write
       	STATUS      current
       	DESCRIPTION
        "The value assigned to a port which designates the IP filter protocol."
       	::= { ifCfgPortEntry 11 }    
       	
       	         
    ifCfgPortReset OBJECT-TYPE
       SYNTAX      INTEGER {           
       					reset(1),
       					noReset(2)
       			   }

       MAX-ACCESS  read-write
       STATUS      current
       DESCRIPTION
       "This value is always read as integer value 2. 
       
       Reset all associated port statistics to zero upon initiation of the 
       reset(1). "
       ::= { ifCfgPortEntry 12 }  
       
    ifCfgPortBkBoneEthType OBJECT-TYPE
       SYNTAX      INTEGER {           
       					ethtype8100(1),
       					ethtype9100(2)
       				}

       MAX-ACCESS  read-write
       STATUS      current
       DESCRIPTION
       "The value assigned to a port which designates the ethernet packet type. "
       ::= { ifCfgPortEntry 13 }      
           	  
ifCfgPortVLANTable OBJECT-TYPE
   	SYNTAX      SEQUENCE OF IfCfgPortVLANEntry
   	MAX-ACCESS  not-accessible
   	STATUS      current
   	DESCRIPTION
    "A list of IPD12000, IPD4000 Access/Inverse module and Mini/Micro DSLAM
    port 802.1Q VLAN entries."
    ::= { prmCfgInterfacePort 2 }

ifCfgPortVLANEntry OBJECT-TYPE
   	SYNTAX			IfCfgPortVLANEntry
   	MAX-ACCESS  	not-accessible
   	STATUS      	current
   	DESCRIPTION
    "An entry containing management information applicable to an IPD12000, IPD4000 
    Access/Inverse module and Mini/Micro DSLAM port."
    INDEX   { ifCfgIfSlotIndex,ifCfgIfPortIndex,ifCfgVLANIndex }
    ::= { ifCfgPortVLANTable 1 }

   	IfCfgPortVLANEntry ::=
       SEQUENCE {
           	ifCfgIfSlotIndex	 	INTEGER,
           	ifCfgIfPortIndex		INTEGER, 
           	ifCfgVLANIndex			INTEGER,
       		ifCfgVLANIdStart		INTEGER,   
        	ifCfgVLANIdEnd			INTEGER	    
       }
   
    ifCfgIfSlotIndex OBJECT-TYPE
       	SYNTAX      INTEGER (1..12)
       	MAX-ACCESS  read-only
       	STATUS      current
       	DESCRIPTION
        "The physical slot number of the IPD chassis to which the interface module
        resides. The Mini/Micro slot index will be 1."
       	::= { ifCfgPortVLANEntry 1 }
   
   	ifCfgIfPortIndex OBJECT-TYPE
       	SYNTAX      INTEGER (1..48)
       	MAX-ACCESS  read-only
       	STATUS      current
       	DESCRIPTION
        "The physical port number of the interface."
       	::= { ifCfgPortVLANEntry 2 }
       	
    ifCfgVLANIndex OBJECT-TYPE
       	SYNTAX      INTEGER (1..10)
       	MAX-ACCESS  read-only
       	STATUS      current
       	DESCRIPTION
        "A pointer to one of ten possible VLAN tags that can be assigned to a port."
       	::= { ifCfgPortVLANEntry 3 } 
                            
    ifCfgVLANIdStart OBJECT-TYPE
       	SYNTAX      INTEGER (0..4085)
       	MAX-ACCESS  read-write
       	STATUS      current
       	DESCRIPTION
        "The value assigned to a port which designates the start of a VLAN ID range."
       	::= { ifCfgPortVLANEntry 4 }  
       	
    ifCfgVLANIdEnd OBJECT-TYPE
       	SYNTAX      INTEGER (0..4085)
       	MAX-ACCESS  read-write
       	STATUS      current
       	DESCRIPTION
        "The value assigned to a port which designates the end of a VLAN ID range."
       	::= { ifCfgPortVLANEntry 5 }

         
-- Unique Interface tables :: Adsl, Idsl, Sdsl, T1, E1   
-- ADSL
      	                 
ifCfgPortAdslTable OBJECT-TYPE
   	SYNTAX      SEQUENCE OF IfCfgPortAdslEntry
   	MAX-ACCESS  not-accessible
   	STATUS      current
   	DESCRIPTION
    "A list of ADSL interface entries."
    ::= { prmCfgInterfacePort 3 }

ifCfgPortAdslEntry OBJECT-TYPE
	SYNTAX			IfCfgPortAdslEntry
    MAX-ACCESS  	not-accessible
    STATUS      	current
    DESCRIPTION
    "An entry containing management information applicable to ADSL module."
    INDEX   { ifCfgAdslSlotIndex,ifCfgAdslPortIndex }
    ::= { ifCfgPortAdslTable 1 }

   	IfCfgPortAdslEntry ::=
       SEQUENCE {
           ifCfgAdslSlotIndex	 			INTEGER,
           ifCfgAdslPortIndex				INTEGER,
           ifCfgPortAdslPortMode			INTEGER,  
           ifCfgPortAdslVpiVciDetect		INTEGER,   
           ifCfgPortAdslRxRate				INTEGER,  
           ifCfgPortAdslTxRate				INTEGER,  
           ifCfgPortAdslFrameType			INTEGER,  
		   ifCfgPortAdslVpi					INTEGER,             
           ifCfgPortAdslVci					INTEGER,  
           ifCfgPortAdslStandardMde			INTEGER,                                            
           ifCfgPortAdslCorrectionUp		INTEGER,                                             
           ifCfgPortAdslCorrectionDn		INTEGER,                                             
           ifCfgPortAdslDelayUp				INTEGER,                                             
           ifCfgPortAdslDelayDn				INTEGER,                                             
           ifCfgPortAdslEcFdm				INTEGER,                                             
           ifCfgPortAdslFastBuffer			INTEGER,   
		   ifCfgPortAdslSnrUp				INTEGER,   
		   ifCfgPortAdslSnrDn				INTEGER,
           ifCfgPortAdslActualRxRate		INTEGER,
           ifCfgPortAdslActualTxRate		INTEGER,
           ifCfgPortAdslActualStandardMde	INTEGER,
		   ifCfgPortAdslActualDepthUp		INTEGER,
		   ifCfgPortAdslActualDepthDn		INTEGER
       } 
	           
	ifCfgAdslSlotIndex OBJECT-TYPE
       	SYNTAX      INTEGER (1..12)
       	MAX-ACCESS  read-only
       	STATUS      current
       	DESCRIPTION
        "The physical slot number of the IPD chassis to which the interface module
        resides. The Mini/Micro slot index will be 1."
        ::= { ifCfgPortAdslEntry 1 }
   
   	ifCfgAdslPortIndex OBJECT-TYPE
       	SYNTAX      INTEGER (1..48)
       	MAX-ACCESS  read-only
       	STATUS      current
       	DESCRIPTION
        "The physical port number of the ADSL interface."
       	::= { ifCfgPortAdslEntry 2 }   
       	
    ifCfgPortAdslPortMode OBJECT-TYPE
       	SYNTAX      INTEGER {
       						on(1),
       						off(2),
       						adaptive(3),
       						fixedadaptive(4)
       				}
       	MAX-ACCESS  read-write
       	STATUS      current
       	DESCRIPTION
        "The port mode of operation, ON, OFF, or Adaptive.
        
        When a port is set to Adaptive mode, the best possible value for the
        Rx/Tx data rates will be achieved.  A successful data rate connection
        will be indicated with a port 'linkup' status."
       	::= { ifCfgPortAdslEntry 3 }
       	
     ifCfgPortAdslVpiVciDetect OBJECT-TYPE
       	SYNTAX      INTEGER {
       						on(1),
       						off(2)
       				}
       	MAX-ACCESS  read-write
       	STATUS      current
       	DESCRIPTION
        "ADSL Virtual Path Identifier (VPI) and Virtual Channel Identifier
        (VCI) detect mode.  If this mode is set to ON, auto-detect the line
        VPI and VCI values."
       	::= { ifCfgPortAdslEntry 4 } 
       	  	
     ifCfgPortAdslRxRate OBJECT-TYPE
       	SYNTAX      INTEGER (1..32)
       	UNITS       "Kbps"
       	MAX-ACCESS  read-write
       	STATUS      current
       	DESCRIPTION
        "ADSL upstream (Rx) data rate.    
        
        The available upstream data rates range from 32Kbps to 1024Kbps.  
        The upstream data rate can be set by the user via the set value x
        where x = 1 to 32.  The actual data rate that is represented by 
        these set values can be calculated using the following formula, 
        
        (x * 32Kbps) = upstream data rate,
        
        i.e.  (3 * 32Kbps) = 96Kbps
        
        Note: if an Rx rate value of zero(0) is returned via a GET operation,
              this would indicate that the port is in 'Adaptive' mode and that
              the link condition is 'linkdown'."  
         ::= { ifCfgPortAdslEntry 5 } 
       	
     ifCfgPortAdslTxRate OBJECT-TYPE
       	SYNTAX      INTEGER  (1..252)
        UNITS       "Kbps"
       	MAX-ACCESS  read-write
       	STATUS      current
       	DESCRIPTION
        "ADSL downstream (Tx) data rates.
        
        The available downstream data rates range from 32Kbps to 8064Kbps.  
        The downstream data rate can be set by the user via the set value x
        where x = 1 to 252.  The actual data rate that is represented by 
        these set values can be calculated using the following formula, 
        
        (x * 32Kbps) = downstream data rate,
        
        i.e.  (252 * 32Kbps) = 8064Kbps
        
        Note: if a Tx rate value of zero(0) is returned via a GET operation,
              this would indicate that the port is in 'Adaptive' mode and that
              the link condition is 'linkdown'."     
       	::= { ifCfgPortAdslEntry 6 }

     ifCfgPortAdslFrameType OBJECT-TYPE
       	SYNTAX      INTEGER {
       						frameType1483LLC(1),
       						frameType1483VCM(2)
       				}
       	MAX-ACCESS  read-write
       	STATUS      current
       	DESCRIPTION
        "ADSL frame type."
       	::= { ifCfgPortAdslEntry 7 }    
       	 	
     ifCfgPortAdslVpi OBJECT-TYPE
       	SYNTAX      INTEGER (0..255)       	
       	MAX-ACCESS  read-write
       	STATUS      current
       	DESCRIPTION
        "ADSL Virtual Path Identifier (VPI) value."
       	::= { ifCfgPortAdslEntry 8 } 
       	
       	
     ifCfgPortAdslVci OBJECT-TYPE
       	SYNTAX      INTEGER (0..65535)
       	MAX-ACCESS  read-write
       	STATUS      current
       	DESCRIPTION
        "ADSL Virtual Channel Identifier (VCI)."
       	::= { ifCfgPortAdslEntry 9 } 
       	
     ifCfgPortAdslStandardMde OBJECT-TYPE
       	SYNTAX      INTEGER {
       						t1413(1),
       						gLite(2), 
       						gDMT(3),  
       						multiMode(4),
       						aLCATEL(5),
							gDMT-BIS(6),
							gDMT-BISplus(7),
							gDMT-BIS-Annex-L(8),
							gDMT-BIS-Annex-M(9),
       						stdMdeNoLink(255)
       				}
       	MAX-ACCESS  read-write
       	STATUS      current
       	DESCRIPTION
        "ADSL standard modes of operation.
        
        Note: if receive a standard mode of integer value 255 (0xFF), this would 
              indicate that the standard mode is unknown due to a port 'linkdown'
              condition."
       	::= { ifCfgPortAdslEntry 10 } 

      ifCfgPortAdslCorrectionUp OBJECT-TYPE
       	SYNTAX      INTEGER {
					corr125us(1),
       				corr250us(2), 
       				corr500us(3),  
       				corr1ms(4),
       				corr2ms(5),
					corr4ms(6)
		}      	
       	MAX-ACCESS  read-write
       	STATUS      current
       	DESCRIPTION
        "ADSL Impulse protection duration in the Upstream duration."
       	::= { ifCfgPortAdslEntry 11 } 

      ifCfgPortAdslCorrectionDn OBJECT-TYPE
       	SYNTAX      INTEGER {
					corr125us(1),
       				corr250us(2), 
       				corr500us(3),  
       				corr1ms(4),
       				corr2ms(5),
					corr4ms(6)
		}      	
       	MAX-ACCESS  read-write
       	STATUS      current
       	DESCRIPTION
        "ADSL Impulse protection duration in the Upstream duration."
       	::= { ifCfgPortAdslEntry 12 } 

      ifCfgPortAdslDelayUp OBJECT-TYPE
       	SYNTAX      INTEGER {
					delay1ms(1),
       				delay2ms(2), 
       				delay4ms(3),  
       				delay8ms(4),
       				delay16ms(5),
					delay32ms(6),
					delay64ms(7)
		}      	
       	MAX-ACCESS  read-write
       	STATUS      current
       	DESCRIPTION
        "ADSL Impulse protection duration in the Upstream direction."
       	::= { ifCfgPortAdslEntry 13 } 
      
	  ifCfgPortAdslDelayDn OBJECT-TYPE
       	SYNTAX      INTEGER {
					delay1ms(1),
       				delay2ms(2), 
       				delay4ms(3),  
       				delay8ms(4),
       				delay16ms(5),
					delay32ms(6),
					delay64ms(7)
		}      	
       	MAX-ACCESS  read-write
       	STATUS      current
       	DESCRIPTION
        "ADSL Impulse protection duration in the Upstream direction."
       	::= { ifCfgPortAdslEntry 14 } 
 
ifCfgPortAdslEcFdm OBJECT-TYPE
       	SYNTAX      INTEGER {
       						ec(1),
       						fdm(2)
       				}
       	MAX-ACCESS  read-write
       	STATUS      current
       	DESCRIPTION
        "ADSL Echo Cancellation uses Upstream Tones for Upstream and Dnstream data."
       	::= { ifCfgPortAdslEntry 15 } 

ifCfgPortAdslFastBuffer OBJECT-TYPE
       	SYNTAX      INTEGER {
       						on(1),
       						off(2)
       				}
       	MAX-ACCESS  read-write
       	STATUS      current
       	DESCRIPTION
        "Selects fast buffer/low latency. Same is interleave delay of 1ms"
       	::= { ifCfgPortAdslEntry 16 } 

ifCfgPortAdslSnrUp OBJECT-TYPE
		SYNTAX      INTEGER (1..15)
       	MAX-ACCESS  read-write
       	STATUS      current
       	DESCRIPTION
        "Selects Target Upstream SNR"
       	::= { ifCfgPortAdslEntry 17 } 

ifCfgPortAdslSnrDn OBJECT-TYPE
		SYNTAX      INTEGER (1..15)
       	MAX-ACCESS  read-write
       	STATUS      current
       	DESCRIPTION
        "Selects Target Dnstream SNR"
       	::= { ifCfgPortAdslEntry 18 } 

ifCfgPortAdslActualRxRate OBJECT-TYPE
       	SYNTAX      INTEGER (0..64)
       	UNITS       "Kbps"
       	MAX-ACCESS  read-only
       	STATUS      current
       	DESCRIPTION
        "ADSL upstream (Rx) data rate.    
        
        The available upstream data rates range from 32Kbps to 1024Kbps.  
        The upstream data rate can be set by the user via the set value x
        where x = 1 to 64.  The actual data rate that is represented by 
        these set values can be calculated using the following formula, 
        
        (x * 32Kbps) = upstream data rate,
        
        i.e.  (3 * 32Kbps) = 96Kbps
        
        Note: if an Rx rate value of zero(0) is returned via a GET operation,
              this would indicate that the port is in 'Adaptive' mode and that
              the link condition is 'linkdown'."  
         ::= { ifCfgPortAdslEntry 19 } 


ifCfgPortAdslActualTxRate OBJECT-TYPE
       	SYNTAX      INTEGER  (0..1024)
        UNITS       "Kbps"
       	MAX-ACCESS  read-only
       	STATUS      current
       	DESCRIPTION
        "ADSL downstream (Tx) data rates.
        
        The available downstream data rates range from 32Kbps to 8064Kbps.  
        The downstream data rate can be set by the user via the set value x
        where x = 1 to 1024.  The actual data rate that is represented by 
        these set values can be calculated using the following formula, 
        
        (x * 32Kbps) = downstream data rate,
        
        i.e.  (252 * 32Kbps) = 8064Kbps
        
        Note: if a Tx rate value of zero(0) is returned via a GET operation,
              this would indicate that the port is in 'Adaptive' mode and that
              the link condition is 'linkdown'."     
       	::= { ifCfgPortAdslEntry 20 }

ifCfgPortAdslActualStandardMde OBJECT-TYPE
       	SYNTAX      INTEGER {
       						t1413(1),
       						gLite(2), 
       						gDMT(3),  
       						multiMode(4),
       						aLCATEL(5),
							gDMT-BIS(6),
							gDMT-BISplus(7),
							gDMT-BIS-Annex-L(8),
							gDMT-BIS-Annex-M(9),
       						stdMdeNoLink(255)
       				}
       	MAX-ACCESS  read-only
       	STATUS      current
       	DESCRIPTION
        "ADSL current operating mode, should match ifCfgPortAdslStandardMde UNLESS operating in MULTIMODE"
         ::= { ifCfgPortAdslEntry 21 } 

ifCfgPortAdslActualDepthUp OBJECT-TYPE
       	SYNTAX      INTEGER (1..64)
       	MAX-ACCESS  read-only
       	STATUS      current
       	DESCRIPTION
        "ADSL upstream interleving depth."
         ::= { ifCfgPortAdslEntry 22 } 

ifCfgPortAdslActualDepthDn OBJECT-TYPE
       	SYNTAX      INTEGER (1..64)
       	MAX-ACCESS  read-only
       	STATUS      current
       	DESCRIPTION
        "ADSL dnstream interleaving depth."
         ::= { ifCfgPortAdslEntry 23 } 
       	
	   	       	
-- IDSL
              
ifCfgPortIdslTable OBJECT-TYPE
	SYNTAX      SEQUENCE OF IfCfgPortIdslEntry
	MAX-ACCESS  not-accessible
    STATUS      current
    DESCRIPTION
    "A list of IDSL interface entries."
    ::= { prmCfgInterfacePort 4 }

ifCfgPortIdslEntry OBJECT-TYPE
   	SYNTAX			IfCfgPortIdslEntry
    MAX-ACCESS  	not-accessible
    STATUS      	current
    DESCRIPTION
    "An entry containing management information applicable to the IDSL interface."
    INDEX   { ifCfgIdslSlotIndex,ifCfgIdslPortIndex }
    ::= { ifCfgPortIdslTable 1 }

   	 IfCfgPortIdslEntry ::=
       SEQUENCE {  
       		ifCfgIdslSlotIndex	 		INTEGER,
           	ifCfgIdslPortIndex			INTEGER,
            ifCfgPortIdslRxTxRate		INTEGER         
       } 
          
     ifCfgIdslSlotIndex OBJECT-TYPE
       	SYNTAX      INTEGER (1..12)
       	MAX-ACCESS  read-only
       	STATUS      current
       	DESCRIPTION
        "The physical slot number of the IPD chassis to which the interface module
        resides. The Mini/Micro slot index will be 1."
       	::= { ifCfgPortIdslEntry 1 }
   
   	 ifCfgIdslPortIndex OBJECT-TYPE
       	SYNTAX      INTEGER (1..48)
       	MAX-ACCESS  read-only
       	STATUS      current
       	DESCRIPTION
        "The physical port number of the IDSL interface."
       	::= { ifCfgPortIdslEntry 2 }   
       	
     ifCfgPortIdslRxTxRate OBJECT-TYPE
       	SYNTAX      INTEGER {     
       					idslRxTxRateDefect(0),
       					idslRxTxRate128(1),
       					idslRxTxRate144(2),
       					idslRxTxRateOff(255)
       				}       
       	UNITS       "Kbps"
       	MAX-ACCESS  read-write
       	STATUS      current
       	DESCRIPTION
        "IDSL symetrical (Rx/Tx) data rates.
        
         IDSL module types and the associated Rx/Tx data rates- 
                        
         IAM144-12:         
         	Data Rates (Kbps): 128,144                     
         	
         Note: if a rate value of zero(0) is returned via a GET operation, 
               it will indicate that the port is defective." 
       	::= { ifCfgPortIdslEntry 3 } 
       	           
-- SDSL
              
ifCfgPortSdslTable OBJECT-TYPE
	SYNTAX      SEQUENCE OF IfCfgPortSdslEntry
	MAX-ACCESS  not-accessible
	STATUS      current
	DESCRIPTION
    "A list of SDSL interface entries."
    ::= { prmCfgInterfacePort 5 }

ifCfgPortSdslEntry OBJECT-TYPE
  	SYNTAX			IfCfgPortSdslEntry
   	MAX-ACCESS  	not-accessible
   	STATUS      	current
   	DESCRIPTION
    "An entry containing management information applicable to the SDSL interface."
    INDEX   { ifCfgSdslSlotIndex,ifCfgSdslPortIndex }
    ::= { ifCfgPortSdslTable 1 }

   	 IfCfgPortSdslEntry ::=
       SEQUENCE {  
       		ifCfgSdslSlotIndex			INTEGER,
           	ifCfgSdslPortIndex			INTEGER, 
           	ifCfgPortSdslRxTxRate		INTEGER,
           	ifCfgPortSdslLineCode		INTEGER    
       } 
          
     ifCfgSdslSlotIndex OBJECT-TYPE
       	SYNTAX      INTEGER (1..12)
       	MAX-ACCESS  read-only
       	STATUS      current
       	DESCRIPTION
        "The physical slot number of the IPD chassis to which the interface module
        resides. The Mini/Micro slot index will be 1."
       	::= { ifCfgPortSdslEntry 1 }
   
   	 ifCfgSdslPortIndex OBJECT-TYPE
       	SYNTAX      INTEGER (1..48)
       	MAX-ACCESS  read-only
       	STATUS      current
       	DESCRIPTION
        "The physical port number of the SDSL interface."
       	::= { ifCfgPortSdslEntry 2 }   
       	
     ifCfgPortSdslRxTxRate OBJECT-TYPE
       	SYNTAX      INTEGER {    
       					sdslRxTxRateDefect(0), 
       					sdslRxTxRate144(1),
       					sdslRxTxRate272(2),
       					sdslRxTxRate400(3),
       					sdslRxTxRate528(4),
       					sdslRxTxRate784(5),
       					sdslRxTxRate1040(6),
       					sdslRxTxRate1168(7),
       					sdslRxTxRate1552(8),
       					sdslRxTxRate2064(9),
       					sdslRxTxRate2320(10),
       					sdslRxTxRateOff(255)
       				}       
       	UNITS       "Kbps"
       	MAX-ACCESS  read-write
       	STATUS      current
       	DESCRIPTION
        "SDSL symetrical (Rx/Tx) data rates.
        
        
         SDSL module types and the associated Rx/Tx data rates- 
                        
         SAM1000-12:       
         	Data Rates (Kbps): 272,528,784,1168
                  
         SAM2000-12,SAM2000Q-12,SAM2000G-12,SAM2000D-12,SAM2000DQ-12,
         SIM2000-24,SuD2011_12T,SuD2011_12E,SuD2003_12T,SuD2003_12E,
         SuD2011_6T,SuD2011_6E,SuD2002_6T,SuD2002_6E:
         	Data Rates (Kbps): 144,272,400,528,784,1040,1552,2064,2320
         	
         SAM2000V-12,SAM2000QV-12,SAM2000GV-12,SIM2000V-12,SIM2000V-24:
         	Data Rates (Kbps): 272,400,528,784,1040,1552,2064,2320  
         	
         Note: if a rate value of zero(0) is returned via a GET operation, 
               it will indicate that the port is defective."

       	::= { ifCfgPortSdslEntry 3 }  
       	
     ifCfgPortSdslLineCode OBJECT-TYPE
       	SYNTAX  INTEGER { 
       				lineCodeCap(1),
       				lineCode2B1Q(2),
       				lineCodeGSHDSL(3)
       			}
       	MAX-ACCESS  read-write
       	STATUS      current
       	DESCRIPTION
        "Line code for the SDSL modules.
        
        Note, the line code may be set on the following modules,
        SIM2000-12,SIM2000-24,SIM2000V-24,SIM2000V-12, or the 
        SDSL micro DSLAM.     
        
        The line code options are described as follows-
       	
        CAP: 		Carrierless Amplitude and Phase modulation
        2B1Q: 		Two Binary, One Quaternary
        G.SHDSL:	Multirate Symmetric Single-pair DSL"
       	::= { ifCfgPortSdslEntry 4 } 

      
-- T1
              
ifCfgPortT1Table OBJECT-TYPE
	SYNTAX      SEQUENCE OF IfCfgPortT1Entry
    MAX-ACCESS  not-accessible
    STATUS      current
    DESCRIPTION
    "A list of T1 interface entries."
    ::= { prmCfgInterfacePort 6 }

ifCfgPortT1Entry OBJECT-TYPE
   	SYNTAX			IfCfgPortT1Entry
   	MAX-ACCESS  	not-accessible
   	STATUS      	current
   	DESCRIPTION
    "An entry containing management information applicable to the T1 interface."
   	INDEX   { ifCfgT1SlotIndex,ifCfgT1PortIndex }
   	::= { ifCfgPortT1Table 1 }

   	 IfCfgPortT1Entry ::=
       SEQUENCE {  
       		ifCfgT1SlotIndex	 		INTEGER,
           	ifCfgT1PortIndex			INTEGER, 
           	ifCfgPortT1RxTxRate			INTEGER,  
           	ifCfgPortT1FrameType		INTEGER,
           	ifCfgPortT1LineCode			INTEGER,
           	ifCfgPortT1TxBuildOut		INTEGER,
           	ifCfgPortT1ClockSrc			INTEGER
       } 
          
     ifCfgT1SlotIndex OBJECT-TYPE
       	SYNTAX      INTEGER (1..12)
       	MAX-ACCESS  read-only
       	STATUS      current
       	DESCRIPTION
        "The physical slot number of the IPD chassis to which the interface module
        resides. The Mini/Micro slot index will be 1."
       	::= { ifCfgPortT1Entry 1 }
   
   	 ifCfgT1PortIndex OBJECT-TYPE
       	SYNTAX      INTEGER (1..48)
       	MAX-ACCESS  read-only
       	STATUS      current
       	DESCRIPTION
        "The physical port number of the T1 interface."
       	::= { ifCfgPortT1Entry 2 }   
       	
     ifCfgPortT1RxTxRate OBJECT-TYPE
       	SYNTAX      INTEGER {   
       					t1RxTxRateDefect(0),     
       					t1RxTxRate192(1),
       					t1RxTxRate384(2),
       					t1RxTxRate576(3),
       					t1RxTxRate768(4),
       					t1RxTxRate960(5),
       					t1RxTxRate1152(6),
       					t1RxTxRate1344(7),
       					t1RxTxRate1536(8),
       					t1RxTxRateOff(255)
       				}       
       	UNITS       "Kbps"
       	MAX-ACCESS  read-write
       	STATUS      current
       	DESCRIPTION
        "T1 symetrical (Rx/Tx) data rates.
       
         T1 module types and the associated Rx/Tx data rates- 
                        
         TAM1500-12,TIM1500-12,TIM1500-24:         
         	Data Rates (Kbps): 192,384,576,768,960,1152,1344,1536 
         	
         Note: if a rate value of zero(0) is returned via a GET operation, 
               it will indicate that the port is defective."
                  
       	::= { ifCfgPortT1Entry 3 } 
       	
     ifCfgPortT1FrameType OBJECT-TYPE
       	SYNTAX      INTEGER {                 
       						t1frameTypeESF(1),
       						t1frameTypeSFD4(2)
       				}
       	MAX-ACCESS  read-write
       	STATUS      current
       	DESCRIPTION
        "T1 frame type."
       	::= { ifCfgPortT1Entry 4 }  
       	
     ifCfgPortT1LineCode OBJECT-TYPE
       	SYNTAX      INTEGER {  
       						t1lineCodeB8ZS(1),
       						t1lineCodeAMI(2)
       				}
       	MAX-ACCESS  read-write
       	STATUS      current
       	DESCRIPTION
        "T1 line code."
       	::= { ifCfgPortT1Entry 5 } 
       	
     ifCfgPortT1TxBuildOut OBJECT-TYPE
       	SYNTAX      INTEGER {   
       	      				t1TxBuildOut0db(1),
       						t1TxBuildOutN7p5db(2),
       						t1TxBuildOutN15db(3),
       						t1TxBuildOutN22db(4)
       				}
       	MAX-ACCESS  read-write
       	STATUS      current
       	DESCRIPTION
        "T1 tx buildout."
       	::= { ifCfgPortT1Entry 6 }  
          	
     ifCfgPortT1ClockSrc OBJECT-TYPE
       	SYNTAX      INTEGER {  
       						t1ClockSrcLocal(1),
       						t1ClockSrcLoop(2)
       				}
       	MAX-ACCESS  read-write
       	STATUS      current
       	DESCRIPTION
        "T1 clock source."
       	::= { ifCfgPortT1Entry 7 } 
       	
     
-- E1
              
ifCfgPortE1Table OBJECT-TYPE
	SYNTAX      SEQUENCE OF IfCfgPortE1Entry
    MAX-ACCESS  not-accessible
    STATUS      current
    DESCRIPTION
    "A list of E1 interface entries."
    ::= { prmCfgInterfacePort 7 }

ifCfgPortE1Entry OBJECT-TYPE
   	SYNTAX			IfCfgPortE1Entry
   	MAX-ACCESS  	not-accessible
   	STATUS      	current
   	DESCRIPTION
    "An entry containing management information applicable to the E1 interface."
   	INDEX   { ifCfgE1SlotIndex,ifCfgE1PortIndex }
   	::= { ifCfgPortE1Table 1 }

	IfCfgPortE1Entry ::=
       SEQUENCE {  
       		ifCfgE1SlotIndex	 		INTEGER,
           	ifCfgE1PortIndex			INTEGER, 
           	ifCfgPortE1RxTxRate			INTEGER,  
           	ifCfgPortE1FrameType		INTEGER,
           	ifCfgPortE1LineCode			INTEGER,
           	ifCfgPortE1ClockSrc			INTEGER 
       } 
          
     ifCfgE1SlotIndex OBJECT-TYPE
       	SYNTAX      INTEGER (1..12)
       	MAX-ACCESS  read-only
       	STATUS      current
       	DESCRIPTION
        "The physical slot number of the IPD chassis to which the interface module
        resides. The Mini/Micro slot index will be 1."
       	::= { ifCfgPortE1Entry 1 }
   
   	 ifCfgE1PortIndex OBJECT-TYPE
       	SYNTAX      INTEGER (1..48)
       	MAX-ACCESS  read-only
       	STATUS      current
       	DESCRIPTION
        "The physical port number of the E1 interface."
       	::= { ifCfgPortE1Entry 2 }   
       	
     ifCfgPortE1RxTxRate OBJECT-TYPE
       	SYNTAX      INTEGER { 
       					e1RxTxRateDefect(0),   
       					e1RxTxRate256(1),
       					e1RxTxRate512(2),
       					e1RxTxRate768(3),
       					e1RxTxRate1024(4),
       					e1RxTxRate1280(5),
       					e1RxTxRate1536(6),
       					e1RxTxRate1792(7),
       					e1RxTxRate1984(8),
       					e1RxTxRateOff(255)
       				}       
       	UNITS       "Kbps"
       	MAX-ACCESS  read-write
       	STATUS      current
       	DESCRIPTION
        "E1 symetrical (Rx/Tx) data rates.
        
         E1 module types and the associated Rx/Tx data rates- 
                        
         EAM2000-12,EIM2000-12,EIM2000-24:         
         	Data Rates (Kbps): 256,512,768,1024,1280,1536,1792,1984 
         
         Note: if a rate value of zero(0) is returned via a GET operation, 
               it will indicate that the port is defective."

       	::= { ifCfgPortE1Entry 3 } 
       	
     ifCfgPortE1FrameType OBJECT-TYPE
       	SYNTAX      INTEGER {      
       						e1frameTypeCRC(1),
       						e1frameTypeNoCRC(2)
       				}
       	MAX-ACCESS  read-write
       	STATUS      current
       	DESCRIPTION
        "E1 frame type."
       	::= { ifCfgPortE1Entry 4 }  
       	
     ifCfgPortE1LineCode OBJECT-TYPE
       	SYNTAX      INTEGER {   
       						e1lineCodeHDB3(1),
       						e1lineCodeAMI(2)
       				}
       	MAX-ACCESS  read-write
       	STATUS      current
       	DESCRIPTION
        "E1 line code."
       	::= { ifCfgPortE1Entry 5 } 
       	
     ifCfgPortE1ClockSrc OBJECT-TYPE
       	SYNTAX      INTEGER {  
       						e1ClockSrcLocal(1),
       						e1ClockSrcLoop(2)
       				}
       	MAX-ACCESS  read-write
       	STATUS      current
       	DESCRIPTION
        "E1 clock source."
       	::= { ifCfgPortE1Entry 6 }    
       
              	
      
END

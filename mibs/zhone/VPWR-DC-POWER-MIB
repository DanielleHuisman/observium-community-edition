VPWR-DC-POWER-MIB DEFINITIONS ::= BEGIN

    IMPORTS
       MODULE-IDENTITY, OBJECT-TYPE, NOTIFICATION-TYPE,
       OBJECT-IDENTITY, Counter32, Gauge32, Integer32,
       enterprises
           FROM SNMPv2-SMI
       DisplayString, TimeStamp, TimeInterval, TestAndIncr,
         AutonomousType, TEXTUAL-CONVENTION
           FROM SNMPv2-TC
       MODULE-COMPLIANCE, OBJECT-GROUP
           FROM SNMPv2-CONF
              sysUpTime		  FROM RFC1213-MIB;
 --
 -- date and time in UTC format YYMMDDHHmmZ
 --
       valereDcPowerMgt	MODULE-IDENTITY
                        LAST-UPDATED "0302080000Z"
                        ORGANIZATION "Valere Power Inc."
                        CONTACT-INFO
                             "Author:  Haluk Aral
                              Contact: Customer Support Group
                              Postal:  661 N. Plano Road, Suite 300
                                       Richardson, TX-75081
                              Web:      http://www.valerepower.com
                              email:    tech.support@valerepower.com
                              Phone    866-240-6614
                             "
                        DESCRIPTION

                       " MIB Version 2.0
                          History
                          Apr 26, 2007  Added SysAlarm Config Table Version 2.0
                          Feb 08, 2003  Changed vpwrTrapDestinationTable to vpwrTrapTable
                                        Corrected entry for vpwrTrapTable to be VpwrTrapTableEntry
                                        This fixes errors generated by MG-SOFT mib compiler.Ver1.0
                          Oct 30, 2002  initial release - version 0.4
                        "

                        ::= {enterprises 13858}

    PositiveInteger ::= TEXTUAL-CONVENTION
       DISPLAY-HINT "d"
       STATUS       current
       DESCRIPTION
               "This data type is a non-zero and non-negative value."
       SYNTAX       INTEGER (1..2147483647)

   NonNegativeInteger ::= TEXTUAL-CONVENTION
       DISPLAY-HINT "d"
       STATUS       current
       DESCRIPTION
               "This data type is a non-negative value."
       SYNTAX       INTEGER (0..2147483647)
       


       vpwrDcPowerProducts         OBJECT IDENTIFIER ::=  { valereDcPowerMgt 1 }
       vpwrDcPowerSystem           OBJECT IDENTIFIER ::=  { valereDcPowerMgt 2 }
       vpwrDcPowerRectifier        OBJECT IDENTIFIER ::=  { valereDcPowerMgt 3 }
       vpwrDcPowerLvd              OBJECT IDENTIFIER ::=  { valereDcPowerMgt 4 }
       vpwrDcPowerTest             OBJECT IDENTIFIER ::=  { valereDcPowerMgt 5 }
       vpwrDcPowerModuleIdent      OBJECT IDENTIFIER ::=  { valereDcPowerMgt 6 }
       vpwrDcPowerBatteryGroup     OBJECT IDENTIFIER ::=  { valereDcPowerMgt 7 }
       vpwrDcPowerAlarmGroup       OBJECT IDENTIFIER ::=  { valereDcPowerMgt 8 }
       vpwrDcPowerSnmpConfig       OBJECT IDENTIFIER ::=  { valereDcPowerMgt 9 }
       vpwrDcPowerTraps           OBJECT IDENTIFIER ::=  { valereDcPowerMgt 10 }
       vpwrDcPowerTrapsMsgString   OBJECT IDENTIFIER ::=  { valereDcPowerMgt 11 }

       vpwrSystemIdentGroup        OBJECT IDENTIFIER ::=  { vpwrDcPowerSystem 1 }
       vpwrSystemConfigGroup       OBJECT IDENTIFIER ::=  { vpwrDcPowerSystem 2 }
       vpwrSystemParameterGroup    OBJECT IDENTIFIER ::=  { vpwrDcPowerSystem 3 }
       
       vpwrLvdConfigGroup          OBJECT IDENTIFIER ::=  { vpwrDcPowerLvd 1 }
       vpwrLvdAlarmGroup           OBJECT IDENTIFIER ::=  { vpwrDcPowerLvd 2 }
       vpwrLvdTestGroup            OBJECT IDENTIFIER ::=  { vpwrDcPowerLvd 3 }

       vpwrRectifierConfigGroup    OBJECT IDENTIFIER ::=  { vpwrDcPowerRectifier 1 }
       vpwrRectifierAlarmGroup     OBJECT IDENTIFIER ::=  { vpwrDcPowerRectifier 2 }
       vpwrRectifierTestGroup      OBJECT IDENTIFIER ::=  { vpwrDcPowerRectifier 3 }
       
       vpwrBatteryTempGroup      OBJECT IDENTIFIER ::=  { vpwrDcPowerBatteryGroup 1 }

   --
   -- The Identification group.
   --


   vpwrIdentManufacturer OBJECT-TYPE
       SYNTAX     DisplayString (SIZE (0..31))
       MAX-ACCESS read-only
       STATUS     current
       DESCRIPTION
               "The name of the DC Power manufacturer."
       ::= { vpwrSystemIdentGroup 1 }

   vpwrIdentModel OBJECT-TYPE
       SYNTAX     DisplayString (SIZE (0..15))
       MAX-ACCESS read-only
       STATUS     current
       DESCRIPTION
               "The DC Power Model designation."
       ::= { vpwrSystemIdentGroup 2 }

   vpwrIdentControllerVersion OBJECT-TYPE
       SYNTAX     DisplayString (SIZE (0..15))
       MAX-ACCESS read-only
       STATUS     current
       DESCRIPTION
               "The hardware/firmware version(s).  This variable
               may or may not have the same value as
               vpwrIdentAgentSoftwareVersion."
       ::= { vpwrSystemIdentGroup 3 }

   vpwrIdentAgentSoftwareVersion OBJECT-TYPE
       SYNTAX     DisplayString (SIZE (0..15))
       MAX-ACCESS read-only
       STATUS     current
       DESCRIPTION
               "The SNMP agent software version.  This variable may or
               may not have the same value as
               vpwrIdentControllerFirmwareVersion."
       ::= { vpwrSystemIdentGroup 4 }

   vpwrIdentName OBJECT-TYPE
       SYNTAX     DisplayString (SIZE(0..31))
       MAX-ACCESS read-write
       STATUS     current
       DESCRIPTION
               "A string identifying the system.  This object should be
               set by the administrator."
       ::= { vpwrSystemIdentGroup 5 }

   --
   -- The System Identifier group.
   --      All objects in this group  are read-only. It describes
   --      various modules (rectifiers, lvd's, etc.) that make up 
   --      the power system
   --
 
   vpwrSystemIdentTable OBJECT-TYPE
       SYNTAX     SEQUENCE OF VpwrSystemIdentEntry
       MAX-ACCESS not-accessible
       STATUS     current
       DESCRIPTION
       " This table describes shelves and modules
         that make up the sysetm.
       "
       ::= { vpwrSystemIdentGroup 6 }

   vpwrSystemIdentEntry OBJECT-TYPE
       SYNTAX     VpwrSystemIdentEntry
       MAX-ACCESS not-accessible
       STATUS     current
       DESCRIPTION
               "An entry containing information applicable to a
               particular module making up the system."

       INDEX { vpwrShelfIndex, vpwrModuleIndex }

       ::= { vpwrSystemIdentTable 1 }

   VpwrSystemIdentEntry ::= SEQUENCE {
       vpwrShelfIndex       PositiveInteger,
       vpwrModuleIndex      PositiveInteger,
       vpwrModuleOID        OBJECT IDENTIFIER  ,
       vpwrModuleParameter  INTEGER ,
       vpwrModuleOperStatus INTEGER ,
       vpwrModuleCapacity   INTEGER 
   }

        vpwrShelfIndex OBJECT-TYPE
                           SYNTAX     PositiveInteger
                           MAX-ACCESS read-only
                           STATUS     current
                           DESCRIPTION
                             "Identifies shelf number that this module belongs to.
                              The possible values are 1 through 16 limited by vpwrSystemShelfCapacity.
                              The shelf that contains the controller is identified as shelf number 1.
                             "
                              ::= { vpwrSystemIdentEntry 1 }
       
         vpwrModuleIndex OBJECT-TYPE
                           SYNTAX     PositiveInteger
                           MAX-ACCESS read-only
                           STATUS     current
                           DESCRIPTION
                             "This object identifies the module by its position in the shelf.
                              Module numbering starts from the controller/expansion controller end of 
                              the shelf.
                              So, the module in the first slot has an index of 1, the next module 
                              is 2 and so on.
                              Under the current scheme 
                               - Rectifier module can have a number between 1 and 5.
                               - LVD module starts with an index of 6.
                             "
                            ::= { vpwrSystemIdentEntry 2 }

         vpwrModuleOID        OBJECT-TYPE
                                SYNTAX        OBJECT IDENTIFIER
                                MAX-ACCESS    read-only
                                STATUS        current
                                DESCRIPTION
                                   "It indicates the type of the module by specifiying its OID"
                           ::= { vpwrSystemIdentEntry 3}

         vpwrModuleParameter   OBJECT-TYPE
                                SYNTAX        INTEGER
                                MAX-ACCESS    read-only
                                STATUS        current
                                DESCRIPTION
                                   "The meaning of this object depends upon the module type
                                    which is indicated by vpwrModuleOID as follows
                                      - Current for Rectifier module.
                                      - Not Applicable for LVD module
                                   "
                           ::= { vpwrSystemIdentEntry 4}
                           
         vpwrModuleOperStatus   OBJECT-TYPE
                                SYNTAX        INTEGER {
                                  moduleStatusOK(0),
                                  moduleStatusAlarm(1)
                                }
                                MAX-ACCESS    read-only
                                STATUS        current
                                DESCRIPTION
                                   "This object indicates current over all status of the module."
                           ::= { vpwrSystemIdentEntry 5}

          vpwrModuleCapacity   OBJECT-TYPE
                                SYNTAX        INTEGER
                                MAX-ACCESS    read-only
                                STATUS        current
                                DESCRIPTION
                                   "The meaning of this object depends upon the module type
                                    which is indicated by vpwrModuleOID as follows
                                      - Capacity for Rectifier module.
                                      - Not Applicable for LVD module
                                   "
                           ::= { vpwrSystemIdentEntry 6}
                           


   --
   -- The System Configuration Parameters group.
   --      

            vpwrSystemTempCompensation OBJECT-TYPE
                         SYNTAX INTEGER {
                                tempCompDisabled(0),
                                tempCompEnabled(1)
                         }
                         MAX-ACCESS read-write
                         STATUS current
                         DESCRIPTION
                         "  This parameter enables/disables temperature compensation.
                         "
                         REFERENCE " "

                         ::= {vpwrSystemConfigGroup 1}

              vpwrSystemTempCompStartTemperature OBJECT-TYPE
                         SYNTAX INTEGER (25 .. 60)
                         UNITS  "degrees Centigrade"
                         MAX-ACCESS read-write
                         STATUS current
                         DESCRIPTION
                         "  The temperature at which temperature compensation becomes
                            active.
                         "
                         REFERENCE " "
                         ::= {vpwrSystemConfigGroup 2}

               vpwrSystemTempCompStopVoltage OBJECT-TYPE
                         SYNTAX INTEGER 
                         UNITS  " vpwrSystemTempCompStopVoltage *.01 Volts"
                         MAX-ACCESS read-write
                         STATUS current
                         DESCRIPTION
                         "  When temperature compensation is active, vpwrSystemTempCompStopVoltage is the
                            limit to which float voltage will be reduced.
				    For example, to set this voltage to 51.75 volts enter a value of 5175.
                         "
                         REFERENCE " "
                         ::= {vpwrSystemConfigGroup 3}

               vpwrSystemTempCompensationSlope OBJECT-TYPE
                         SYNTAX INTEGER (0 .. 250)
                         UNITS  " milli-Volts per degrees Centigrade"
                         MAX-ACCESS read-write
                         STATUS current
                         DESCRIPTION
                         "  The rate at which float voltage is changed, within the specified limits,
                            when temperature compensation is active.
                         "
                         REFERENCE " "
                         ::= {vpwrSystemConfigGroup 4}

              vpwrSystemThermalSenseType OBJECT-TYPE
                         SYNTAX INTEGER {
                                external(0),
                                internal(1)
                         }
                         MAX-ACCESS read-write
                         STATUS current
                         DESCRIPTION
                         "  This parameter selects the temperature sensing point for temperature
                            compensation (in)activation.
                         "
                         REFERENCE " "
                         ::= {vpwrSystemConfigGroup 5}

         vpwrSystemHVAlarmSetpoint   OBJECT-TYPE
                                SYNTAX        INTEGER
                                UNITS  " vpwrSystemHVAlarmSetpoint *.01 Volts"
                                MAX-ACCESS    read-write
                                STATUS        current
                                DESCRIPTION
                                   "System High voltage alarm voltage setting.
                                   "
                           ::= { vpwrSystemConfigGroup 6}
         vpwrSystemBDAlarmSetpoint   OBJECT-TYPE
                                SYNTAX        INTEGER
                                UNITS  " vpwrSystemBDAlarmSetpoint *.01 Volts"
                                MAX-ACCESS    read-write
                                STATUS        current
                                DESCRIPTION
                                   "System Battery Discharge voltage setting."
                           ::= { vpwrSystemConfigGroup 7}

--
-- Threshold for Internal Temperature Trap
--
         vpwrSystemInternalTempLThreshold   OBJECT-TYPE
                                SYNTAX        INTEGER
                                UNITS         "degrees Centigrade"
                                MAX-ACCESS    read-write
                                STATUS        current
                                DESCRIPTION
                                   "Temperature value at which temperature compensation inactive (clear)
                                    trap would be sent if temperature compensation was active when this 
                                    value is reached.
                                    "
                           ::= { vpwrSystemConfigGroup 8}

          vpwrSystemInternalTempUThreshold   OBJECT-TYPE
                                SYNTAX        INTEGER
                                UNITS         "degrees Centigrade"
                                MAX-ACCESS    read-write
                                STATUS        current
                                DESCRIPTION
                                   "Temperature value at which temperature compensation active (set) trap 
                                    would be sent.
                                   "
                           ::= { vpwrSystemConfigGroup 9}

   --
   -- The System Current Operating Parameters group.
   --


        vpwrSystemShelfCapacity OBJECT-TYPE
                         SYNTAX INTEGER (1 .. 16)
                         MAX-ACCESS read-only
                         STATUS current
                         DESCRIPTION
                         "  It describes the maximum number of shelves that can/are controlled
                            by the controller. Each shelf is uniquely numbered in the range
                            from 1 to  vpwrShelfCapacity.
                         "
                         REFERENCE " "
                         ::= {vpwrSystemParameterGroup 1}
                         
         vpwrSystemVoltage OBJECT-TYPE
                         SYNTAX INTEGER 
                          UNITS  " vpwrSystemVoltage *.01 Volts"
                          MAX-ACCESS read-only
                         STATUS current
                         DESCRIPTION
                         "  The current system voltage.
                         "
                         REFERENCE " "
                         ::= {vpwrSystemParameterGroup 2}
                         
          vpwrSystemCurrent OBJECT-TYPE
                         SYNTAX INTEGER
                         UNITS  " Amperes"
                         MAX-ACCESS read-only
                         STATUS current
                         DESCRIPTION
                         "  The current system current.
                         "
                         REFERENCE " "
                         ::= {vpwrSystemParameterGroup 3}
                         
           vpwrSystemControllerState OBJECT-TYPE
                         SYNTAX INTEGER {
                                systemControllerStateUnknown(0),
                                systemControllerStateNormal(1),
                                systemControllerStateChange(2) ,
                                systemControllerStateAlarm(3),
                                systemControllerStateMenu(4 ),
                                systemControllerStateIrActive(5)
                         }
                         MAX-ACCESS read-only
                         STATUS current
                         DESCRIPTION
                         "  Current System state as shown on the enhanced display.
                         "
                         REFERENCE " "
                         ::= {vpwrSystemParameterGroup 4}


                vpwrSystemInternalTemperature OBJECT-TYPE
                         SYNTAX INTEGER 
                         UNITS  "degrees Centigrade"
                         MAX-ACCESS read-only
                         STATUS current
                         DESCRIPTION
                         "  The current controller internal temperature.
                         "
                         REFERENCE " "
                         ::= {vpwrSystemParameterGroup 5}
                         
                 vpwrSystemTempCompensationState OBJECT-TYPE
                         SYNTAX INTEGER {
                                systemTempCompInactive(0),
                                systemTempCompActive(1)
                         }
                         MAX-ACCESS read-only
                         STATUS current
                         DESCRIPTION
                         "  Active or Inactive. Applicable only if temperature compensation is enabled.
                            This means that the controller is temperature compensating the float voltage.
                         "
                         REFERENCE " "
                         ::= {vpwrSystemParameterGroup 6}
                        
             vpwrSystemType OBJECT-TYPE
                         SYNTAX     INTEGER {
                           sysType48V (0),
                           sysType24V(1)
                         }
                         MAX-ACCESS read-only
                         STATUS     current
                         DESCRIPTION
                         "This parameter describes the type of the system being managed.
                          This object is set by Valere Power Inc.
                         "
                         ::= { vpwrSystemParameterGroup 7 }

   --
   -- The System LVD Operating Setpoints group.
   --      

         vpwrLvdWarningSetpoint   OBJECT-TYPE
                                SYNTAX        INTEGER
                                UNITS  " vpwrLvdWarningSetpoint * .01 Volts"
                                MAX-ACCESS    read-write
                                STATUS        current
                                DESCRIPTION
                                   "LVD Warning voltage setpoint."
                           ::= { vpwrLvdConfigGroup 1}

          vpwrLvdDisconnectSetpoint   OBJECT-TYPE
                                SYNTAX        INTEGER
                                UNITS  " vpwrLvdDisconnectSetpoint *.01 Volts"
                                MAX-ACCESS    read-write
                                STATUS        current
                                DESCRIPTION
                                   "LVD disconnect voltage setpoint."
                           ::= { vpwrLvdConfigGroup 2}
         vpwrLvdReconnectSetpoint   OBJECT-TYPE
                                SYNTAX        INTEGER
                                UNITS  " vpwrLvdReconnectSetpoint *.01 Volts"
                                MAX-ACCESS    read-write
                                STATUS        current
                                DESCRIPTION
                                   "LVD Reconnect voltage setpoint."
                           ::= { vpwrLvdConfigGroup 3}
         vpwrLvdReconnectDelayTimer   OBJECT-TYPE
                                SYNTAX        INTEGER (20..240)
                                UNITS  " Seconds"
                                MAX-ACCESS    read-write
                                STATUS        current
                                DESCRIPTION
                                   "The delay time, in seconds, before LVD is reconnected"
                           ::= { vpwrLvdConfigGroup 4}
                           
                           

   --
   -- The Rectifier Operating Parameters group.
   --

         vpwrRectifierFVSetpoint   OBJECT-TYPE
                                SYNTAX        INTEGER
                                 UNITS  " vpwrRectifierFVSetpoint *.01 Volts"
                               MAX-ACCESS    read-write
                                STATUS        current
                                DESCRIPTION
                                   "System Float Voltage setting"
                           ::= { vpwrRectifierConfigGroup 1}
           vpwrRectifierHVSDSetpoint   OBJECT-TYPE
                                SYNTAX        INTEGER
                                UNITS  " vpwrRectifierHVSDSetpoint *.01 Volts"
                                MAX-ACCESS    read-write
                                STATUS        current
                                DESCRIPTION
                                   "System High Voltage Shutdown voltage setting"
                           ::= { vpwrRectifierConfigGroup 2}



   --
   -- The Alarm group.
   --


--H   vpwrAlarmsPresent OBJECT-TYPE
--       SYNTAX     Gauge32
--       MAX-ACCESS read-only
--       STATUS     current
--       DESCRIPTION
--               "The present number of active alarm conditions."
--       ::= { vpwrDcPowerAlarmGroup 1 }
--
--   vpwrAlarmTable OBJECT-TYPE
--       SYNTAX     SEQUENCE OF VpwrAlarmEntry
--       MAX-ACCESS not-accessible
--       STATUS     current
--       DESCRIPTION
--               "A list of alarm table entries.  The table contains
--               zero, one, or many rows at any moment, depending upon
--               the number of alarm conditions in effect.  The table
--               is initially empty at agent startup.  The agent
--               creates a row in the table each time a condition is
--               detected and deletes that row when that condition no
--               longer pertains.  
--               The vpwrAlarmIndex, for each type of module starts at 1
--               and is limited by the total number of alarams that can be
--               generated by the module. 
--
--               Alarms are named by an AutonomousType (OBJECT
--               IDENTIFIER), vpwrAlarmDescr, to allow a single table to
--               reflect alarms for different type of modules.
--
--               The number of rows in the table at any given time is
--               reflected by the value of vpwrAlarmsPresent."
--               
--       ::= { vpwrDcPowerAlarmGroup 2 }  
--  
--   vpwrAlarmEntry OBJECT-TYPE
--       SYNTAX     VpwrAlarmEntry
--       MAX-ACCESS not-accessible
--       STATUS     current
--       DESCRIPTION
--               "An entry containing information applicable to a
--               particular alarm."
--       INDEX { vpwrShelfIndex, vpwrModuleIndex, vpwrAlarmIndex }
--       ::= { vpwrAlarmTable 1 }
--
--   VpwrAlarmEntry ::= SEQUENCE {
--       vpwrAlarmIndex       PositiveInteger,
--       vpwrAlarmDescr       AutonomousType,
--       vpwrAlarmTime        TimeStamp
--   }
--
--      vpwrAlarmIndex OBJECT-TYPE
--       SYNTAX     PositiveInteger
--       MAX-ACCESS read-only
--       STATUS     current
--       DESCRIPTION
--               "Identifies the alarm associated with the module. 
--                It is unique on per module type basis. For example,
--                multiple rectifiers can have the same alarm and therefore same
--                vpwrAlarmIndex active at any one time. 
--               "
--       ::= { vpwrAlarmEntry 1 }
--       
--
--   vpwrAlarmDescr OBJECT-TYPE
--       SYNTAX     AutonomousType
--       MAX-ACCESS read-only
--       STATUS     current
--       DESCRIPTION
--               "A reference to an alarm description object.  The
--               object referenced should not be accessible, but rather
--               be used to provide a unique description of the alarm
--               condition."
--       ::= { vpwrAlarmEntry 2 }
--
--   vpwrAlarmTime OBJECT-TYPE
--       SYNTAX     TimeStamp
--       MAX-ACCESS read-only
--       STATUS     current
--       DESCRIPTION
--               "The value of sysUpTime when the alarm condition was
--               detected."
--               
--       ::= { vpwrAlarmEntry 3 }



   --
   -- The Battery Group
   --

 

   vpwrBatteryTempTable OBJECT-TYPE
       SYNTAX     SEQUENCE OF VpwrBatteryTempTableEntry
       MAX-ACCESS not-accessible
       STATUS     current
       DESCRIPTION
       "This table describes battery temperature probes.
       "
       ::= { vpwrBatteryTempGroup 1 }

   vpwrBatteryTempTableEntry OBJECT-TYPE
       SYNTAX     VpwrBatteryTempTableEntry
       MAX-ACCESS not-accessible
       STATUS     current
       DESCRIPTION
               "An entry containing information applicable to a
               particular temperature probe."
       INDEX { vpwrBatteryTempIndex }
       ::= { vpwrBatteryTempTable 1 }

   VpwrBatteryTempTableEntry ::= SEQUENCE {
       vpwrBatteryTempIndex       INTEGER,
       vpwrBatteryTempName      DisplayString,
       vpwrBatteryTemp        INTEGER
   }

         vpwrBatteryTempIndex   OBJECT-TYPE
                                SYNTAX        INTEGER
                                MAX-ACCESS    read-only
                                STATUS        current
                                DESCRIPTION
                                   "Index into temperature table"
                           ::= { vpwrBatteryTempTableEntry 1}

         vpwrBatteryTempName   OBJECT-TYPE
                                SYNTAX        DisplayString (SIZE (1 .. 8))
                                MAX-ACCESS    read-write
                                STATUS        current
                                DESCRIPTION
                                   "A string identifying probe location."
                           ::= { vpwrBatteryTempTableEntry 2}

         vpwrBatteryTemp   OBJECT-TYPE
                                SYNTAX        INTEGER
                                UNITS         "degrees Centigrade"
                                MAX-ACCESS    read-only
                                STATUS        current
                                DESCRIPTION
                                   "Current temperature as recorded by the probe."
                           ::= { vpwrBatteryTempTableEntry 3}


-- Threshold for Battery Temperature Trap

         vpwrBatteryTempLThreshold   OBJECT-TYPE
                                SYNTAX        INTEGER
                                UNITS         "degrees Centigrade"
                                MAX-ACCESS    read-write
                                STATUS        current
                                DESCRIPTION
                                   "Temperature value at which a clear trap would be sent.
                                    All three battery temperature must be at or below this value
                                    to trigger this trap.
                                    "
                           ::= { vpwrBatteryTempGroup 2}

          vpwrBatteryTempUThreshold   OBJECT-TYPE
                                SYNTAX        INTEGER
                                UNITS         "degrees Centigrade"
                                MAX-ACCESS    read-write
                                STATUS        current
                                DESCRIPTION
                                   "Temperature value at which a set trap would be sent.
                                   Any one of the three battery temperatures at or exceeding this limit
                                   would trigger the trap.
                                   "
                           ::= { vpwrBatteryTempGroup 3}




   vpwrAlarmsPresent OBJECT-TYPE
       SYNTAX     Gauge32
       MAX-ACCESS read-only
       STATUS     current
       DESCRIPTION
               "The present number of active alarm conditions."
       ::= { vpwrDcPowerAlarmGroup 1 }

   vpwrAlarmTable OBJECT-TYPE
       SYNTAX     SEQUENCE OF VpwrAlarmEntry
       MAX-ACCESS not-accessible
       STATUS     current
       DESCRIPTION
               "A list of alarm table entries.  The table contains
               zero, one, or many rows at any moment, depending upon
               the number of alarm conditions in effect.  The table
               is initially empty at agent startup.  The agent
               creates a row in the table each time a condition is
               detected and deletes that row when that condition no
               longer pertains.  
               The vpwrAlarmIndex, for each type of module starts at 1
               and is limited by the total number of alarams that can be
               generated by the module. 

               Alarms are named by an AutonomousType (OBJECT
               IDENTIFIER), vpwrAlarmDescr, to allow a single table to
               reflect alarms for different type of modules.

               The number of rows in the table at any given time is
               reflected by the value of vpwrAlarmsPresent."
               
       ::= { vpwrDcPowerAlarmGroup 2 }  
--WAS 2
   vpwrAlarmEntry OBJECT-TYPE
       SYNTAX     VpwrAlarmEntry
       MAX-ACCESS not-accessible
       STATUS     current
       DESCRIPTION
               "An entry containing information applicable to a
               particular alarm."
       INDEX { vpwrShelfIndex, vpwrModuleIndex, vpwrAlarmIndex }
       ::= { vpwrAlarmTable 1 }

   VpwrAlarmEntry ::= SEQUENCE {
       vpwrAlarmIndex       PositiveInteger,
       vpwrAlarmDescr       AutonomousType,
       vpwrAlarmTime        TimeStamp
   }

      vpwrAlarmIndex OBJECT-TYPE
       SYNTAX     PositiveInteger
       MAX-ACCESS read-only
       STATUS     current
       DESCRIPTION
               "Identifies the alarm associated with the module. 
                It is unique on per module type basis. For example,
                multiple rectifiers can have the same alarm and therefore same
                vpwrAlarmIndex active at any one time. 
               "
       ::= { vpwrAlarmEntry 1 }
       

   vpwrAlarmDescr OBJECT-TYPE
       SYNTAX     AutonomousType
       MAX-ACCESS read-only
       STATUS     current
       DESCRIPTION
               "A reference to an alarm description object.  The
               object referenced should not be accessible, but rather
               be used to provide a unique description of the alarm
               condition."
       ::= { vpwrAlarmEntry 2 }

   vpwrAlarmTime OBJECT-TYPE
       SYNTAX     TimeStamp
       MAX-ACCESS read-only
       STATUS     current
       DESCRIPTION
               "The value of sysUpTime when the alarm condition was
               detected."
               
       ::= { vpwrAlarmEntry 3 }

	sysAlarmConfigTable OBJECT-TYPE
	   SYNTAX     SEQUENCE OF SysAlarmConfigEntry
	   MAX-ACCESS not-accessible
	   STATUS     current
	   DESCRIPTION
	   "This table describes battery temperature probes.
	   "
   	   ::= { vpwrDcPowerAlarmGroup 4  }
	sysAlarmConfigEntry OBJECT-TYPE
	   SYNTAX     SysAlarmConfigEntry
	   MAX-ACCESS not-accessible
	   STATUS     current
	   DESCRIPTION
	           "An entry containing information applicable to a
	           particular temperature probe."
	   INDEX { sysAlarmIndex }
	   ::= { sysAlarmConfigTable 1 }





	SysAlarmConfigEntry ::= SEQUENCE {
	   sysAlarmIndex       INTEGER,
	   sysAlarmDefaultName        DisplayString,
	   sysAlarmCustomName        DisplayString,
	   sysAlarmSeverity        INTEGER   ,
	   sysAlarmToRelayMapping  DisplayString  ,
	   sysAlarmOperStatus      INTEGER
	}

	     sysAlarmIndex    OBJECT-TYPE
	                            SYNTAX        INTEGER
	                            MAX-ACCESS    read-only
	                            STATUS        current
	                            DESCRIPTION
	                               "Index into temperature table"
	                       ::= { sysAlarmConfigEntry 1}

	     sysAlarmDefaultName   OBJECT-TYPE
	                            SYNTAX        DisplayString (SIZE (1 .. 8))
	                            MAX-ACCESS    read-only
	                            STATUS        current
	                            DESCRIPTION
	                               "A string identifying probe location."
	                       ::= { sysAlarmConfigEntry 2}

	     sysAlarmCustomName   OBJECT-TYPE
	                            SYNTAX        DisplayString (SIZE (1 .. 8))
	                            MAX-ACCESS    read-write
	                            STATUS        current
	                            DESCRIPTION
	                               "A string identifying probe location."
	                       ::= { sysAlarmConfigEntry 3}

	     sysAlarmSeverity   OBJECT-TYPE
	                          SYNTAX INTEGER {
	                                 none(0),
	                                 major(1),
	                                 minor(2),
	                                 majorAndMinor(3)
	                                 }
	                            MAX-ACCESS    read-write
	                            STATUS        current
	                            DESCRIPTION
	                               "Alarm Severity as denoted by Major and Minor Alarm Mask"
	                       ::= { sysAlarmConfigEntry 4}

	       sysAlarmToRelayMapping   OBJECT-TYPE
	                            SYNTAX DisplayString (SIZE (1 .. 8))
	                            MAX-ACCESS    read-write
	                            STATUS        current
	                            DESCRIPTION
	                               "No additional mapping = 0
	                                Map to Relay A  = 1
	                                Map to Relay B  = 2
	                                Map to Relay C  = 4
	                                Map to Relay D  = 8
	                                Map to Relay E  = 16
	                                Map to Relay F  = 32
	                                Map to Relay A and B  = (1 + 2) and so on
	                                The major/minor classification of alarms automatically
	                                associates it with Major/Minor relay. Assigning a null
	                                mapping here does not override sysRelayAlarmSeverity for
	                                the alarm.
	                                It should be used to define mapping to additional relays.
	                               "
	                       ::= { sysAlarmConfigEntry 5}

	     sysAlarmOperStatus   OBJECT-TYPE
	                          SYNTAX INTEGER {
	                                 inactive(0),
	                                 active(1)
	                                }
	                            MAX-ACCESS    read-only
	                            STATUS        current
	                            DESCRIPTION
	                               "Indicates current alarm status"
	                       ::= { sysAlarmConfigEntry 6}

--
-- The SNMP Configuration Parameters
--
--

   vpwrTrapTable OBJECT-TYPE
       SYNTAX     SEQUENCE OF VpwrTrapTableEntry
       MAX-ACCESS not-accessible
       STATUS     current
       DESCRIPTION
       "A list of possible trap destinations depending upon
        the criticality of the trap.
       "
       ::= { vpwrDcPowerSnmpConfig 1 }

   vpwrTrapTableEntry OBJECT-TYPE
       SYNTAX     VpwrTrapTableEntry
       MAX-ACCESS not-accessible
       STATUS     current
       DESCRIPTION
               "An entry containing information applicable to a
               particular trap destination."
       INDEX { vpwrTrapIpIndex }
       ::= { vpwrTrapTable 1 }

   VpwrTrapTableEntry ::= SEQUENCE {
       vpwrTrapIpIndex         INTEGER,
       vpwrTrapIpAddress       IpAddress,
       vpwrTrapCriticality      INTEGER
   }
           vpwrTrapIpIndex   OBJECT-TYPE
                                SYNTAX          INTEGER
                                MAX-ACCESS    read-only
                                STATUS        current
                                DESCRIPTION
                                   "Trap Entry Index "
                           ::= { vpwrTrapTableEntry 1}

         vpwrTrapIpAddress   OBJECT-TYPE
                                SYNTAX        IpAddress
                                MAX-ACCESS    read-write
                                STATUS        current
                                DESCRIPTION
                                   "Trap destination IP Address"
                           ::= { vpwrTrapTableEntry 2}

         vpwrTrapCriticality   OBJECT-TYPE
                                SYNTAX          INTEGER
                                MAX-ACCESS    read-write
                                STATUS        current
                                DESCRIPTION
                                   "Criticality of traps sent to this IP Address"
                           ::= { vpwrTrapTableEntry 3}

        vpwrReadCommunityString OBJECT-TYPE
                          SYNTAX     DisplayString(SIZE (3 .. 8))
                          MAX-ACCESS read-write
                          STATUS     current
                          DESCRIPTION
                         " This allows setting password to be able to do Get operations"
                         ::= { vpwrDcPowerSnmpConfig 2 }

       vpwrWriteCommunityString OBJECT-TYPE
                          SYNTAX     DisplayString(SIZE (3 .. 8))
                          MAX-ACCESS read-write
                          STATUS     current
                          DESCRIPTION
                          " This allows setting password to be able to do Get and Set 
                            operations. 
                            The read-access is not allowed in the actual implementation.
                          "
                          ::= { vpwrDcPowerSnmpConfig 3 }

      vpwrTrapCommunityString OBJECT-TYPE
                           SYNTAX     DisplayString(SIZE (3 .. 8))
                           MAX-ACCESS read-write
                           STATUS     current
                           DESCRIPTION
                          " This allows setting community string required for the 
                            trap to be accepted at the destination.
                          "
                           ::= { vpwrDcPowerSnmpConfig 4 }

--
--  traps
--
    vpwrTrapPowerMajorAlarm TRAP-TYPE
       ENTERPRISE      vpwrDcPowerTraps
        VARIABLES { vpwrTrapsMsgString }
                        DESCRIPTION
                          "Major Alarm"
                          ::= 1

    vpwrTrapPowerMinorAlarm   TRAP-TYPE
       ENTERPRISE      vpwrDcPowerTraps
        VARIABLES { vpwrTrapsMsgString }
                              DESCRIPTION
                              "Minor Alarm"
                              ::= 2

     vpwrTrapACFAlarm   TRAP-TYPE
       ENTERPRISE      vpwrDcPowerTraps
        VARIABLES { vpwrTrapsMsgString }
                              DESCRIPTION
                              "AC Fail Alarm"
                              ::= 3

    vpwrTrapHVAlarm   TRAP-TYPE
       ENTERPRISE      vpwrDcPowerTraps
        VARIABLES { vpwrTrapsMsgString }
                              DESCRIPTION
                              "High Voltage Warning Alarm"
                              ::= 4

    vpwrTrapHVSDAlarm   TRAP-TYPE
       ENTERPRISE      vpwrDcPowerTraps
        VARIABLES { vpwrTrapsMsgString }
                              DESCRIPTION
                              "High Voltage Shutdown Alarm"
                              ::= 5
    vpwrTrapBDAlarm   TRAP-TYPE
       ENTERPRISE      vpwrDcPowerTraps
        VARIABLES { vpwrTrapsMsgString }
                              DESCRIPTION
                              "Battery on Discharge Alarm"
                              ::= 6
     vpwrTrapLVDWarningAlarm   TRAP-TYPE
       ENTERPRISE      vpwrDcPowerTraps
        VARIABLES { vpwrTrapsMsgString }
                              DESCRIPTION
                              "LVD Warning Alarm"
                              ::= 7

      vpwrTrapLVDOpenAlarm   TRAP-TYPE
       ENTERPRISE      vpwrDcPowerTraps
        VARIABLES { vpwrTrapsMsgString }
                              DESCRIPTION
                              "LVD Open Alarm"
                              ::= 8

     vpwrTrapDistAlarm   TRAP-TYPE
       ENTERPRISE      vpwrDcPowerTraps
        VARIABLES { vpwrTrapsMsgString }
                              DESCRIPTION
                              "Distribution Open Alarm"
                              ::= 9

     vpwrTrapAuxAlarm   TRAP-TYPE
       ENTERPRISE      vpwrDcPowerTraps
        VARIABLES { vpwrTrapsMsgString }
                              DESCRIPTION
                              "Auxiliary System Alarm"
                              ::= 10

     vpwrTrapSystemRedundancyAlarm   TRAP-TYPE
       ENTERPRISE      vpwrDcPowerTraps
        VARIABLES { vpwrTrapsMsgString }
                              DESCRIPTION
                              "System Redundant Capacity Alarm"
                              ::=  11

     vpwrTrapIShareAlarm   TRAP-TYPE
       ENTERPRISE      vpwrDcPowerTraps
        VARIABLES { vpwrTrapsMsgString }
                              DESCRIPTION
                              "Rectifier Current Share Alarm"
                              ::=  12
     vpwrTrapModuleFailAlarm   TRAP-TYPE
       ENTERPRISE      vpwrDcPowerTraps
        VARIABLES { vpwrTrapsMsgString }
                              DESCRIPTION
                              "Single Rectifier Fail Alarm"
                              ::=  13

     vpwrTrapMultipleModuleFailAlarm   TRAP-TYPE
       ENTERPRISE      vpwrDcPowerTraps
        VARIABLES { vpwrTrapsMsgString }
                              DESCRIPTION
                              "Multiple Rectifier Fail Alarm"
                              ::= 14

     vpwrTrapModuleCommAlarm   TRAP-TYPE
       ENTERPRISE      vpwrDcPowerTraps
        VARIABLES { vpwrTrapsMsgString }
                              DESCRIPTION
                              "Module Communication Alarm"
                              ::=  15
     vpwrTrapSystemOverTemperatureAlarm   TRAP-TYPE
       ENTERPRISE      vpwrDcPowerTraps
        VARIABLES { vpwrTrapsMsgString }
                              DESCRIPTION
                              "System Over Temperature Alarm"
                              ::= 16
     vpwrTrapSystemOK   TRAP-TYPE
       ENTERPRISE      vpwrDcPowerTraps
        VARIABLES { vpwrTrapsMsgString }
                              DESCRIPTION
                              "SYSTEM OK - No Active Alarms"
                              ::=  17

   vpwrTrapModuleInserted TRAP-TYPE
       ENTERPRISE      vpwrDcPowerTraps
       VARIABLES { vpwrTrapsMsgString,vpwrShelfIndex, vpwrModuleIndex }
       DESCRIPTION
               "A new module has been inserted into the system."
     ::= 18

   vpwrTrapModuleRemoved TRAP-TYPE
       ENTERPRISE      vpwrDcPowerTraps
       VARIABLES { vpwrTrapsMsgString,vpwrShelfIndex, vpwrModuleIndex }
       DESCRIPTION
               "A module has been removed from the system."
     ::= 19


    vpwrTrapThermalCompActive   TRAP-TYPE
       ENTERPRISE      vpwrDcPowerTraps
        VARIABLES { vpwrTrapsMsgString }
                              DESCRIPTION
                              "Thermal compensation has become active."
                              ::=  20

    vpwrTrapThermalCompInactive   TRAP-TYPE

       ENTERPRISE      vpwrDcPowerTraps
        VARIABLES { vpwrTrapsMsgString }
                              DESCRIPTION
                              "Thermal compensation has been de-activated."
                              ::=  21

    vpwrTrapInternalTempAlarmSet   TRAP-TYPE

       ENTERPRISE      vpwrDcPowerTraps
        VARIABLES { vpwrTrapsMsgString }
                              DESCRIPTION
                              "Internal Temperature upper threshold exceeded."
                              ::=  22

    vpwrTrapInternalTempAlarmCleared   TRAP-TYPE

       ENTERPRISE      vpwrDcPowerTraps
        VARIABLES { vpwrTrapsMsgString }
                              DESCRIPTION
                              "Internal Temperature within limits"
                              ::=  23

    vpwrTrapBatteryTempAlarmSet   TRAP-TYPE

       ENTERPRISE      vpwrDcPowerTraps
        VARIABLES { vpwrTrapsMsgString }
                              DESCRIPTION
                              "At least one Battery Temperature exceeded upper threshold."
                              ::=  24

    vpwrTrapBatteryTempAlarmCleared   TRAP-TYPE

       ENTERPRISE      vpwrDcPowerTraps
        VARIABLES { vpwrTrapsMsgString }
                              DESCRIPTION
                              "All Battery Temperatures within limits"
                              ::=  25

--
--    LVD Alarm Group
--

     vpwrLvdAlarmContactorOpen	OBJECT-IDENTITY
                        STATUS  current
			DESCRIPTION
			"Contactor open"
			::= {vpwrLvdAlarmGroup 1   }


     vpwrLvdAlarmCBOpen	OBJECT-IDENTITY
                        STATUS  current
			DESCRIPTION
			"Circuit Breaker open"
			::= {vpwrLvdAlarmGroup 2   }

     vpwrTrapLvdFuseOpen	OBJECT-IDENTITY
                        STATUS  current
			DESCRIPTION
			"Fuse open"
			::= {vpwrLvdAlarmGroup 3   }
     vpwrLvdAlarmWarning	OBJECT-IDENTITY
                        STATUS  current
			DESCRIPTION
			"Plant Voltage below warning threshold"
			::= {vpwrLvdAlarmGroup 4   }

--
--    Rectifier Alarm Group
--

vpwrRectAlarmDCFail   OBJECT-IDENTITY
           STATUS          current
           DESCRIPTION 
           "
           "
           ::= {vpwrRectifierAlarmGroup   1}

vpwrRectAlarmBoostFail   OBJECT-IDENTITY
           STATUS          current
           DESCRIPTION
           "
           "
           ::= {vpwrRectifierAlarmGroup   2}

vpwrRectAlarmACFail   OBJECT-IDENTITY
           STATUS          current
           DESCRIPTION 
           "
           "
           ::= {vpwrRectifierAlarmGroup   3}

vpwrRectAlarmHVSD   OBJECT-IDENTITY
           STATUS          current
           DESCRIPTION
           "
           "
           ::= {vpwrRectifierAlarmGroup   4}
           
vpwrRectAlarmFanFail   OBJECT-IDENTITY
           STATUS          current
           DESCRIPTION 
           "
           "
           ::= {vpwrRectifierAlarmGroup   5}

vpwrRectAlarmAmbTemp   OBJECT-IDENTITY
           STATUS          current
           DESCRIPTION 
           "
           "
           ::= {vpwrRectifierAlarmGroup   6}
vpwrRectAlarmIntTemp   OBJECT-IDENTITY
           STATUS          current
           DESCRIPTION 
           "
           "
           ::= {vpwrRectifierAlarmGroup   7}
           
vpwrRectAlarmIShare   OBJECT-IDENTITY
           STATUS          current
           DESCRIPTION 
           "
           "
           ::= {vpwrRectifierAlarmGroup   8}

vpwrRectAlarmUV   OBJECT-IDENTITY
           STATUS          current
           DESCRIPTION 
           "
           "
           ::= {vpwrRectifierAlarmGroup   9}

vpwrRectAlarmLowVoltage   OBJECT-IDENTITY
           STATUS          current
           DESCRIPTION 
           "
           "
           ::= {vpwrRectifierAlarmGroup   10}

vpwrRectAlarmReserved   OBJECT-IDENTITY
           STATUS          current
           DESCRIPTION 
           "
           "
           ::= {vpwrRectifierAlarmGroup   11}

vpwrRectAlarmDCEnable   OBJECT-IDENTITY
           STATUS          current
           DESCRIPTION 
           "
           "
           ::= {vpwrRectifierAlarmGroup   12}

vpwrRectAlarmRemoteShutdown   OBJECT-IDENTITY
           STATUS          current
           DESCRIPTION 
           "
           "
           ::= {vpwrRectifierAlarmGroup   13}

vpwrRectAlarmModDisableShutdown   OBJECT-IDENTITY
           STATUS          current
           DESCRIPTION 
           "
           "
           ::= {vpwrRectifierAlarmGroup   14}

vpwrRectAlarmShortPinShutdown   OBJECT-IDENTITY
           STATUS          current
           DESCRIPTION 
           "
           "
           ::= {vpwrRectifierAlarmGroup   15}

vpwrRectAlarmBoostComm   OBJECT-IDENTITY
           STATUS          current
           DESCRIPTION 
           "
           "
           ::= {vpwrRectifierAlarmGroup   16}


vpwrTrapsMsgString  OBJECT-TYPE
                          SYNTAX     DisplayString(SIZE (0 .. 127))
                          MAX-ACCESS not-accessible
                          STATUS     current
                          DESCRIPTION
                         " Place holder for trap notification message string"
                         ::= { vpwrDcPowerTrapsMsgString 1 }


END

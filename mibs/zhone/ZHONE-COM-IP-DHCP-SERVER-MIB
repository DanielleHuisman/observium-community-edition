--
-- comIpDhcpServer.mib
-- MIB generated by MG-SOFT Visual MIB Builder Version 3.0 Build 285
-- Thursday, September 18, 2008 at 15:40:21
--

    ZHONE-COM-IP-DHCP-SERVER-MIB DEFINITIONS ::= BEGIN
 
        IMPORTS
            InterfaceIndex            
                FROM IF-MIB            
            SnmpAdminString            
                FROM SNMP-FRAMEWORK-MIB            
            sysObjectID            
                FROM SNMPv2-MIB            
            TimeTicks, IpAddress, Integer32, Unsigned32, Counter32, 
            OBJECT-TYPE, MODULE-IDENTITY, OBJECT-IDENTITY, NOTIFICATION-TYPE            
                FROM SNMPv2-SMI            
            PhysAddress, TruthValue            
                FROM SNMPv2-TC            
            cardMfgSerialNumber, cardPostResults            
                FROM ZHONE-CARD-RESOURCES-MIB            
            rdEntry, ZhoneRDIndex            
                FROM ZHONE-COM-IP-RD-MIB            
            ipIfLgId, ipIfVpi, ipIfVci, ipIfAddr            
                FROM ZHONE-COM-IP-REC-MIB            
            zhoneShelfNumber, zhoneSlotNumber, pportNumber, subPortNumber            
                FROM ZHONE-INTERFACE-TRANSLATION-MIB            
            zhoneSysCardSwSpecificVers            
                FROM ZHONE-SYSTEM-MIB            
            zhoneIp, zhoneModules            
                FROM Zhone            
            ZhoneFileName, ZhoneAdminString, ZhoneRowStatus, ZhoneShelfValue, ZhoneSlotValue            
                FROM Zhone-TC;
    
    
-- This MIB contains configuration and statistic information
-- for the Zhone DHCP server.
-- 
-- 
-- 
-- 
-- 
-- 
-- 
-- 
-- 
        -- 1.3.6.1.4.1.5504.6.61
        comIpDhcpServer MODULE-IDENTITY 
            LAST-UPDATED "200309101500Z"		-- September 10, 2003 at 15:00 GMT
            ORGANIZATION 
                "Zhone Technologies, Inc."
            CONTACT-INFO 
                "  Postal: 
                           Zhone Technologies, Inc.
                           @ Zhone Way
                           7001 Oakport Street
                           Oakland, CA  94621
                           USA
                Toll-Free: +1 877-ZHONE20 (+1 877-946-6320)
                      Tel: +1-510-777-7000
                      Fax: +1-510-777-7001
                   E-mail: support@zhone.com"
            DESCRIPTION 
                "DHCP Server MIB using SNMPv2 SMI."
            REVISION "200309101047Z"		-- September 10, 2003 at 10:47 GMT
            DESCRIPTION 
                "V01.06.00 - add Ip Trap."
            REVISION "200304181010Z"		-- April 18, 2003 at 10:10 GMT
            DESCRIPTION 
                "V01.05.00 - Added subnetgroup and stickyaddr in order to support
                           the point-to-multipoint feature."
            REVISION "200012031400Z"		-- December 03, 2000 at 14:00 GMT
            DESCRIPTION 
                "V01.04.00 - Add dhcpTrapZhoneCpeSysObjectID and change
                             cardSwCurrentVersion to zhoneSysCardSwSpecificVers
                             in cpe detect trap."
            REVISION "200011281500Z"		-- November 28, 2000 at 15:00 GMT
            DESCRIPTION 
                "V01.03.00 - Deprecate dhcpServerConfigurationVersion
                             and add replacement dhcpServerRestart.
                             Remove DEFVALs for all read-write fields."
            REVISION "200012051211Z"		-- December 05, 2000 at 12:11 GMT
            DESCRIPTION 
                "V01.02.01 - Add ZHONE markup"
            REVISION "200010021205Z"		-- October 02, 2000 at 12:05 GMT
            DESCRIPTION 
                "V01.02.00 - Modified dhcpTrapZhoneCpeDetected"
            REVISION "200009151650Z"		-- September 15, 2000 at 16:50 GMT
            DESCRIPTION 
                "V01.01.00 - Added dhcpTrapZhoneCpeDetected trap
                             Added enumeration to dhcpLeaseFlags"
            REVISION "200009111541Z"		-- September 11, 2000 at 15:41 GMT
            DESCRIPTION 
                "V01.00.00 - Initial Release"
            ::= { zhoneModules 61 }

        
    
    
--
-- Node definitions
--
    
        -- 1.3.6.1.4.1.5504.4.1.11
        dhcpServer OBJECT-IDENTITY
            STATUS current
            DESCRIPTION 
                "Zhone DHCP Server Configuration and Monitoring MIB"
            ::= { zhoneIp 11 }

        
        -- 1.3.6.1.4.1.5504.4.1.11.0
        dhcpServerTraps OBJECT-IDENTITY
            STATUS current
            DESCRIPTION 
                "Traps which apply to the DHCP Server."
            ::= { dhcpServer 0 }

        
        -- 1.3.6.1.4.1.5504.4.1.11.0.1
        dhcpTrapZhoneCpeDetected NOTIFICATION-TYPE
            OBJECTS { zhoneShelfNumber, zhoneSlotNumber, pportNumber, subPortNumber, ipIfVpi, 
                ipIfVci, ipIfLgId, dhcpTrapZhoneCpeSysObjectID, cardMfgSerialNumber, cardPostResults, 
                zhoneSysCardSwSpecificVers, ipIfAddr }
            STATUS current
            DESCRIPTION 
                "Trap sent whenever an IP address is being offerred to a
                Zhone CPE device."
            ::= { dhcpServerTraps 1 }

        
        -- 1.3.6.1.4.1.5504.4.1.11.0.2
        dhcpTrapZhoneCpeSysObjectID OBJECT-TYPE
            SYNTAX OBJECT IDENTIFIER
            MAX-ACCESS accessible-for-notify
            STATUS current
            DESCRIPTION
                "System Object ID of attached Zhone CPE device"
            ::= { dhcpServerTraps 2 }

        
        -- 1.3.6.1.4.1.5504.4.1.11.0.3
        dhcpTrapZhoneIpAddressUpdate NOTIFICATION-TYPE
            OBJECTS { dhcpTrapZhoneIpInterfaceIndex, ipIfAddr }
            STATUS current
            DESCRIPTION 
                "Trap sent whenever the dhcp ip addresses are assigned
                or modified."
            ::= { dhcpServerTraps 3 }

        
        -- 1.3.6.1.4.1.5504.4.1.11.0.4
        dhcpTrapZhoneIpInterfaceIndex OBJECT-TYPE
            SYNTAX InterfaceIndex
            MAX-ACCESS accessible-for-notify
            STATUS current
            DESCRIPTION
                "Interface Index of the ip-interface-record which
                contains the updated ip address.  This is sent
                within the dhcpTrapZhoneIpAddressUpdate trap."
            ::= { dhcpServerTraps 4 }

        
        -- 1.3.6.1.4.1.5504.4.1.11.1
        dhcpServerDefaultLeaseTime OBJECT-TYPE
            SYNTAX Integer32 (0..2147483647)
            UNITS "seconds"
            MAX-ACCESS read-write
            STATUS current
            DESCRIPTION
                "The global default time in seconds that will be assigned
                to a lease if the client requesting the lease does not
                ask for a specific expiration time.  Default value is 
                43200 seconds."
            ::= { dhcpServer 1 }

        
        -- 1.3.6.1.4.1.5504.4.1.11.2
        dhcpServerDefaultMinLeaseTime OBJECT-TYPE
            SYNTAX Integer32 (0..2147483647)
            UNITS "seconds"
            MAX-ACCESS read-write
            STATUS current
            DESCRIPTION
                "The global minimum expiration time in seconds that will
                be assigned to a lease regardless of the value specified
                by a client.  Default value is 0"
            ::= { dhcpServer 2 }

        
        -- 1.3.6.1.4.1.5504.4.1.11.3
        dhcpServerDefaultMaxLeaseTime OBJECT-TYPE
            SYNTAX Integer32 (0..2147483647)
            UNITS "seconds"
            MAX-ACCESS read-write
            STATUS current
            DESCRIPTION
                "The global maximum time in seconds that will be assigned
                to a lease regardless of the value specified by a client.
                Default value is 86400 seconds."
            ::= { dhcpServer 3 }

        
        -- 1.3.6.1.4.1.5504.4.1.11.4
        dhcpServerDefaultReserveStart OBJECT-TYPE
            SYNTAX Integer32 (0..255)
            MAX-ACCESS read-write
            STATUS current
            DESCRIPTION
                "The default number of IP addresses at the start of a
                subnet's IP address space that are reserved by the
                DHCP server.  To override this default a specific 
                subnet rule must be created for each subnet that 
                needs to be handled differently. Default value is 5"
            ::= { dhcpServer 4 }

        
        -- 1.3.6.1.4.1.5504.4.1.11.5
        dhcpServerDefaultReserveEnd OBJECT-TYPE
            SYNTAX Integer32 (0..255)
            MAX-ACCESS read-write
            STATUS current
            DESCRIPTION
                "The default number of IP addresses at the end of a
                subnet's IP address space that are reserved by the
                DHCP server.  To override this default a specific 
                subnet rule must be created for each subnet that 
                needs to be handled differently. Default value is 5"
            ::= { dhcpServer 5 }

        
        -- 1.3.6.1.4.1.5504.4.1.11.6
        dhcpServerLeaseTable OBJECT-TYPE
            SYNTAX SEQUENCE OF DhcpServerLeaseEntry
            MAX-ACCESS not-accessible
            STATUS current
            DESCRIPTION
                "Provides access to the DHCP Server Client Lease Database"
            ::= { dhcpServer 6 }

        
        -- 1.3.6.1.4.1.5504.4.1.11.6.1
        dhcpServerLeaseEntry OBJECT-TYPE
            SYNTAX DhcpServerLeaseEntry
            MAX-ACCESS not-accessible
            STATUS current
            DESCRIPTION
                "Required server lease fields: 
                    dhcpLeaseDomain, 
                    dhcpLeaseIpAddres, 
                    dhcpLeaseStarts,
                    dhcpLeaseEnds
                    Plus at lease one of:
                        dhcpLeaseHardwareAddress,
                        dhcpLeaseClientId
                "
            INDEX { dhcpLeaseDomain, dhcpLeaseIpAddress }
            ::= { dhcpServerLeaseTable 1 }

        
        DhcpServerLeaseEntry ::=
            SEQUENCE { 
                dhcpLeaseDomain
                    ZhoneRDIndex,
                dhcpLeaseIpAddress
                    IpAddress,
                dhcpLeaseStarts
                    Unsigned32,
                dhcpLeaseEnds
                    Unsigned32,
                dhcpLeaseHardwareAddress
                    PhysAddress,
                dhcpLeaseFlags
                    BITS,
                dhcpLeaseClientId
                    OCTET STRING,
                dhcpLeaseClientHostname
                    SnmpAdminString,
                dhcpLeaseHostname
                    SnmpAdminString,
                dhcpLeaseDDNSFwdName
                    SnmpAdminString,
                dhcpLeaseDDNSRevName
                    SnmpAdminString,
                dhcpLeaseRowStatus
                    ZhoneRowStatus
             }

        -- 1.3.6.1.4.1.5504.4.1.11.6.1.1
        dhcpLeaseDomain OBJECT-TYPE
            SYNTAX ZhoneRDIndex
            MAX-ACCESS not-accessible
            STATUS current
            DESCRIPTION
                "Routing domain of the client the lease was created for."
            ::= { dhcpServerLeaseEntry 1 }

        
        -- 1.3.6.1.4.1.5504.4.1.11.6.1.2
        dhcpLeaseIpAddress OBJECT-TYPE
            SYNTAX IpAddress
            MAX-ACCESS not-accessible
            STATUS current
            DESCRIPTION
                "IP Address of this lease."
            ::= { dhcpServerLeaseEntry 2 }

        
        -- 1.3.6.1.4.1.5504.4.1.11.6.1.3
        dhcpLeaseStarts OBJECT-TYPE
            SYNTAX Unsigned32
            MAX-ACCESS read-create
            STATUS current
            DESCRIPTION
                "Time in GMT that the lease was assigned."
            ::= { dhcpServerLeaseEntry 3 }

        
        -- 1.3.6.1.4.1.5504.4.1.11.6.1.4
        dhcpLeaseEnds OBJECT-TYPE
            SYNTAX Unsigned32
            MAX-ACCESS read-create
            STATUS current
            DESCRIPTION
                "Time in GMT that the lease will expire."
            ::= { dhcpServerLeaseEntry 4 }

        
        -- 1.3.6.1.4.1.5504.4.1.11.6.1.5
        dhcpLeaseHardwareAddress OBJECT-TYPE
            SYNTAX PhysAddress (SIZE (0..16))
            MAX-ACCESS read-create
            STATUS current
            DESCRIPTION
                "The MAC address of the network interface that was used
                to acquire the lease."
            DEFVAL { '0000'h }
            ::= { dhcpServerLeaseEntry 5 }

        
        -- 1.3.6.1.4.1.5504.4.1.11.6.1.6
        dhcpLeaseFlags OBJECT-TYPE
            SYNTAX BITS
                {
                static(0),
                bootp(1),
                unused2(2),
                unused3(3),
                abandoned(4),
                zhoneCPE(5)
                }
            MAX-ACCESS read-create
            STATUS current
            DESCRIPTION
                "Lease flags currently defined as follows.
                    #define STATIC_LEASE             1
                    #define BOOTP_LEASE              2
                    #define ABANDONED_LEASE          16
                    #define ZHONE_CPE                32
                
                The default value for this object is 0 (no bits up).
                "
            ::= { dhcpServerLeaseEntry 6 }

        
        -- 1.3.6.1.4.1.5504.4.1.11.6.1.7
        dhcpLeaseClientId OBJECT-TYPE
            SYNTAX OCTET STRING (SIZE (0..255))
            MAX-ACCESS read-create
            STATUS current
            DESCRIPTION
                "Client identifier (if any) the client used to acquire
                its address. The default value for this object is an 
                empty octet string.
                "
            ::= { dhcpServerLeaseEntry 7 }

        
        -- 1.3.6.1.4.1.5504.4.1.11.6.1.8
        dhcpLeaseClientHostname OBJECT-TYPE
            SYNTAX SnmpAdminString (SIZE (0..127))
            MAX-ACCESS read-create
            STATUS current
            DESCRIPTION
                "Client hostname (if any) the client used to acquire
                its address. The default value for this object is an
                empty string.
                "
            ::= { dhcpServerLeaseEntry 8 }

        
        -- 1.3.6.1.4.1.5504.4.1.11.6.1.9
        dhcpLeaseHostname OBJECT-TYPE
            SYNTAX SnmpAdminString (SIZE (0..127))
            MAX-ACCESS read-create
            STATUS current
            DESCRIPTION
                "Client hostname (if any) the client used to acquire
                its address. The default value for this object is an
                empty string.
                "
            ::= { dhcpServerLeaseEntry 9 }

        
        -- 1.3.6.1.4.1.5504.4.1.11.6.1.10
        dhcpLeaseDDNSFwdName OBJECT-TYPE
            SYNTAX SnmpAdminString (SIZE (0..127))
            MAX-ACCESS read-create
            STATUS current
            DESCRIPTION
                "Dynamic DNS forward host name. Not currently used. 
                The default value for this object is an empty string."
            ::= { dhcpServerLeaseEntry 10 }

        
        -- 1.3.6.1.4.1.5504.4.1.11.6.1.11
        dhcpLeaseDDNSRevName OBJECT-TYPE
            SYNTAX SnmpAdminString (SIZE (0..127))
            MAX-ACCESS read-create
            STATUS current
            DESCRIPTION
                "Dynamic DNS reverse host name. Not currently used. 
                The default value for this object is an empty string."
            ::= { dhcpServerLeaseEntry 11 }

        
        -- 1.3.6.1.4.1.5504.4.1.11.6.1.12
        dhcpLeaseRowStatus OBJECT-TYPE
            SYNTAX ZhoneRowStatus
            MAX-ACCESS read-create
            STATUS current
            DESCRIPTION
                "Used to create and/or remove rows from this table."
            ::= { dhcpServerLeaseEntry 12 }

        
        -- 1.3.6.1.4.1.5504.4.1.11.7
        dhcpServerNextGroupIndex OBJECT-TYPE
            SYNTAX Integer32 (0..2147483647)
            MAX-ACCESS read-only
            STATUS current
            DESCRIPTION
                "This object will return the next valid value for dhcpGroupIndex.
                This is used to manage the indices for the dhcpServerGroupTable.
                Upon creating a row in the dhcpServerGroupTable, the user must
                first obtain the next index by performing a get on this object."
            ::= { dhcpServer 7 }

        
        -- 1.3.6.1.4.1.5504.4.1.11.8
        dhcpServerGroupTable OBJECT-TYPE
            SYNTAX SEQUENCE OF DhcpServerGroupEntry
            MAX-ACCESS not-accessible
            STATUS current
            DESCRIPTION
                "Provides access to the DHCP Server Group object
                configurations."
            ::= { dhcpServer 8 }

        
        -- 1.3.6.1.4.1.5504.4.1.11.8.1
        dhcpServerGroupEntry OBJECT-TYPE
            SYNTAX DhcpServerGroupEntry
            MAX-ACCESS not-accessible
            STATUS current
            DESCRIPTION
                "Required group object fields: 
                    dhcpGroupIndex, 
                    dhcpGroupName, 
                    dhcpGroupDomain,
                    Plus one of:
                        dhcpGroupVendorMatchString,
                        dhcpGroupClientMatchString
                
                The value for dhcpGroupIndex must be obtained by performing a GET
                on dhcpServerNextGroupIndex."
            INDEX { dhcpGroupIndex }
            ::= { dhcpServerGroupTable 1 }

        
        DhcpServerGroupEntry ::=
            SEQUENCE { 
                dhcpGroupIndex
                    Integer32,
                dhcpGroupName
                    ZhoneAdminString,
                dhcpGroupDomain
                    ZhoneRDIndex,
                dhcpGroupVendorMatchString
                    OCTET STRING,
                dhcpGroupVendorMatchOffset
                    Integer32,
                dhcpGroupVendorMatchLength
                    Integer32,
                dhcpGroupClientMatchString
                    OCTET STRING,
                dhcpGroupClientMatchOffset
                    Integer32,
                dhcpGroupClientMatchLength
                    Integer32,
                dhcpGroupRowStatus
                    ZhoneRowStatus
             }

        -- 1.3.6.1.4.1.5504.4.1.11.8.1.1
        dhcpGroupIndex OBJECT-TYPE
            SYNTAX Integer32 (0..2147483647)
            MAX-ACCESS not-accessible
            STATUS current
            DESCRIPTION
                "Table Index."
            ::= { dhcpServerGroupEntry 1 }

        
        -- 1.3.6.1.4.1.5504.4.1.11.8.1.2
        dhcpGroupName OBJECT-TYPE
            SYNTAX ZhoneAdminString
            MAX-ACCESS read-create
            STATUS current
            DESCRIPTION
                "Group object name.  The default value for 
                this object is the empty string."
            ::= { dhcpServerGroupEntry 2 }

        
        -- 1.3.6.1.4.1.5504.4.1.11.8.1.3
        dhcpGroupDomain OBJECT-TYPE
            SYNTAX ZhoneRDIndex
            MAX-ACCESS read-create
            STATUS current
            DESCRIPTION
                "Routing domain that this group object applies to."
            ::= { dhcpServerGroupEntry 3 }

        
        -- 1.3.6.1.4.1.5504.4.1.11.8.1.4
        dhcpGroupVendorMatchString OBJECT-TYPE
            SYNTAX OCTET STRING (SIZE (0..255))
            MAX-ACCESS read-create
            STATUS current
            DESCRIPTION
                "Vendor class identifier match string that is used to 
                determine which clients should be placed in this group.
                The default value for this object is an empty octet string.
                "
            ::= { dhcpServerGroupEntry 4 }

        
        -- 1.3.6.1.4.1.5504.4.1.11.8.1.5
        dhcpGroupVendorMatchOffset OBJECT-TYPE
            SYNTAX Integer32 (0..255)
            MAX-ACCESS read-create
            STATUS current
            DESCRIPTION
                "Offset into the client passed vendor class identifier
                string where the string match should start."
            DEFVAL { 0 }
            ::= { dhcpServerGroupEntry 5 }

        
        -- 1.3.6.1.4.1.5504.4.1.11.8.1.6
        dhcpGroupVendorMatchLength OBJECT-TYPE
            SYNTAX Integer32 (-1..255)
            MAX-ACCESS read-create
            STATUS current
            DESCRIPTION
                "Length of the vendor class identifier substring to match.
                A value of -1 indicates that the entire string starting
                at the match offset value should be matched."
            DEFVAL { -1 }
            ::= { dhcpServerGroupEntry 6 }

        
        -- 1.3.6.1.4.1.5504.4.1.11.8.1.7
        dhcpGroupClientMatchString OBJECT-TYPE
            SYNTAX OCTET STRING (SIZE (0..255))
            MAX-ACCESS read-create
            STATUS current
            DESCRIPTION
                "Client identifier match string that is used to determine
                which clients should be placed in this group.  The default 
                value for this object is an empty octet string."
            ::= { dhcpServerGroupEntry 7 }

        
        -- 1.3.6.1.4.1.5504.4.1.11.8.1.8
        dhcpGroupClientMatchOffset OBJECT-TYPE
            SYNTAX Integer32 (0..255)
            MAX-ACCESS read-create
            STATUS current
            DESCRIPTION
                "Offset into the client passed client identifier string
                where the string match should start."
            DEFVAL { 0 }
            ::= { dhcpServerGroupEntry 8 }

        
        -- 1.3.6.1.4.1.5504.4.1.11.8.1.9
        dhcpGroupClientMatchLength OBJECT-TYPE
            SYNTAX Integer32 (-1..255)
            MAX-ACCESS read-create
            STATUS current
            DESCRIPTION
                "Length of the client identifier substring to match.
                A value of -1 indicates that the entire string starting
                at the match offset value should be matched."
            DEFVAL { -1 }
            ::= { dhcpServerGroupEntry 9 }

        
        -- 1.3.6.1.4.1.5504.4.1.11.8.1.10
        dhcpGroupRowStatus OBJECT-TYPE
            SYNTAX ZhoneRowStatus
            MAX-ACCESS read-create
            STATUS current
            DESCRIPTION
                "Used to create and/or remove rows from this table."
            ::= { dhcpServerGroupEntry 10 }

        
        -- 1.3.6.1.4.1.5504.4.1.11.9
        dhcpServerGroupOptionTable OBJECT-TYPE
            SYNTAX SEQUENCE OF DhcpServerGroupOptionEntry
            MAX-ACCESS not-accessible
            STATUS current
            DESCRIPTION
                "DHCP Server Group Object Options"
            ::= { dhcpServer 9 }

        
        -- 1.3.6.1.4.1.5504.4.1.11.9.1
        dhcpServerGroupOptionEntry OBJECT-TYPE
            SYNTAX DhcpServerGroupOptionEntry
            MAX-ACCESS not-accessible
            STATUS current
            DESCRIPTION
                "All fields in this table are optional."
            AUGMENTS { dhcpServerGroupEntry }
            ::= { dhcpServerGroupOptionTable 1 }

        
        DhcpServerGroupOptionEntry ::=
            SEQUENCE { 
                dhcpGroupOptionDefaultLeaseTime
                    Integer32,
                dhcpGroupOptionMinLeaseTime
                    Integer32,
                dhcpGroupOptionMaxLeaseTime
                    Integer32,
                dhcpGroupOptionBootFile
                    ZhoneFileName,
                dhcpGroupOptionBootServer
                    IpAddress,
                dhcpGroupOptionDefaultRouter
                    IpAddress,
                dhcpGroupOptionPrimaryNameServer
                    IpAddress,
                dhcpGroupOptionSecondaryNameServer
                    IpAddress,
                dhcpGroupOptionDomainName
                    SnmpAdminString
             }

        -- 1.3.6.1.4.1.5504.4.1.11.9.1.1
        dhcpGroupOptionDefaultLeaseTime OBJECT-TYPE
            SYNTAX Integer32 (-1..2147483647)
            UNITS "seconds"
            MAX-ACCESS read-write
            STATUS current
            DESCRIPTION
                "The default time in seconds that will be assigned to a
                lease if the client requesting the lease does not ask 
                for a specific expiration time.  A value of -1 indicates
                that this field should be ignored.  Default value is -1
                seconds."
            ::= { dhcpServerGroupOptionEntry 1 }

        
        -- 1.3.6.1.4.1.5504.4.1.11.9.1.2
        dhcpGroupOptionMinLeaseTime OBJECT-TYPE
            SYNTAX Integer32 (-1..2147483647)
            UNITS "seconds"
            MAX-ACCESS read-write
            STATUS current
            DESCRIPTION
                "The minimum expiration time in seconds that will be 
                assigned to a lease regardless of the value specified
                by a client. A value of -1 indicates that this field
                should be ignored.  Default value is -1 seconds."
            ::= { dhcpServerGroupOptionEntry 2 }

        
        -- 1.3.6.1.4.1.5504.4.1.11.9.1.3
        dhcpGroupOptionMaxLeaseTime OBJECT-TYPE
            SYNTAX Integer32 (-1..2147483647)
            UNITS "seconds"
            MAX-ACCESS read-write
            STATUS current
            DESCRIPTION
                "The maximum time in seconds that will be assigned
                to a lease regardless of the value specified by a
                client.  A value of -1 indicates that this field
                should be ignored.  Default value is -1 seconds."
            ::= { dhcpServerGroupOptionEntry 3 }

        
        -- 1.3.6.1.4.1.5504.4.1.11.9.1.4
        dhcpGroupOptionBootFile OBJECT-TYPE
            SYNTAX ZhoneFileName
            MAX-ACCESS read-write
            STATUS current
            DESCRIPTION
                "Name of the initial boot file which is to be loaded
                by the client.  The filename should be a filename
                recognizable to whatever file transfer protocol the
                client can be expected to use to load the file.  The
                default value for this object is an empty string."
            ::= { dhcpServerGroupOptionEntry 4 }

        
        -- 1.3.6.1.4.1.5504.4.1.11.9.1.5
        dhcpGroupOptionBootServer OBJECT-TYPE
            SYNTAX IpAddress
            MAX-ACCESS read-write
            STATUS current
            DESCRIPTION
                "IP Address of the server from which the initial boot
                file (specified in the BootFile option) is to be loaded.
                If this IP address is specified as 0.0.0.0 then primary
                interface address of the DHCP Server is used.  Default
                value is 0.0.0.0"
            ::= { dhcpServerGroupOptionEntry 5 }

        
        -- 1.3.6.1.4.1.5504.4.1.11.9.1.6
        dhcpGroupOptionDefaultRouter OBJECT-TYPE
            SYNTAX IpAddress
            MAX-ACCESS read-write
            STATUS current
            DESCRIPTION
                "IP Address of the client's default gateway.
                Default value is 0.0.0.0"
            ::= { dhcpServerGroupOptionEntry 6 }

        
        -- 1.3.6.1.4.1.5504.4.1.11.9.1.7
        dhcpGroupOptionPrimaryNameServer OBJECT-TYPE
            SYNTAX IpAddress
            MAX-ACCESS read-write
            STATUS current
            DESCRIPTION
                "IP Address of the primary domain name server that
                the client should use for DNS resolution.  Default
                value is 0.0.0.0"
            ::= { dhcpServerGroupOptionEntry 7 }

        
        -- 1.3.6.1.4.1.5504.4.1.11.9.1.8
        dhcpGroupOptionSecondaryNameServer OBJECT-TYPE
            SYNTAX IpAddress
            MAX-ACCESS read-write
            STATUS current
            DESCRIPTION
                "IP Address of the secondary domain name server that
                the client should use for DNS resolution.  Default
                value is 0.0.0.0"
            ::= { dhcpServerGroupOptionEntry 8 }

        
        -- 1.3.6.1.4.1.5504.4.1.11.9.1.9
        dhcpGroupOptionDomainName OBJECT-TYPE
            SYNTAX SnmpAdminString (SIZE (0..127))
            MAX-ACCESS read-write
            STATUS current
            DESCRIPTION
                "The default domain name that the client should use
                when resolving hostnames via DNS. The default value
                for this object is an empty string."
            ::= { dhcpServerGroupOptionEntry 9 }

        
        -- 1.3.6.1.4.1.5504.4.1.11.10
        dhcpServerNextSubnetIndex OBJECT-TYPE
            SYNTAX Integer32 (0..2147483647)
            MAX-ACCESS read-only
            STATUS current
            DESCRIPTION
                "This object will return the next valid value for dhcpSubnetIndex.
                This is used to manage the indices for the dhcpServerSubnetTable.
                Upon creating a row in the dhcpServerSubnetTable, the user must
                first obtain the next index by performing a get on this object."
            ::= { dhcpServer 10 }

        
        -- 1.3.6.1.4.1.5504.4.1.11.11
        dhcpServerSubnetTable OBJECT-TYPE
            SYNTAX SEQUENCE OF DhcpServerSubnetEntry
            MAX-ACCESS not-accessible
            STATUS current
            DESCRIPTION
                "Provides access to the DHCP Server Subnet object
                configurations."
            ::= { dhcpServer 11 }

        
        -- 1.3.6.1.4.1.5504.4.1.11.11.1
        dhcpServerSubnetEntry OBJECT-TYPE
            SYNTAX DhcpServerSubnetEntry
            MAX-ACCESS not-accessible
            STATUS current
            DESCRIPTION
                "Required subnet object fields: 
                    dhcpSubnetIndex, 
                    dhcpSubnetNetwork, 
                    dhcpSubnetNetmask,
                    dhcpSubnetDomain,
                    dhcpSubnetRange1Start,
                    dhcpSubnetRange1End.
                
                The value for dhcpSubnetIndex must be obtained by performing a GET
                on dhcpServerNextSubnetIndex."
            INDEX { dhcpSubnetIndex }
            ::= { dhcpServerSubnetTable 1 }

        
        DhcpServerSubnetEntry ::=
            SEQUENCE { 
                dhcpSubnetIndex
                    Integer32,
                dhcpSubnetNetwork
                    IpAddress,
                dhcpSubnetNetmask
                    IpAddress,
                dhcpSubnetDomain
                    ZhoneRDIndex,
                dhcpSubnetRange1Start
                    IpAddress,
                dhcpSubnetRange1End
                    IpAddress,
                dhcpSubnetRange2Start
                    IpAddress,
                dhcpSubnetRange2End
                    IpAddress,
                dhcpSubnetRange3Start
                    IpAddress,
                dhcpSubnetRange3End
                    IpAddress,
                dhcpSubnetRange4Start
                    IpAddress,
                dhcpSubnetRange4End
                    IpAddress,
                dhcpSubnetRowStatus
                    ZhoneRowStatus,
                dhcpSubnetGroup2
                    Integer32,
                dhcpStickyAddr
                    TruthValue,
                dhcpSubnetExternalServer
                    IpAddress,
                dhcpSubnetExternalServerAlt
                    IpAddress
             }

        -- 1.3.6.1.4.1.5504.4.1.11.11.1.1
        dhcpSubnetIndex OBJECT-TYPE
            SYNTAX Integer32 (0..2147483647)
            MAX-ACCESS not-accessible
            STATUS current
            DESCRIPTION
                "Table Index."
            ::= { dhcpServerSubnetEntry 1 }

        
        -- 1.3.6.1.4.1.5504.4.1.11.11.1.2
        dhcpSubnetNetwork OBJECT-TYPE
            SYNTAX IpAddress
            MAX-ACCESS read-create
            STATUS current
            DESCRIPTION
                "Network address of this subnet object."
            ::= { dhcpServerSubnetEntry 2 }

        
        -- 1.3.6.1.4.1.5504.4.1.11.11.1.3
        dhcpSubnetNetmask OBJECT-TYPE
            SYNTAX IpAddress
            MAX-ACCESS read-create
            STATUS current
            DESCRIPTION
                "Network mask of this subnet object."
            ::= { dhcpServerSubnetEntry 3 }

        
        -- 1.3.6.1.4.1.5504.4.1.11.11.1.4
        dhcpSubnetDomain OBJECT-TYPE
            SYNTAX ZhoneRDIndex
            MAX-ACCESS read-create
            STATUS current
            DESCRIPTION
                "Routing domain that this subnet object applies to."
            ::= { dhcpServerSubnetEntry 4 }

        
        -- 1.3.6.1.4.1.5504.4.1.11.11.1.5
        dhcpSubnetRange1Start OBJECT-TYPE
            SYNTAX IpAddress
            MAX-ACCESS read-create
            STATUS current
            DESCRIPTION
                "Starting IP address of the first address pool in this
                subnet.  If either the start or end range has a value
                of 0 then the entire address pool is ignored."
            ::= { dhcpServerSubnetEntry 5 }

        
        -- 1.3.6.1.4.1.5504.4.1.11.11.1.6
        dhcpSubnetRange1End OBJECT-TYPE
            SYNTAX IpAddress
            MAX-ACCESS read-create
            STATUS current
            DESCRIPTION
                "Last IP address of the first address pool in this
                subnet.  If either the start or end range has a value
                of 0 then the entire address pool is ignored."
            ::= { dhcpServerSubnetEntry 6 }

        
        -- 1.3.6.1.4.1.5504.4.1.11.11.1.7
        dhcpSubnetRange2Start OBJECT-TYPE
            SYNTAX IpAddress
            MAX-ACCESS read-create
            STATUS current
            DESCRIPTION
                "Starting IP address of the second address pool in this
                subnet.  If either the start or end range has a value
                of 0 then the entire address pool is ignored."
            DEFVAL { '00000000'h }
            ::= { dhcpServerSubnetEntry 7 }

        
        -- 1.3.6.1.4.1.5504.4.1.11.11.1.8
        dhcpSubnetRange2End OBJECT-TYPE
            SYNTAX IpAddress
            MAX-ACCESS read-create
            STATUS current
            DESCRIPTION
                "Last IP address of the second address pool in this
                subnet.  If either the start or end range has a value
                of 0 then the entire address pool is ignored."
            DEFVAL { '00000000'h }
            ::= { dhcpServerSubnetEntry 8 }

        
        -- 1.3.6.1.4.1.5504.4.1.11.11.1.9
        dhcpSubnetRange3Start OBJECT-TYPE
            SYNTAX IpAddress
            MAX-ACCESS read-create
            STATUS current
            DESCRIPTION
                "Starting IP address of the third address pool in this
                subnet.  If either the start or end range has a value
                of 0 then the entire address pool is ignored."
            DEFVAL { '00000000'h }
            ::= { dhcpServerSubnetEntry 9 }

        
        -- 1.3.6.1.4.1.5504.4.1.11.11.1.10
        dhcpSubnetRange3End OBJECT-TYPE
            SYNTAX IpAddress
            MAX-ACCESS read-create
            STATUS current
            DESCRIPTION
                "Last IP address of the third address pool in this
                subnet.  If either the start or end range has a value
                of 0 then the entire address pool is ignored."
            DEFVAL { '00000000'h }
            ::= { dhcpServerSubnetEntry 10 }

        
        -- 1.3.6.1.4.1.5504.4.1.11.11.1.11
        dhcpSubnetRange4Start OBJECT-TYPE
            SYNTAX IpAddress
            MAX-ACCESS read-create
            STATUS current
            DESCRIPTION
                "Starting IP address of the fourth address pool in this
                subnet.  If either the start or end range has a value
                of 0 then the entire address pool is ignored."
            DEFVAL { '00000000'h }
            ::= { dhcpServerSubnetEntry 11 }

        
        -- 1.3.6.1.4.1.5504.4.1.11.11.1.12
        dhcpSubnetRange4End OBJECT-TYPE
            SYNTAX IpAddress
            MAX-ACCESS read-create
            STATUS current
            DESCRIPTION
                "Last IP address of the fourth address pool in this
                subnet.  If either the start or end range has a value
                of 0 then the entire address pool is ignored."
            DEFVAL { '00000000'h }
            ::= { dhcpServerSubnetEntry 12 }

        
        -- 1.3.6.1.4.1.5504.4.1.11.11.1.13
        dhcpSubnetRowStatus OBJECT-TYPE
            SYNTAX ZhoneRowStatus
            MAX-ACCESS read-create
            STATUS current
            DESCRIPTION
                "Used to create and/or remove rows from this table."
            ::= { dhcpServerSubnetEntry 13 }

        
        -- 1.3.6.1.4.1.5504.4.1.11.11.1.14
        dhcpSubnetGroup2 OBJECT-TYPE
            SYNTAX Integer32
            MAX-ACCESS read-write
            STATUS current
            DESCRIPTION
                "A number which indicates which DHCP subnet group this pool is a
                member of. A value of 0 ( default) indicates not a member of 
                any group."
            DEFVAL { '0'b }
            ::= { dhcpServerSubnetEntry 14 }

        
        -- 1.3.6.1.4.1.5504.4.1.11.11.1.15
        dhcpStickyAddr OBJECT-TYPE
            SYNTAX TruthValue
            MAX-ACCESS read-write
            STATUS current
            DESCRIPTION
                "If true we will attempt to hand out the same IP address to the same
                host, when possible based on HW address. Default value is TRUE
                for backwards compatability."
            DEFVAL { 1 }
            ::= { dhcpServerSubnetEntry 15 }

        
        -- 1.3.6.1.4.1.5504.4.1.11.11.1.16
        dhcpSubnetExternalServer OBJECT-TYPE
            SYNTAX IpAddress
            MAX-ACCESS read-create
            STATUS current
            DESCRIPTION
                "Non-null IP address value indicates use of external 
                DHCP server instead of internal for this subnet."
            DEFVAL { '00000000'h }
            ::= { dhcpServerSubnetEntry 16 }

        
        -- 1.3.6.1.4.1.5504.4.1.11.11.1.17
        dhcpSubnetExternalServerAlt OBJECT-TYPE
            SYNTAX IpAddress
            MAX-ACCESS read-create
            STATUS current
            DESCRIPTION
                "Non-null IP address value indicates use of alternate external 
                DHCP server."
            DEFVAL { '00000000'h }
            ::= { dhcpServerSubnetEntry 17 }

        
        -- 1.3.6.1.4.1.5504.4.1.11.12
        dhcpServerSubnetOptionTable OBJECT-TYPE
            SYNTAX SEQUENCE OF DhcpServerSubnetOptionEntry
            MAX-ACCESS not-accessible
            STATUS current
            DESCRIPTION
                "DHCP Server Subnet Object Options"
            ::= { dhcpServer 12 }

        
        -- 1.3.6.1.4.1.5504.4.1.11.12.1
        dhcpServerSubnetOptionEntry OBJECT-TYPE
            SYNTAX DhcpServerSubnetOptionEntry
            MAX-ACCESS not-accessible
            STATUS current
            DESCRIPTION
                "All fields in this table are optional."
            AUGMENTS { dhcpServerSubnetEntry }
            ::= { dhcpServerSubnetOptionTable 1 }

        
        DhcpServerSubnetOptionEntry ::=
            SEQUENCE { 
                dhcpSubnetOptionDefaultLeaseTime
                    Integer32,
                dhcpSubnetOptionMinLeaseTime
                    Integer32,
                dhcpSubnetOptionMaxLeaseTime
                    Integer32,
                dhcpSubnetOptionBootFile
                    ZhoneFileName,
                dhcpSubnetOptionBootServer
                    IpAddress,
                dhcpSubnetOptionDefaultRouter
                    IpAddress,
                dhcpSubnetOptionPrimaryNameServer
                    IpAddress,
                dhcpSubnetOptionSecondaryNameServer
                    IpAddress,
                dhcpSubnetOptionDomainName
                    SnmpAdminString
             }

        -- 1.3.6.1.4.1.5504.4.1.11.12.1.1
        dhcpSubnetOptionDefaultLeaseTime OBJECT-TYPE
            SYNTAX Integer32 (-1..2147483647)
            UNITS "seconds"
            MAX-ACCESS read-write
            STATUS current
            DESCRIPTION
                "The default time in seconds that will be assigned to a
                lease if the client requesting the lease does not ask 
                for a specific expiration time.  A value of -1 indicates
                that this field should be ignored.  Default value is -1
                seconds."
            ::= { dhcpServerSubnetOptionEntry 1 }

        
        -- 1.3.6.1.4.1.5504.4.1.11.12.1.2
        dhcpSubnetOptionMinLeaseTime OBJECT-TYPE
            SYNTAX Integer32 (-1..2147483647)
            UNITS "seconds"
            MAX-ACCESS read-write
            STATUS current
            DESCRIPTION
                "The minimum expiration time in seconds that will be 
                assigned to a lease regardless of the value specified
                by a client.  A value of -1 indicates that this field
                should be ignored.  Default value is -1 seconds."
            ::= { dhcpServerSubnetOptionEntry 2 }

        
        -- 1.3.6.1.4.1.5504.4.1.11.12.1.3
        dhcpSubnetOptionMaxLeaseTime OBJECT-TYPE
            SYNTAX Integer32 (-1..2147483647)
            UNITS "seconds"
            MAX-ACCESS read-write
            STATUS current
            DESCRIPTION
                "The maximum time in seconds that will be assigned
                to a lease regardless of the value specified by a
                client.  A value of -1 indicates that this field
                should be ignored.  Default value is -1 seconds."
            ::= { dhcpServerSubnetOptionEntry 3 }

        
        -- 1.3.6.1.4.1.5504.4.1.11.12.1.4
        dhcpSubnetOptionBootFile OBJECT-TYPE
            SYNTAX ZhoneFileName
            MAX-ACCESS read-write
            STATUS current
            DESCRIPTION
                "Name of the initial boot file which is to be loaded
                by the client.  The filename should be a filename
                recognizable to whatever file transfer protocol the
                client can be expected to use to load the file. The
                default value for this object is an empty string."
            ::= { dhcpServerSubnetOptionEntry 4 }

        
        -- 1.3.6.1.4.1.5504.4.1.11.12.1.5
        dhcpSubnetOptionBootServer OBJECT-TYPE
            SYNTAX IpAddress
            MAX-ACCESS read-write
            STATUS current
            DESCRIPTION
                "IP Address of the server from which the initial boot
                file (specified in the BootFile option) is to be loaded.
                If this IP address is specified as 0.0.0.0 then the 
                DHCP Server's address is used.  Default value is 0.0.0.0"
            ::= { dhcpServerSubnetOptionEntry 5 }

        
        -- 1.3.6.1.4.1.5504.4.1.11.12.1.6
        dhcpSubnetOptionDefaultRouter OBJECT-TYPE
            SYNTAX IpAddress
            MAX-ACCESS read-write
            STATUS current
            DESCRIPTION
                "IP Address of the client's default gateway.
                Default value is 0.0.0.0"
            ::= { dhcpServerSubnetOptionEntry 6 }

        
        -- 1.3.6.1.4.1.5504.4.1.11.12.1.7
        dhcpSubnetOptionPrimaryNameServer OBJECT-TYPE
            SYNTAX IpAddress
            MAX-ACCESS read-write
            STATUS current
            DESCRIPTION
                "IP Address of the primary domain name server that
                the client should use for DNS resolution.  Default
                value is 0.0.0.0"
            ::= { dhcpServerSubnetOptionEntry 7 }

        
        -- 1.3.6.1.4.1.5504.4.1.11.12.1.8
        dhcpSubnetOptionSecondaryNameServer OBJECT-TYPE
            SYNTAX IpAddress
            MAX-ACCESS read-write
            STATUS current
            DESCRIPTION
                "IP Address of the secondary domain name server that
                the client should use for DNS resolution.  Default
                value is 0.0.0.0"
            ::= { dhcpServerSubnetOptionEntry 8 }

        
        -- 1.3.6.1.4.1.5504.4.1.11.12.1.9
        dhcpSubnetOptionDomainName OBJECT-TYPE
            SYNTAX SnmpAdminString (SIZE (0..127))
            MAX-ACCESS read-write
            STATUS current
            DESCRIPTION
                "The default domain name that the client should use
                when resolving hostnames via DNS. The default value
                for this object is an empty string."
            ::= { dhcpServerSubnetOptionEntry 9 }

        
        -- 1.3.6.1.4.1.5504.4.1.11.13
        dhcpServerNextHostIndex OBJECT-TYPE
            SYNTAX Integer32 (0..2147483647)
            MAX-ACCESS read-only
            STATUS current
            DESCRIPTION
                "This object will return the next valid value for dhcpHostIndex.
                This is used to manage the indices for the dhcpServerHostTable.
                Upon creating a row in the dhcpServerHostTable, the user must
                first obtain the next index by performing a get on this object."
            ::= { dhcpServer 13 }

        
        -- 1.3.6.1.4.1.5504.4.1.11.14
        dhcpServerHostTable OBJECT-TYPE
            SYNTAX SEQUENCE OF DhcpServerHostEntry
            MAX-ACCESS not-accessible
            STATUS current
            DESCRIPTION
                "Provides access to the DHCP Server Host object
                configurations."
            ::= { dhcpServer 14 }

        
        -- 1.3.6.1.4.1.5504.4.1.11.14.1
        dhcpServerHostEntry OBJECT-TYPE
            SYNTAX DhcpServerHostEntry
            MAX-ACCESS not-accessible
            STATUS current
            DESCRIPTION
                "Required host object fields: 
                    dhcpHostIndex, 
                    dhcpHostDomain,
                    Plus one of:
                        dhcpHostHardwareAddress,
                        dhcpHostClientId
                
                The value for dhcpHostIndex must be obtained by performing a GET
                on dhcpServerNextHostIndex."
            INDEX { dhcpHostIndex }
            ::= { dhcpServerHostTable 1 }

        
        DhcpServerHostEntry ::=
            SEQUENCE { 
                dhcpHostIndex
                    Integer32,
                dhcpHostHostname
                    ZhoneAdminString,
                dhcpHostDomain
                    ZhoneRDIndex,
                dhcpHostHardwareAddress
                    PhysAddress,
                dhcpHostClientId
                    OCTET STRING,
                dhcpHostIpAddress1
                    IpAddress,
                dhcpHostIpAddress2
                    IpAddress,
                dhcpHostIpAddress3
                    IpAddress,
                dhcpHostIpAddress4
                    IpAddress,
                dhcpHostRowStatus
                    ZhoneRowStatus
             }

        -- 1.3.6.1.4.1.5504.4.1.11.14.1.1
        dhcpHostIndex OBJECT-TYPE
            SYNTAX Integer32 (0..2147483647)
            MAX-ACCESS not-accessible
            STATUS current
            DESCRIPTION
                "Table Index."
            ::= { dhcpServerHostEntry 1 }

        
        -- 1.3.6.1.4.1.5504.4.1.11.14.1.2
        dhcpHostHostname OBJECT-TYPE
            SYNTAX ZhoneAdminString
            MAX-ACCESS read-create
            STATUS current
            DESCRIPTION
                "Hostname for this client.  This may or may not be fully
                qualified with the local domain name but it is preferable
                to use the dhcpHostOptionDomainName option to specify 
                the domain name.  The default value for this field is an
                empty string.
                "
            ::= { dhcpServerHostEntry 2 }

        
        -- 1.3.6.1.4.1.5504.4.1.11.14.1.3
        dhcpHostDomain OBJECT-TYPE
            SYNTAX ZhoneRDIndex
            MAX-ACCESS read-create
            STATUS current
            DESCRIPTION
                "Routing domain that this host object applies to."
            ::= { dhcpServerHostEntry 3 }

        
        -- 1.3.6.1.4.1.5504.4.1.11.14.1.4
        dhcpHostHardwareAddress OBJECT-TYPE
            SYNTAX PhysAddress (SIZE (0..16))
            MAX-ACCESS read-create
            STATUS current
            DESCRIPTION
                "Hardware address of the client that matches this host
                object. If the dhcpHostClientId field is specified
                then this field is ignored.  However, at least one of
                these fields must be configured per host object.
                "
            DEFVAL { '0000'h }
            ::= { dhcpServerHostEntry 4 }

        
        -- 1.3.6.1.4.1.5504.4.1.11.14.1.5
        dhcpHostClientId OBJECT-TYPE
            SYNTAX OCTET STRING (SIZE (0..127))
            MAX-ACCESS read-create
            STATUS current
            DESCRIPTION
                "DHCP client identifier of the client that matches this
                host object. If this field is specified then the 
                dhcpHostHardwareAddress value is not used. However, at
                least one of these fields must be configured per host
                object. The default value for this object is an empty 
                octet string."
            ::= { dhcpServerHostEntry 5 }

        
        -- 1.3.6.1.4.1.5504.4.1.11.14.1.6
        dhcpHostIpAddress1 OBJECT-TYPE
            SYNTAX IpAddress
            MAX-ACCESS read-create
            STATUS current
            DESCRIPTION
                "Fixed IP address that should be assigned to this client."
            DEFVAL { '00000000'h }
            ::= { dhcpServerHostEntry 6 }

        
        -- 1.3.6.1.4.1.5504.4.1.11.14.1.7
        dhcpHostIpAddress2 OBJECT-TYPE
            SYNTAX IpAddress
            MAX-ACCESS read-create
            STATUS current
            DESCRIPTION
                "Fixed IP address that should be assigned to this client."
            DEFVAL { '00000000'h }
            ::= { dhcpServerHostEntry 7 }

        
        -- 1.3.6.1.4.1.5504.4.1.11.14.1.8
        dhcpHostIpAddress3 OBJECT-TYPE
            SYNTAX IpAddress
            MAX-ACCESS read-create
            STATUS current
            DESCRIPTION
                "Fixed IP address that should be assigned to this client."
            DEFVAL { '00000000'h }
            ::= { dhcpServerHostEntry 8 }

        
        -- 1.3.6.1.4.1.5504.4.1.11.14.1.9
        dhcpHostIpAddress4 OBJECT-TYPE
            SYNTAX IpAddress
            MAX-ACCESS read-create
            STATUS current
            DESCRIPTION
                "Fixed IP address that should be assigned to this client."
            DEFVAL { '00000000'h }
            ::= { dhcpServerHostEntry 9 }

        
        -- 1.3.6.1.4.1.5504.4.1.11.14.1.10
        dhcpHostRowStatus OBJECT-TYPE
            SYNTAX ZhoneRowStatus
            MAX-ACCESS read-create
            STATUS current
            DESCRIPTION
                "Used to create and/or remove rows from this table."
            ::= { dhcpServerHostEntry 10 }

        
        -- 1.3.6.1.4.1.5504.4.1.11.15
        dhcpServerHostOptionTable OBJECT-TYPE
            SYNTAX SEQUENCE OF DhcpServerHostOptionEntry
            MAX-ACCESS not-accessible
            STATUS current
            DESCRIPTION
                "DHCP Server Host Object Options"
            ::= { dhcpServer 15 }

        
        -- 1.3.6.1.4.1.5504.4.1.11.15.1
        dhcpServerHostOptionEntry OBJECT-TYPE
            SYNTAX DhcpServerHostOptionEntry
            MAX-ACCESS not-accessible
            STATUS current
            DESCRIPTION
                "All fields in this table are optional."
            AUGMENTS { dhcpServerHostEntry }
            ::= { dhcpServerHostOptionTable 1 }

        
        DhcpServerHostOptionEntry ::=
            SEQUENCE { 
                dhcpHostOptionDefaultLeaseTime
                    Integer32,
                dhcpHostOptionMinLeaseTime
                    Integer32,
                dhcpHostOptionMaxLeaseTime
                    Integer32,
                dhcpHostOptionBootFile
                    ZhoneFileName,
                dhcpHostOptionBootServer
                    IpAddress,
                dhcpHostOptionDefaultRouter
                    IpAddress,
                dhcpHostOptionPrimaryNameServer
                    IpAddress,
                dhcpHostOptionSecondaryNameServer
                    IpAddress,
                dhcpHostOptionDomainName
                    SnmpAdminString
             }

        -- 1.3.6.1.4.1.5504.4.1.11.15.1.1
        dhcpHostOptionDefaultLeaseTime OBJECT-TYPE
            SYNTAX Integer32 (-1..2147483647)
            UNITS "seconds"
            MAX-ACCESS read-write
            STATUS current
            DESCRIPTION
                "The default time in seconds that will be assigned to a
                lease if the client requesting the lease does not ask 
                for a specific expiration time.  A value of -1 indicates
                that this field should be ignored.  Default value is 
                -1 seconds."
            ::= { dhcpServerHostOptionEntry 1 }

        
        -- 1.3.6.1.4.1.5504.4.1.11.15.1.2
        dhcpHostOptionMinLeaseTime OBJECT-TYPE
            SYNTAX Integer32 (-1..2147483647)
            UNITS "seconds"
            MAX-ACCESS read-write
            STATUS current
            DESCRIPTION
                "The minimum expiration time in seconds that will be 
                assigned to a lease regardless of the value specified
                by a client.  A value of -1 indicates that this field 
                should be ignored.  Default value is -1 seconds."
            ::= { dhcpServerHostOptionEntry 2 }

        
        -- 1.3.6.1.4.1.5504.4.1.11.15.1.3
        dhcpHostOptionMaxLeaseTime OBJECT-TYPE
            SYNTAX Integer32 (-1..2147483647)
            UNITS "seconds"
            MAX-ACCESS read-write
            STATUS current
            DESCRIPTION
                "The maximum time in seconds that will be assigned
                to a lease regardless of the value specified by a
                client.  A value of -1 indicates that this field
                should be ignored.  Default value is -1 seconds."
            ::= { dhcpServerHostOptionEntry 3 }

        
        -- 1.3.6.1.4.1.5504.4.1.11.15.1.4
        dhcpHostOptionBootFile OBJECT-TYPE
            SYNTAX ZhoneFileName
            MAX-ACCESS read-write
            STATUS current
            DESCRIPTION
                "Name of the initial boot file which is to be loaded
                by the client.  The filename should be a filename
                recognizable to whatever file transfer protocol the
                client can be expected to use to load the file. The 
                default value for this object is an empty string."
            ::= { dhcpServerHostOptionEntry 4 }

        
        -- 1.3.6.1.4.1.5504.4.1.11.15.1.5
        dhcpHostOptionBootServer OBJECT-TYPE
            SYNTAX IpAddress
            MAX-ACCESS read-write
            STATUS current
            DESCRIPTION
                "IP Address of the server from which the initial boot
                file (specified in the BootFile option) is to be loaded.
                If this IP address is specified as 0.0.0.0 then the 
                DHCP Server's address is used.  Default value is 0.0.0.0"
            ::= { dhcpServerHostOptionEntry 5 }

        
        -- 1.3.6.1.4.1.5504.4.1.11.15.1.6
        dhcpHostOptionDefaultRouter OBJECT-TYPE
            SYNTAX IpAddress
            MAX-ACCESS read-write
            STATUS current
            DESCRIPTION
                "IP Address of the client's default gateway.
                Default value is 0.0.0.0"
            ::= { dhcpServerHostOptionEntry 6 }

        
        -- 1.3.6.1.4.1.5504.4.1.11.15.1.7
        dhcpHostOptionPrimaryNameServer OBJECT-TYPE
            SYNTAX IpAddress
            MAX-ACCESS read-write
            STATUS current
            DESCRIPTION
                "IP Address of the primary domain name server that
                the client should use for DNS resolution.  Default
                value is 0.0.0.0"
            ::= { dhcpServerHostOptionEntry 7 }

        
        -- 1.3.6.1.4.1.5504.4.1.11.15.1.8
        dhcpHostOptionSecondaryNameServer OBJECT-TYPE
            SYNTAX IpAddress
            MAX-ACCESS read-write
            STATUS current
            DESCRIPTION
                "IP Address of the secondary domain name server that
                the client should use for DNS resolution.  Default
                value is 0.0.0.0"
            ::= { dhcpServerHostOptionEntry 8 }

        
        -- 1.3.6.1.4.1.5504.4.1.11.15.1.9
        dhcpHostOptionDomainName OBJECT-TYPE
            SYNTAX SnmpAdminString (SIZE (0..127))
            MAX-ACCESS read-write
            STATUS current
            DESCRIPTION
                "The default domain name that the client should use
                when resolving hostnames via DNS. The default value
                for this object is an empty string."
            ::= { dhcpServerHostOptionEntry 9 }

        
        -- 1.3.6.1.4.1.5504.4.1.11.16
        dhcpServerStatistics OBJECT-IDENTITY
            STATUS current
            DESCRIPTION 
                "DHCP Server MIB statistic objects are all defined in
                this branch."
            REFERENCE 
                "Based on IETF draft DHCP Server MIB.  
                See: http://www.ietf.org/internet-drafts/draft-ietf-dhc-server-mib-04.txt"
            ::= { dhcpServer 16 }

        
        -- 1.3.6.1.4.1.5504.4.1.11.16.1
        serverSystem OBJECT-IDENTITY
            STATUS current
            DESCRIPTION 
                "Group of objects that are related to the overall system."
            ::= { dhcpServerStatistics 1 }

        
        -- 1.3.6.1.4.1.5504.4.1.11.16.1.1
        serverSystemDescr OBJECT-TYPE
            SYNTAX ZhoneAdminString
            MAX-ACCESS read-only
            STATUS current
            DESCRIPTION
                "A textual description of the server.  This value should
                include the full name and version identification of the
                server.
                
                This string MUST contain only printable NVT ASCII
                characters."
            ::= { serverSystem 1 }

        
        -- 1.3.6.1.4.1.5504.4.1.11.16.1.2
        serverSystemObjectID OBJECT-TYPE
            SYNTAX OBJECT IDENTIFIER
            MAX-ACCESS read-only
            STATUS current
            DESCRIPTION
                "The vendor's authoritative identification of the network
                management subsystem contained in this entity.  This value is
                allocated within the SMI enterprise subtree (1.3.6.1.4.1) and
                provides an easy and unambiguous means for determining 'what
                kind of server' is being managed.  For example, if vendor
                'VeryBigServers, Inc.' is assigned the subtree
                1.3.6.1.4.1.4242, it may assign the identifier
                1.3.6.1.4.1.4242.1.1 to its `Hercules DHCP Server'."
            ::= { serverSystem 2 }

        
        -- 1.3.6.1.4.1.5504.4.1.11.16.1.3
        serverUptime OBJECT-TYPE
            SYNTAX TimeTicks
            MAX-ACCESS read-only
            STATUS current
            DESCRIPTION
                "The value of sysUpTime when the server started handling
                requests."
            ::= { serverSystem 3 }

        
        -- 1.3.6.1.4.1.5504.4.1.11.16.1.4
        serverActiveShelf OBJECT-TYPE
            SYNTAX ZhoneShelfValue
            MAX-ACCESS read-only
            STATUS current
            DESCRIPTION
                "The shelf ID of the active DHCP server."
            ::= { serverSystem 4 }

        
        -- 1.3.6.1.4.1.5504.4.1.11.16.1.5
        serverActiveSlot OBJECT-TYPE
            SYNTAX ZhoneSlotValue
            MAX-ACCESS read-only
            STATUS current
            DESCRIPTION
                "The slot ID of the active DHCP server."
            ::= { serverSystem 5 }

        
        -- 1.3.6.1.4.1.5504.4.1.11.16.1.6
        serverStandbyShelf OBJECT-TYPE
            SYNTAX ZhoneShelfValue
            MAX-ACCESS read-only
            STATUS current
            DESCRIPTION
                "The shelf ID of the standby DHCP server."
            ::= { serverSystem 6 }

        
        -- 1.3.6.1.4.1.5504.4.1.11.16.1.7
        serverStandbySlot OBJECT-TYPE
            SYNTAX ZhoneSlotValue
            MAX-ACCESS read-only
            STATUS current
            DESCRIPTION
                "The slot ID of the standby DHCP server."
            ::= { serverSystem 7 }

        
        -- 1.3.6.1.4.1.5504.4.1.11.16.2
        bootpCountersTable OBJECT-TYPE
            SYNTAX SEQUENCE OF BootpCountersEntry
            MAX-ACCESS not-accessible
            STATUS current
            DESCRIPTION
                "Table indexed on routing domain of objects that count
                various BOOTP events."
            REFERENCE
                "Based on IETF draft DHCP Server MIB.  
                See: http://www.ietf.org/internet-drafts/draft-ietf-dhc-server-mib-04.txt"
            ::= { dhcpServerStatistics 2 }

        
        -- 1.3.6.1.4.1.5504.4.1.11.16.2.1
        bootpCountersEntry OBJECT-TYPE
            SYNTAX BootpCountersEntry
            MAX-ACCESS not-accessible
            STATUS current
            DESCRIPTION
                "Group of objects that count various BOOTP events on
                a per routing domain basis."
            AUGMENTS { rdEntry }
            ::= { bootpCountersTable 1 }

        
        BootpCountersEntry ::=
            SEQUENCE { 
                bootpCountRequests
                    Counter32,
                bootpCountInvalids
                    Counter32,
                bootpCountReplies
                    Counter32,
                bootpCountDroppedUnknownClients
                    Counter32,
                bootpCountDroppedNotServingSubnet
                    Counter32
             }

        -- 1.3.6.1.4.1.5504.4.1.11.16.2.1.1
        bootpCountRequests OBJECT-TYPE
            SYNTAX Counter32
            MAX-ACCESS read-only
            STATUS current
            DESCRIPTION
                "The number of packets received that contain a Message Type of
                1 (BOOTREQUEST) in the first octet and do not contain option
                number 53 (DHCP Message Type) in the options."
            ::= { bootpCountersEntry 1 }

        
        -- 1.3.6.1.4.1.5504.4.1.11.16.2.1.2
        bootpCountInvalids OBJECT-TYPE
            SYNTAX Counter32
            MAX-ACCESS read-only
            STATUS current
            DESCRIPTION
                "The number of packets received that do not contain a Message
                Type of 1 (BOOTREQUEST) in the first octet or are not valid
                BOOTP packets (e.g., too short, invalid field in packet
                header)."
            ::= { bootpCountersEntry 2 }

        
        -- 1.3.6.1.4.1.5504.4.1.11.16.2.1.3
        bootpCountReplies OBJECT-TYPE
            SYNTAX Counter32
            MAX-ACCESS read-only
            STATUS current
            DESCRIPTION
                "The number of packets sent that contain a Message Type of 1
                (BOOTREQUEST) in the first octet and do not contain option
                number 53 (DHCP Message Type) in the options."
            ::= { bootpCountersEntry 3 }

        
        -- 1.3.6.1.4.1.5504.4.1.11.16.2.1.4
        bootpCountDroppedUnknownClients OBJECT-TYPE
            SYNTAX Counter32
            MAX-ACCESS read-only
            STATUS current
            DESCRIPTION
                "The number of BOOTP packets dropped due to the server not
                recognizing or not providing service to the hardware address
                received in the incoming packet."
            ::= { bootpCountersEntry 4 }

        
        -- 1.3.6.1.4.1.5504.4.1.11.16.2.1.5
        bootpCountDroppedNotServingSubnet OBJECT-TYPE
            SYNTAX Counter32
            MAX-ACCESS read-only
            STATUS current
            DESCRIPTION
                "The number of BOOTP packets dropped due to the server not
                being configured or not otherwise able to serve addresses on
                the subnet from which this message was received."
            ::= { bootpCountersEntry 5 }

        
        -- 1.3.6.1.4.1.5504.4.1.11.16.3
        dhcpCountersTable OBJECT-TYPE
            SYNTAX SEQUENCE OF DhcpCountersEntry
            MAX-ACCESS not-accessible
            STATUS current
            DESCRIPTION
                "Table indexed on routing domain of objects that count
                various DHCP events."
            REFERENCE
                "Based on IETF draft DHCP Server MIB.  
                See: http://www.ietf.org/internet-drafts/draft-ietf-dhc-server-mib-04.txt"
            ::= { dhcpServerStatistics 3 }

        
        -- 1.3.6.1.4.1.5504.4.1.11.16.3.1
        dhcpCountersEntry OBJECT-TYPE
            SYNTAX DhcpCountersEntry
            MAX-ACCESS not-accessible
            STATUS current
            DESCRIPTION
                "Group of objects that count various DHCP events on a
                per routing domain basis."
            AUGMENTS { rdEntry }
            ::= { dhcpCountersTable 1 }

        
        DhcpCountersEntry ::=
            SEQUENCE { 
                dhcpCountDiscovers
                    Counter32,
                dhcpCountRequests
                    Counter32,
                dhcpCountReleases
                    Counter32,
                dhcpCountDeclines
                    Counter32,
                dhcpCountInforms
                    Counter32,
                dhcpCountInvalids
                    Counter32,
                dhcpCountOffers
                    Counter32,
                dhcpCountAcks
                    Counter32,
                dhcpCountNacks
                    Counter32,
                dhcpCountDroppedUnknownClient
                    Counter32,
                dhcpCountDroppedNotServingSubnet
                    Counter32
             }

        -- 1.3.6.1.4.1.5504.4.1.11.16.3.1.1
        dhcpCountDiscovers OBJECT-TYPE
            SYNTAX Counter32
            MAX-ACCESS read-only
            STATUS current
            DESCRIPTION
                "The number of DHCPDISCOVER (option 53 with value 1) packets
                received."
            ::= { dhcpCountersEntry 1 }

        
        -- 1.3.6.1.4.1.5504.4.1.11.16.3.1.2
        dhcpCountRequests OBJECT-TYPE
            SYNTAX Counter32
            MAX-ACCESS read-only
            STATUS current
            DESCRIPTION
                "The number of DHCPREQUEST (option 53 with value 3) packets
                received."
            ::= { dhcpCountersEntry 2 }

        
        -- 1.3.6.1.4.1.5504.4.1.11.16.3.1.3
        dhcpCountReleases OBJECT-TYPE
            SYNTAX Counter32
            MAX-ACCESS read-only
            STATUS current
            DESCRIPTION
                "The number of DHCPRELEASE (option 53 with value 7) packets
                received."
            ::= { dhcpCountersEntry 3 }

        
        -- 1.3.6.1.4.1.5504.4.1.11.16.3.1.4
        dhcpCountDeclines OBJECT-TYPE
            SYNTAX Counter32
            MAX-ACCESS read-only
            STATUS current
            DESCRIPTION
                "The number of DHCPDECLINE (option 53 with value 4) packets
                received."
            ::= { dhcpCountersEntry 4 }

        
        -- 1.3.6.1.4.1.5504.4.1.11.16.3.1.5
        dhcpCountInforms OBJECT-TYPE
            SYNTAX Counter32
            MAX-ACCESS read-only
            STATUS current
            DESCRIPTION
                "The number of DHCPINFORM (option 53 with value 8) packets
                received."
            ::= { dhcpCountersEntry 5 }

        
        -- 1.3.6.1.4.1.5504.4.1.11.16.3.1.6
        dhcpCountInvalids OBJECT-TYPE
            SYNTAX Counter32
            MAX-ACCESS read-only
            STATUS current
            DESCRIPTION
                "The number of DHCP packets received whose DHCP message type
                (i.e., option number 53) is not understood or handled by the
                server."
            ::= { dhcpCountersEntry 6 }

        
        -- 1.3.6.1.4.1.5504.4.1.11.16.3.1.7
        dhcpCountOffers OBJECT-TYPE
            SYNTAX Counter32
            MAX-ACCESS read-only
            STATUS current
            DESCRIPTION
                "The number of DHCPOFFER (option 53 with value 2) packets
                sent."
            ::= { dhcpCountersEntry 7 }

        
        -- 1.3.6.1.4.1.5504.4.1.11.16.3.1.8
        dhcpCountAcks OBJECT-TYPE
            SYNTAX Counter32
            MAX-ACCESS read-only
            STATUS current
            DESCRIPTION
                "The number of DHCPACK (option 53 with value 5) packets
                sent."
            ::= { dhcpCountersEntry 8 }

        
        -- 1.3.6.1.4.1.5504.4.1.11.16.3.1.9
        dhcpCountNacks OBJECT-TYPE
            SYNTAX Counter32
            MAX-ACCESS read-only
            STATUS current
            DESCRIPTION
                "The number of DHCPNACK (option 53 with value 6) packets
                sent."
            ::= { dhcpCountersEntry 9 }

        
        -- 1.3.6.1.4.1.5504.4.1.11.16.3.1.10
        dhcpCountDroppedUnknownClient OBJECT-TYPE
            SYNTAX Counter32
            MAX-ACCESS read-only
            STATUS current
            DESCRIPTION
                "The number of DHCP packets dropped due to the server not
                recognizing or not providing service to the client-id and/or
                hardware address received in the incoming packet."
            ::= { dhcpCountersEntry 10 }

        
        -- 1.3.6.1.4.1.5504.4.1.11.16.3.1.11
        dhcpCountDroppedNotServingSubnet OBJECT-TYPE
            SYNTAX Counter32
            MAX-ACCESS read-only
            STATUS current
            DESCRIPTION
                "The number of DHCP packets dropped due to the server not
                being configured or not otherwise able to serve addresses 
                on the subnet from which this message was received."
            ::= { dhcpCountersEntry 11 }

        
        -- 1.3.6.1.4.1.5504.4.1.11.17
        dhcpServerConfigurationVersion OBJECT-TYPE
            SYNTAX Unsigned32
            MAX-ACCESS read-write
            STATUS deprecated
            DESCRIPTION
                "Version number of the current DHCP server configuration.
                If this value is changed the server will reload all
                configuration rules and reinitialize itself.  Any
                configuration rules modified before this field is
                changed will not have any affect on the currently 
                running DHCP server configuration."
            ::= { dhcpServer 17 }

        
        -- 1.3.6.1.4.1.5504.4.1.11.18
        dhcpServerRestart OBJECT-TYPE
            SYNTAX INTEGER
                {
                true(1),
                false(2)
                }
            MAX-ACCESS read-write
            STATUS current
            DESCRIPTION
                "If set to value 'true(1)' indicates that the server should restart
                by doing a complete reload of it's configuration.  The value of 
                this field will be reset to 'false(2)' once the restart command has
                been acknowledged by the server.
                
                A restart would typically only be done after making manual changes 
                to the DHCP server lease table.  All other configuration changes
                done via SNMP are automatically loaded by the server.  
                
                Default value is 'false(2)'"
            ::= { dhcpServer 18 }

        
    
    END

--
-- comIpDhcpServer.mib
--

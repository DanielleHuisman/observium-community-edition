--
-- comIpIp.mib
-- MIB generated by MG-SOFT Visual MIB Builder Version 2.1 Build 199
-- Monday, November 06, 2000 at 16:17:20
--

    ZHONE-COM-IP-IP-MIB DEFINITIONS ::= BEGIN

        IMPORTS 
            InterfaceIndex            
                FROM IF-MIB            
            IpAddress, Integer32, Unsigned32, Counter32, OBJECT-TYPE, 
            MODULE-IDENTITY, OBJECT-IDENTITY            
                FROM SNMPv2-SMI            
            PhysAddress            
                FROM SNMPv2-TC            
            rdEntry            
                FROM ZHONE-COM-IP-RD-MIB            
            zhoneIp, zhoneModules            
                FROM Zhone            
            ZhoneRowStatus            
                FROM Zhone-TC;
    
    
-- Make this generate IP_Resource, IPStatistics_Resource, and 
-- IPNetToMedia_Resource record definitions in the
-- files ipProfile.c/h
-- 
-- 
-- 
-- 
        comIpIp MODULE-IDENTITY
            LAST-UPDATED "200009111700Z"
            ORGANIZATION
                "Zhone Technologies, Inc."
            CONTACT-INFO
                "  Postal: 
                           Zhone Technologies, Inc.
                           @ Zhone Way
                           7001 Oakport Street
                           Oakland, CA  94621
                           USA
                Toll-Free: +1 877-ZHONE20 (+1 877-946-6320)
                      Tel: +1-510-777-7000
                      Fax: +1-510-777-7001
                   E-mail: support@zhone.com
                
                "
            DESCRIPTION
                "Zhone IP MIB Module.
                IP Software
                Minneapolis, MN"
            REVISION "200011021730Z"
            DESCRIPTION
                "V01.00.01 - Update markup language"
            REVISION "200009111630Z"
            DESCRIPTION
                "V01.00.00 - Initial Release"
            ::= { zhoneModules 54 }
        
    
    
--
-- Node definitions
--
    
        ip OBJECT-IDENTITY
            STATUS current
            DESCRIPTION
                "IP objects based on RFC 2011.  The ipAddrTable has been
                removed as that information is now reflected in the
                ipInterfaceTable."
            ::= { zhoneIp 4 }
        
        zhoneIpTable OBJECT-TYPE
            SYNTAX SEQUENCE OF ZhoneIpEntry
            MAX-ACCESS not-accessible
            STATUS current
            DESCRIPTION
                "Zhone IP Table."
            ::= { ip 2 }
        
        zhoneIpEntry OBJECT-TYPE
            SYNTAX ZhoneIpEntry
            MAX-ACCESS not-accessible
            STATUS current
            DESCRIPTION
                "Zhone IP Entry.  This table augments the Routing Domain Table
                defined in comIpRD.mib.  A row will be added to this table 
                whenever a domain is added to the Routing Domain Table."
            AUGMENTS { rdEntry }
            ::= { zhoneIpTable 1 }
        
        ZhoneIpEntry ::=
            SEQUENCE { 
                zhIpForwarding
                    INTEGER,
                zhIpDefaultTTL
                    Integer32,
                zhIpInReceives
                    Counter32,
                zhIpInHdrErrors
                    Counter32,
                zhIpInAddrErrors
                    Counter32,
                zhIpForwDatagrams
                    Counter32,
                zhIpInUnknownProtos
                    Counter32,
                zhIpInDiscards
                    Counter32,
                zhIpInDelivers
                    Counter32,
                zhIpOutRequests
                    Counter32,
                zhIpOutDiscards
                    Counter32,
                zhIpOutNoRoutes
                    Counter32,
                zhIpReasmTimeout
                    Unsigned32,
                zhIpReasmReqds
                    Counter32,
                zhIpReasmOKs
                    Counter32,
                zhIpReasmFails
                    Counter32,
                zhIpFragOKs
                    Counter32,
                zhIpFragFails
                    Counter32,
                zhIpFragCreates
                    Counter32,
                zhIpRoutingDiscards
                    Counter32
             }

        zhIpForwarding OBJECT-TYPE
            SYNTAX INTEGER
                {
                forwarding(1),
                notForwarding(2)
                }
            MAX-ACCESS read-write
            STATUS current
            DESCRIPTION
                "The indication of whether this entity is acting as an IP
                router in respect to the forwarding of datagrams received
                by, but not addressed to, this entity.  IP routers forward
                datagrams.  IP hosts do not (except those source-routed via
                the host)."
            REFERENCE
                "See RFC2011:  ip.ipForwarding"
            DEFVAL { forwarding }
            ::= { zhoneIpEntry 1 }
        
        zhIpDefaultTTL OBJECT-TYPE
            SYNTAX Integer32 (1..255)
            MAX-ACCESS read-write
            STATUS current
            DESCRIPTION
                "The default value inserted into the Time-To-Live field of
                the IP header of datagrams originated at this entity,
                whenever a TTL value is not supplied by the transport layer
                protocol."
            REFERENCE
                "See RFC2011: ip.ipDefaultTTL"
            DEFVAL { 64 }
            ::= { zhoneIpEntry 2 }
        
        zhIpInReceives OBJECT-TYPE
            SYNTAX Counter32
            MAX-ACCESS read-only
            STATUS current
            DESCRIPTION
                "The total number of input datagrams received from
                interfaces, including those received in error."
            REFERENCE
                "See RFC2011:  ip.ipInReceives"
            ::= { zhoneIpEntry 3 }
        
        zhIpInHdrErrors OBJECT-TYPE
            SYNTAX Counter32
            MAX-ACCESS read-only
            STATUS current
            DESCRIPTION
                "The number of input datagrams discarded due to errors in
                their IP headers, including bad checksums, version number
                mismatch, other format errors, time-to-live exceeded, errors
                discovered in processing their IP options, etc."
            REFERENCE
                "See RFC2011:  ip.ipInHdrErrors"
            ::= { zhoneIpEntry 4 }
        
        zhIpInAddrErrors OBJECT-TYPE
            SYNTAX Counter32
            MAX-ACCESS read-only
            STATUS current
            DESCRIPTION
                "The number of input datagrams discarded because the IP
                address in their IP header's destination field was not a
                valid address to be received at this entity.  This count
                includes invalid addresses (e.g., 0.0.0.0) and addresses of
                unsupported Classes (e.g., Class E).  For entities which are
                not IP routers and therefore do not forward datagrams, this
                counter includes datagrams discarded because the destination
                address was not a local address."
            REFERENCE
                "See RFC2011:  ip.ipInAddrErrors"
            ::= { zhoneIpEntry 5 }
        
        zhIpForwDatagrams OBJECT-TYPE
            SYNTAX Counter32
            MAX-ACCESS read-only
            STATUS current
            DESCRIPTION
                "The number of input datagrams for which this entity was not
                their final IP destination, as a result of which an attempt
                was made to find a route to forward them to that final
                destination.  In entities which do not act as IP routers,
                this counter will include only those packets which were
                Source-Routed via this entity, and the Source-Route option
                processing was successful."
            REFERENCE
                "See RFC2011:  ip.ipForwDatagrams"
            ::= { zhoneIpEntry 6 }
        
        zhIpInUnknownProtos OBJECT-TYPE
            SYNTAX Counter32
            MAX-ACCESS read-only
            STATUS current
            DESCRIPTION
                "The number of locally-addressed datagrams received
                successfully but discarded because of an unknown or
                unsupported protocol."
            REFERENCE
                "See RFC2011:  ip.ipInUnknownProtos"
            ::= { zhoneIpEntry 7 }
        
        zhIpInDiscards OBJECT-TYPE
            SYNTAX Counter32
            MAX-ACCESS read-only
            STATUS current
            DESCRIPTION
                "The number of input IP datagrams for which no problems were
                encountered to prevent their continued processing, but which
                were discarded (e.g., for lack of buffer space).  Note that
                this counter does not include any datagrams discarded while
                awaiting re-assembly."
            REFERENCE
                "See RFC2011:  ip.ipInDiscards"
            ::= { zhoneIpEntry 8 }
        
        zhIpInDelivers OBJECT-TYPE
            SYNTAX Counter32
            MAX-ACCESS read-only
            STATUS current
            DESCRIPTION
                "The total number of input datagrams successfully delivered
                to IP user-protocols (including ICMP)."
            REFERENCE
                "See RFC2011:  ip.ipInDelivers"
            ::= { zhoneIpEntry 9 }
        
        zhIpOutRequests OBJECT-TYPE
            SYNTAX Counter32
            MAX-ACCESS read-only
            STATUS current
            DESCRIPTION
                "The total number of IP datagrams which local IP user-
                protocols (including ICMP) supplied to IP in requests for
                transmission.  Note that this counter does not include any
                datagrams counted in ipForwDatagrams."
            REFERENCE
                "See RFC2011:  ip.ipOutRequests"
            ::= { zhoneIpEntry 10 }
        
        zhIpOutDiscards OBJECT-TYPE
            SYNTAX Counter32
            MAX-ACCESS read-only
            STATUS current
            DESCRIPTION
                "The number of output IP datagrams for which no problem was
                encountered to prevent their transmission to their
                destination, but which were discarded (e.g., for lack of
                buffer space).  Note that this counter would include
                datagrams counted in ipForwDatagrams if any such packets met
                this (discretionary) discard criterion."
            REFERENCE
                "See RFC2011:  ip.ipOutDiscards"
            ::= { zhoneIpEntry 11 }
        
        zhIpOutNoRoutes OBJECT-TYPE
            SYNTAX Counter32
            MAX-ACCESS read-only
            STATUS current
            DESCRIPTION
                "The number of IP datagrams discarded because no route could
                be found to transmit them to their destination.  Note that
                this counter includes any packets counted in ipForwDatagrams
                which meet this `no-route' criterion.  Note that this
                includes any datagrams which a host cannot route because all
                of its default routers are down."
            REFERENCE
                "See RFC2011:  ip.ipOutNoRoutes"
            ::= { zhoneIpEntry 12 }
        
        zhIpReasmTimeout OBJECT-TYPE
            SYNTAX Unsigned32
            UNITS "seconds"
            MAX-ACCESS read-only
            STATUS current
            DESCRIPTION
                "The maximum number of seconds which received fragments are
                held while they are awaiting reassembly at this entity."
            REFERENCE
                "See RFC2011:  ip.ipReasmTimeout"
            ::= { zhoneIpEntry 13 }
        
        zhIpReasmReqds OBJECT-TYPE
            SYNTAX Counter32
            MAX-ACCESS read-only
            STATUS current
            DESCRIPTION
                "The number of IP fragments received which needed to be
                reassembled at this entity."
            REFERENCE
                "See RFC2011:  ip.ipReasmReqds"
            ::= { zhoneIpEntry 14 }
        
        zhIpReasmOKs OBJECT-TYPE
            SYNTAX Counter32
            MAX-ACCESS read-only
            STATUS current
            DESCRIPTION
                "The number of IP datagrams successfully re-assembled."
            REFERENCE
                "See RFC2011:  ip.ipReasmOKs"
            ::= { zhoneIpEntry 15 }
        
        zhIpReasmFails OBJECT-TYPE
            SYNTAX Counter32
            MAX-ACCESS read-only
            STATUS current
            DESCRIPTION
                "The number of failures detected by the IP re-assembly
                algorithm (for whatever reason: timed out, errors, etc).
                Note that this is not necessarily a count of discarded IP
                fragments since some algorithms (notably the algorithm in
                RFC 815) can lose track of the number of fragments by
                combining them as they are received."
            REFERENCE
                "See RFC2011:  ip.ipReasmFails"
            ::= { zhoneIpEntry 16 }
        
        zhIpFragOKs OBJECT-TYPE
            SYNTAX Counter32
            MAX-ACCESS read-only
            STATUS current
            DESCRIPTION
                "The number of IP datagrams that have been successfully
                fragmented at this entity."
            REFERENCE
                "See RFC2011:  ip.ipFragOKs"
            ::= { zhoneIpEntry 17 }
        
        zhIpFragFails OBJECT-TYPE
            SYNTAX Counter32
            MAX-ACCESS read-only
            STATUS current
            DESCRIPTION
                "The number of IP datagrams that have been discarded because
                they needed to be fragmented at this entity but could not
                be, e.g., because their Don't Fragment flag was set."
            REFERENCE
                "See RFC2011:  ip.ipFragFails"
            ::= { zhoneIpEntry 18 }
        
        zhIpFragCreates OBJECT-TYPE
            SYNTAX Counter32
            MAX-ACCESS read-only
            STATUS current
            DESCRIPTION
                "The number of IP datagram fragments that have been
                generated as a result of fragmentation at this entity."
            REFERENCE
                "See RFC2011:  ip.ipFragCreates"
            ::= { zhoneIpEntry 19 }
        
        zhIpRoutingDiscards OBJECT-TYPE
            SYNTAX Counter32
            MAX-ACCESS read-only
            STATUS current
            DESCRIPTION
                "The number of routing entries which were chosen to be
                discarded even though they are valid.  One possible reason
                for discarding such an entry could be to free-up buffer
                space for other routing entries."
            REFERENCE
                "See RFC2011:  ip.ipRoutingDiscards"
            ::= { zhoneIpEntry 20 }
        
        zhoneIpNetToMediaTable OBJECT-TYPE
            SYNTAX SEQUENCE OF ZhoneIpNetToMediaEntry
            MAX-ACCESS not-accessible
            STATUS current
            DESCRIPTION
                "The IP Address Translation table used for mapping from IP
                addresses to physical addresses."
            ::= { ip 4 }
        
        zhoneIpNetToMediaEntry OBJECT-TYPE
            SYNTAX ZhoneIpNetToMediaEntry
            MAX-ACCESS not-accessible
            STATUS current
            DESCRIPTION
                "Each entry contains one IpAddress to `physical' address
                equivalence.  An IpAddress is unique to the routing domain.
                An entry may be added to or removed from the table using the
                zhIpNetToMediaRowStatus object.  The columnar objects required 
                to create the row are zhIpNetToMediaIpIfIndex, 
                zhIpNetToMediaNetAddress, zhIpNetToMediaPhysAddress,
                and zhIpNetToMediaType."
            INDEX { zhIpNetToMediaIfIndex, zhIpNetToMediaNetAddress }
            ::= { zhoneIpNetToMediaTable 1 }
        
        ZhoneIpNetToMediaEntry ::=
            SEQUENCE { 
                zhIpNetToMediaIfIndex
                    InterfaceIndex,
                zhIpNetToMediaNetAddress
                    IpAddress,
                zhIpNetToMediaPhysAddress
                    PhysAddress,
                zhIpNetToMediaType
                    INTEGER,
                zhIpNetToMediaRowStatus
                    ZhoneRowStatus
             }

        zhIpNetToMediaIfIndex OBJECT-TYPE
            SYNTAX InterfaceIndex
            MAX-ACCESS not-accessible
            STATUS current
            DESCRIPTION
                "The IP interface on which this entry's equivalence is
                effective.  The interface identified by a particular value
                of this index is the same interface as identified by the
                same value of ifIndex in MIB-II (rfc2233)."
            REFERENCE
                "See RFC2011:  ip.ipNetToMediaTable.ipNetToMediaEntry.ipNetToMediaIfIndex"
            ::= { zhoneIpNetToMediaEntry 1 }
        
        zhIpNetToMediaNetAddress OBJECT-TYPE
            SYNTAX IpAddress
            MAX-ACCESS not-accessible
            STATUS current
            DESCRIPTION
                "The IpAddress corresponding to the media-dependent
                `physical' address."
            REFERENCE
                "See RFC2011:  ip.ipNetToMediaTable.ipNetToMediaEntry.ipNetToMediaNetAddress"
            ::= { zhoneIpNetToMediaEntry 2 }
        
        zhIpNetToMediaPhysAddress OBJECT-TYPE
            SYNTAX PhysAddress
            MAX-ACCESS read-create
            STATUS current
            DESCRIPTION
                "The media-dependent `physical' address."
            REFERENCE
                "See RFC2011:  ip.ipNetToMediaTable.ipNetToMediaEntry.ipNetToMediaPhysAddress"
            ::= { zhoneIpNetToMediaEntry 3 }
        
        zhIpNetToMediaType OBJECT-TYPE
            SYNTAX INTEGER
                {
                other(1),
                invalid(2),
                dynamic(3),
                static(4)
                }
            MAX-ACCESS read-create
            STATUS current
            DESCRIPTION
                "The type of mapping.
                other(1)   -- cannot be determined
                dynamic(3) -- mapping is supplied by the ARP server.
                static(4)  -- mapping is configured by the user.
                
                Setting this object to the value invalid(2) has the effect
                of invalidating the corresponding entry in the
                ipNetToMediaTable.  That is, it effectively disassociates
                the interface identified with said entry from the mapping
                identified with said entry.  It is an implementation-
                specific matter as to whether the agent removes an
                invalidated entry from the table.  Accordingly, management
                stations must be prepared to receive tabular information
                from agents that corresponds to entries not currently in
                use.  Proper interpretation of such entries requires
                examination of the relevant ipNetToMediaType object."
            REFERENCE
                "See RFC2011:  ip.ipNetToMediaTable.ipNetToMediaEntry.ipNetToMediaType"
            DEFVAL { static }
            ::= { zhoneIpNetToMediaEntry 4 }
        
-- 
-- 
        zhIpNetToMediaRowStatus OBJECT-TYPE
            SYNTAX ZhoneRowStatus
            MAX-ACCESS read-create
            STATUS current
            DESCRIPTION
                "This is required to be able to add/remove entries to/from
                the table."
            REFERENCE
                "See ZHONE-TC-MIB for definition of ZhoneRowStatus."
            ::= { zhoneIpNetToMediaEntry 5 }
        
    
    END

--
-- comIpIp.mib
--

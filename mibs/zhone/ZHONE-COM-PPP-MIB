--
-- comPpp.mib
-- MIB generated by MG-SOFT Visual MIB Builder Version 2.5 Build 225
-- Wednesday, June 06, 2001 at 18:26:40
--

    ZHONE-COM-PPP-MIB DEFINITIONS ::= BEGIN

        IMPORTS 
            AtmVpIdentifier, AtmVcIdentifier            
                FROM ATM-TC-MIB            
            ifIndex, InterfaceIndex, InterfaceIndexOrZero            
                FROM IF-MIB            
            Integer32, Unsigned32, OBJECT-TYPE, MODULE-IDENTITY            
                FROM SNMPv2-SMI            
            TEXTUAL-CONVENTION            
                FROM SNMPv2-TC            
            zhonePpp, zhoneModules            
                FROM Zhone            
            ZhoneRowStatus            
                FROM Zhone-TC;
    
    
-- 
-- 
-- 
        comPpp MODULE-IDENTITY
            LAST-UPDATED "200106061600Z"
            ORGANIZATION
                "Zhone Technologies, Inc."
            CONTACT-INFO
                "   Postal: 
                Zhone Technologies, Inc.
                @ Zhone Way
                7001 Oakport Street
                Oakland, CA  94621
                USA
                Toll-Free: +1 877-ZHONE20 (+1 877-946-6320)
                Tel: +1-510-777-7000
                Fax: +1-510-777-7001
                E-mail: support@zhone.com"
            DESCRIPTION
                "Point-to-Point Protocol (PPP) MIB
                IP Software
                Minneapolis, MN"
            REVISION "200106061600Z"
            DESCRIPTION
                "V01.03.00 - Replaced pppIfLgId with pppIfLowerIfIndex
                            Removed pppIfLinkType.
                            Removed ncpExtRowStatus from pppNCPExtenstionsTable.
                            Modified description of pppAuthPAPPassword and pppAuthCHAPSecret
                            to indicate that empty string will be returned on a GET."
            REVISION "200104191500Z"
            DESCRIPTION
                "V01.02.00 - Added pppAuthenticationTable and added
                            authentication fields to the pppLCPExtensionsTable."
            REVISION "200103200930Z"
            DESCRIPTION
                "V01.01.01 -  Fix defaults, change AFFC to ACFC,
                             add isdn link-type."
            REVISION "200103121100Z"
            DESCRIPTION
                "V01.01.00 - Removed ncpExtServProv from pppNCPExtensionsTable.
                            Changed default for ncpExtMaxConfigRetries and
                            ncpExtMaxFailureRetries to 10."
            REVISION "200103011100Z"
            DESCRIPTION
                "V01.00.01 - Changed pppIfVci from Integer32 to AtmVcIdentifier.
                            Changed pppIfRowStatus from Integer32 to zhoneRowStatus."
            REVISION "200102081002Z"
            DESCRIPTION
                "V01.00.00 - Initial Release"
            ::= { zhoneModules 69 }
        
    
--
-- Textual conventions
--
    
        ZhoneAuthenticationProtocol ::= TEXTUAL-CONVENTION
            STATUS current
            DESCRIPTION
                "The protocol used for authentication:
                      PAP  - Password Authentication Protocol
                      CHAP - Challenge Handshake Authentication Protocol"
            SYNTAX INTEGER
                {
                pap(1),
                chap(2)
                }
            
        EnableFlag ::= TEXTUAL-CONVENTION
            STATUS current
            DESCRIPTION
                "A boolean type used to indicate if a feature is enabled
                or disabled."
            SYNTAX INTEGER
                {
                enabled(1),
                disabled(2)
                }
            
    
--
-- Node definitions
--
    
        pppInterfaceTable OBJECT-TYPE
            SYNTAX SEQUENCE OF PppInterfaceEntry
            MAX-ACCESS not-accessible
            STATUS current
            DESCRIPTION
                "This table is used to configure attributes of a PPP
                interface that are not currently covered by the
                standard MIBs.  This table is indexed by the ifIndex
                of the PPP interface.  IANA iftype ppp is #23."
            ::= { zhonePpp 1 }
        
        pppInterfaceEntry OBJECT-TYPE
            SYNTAX PppInterfaceEntry
            MAX-ACCESS not-accessible
            STATUS current
            DESCRIPTION
                "There is an entry in this table for every provisioned
                PPP interface.  Rows are created by setting pppIfRowStatus
                to createAndGo(4).  Rows are removed by setting
                pppIfRowStatus to destroy(6).  When a row is created or
                deleted in this table, a row is also created or deleted in
                the pppLCPExtensionsTable in this MIB module and 
                the pppLinkConfigTable and pppLqrConfigTable in RFC 1471.
                An entry will also be created/destroyed in the ifTable (RFC2233).
                The pppIfLowerIfIndex is required for row creation."
            REFERENCE
                "See pppLCPExtensionsEntry in this MIB module and
                pppLinkConfigTable and pppLqrConfigTable in rfc1471.mib."
            INDEX { ifIndex }
            ::= { pppInterfaceTable 1 }
        
        PppInterfaceEntry ::=
            SEQUENCE { 
                pppIfLowerIfIndex
                    InterfaceIndex,
                pppIfVpi
                    AtmVpIdentifier,
                pppIfVci
                    AtmVcIdentifier,
                pppIfCallMode
                    INTEGER,
                pppIfFrameType
                    INTEGER,
                pppIfNumChannels
                    Integer32,
                pppIfRowStatus
                    ZhoneRowStatus
             }

-- since the information is reflected in the ifStack.
        pppIfLowerIfIndex OBJECT-TYPE
            SYNTAX InterfaceIndex
            MAX-ACCESS read-create
            STATUS current
            DESCRIPTION
                "The ifIndex of the lower layer interface to which this PPP
                interface should be bound.  Since PPP interfaces are always
                statically bound, this value can never be zero.
                Upon setting this field, the ifStack will be modified to reflect
                the appropriate binding.  This object is required for row creation.
                "
            REFERENCE
                "see rfc2233.mib: ifStackTable"
            ::= { pppInterfaceEntry 1 }
        
        pppIfVpi OBJECT-TYPE
            SYNTAX AtmVpIdentifier
            MAX-ACCESS read-create
            STATUS current
            DESCRIPTION
                "If this IP interface is on an ATM VC, the ATM VPI is 
                specified here.  If the IP interface is not an ATM VC, 
                this field is ignored.  The VPI value for a VPL or VCL. 
                The value VPI=0 is only allowed for a VCL. For ATM UNIs 
                supporting VPCs the VPI value ranges from 0 to 255.  The 
                VPI value 0 is supported for ATM UNIs conforming to the 
                ATM Forum UNI 4.0 Annex 8 (Virtual UNIs) specification. 
                For ATM UNIs supporting VCCs the VPI value ranges from 
                0 to 255.  For ATM NNIs the VPI value ranges from 0 to 4095.
                The maximum VPI value cannot exceed the value allowable by
                atmInterfaceMaxActiveVpiBits defined in ATM-MIB."
            REFERENCE
                "See rfc2515.mib:  atmInterfaceMaxActiveVpiBits"
            DEFVAL { 0 }
            ::= { pppInterfaceEntry 2 }
        
        pppIfVci OBJECT-TYPE
            SYNTAX AtmVcIdentifier
            MAX-ACCESS read-create
            STATUS current
            DESCRIPTION
                "If this PPP interface is on an ATM VC, the ATM VCI is specified here.
                If the PPP interface is not an ATM VC, this field is ignored.
                The maximum VCI value cannot exceed the value allowable by
                atmInterfaceMaxActiveVciBits defined in ATM-MIB."
            REFERENCE
                "See rfc2515.mib:  atmInterfaceMaxActiveVciBits"
            DEFVAL { 0 }
            ::= { pppInterfaceEntry 3 }
        
        pppIfCallMode OBJECT-TYPE
            SYNTAX INTEGER
                {
                noCall(1),
                inCall(2),
                outCall(3)
                }
            MAX-ACCESS read-create
            STATUS current
            DESCRIPTION
                "Indicates where the PPP call is initiated.
                
                noCall:    No call is initiated
                inCall:    Call is intiated remotely.
                outCall:   Call is intiated locally."
            DEFVAL { noCall }
            ::= { pppInterfaceEntry 4 }
        
        pppIfFrameType OBJECT-TYPE
            SYNTAX INTEGER
                {
                none(1),
                frameRelay(2),
                atmLLC(3),
                atmVc(4)
                }
            MAX-ACCESS read-create
            STATUS current
            DESCRIPTION
                "The type of framing used if the link type is ATM or Frame
                Relay.  
                
                If link type is atm, pppIfFrameType must be atmLLC or atmVc.
                If link type is frameRelay, pppIfFrameType must be frameRelay.
                If link type is any other value, pppIfFrameType must be none.
                
                Currently, only atmLLC and atmVC are supported."
            DEFVAL { atmLLC }
            ::= { pppInterfaceEntry 5 }
        
        pppIfNumChannels OBJECT-TYPE
            SYNTAX Integer32 (1..65535)
            MAX-ACCESS read-create
            STATUS current
            DESCRIPTION
                "The maximum number of channels allowed on this interface.
                Currently, only one channel is supported."
            DEFVAL { 1 }
            ::= { pppInterfaceEntry 6 }
        
        pppIfRowStatus OBJECT-TYPE
            SYNTAX ZhoneRowStatus
            MAX-ACCESS read-create
            STATUS current
            DESCRIPTION
                "Zhone convention to support row creation and deletion.
                pppIfLgId is required to create or destroy a row in this 
                table."
            ::= { pppInterfaceEntry 7 }
        
        pppLCPExtensionsTable OBJECT-TYPE
            SYNTAX SEQUENCE OF PppLCPExtensionsEntry
            MAX-ACCESS not-accessible
            STATUS current
            DESCRIPTION
                "This table is used to configure attributes not found
                in the pppLinkConfigTable defined in RFC 1471.  This 
                table is indexed by the ifIndex of the PPP interface
                to which these LCP attributes apply."
            ::= { zhonePpp 2 }
        
        pppLCPExtensionsEntry OBJECT-TYPE
            SYNTAX PppLCPExtensionsEntry
            MAX-ACCESS not-accessible
            STATUS current
            DESCRIPTION
                "There is an entry in this table for every provisioned PPP 
                interface.  Rows in this table are created or deleted when 
                a row in the pppInterfaceTable is created or deleted using 
                pppIfRowStatus.  Therefore, objects in this table cannot
                be set in the same SNMP PDU as the objects used to create
                a row in the pppInterfaceTable."
            REFERENCE
                "See pppInterfaceTable in this MIB module."
            AUGMENTS { pppInterfaceEntry }
            ::= { pppLCPExtensionsTable 1 }
        
        PppLCPExtensionsEntry ::=
            SEQUENCE { 
                lcpExtReceiveAuthEnable
                    EnableFlag,
                lcpExtReceiveAuthProtocol
                    ZhoneAuthenticationProtocol,
                lcpExtSendAuthEnable
                    EnableFlag,
                lcpExtSendAuthProtocol
                    ZhoneAuthenticationProtocol,
                lcpExtSendAuthIdentity
                    OCTET STRING,
                lcpExtQualityProtocol
                    INTEGER,
                lcpExtMagicNumber
                    Unsigned32,
                lcpExtMaxPad
                    Integer32,
                lcpExtCallbackEnable
                    EnableFlag,
                lcpExtCallbackType
                    INTEGER,
                lcpExtCallbackDialString
                    OCTET STRING,
                lcpExtRestartTimer
                    Integer32,
                lcpExtMaxConfigRetries
                    Integer32,
                lcpExtMaxTerminateRetries
                    Integer32,
                lcpExtMaxFailureRetries
                    Integer32,
                lcpExtMRUEnable
                    EnableFlag,
                lcpExtACCMEnable
                    EnableFlag,
                lcpExtPFCEnable
                    EnableFlag,
                lcpExtACFCEnable
                    EnableFlag,
                lcpExtFCSAltEnable
                    EnableFlag,
                lcpExtSDPEnable
                    EnableFlag,
                lcpExtNumModeEnable
                    EnableFlag
             }

        lcpExtReceiveAuthEnable OBJECT-TYPE
            SYNTAX EnableFlag
            MAX-ACCESS read-create
            STATUS current
            DESCRIPTION
                "Enable or disable incoming authentication."
            REFERENCE
                "From RFC 1661:
                'This Configuration Option provides a method to negotiate 
                 the use of a specific protocol for authentication.'"
            DEFVAL { enabled }
            ::= { pppLCPExtensionsEntry 1 }
        
        lcpExtReceiveAuthProtocol OBJECT-TYPE
            SYNTAX ZhoneAuthenticationProtocol
            MAX-ACCESS read-create
            STATUS current
            DESCRIPTION
                "The preferred protocol used for incoming authentication.  
                If lcpExtReceiveAuthEnable is enabled, the authentication 
                protocol will be negotiated with the peer."
            DEFVAL { pap }
            ::= { pppLCPExtensionsEntry 2 }
        
        lcpExtSendAuthEnable OBJECT-TYPE
            SYNTAX EnableFlag
            MAX-ACCESS read-create
            STATUS current
            DESCRIPTION
                "Enable or disable outgoing authentication."
            DEFVAL { disabled }
            ::= { pppLCPExtensionsEntry 3 }
        
        lcpExtSendAuthProtocol OBJECT-TYPE
            SYNTAX ZhoneAuthenticationProtocol
            MAX-ACCESS read-create
            STATUS current
            DESCRIPTION
                "The protocol used with lcpExtSendAuthIdentity to look up 
                the outgoing authentication information."
            DEFVAL { pap }
            ::= { pppLCPExtensionsEntry 4 }
        
        lcpExtSendAuthIdentity OBJECT-TYPE
            SYNTAX OCTET STRING (SIZE (0..24))
            MAX-ACCESS read-create
            STATUS current
            DESCRIPTION
                "The identity (PAP peer ID or CHAP name) used with
                lcpExtSendAuthProtocol to look up the outgoing
                authentication information.  Default value is the empty 
                string."
            ::= { pppLCPExtensionsEntry 5 }
        
        lcpExtQualityProtocol OBJECT-TYPE
            SYNTAX INTEGER { lqr(1) }
            MAX-ACCESS read-create
            STATUS current
            DESCRIPTION
                "The Quality Protocol used.  Currently, the only valid
                quality protocl is LQR.  Quality protocol must be enabled
                using pppLqrConfigStatus in RFC1471."
            REFERENCE
                "See rfc1471.mib:  pppLqrConfigStatus
                
                From RFC 1661:
                'This Configuration Option provides a method to negotiate 
                 the use of a specific protocol for link quality monitoring.'"
            DEFVAL { lqr }
            ::= { pppLCPExtensionsEntry 6 }
        
        lcpExtMagicNumber OBJECT-TYPE
            SYNTAX Unsigned32
            MAX-ACCESS read-create
            STATUS current
            DESCRIPTION
                "The number used in Magic Number negotiation.  Magic
                number negotiation must be enabled using 
                pppLinkConfigMagicNumber in RFC1471.
                
                When set to zero, a random number will be used for
                the magic number.  This allows us to better prevent
                having two devices with the same magic number."
            REFERENCE
                "See rfc1471.mib:  pppLinkConfigMagicNumber
                
                From RFC 1661:
                'This Configuration Option provides a method to detect 
                 looped-back links and other Data Link Layer anomalies.  
                 This Configuration Option MAY be required by some other 
                 Configuration Options such as the Quality-Protocol 
                 Configuration Option.  By default, the Magic-Number is 
                 not negotiated, and zero is inserted where a Magic-Number 
                 might otherwise be used.'"
            DEFVAL { 0 }
            ::= { pppLCPExtensionsEntry 7 }
        
        lcpExtMaxPad OBJECT-TYPE
            SYNTAX Integer32 (1..255)
            MAX-ACCESS read-create
            STATUS current
            DESCRIPTION
                "The number of padded bytes at the end of data.  This is
                used for Self-Describing Padding, a method for placing
                unambiguous padding octets at the end of the PPP Information
                field in order to cause messages to fall on a natural boundary."
            REFERENCE
                "See Self-Describing Padding in RFC 1570."
            DEFVAL { 4 }
            ::= { pppLCPExtensionsEntry 8 }
        
        lcpExtCallbackEnable OBJECT-TYPE
            SYNTAX EnableFlag
            MAX-ACCESS read-create
            STATUS current
            DESCRIPTION
                "Enable or disable Callback negotiation.  "
            REFERENCE
                "From RFC 1570:
                'This Configuration Option provides a method for an 
                 implementation to request a dial-up peer to call back.'"
            DEFVAL { disabled }
            ::= { pppLCPExtensionsEntry 9 }
        
        lcpExtCallbackType OBJECT-TYPE
            SYNTAX INTEGER
                {
                byAuth(1),
                byDialStr(2),
                byIdentifier(3),
                byE164(4),
                byName(5)
                }
            MAX-ACCESS read-create
            STATUS current
            DESCRIPTION
                "The method of determining the location to callback.
                
                byAuth:        Location is determined by authorization information.
                byDialString:  Location is determined by a dialing string.
                byIdentifier:  Location is determined by a location ID.
                byE164:        Location is determined by an E.164 number.
                byName:        Location is determined by a distinguished name.
                
                These objects only apply when callback negotiation is enabled
                using lcpExtCallbackEnable."
            DEFVAL { byAuth }
            ::= { pppLCPExtensionsEntry 10 }
        
        lcpExtCallbackDialString OBJECT-TYPE
            SYNTAX OCTET STRING (SIZE (0..24))
            MAX-ACCESS read-create
            STATUS current
            DESCRIPTION
                "The dialing string used for a callback.  The format of
                this string is determined by lcpExtCallbackType.
                
                This object only applies when callback negotiation is enabled 
                using lcpExtCallbackEnable.
                
                Default value is the empty string."
            ::= { pppLCPExtensionsEntry 11 }
        
        lcpExtRestartTimer OBJECT-TYPE
            SYNTAX Integer32 (1..999)
            UNITS "seconds"
            MAX-ACCESS read-create
            STATUS current
            DESCRIPTION
                "Number of seconds before retransmission of an LCP packet."
            DEFVAL { 3 }
            ::= { pppLCPExtensionsEntry 12 }
        
        lcpExtMaxConfigRetries OBJECT-TYPE
            SYNTAX Integer32 (1..999)
            MAX-ACCESS read-create
            STATUS current
            DESCRIPTION
                "Number of LCP configuration retries without response before 
                the link is brought down."
            DEFVAL { 10 }
            ::= { pppLCPExtensionsEntry 13 }
        
        lcpExtMaxTerminateRetries OBJECT-TYPE
            SYNTAX Integer32 (1..999)
            MAX-ACCESS read-create
            STATUS current
            DESCRIPTION
                "Number of LCP termination retries without response before
                the link is brought down."
            DEFVAL { 2 }
            ::= { pppLCPExtensionsEntry 14 }
        
        lcpExtMaxFailureRetries OBJECT-TYPE
            SYNTAX Integer32 (1..999)
            MAX-ACCESS read-create
            STATUS current
            DESCRIPTION
                "Number of times a Configuration Nak is sent before a
                Configuration Rej is sent."
            DEFVAL { 10 }
            ::= { pppLCPExtensionsEntry 15 }
        
        lcpExtMRUEnable OBJECT-TYPE
            SYNTAX EnableFlag
            MAX-ACCESS read-create
            STATUS current
            DESCRIPTION
                "Enable or disable MRU negotiation."
            REFERENCE
                "From RFC 1661:
                'This Configuration Option may be sent to inform the peer 
                 that the implementation can receive larger packets, or to 
                 request that the peer send smaller packets.'"
            DEFVAL { enabled }
            ::= { pppLCPExtensionsEntry 16 }
        
        lcpExtACCMEnable OBJECT-TYPE
            SYNTAX EnableFlag
            MAX-ACCESS read-create
            STATUS current
            DESCRIPTION
                "Enable or disable Asynchronous Control Character Map
                negotiation."
            REFERENCE
                "From RFC 1548:
                'This Configuration Option provides a method to negotiate 
                 the use of control character transparency on asynchronous 
                 links.'"
            DEFVAL { disabled }
            ::= { pppLCPExtensionsEntry 17 }
        
        lcpExtPFCEnable OBJECT-TYPE
            SYNTAX EnableFlag
            MAX-ACCESS read-create
            STATUS current
            DESCRIPTION
                "Enable or disable Protocol Field Compression negotiation."
            REFERENCE
                "From RFC 1661:
                'This Configuration Option provides a method to negotiate 
                 the compression of the PPP Protocol field.'"
            DEFVAL { disabled }
            ::= { pppLCPExtensionsEntry 18 }
        
        lcpExtACFCEnable OBJECT-TYPE
            SYNTAX EnableFlag
            MAX-ACCESS read-create
            STATUS current
            DESCRIPTION
                "Enable or disable Address and Control Field Compression
                negotiation."
            REFERENCE
                "From RFC 1661:
                'This Configuration Option provides a method to negotiate 
                 the compression of the Data Link Layer Address and Control 
                 fields.'"
            DEFVAL { disabled }
            ::= { pppLCPExtensionsEntry 19 }
        
        lcpExtFCSAltEnable OBJECT-TYPE
            SYNTAX EnableFlag
            MAX-ACCESS read-create
            STATUS current
            DESCRIPTION
                "Enable or disable FCS Alternative negotiation.  
                The negotiated FCS values take effect only during 
                Authentication and Network-Layer Protocol phases."
            REFERENCE
                "From RFC 1570:
                'This Configuration Option provides a method for an 
                 implementation to specify another FCS format to be sent 
                 by the peer, or to negotiate away the FCS altogether.'"
            DEFVAL { disabled }
            ::= { pppLCPExtensionsEntry 20 }
        
        lcpExtSDPEnable OBJECT-TYPE
            SYNTAX EnableFlag
            MAX-ACCESS read-create
            STATUS current
            DESCRIPTION
                "Enable or disable Self-Describing Padding negotiation."
            REFERENCE
                "From RFC 1570:
                'This Configuration Option provides a method for an 
                 implementation to indicate to the peer that it understands 
                 self-describing pads when padding is added at the end of 
                 the PPP Information field.'"
            DEFVAL { disabled }
            ::= { pppLCPExtensionsEntry 21 }
        
        lcpExtNumModeEnable OBJECT-TYPE
            SYNTAX EnableFlag
            MAX-ACCESS read-create
            STATUS current
            DESCRIPTION
                "Enable or disable Numbered Mode negotiation."
            REFERENCE
                "From RFC 1663:
                'The LCP Numbered-Mode Configuration Option negotiates the 
                 use of Numbered-Mode on the link.  By default or ultimate 
                 disagreement, Unnumbered-Mode is used.'"
            DEFVAL { disabled }
            ::= { pppLCPExtensionsEntry 22 }
        
        pppNCPExtensionsTable OBJECT-TYPE
            SYNTAX SEQUENCE OF PppNCPExtensionsEntry
            MAX-ACCESS not-accessible
            STATUS current
            DESCRIPTION
                "This table is used to configure attributes not found
                in the pppIpConfigTable defined in RFC 1473.  This 
                table is indexed by the ifIndex of the network (IP) interface
                to which these NCP attributes apply."
            ::= { zhonePpp 3 }
        
        pppNCPExtensionsEntry OBJECT-TYPE
            SYNTAX PppNCPExtensionsEntry
            MAX-ACCESS not-accessible
            STATUS current
            DESCRIPTION
                "A row must be created in this table when an IP over PPP
                interface is provisioned.  Rows are created by setting 
                ipIfPppEnabled in the ipInterfaceTable to 'true'.  
                Rows are deleted by setting ipIfPppEnabled in the ipInterfaceTable
                to 'false'.  Creating or deleting a row in this table will do 
                the same in the pppIpConfigTable in rfc1473.mib."
            REFERENCE
                "See rfc1473.mib:  pppIpConfigTable
                See comIpRec.mib: ipInterfaceTable
                "
            INDEX { ifIndex }
            ::= { pppNCPExtensionsTable 1 }
        
        PppNCPExtensionsEntry ::=
            SEQUENCE { 
                ncpExtVJCompMaxSlotID
                    Integer32,
                ncpExtVJCompSlotID
                    EnableFlag,
                ncpExtIpAddrOptionEnable
                    EnableFlag,
                ncpExtRestartTimer
                    Integer32,
                ncpExtMaxConfigRetries
                    Integer32,
                ncpExtMaxTerminateRetries
                    Integer32,
                ncpExtFailureRetries
                    Integer32
             }

        ncpExtVJCompMaxSlotID OBJECT-TYPE
            SYNTAX Integer32 (3..16)
            MAX-ACCESS read-write
            STATUS current
            DESCRIPTION
                "The maximum slot ID for Van Jacobson Header Compression."
            DEFVAL { 3 }
            ::= { pppNCPExtensionsEntry 1 }
        
        ncpExtVJCompSlotID OBJECT-TYPE
            SYNTAX EnableFlag
            MAX-ACCESS read-write
            STATUS current
            DESCRIPTION
                "Indicates whether the slot identifier field may be compressed:
                
                disabled:  The slot identifier must not be compressed.  All
                           compressed TCP packets must set the C bit in every
                           change mask, and must include the slot identifier.
                enabled:   The slot identifier may be compressed."
            DEFVAL { disabled }
            ::= { pppNCPExtensionsEntry 2 }
        
        ncpExtIpAddrOptionEnable OBJECT-TYPE
            SYNTAX EnableFlag
            MAX-ACCESS read-write
            STATUS current
            DESCRIPTION
                "Enable or disable IP Address Negotiation."
            DEFVAL { disabled }
            ::= { pppNCPExtensionsEntry 3 }
        
        ncpExtRestartTimer OBJECT-TYPE
            SYNTAX Integer32 (1..999)
            UNITS "seconds"
            MAX-ACCESS read-write
            STATUS current
            DESCRIPTION
                "Number of seconds before retransmission of an IP packet."
            DEFVAL { 3 }
            ::= { pppNCPExtensionsEntry 4 }
        
        ncpExtMaxConfigRetries OBJECT-TYPE
            SYNTAX Integer32 (1..999)
            MAX-ACCESS read-write
            STATUS current
            DESCRIPTION
                "Number of IP configuration retries without response before 
                the session is brought down."
            DEFVAL { 10 }
            ::= { pppNCPExtensionsEntry 5 }
        
        ncpExtMaxTerminateRetries OBJECT-TYPE
            SYNTAX Integer32 (1..999)
            MAX-ACCESS read-write
            STATUS current
            DESCRIPTION
                "Number of IP termination retries without response before
                the session is brought down."
            DEFVAL { 2 }
            ::= { pppNCPExtensionsEntry 6 }
        
        ncpExtFailureRetries OBJECT-TYPE
            SYNTAX Integer32 (1..999)
            MAX-ACCESS read-write
            STATUS current
            DESCRIPTION
                "Number of times a Configuration Nak is sent before a
                Configuration Rej is sent"
            DEFVAL { 10 }
            ::= { pppNCPExtensionsEntry 7 }
        
        pppNextAuthId OBJECT-TYPE
            SYNTAX Integer32 (1..2147483647)
            MAX-ACCESS read-only
            STATUS current
            DESCRIPTION
                "A GET of this object will return the next available
                pppAuthId to be used when creating an entry in the
                pppAuthenticationTable.
                
                A GET-NEXT of this object will return the last number
                given out."
            ::= { zhonePpp 4 }
        
        pppAuthenticationTable OBJECT-TYPE
            SYNTAX SEQUENCE OF PppAuthenticationEntry
            MAX-ACCESS not-accessible
            STATUS current
            DESCRIPTION
                "This table contains provisioning for incoming and/or
                outgoing PPP authentication."
            ::= { zhonePpp 5 }
        
        pppAuthenticationEntry OBJECT-TYPE
            SYNTAX PppAuthenticationEntry
            MAX-ACCESS not-accessible
            STATUS current
            DESCRIPTION
                "An entry exists in the pppAuthenticationTable for each set
                of data used for PPP authentication. A set of PPP
                authentication data can be used for incoming authentication,
                outgoing authentication or both.  A row can be created/deleted 
                using pppAuthRowStatus.  
                
                The next available pppAuthId value can be obtained using
                pppNextAuthId."
            INDEX { pppAuthSubId, pppAuthId }
            ::= { pppAuthenticationTable 1 }
        
        PppAuthenticationEntry ::=
            SEQUENCE { 
                pppAuthSubId
                    Integer32,
                pppAuthId
                    Integer32,
                pppAuthIpIfIndex
                    InterfaceIndexOrZero,
                pppAuthLgId
                    InterfaceIndexOrZero,
                pppAuthProtocol
                    BITS,
                pppAuthPAPPeerID
                    OCTET STRING,
                pppAuthPAPPassword
                    OCTET STRING,
                pppAuthCHAPName
                    OCTET STRING,
                pppAuthCHAPSecret
                    OCTET STRING,
                pppAuthStatus
                    INTEGER,
                pppAuthRowStatus
                    ZhoneRowStatus
             }

        pppAuthSubId OBJECT-TYPE
            SYNTAX Integer32 (0..2147483647)
            MAX-ACCESS not-accessible
            STATUS current
            DESCRIPTION
                "The unique identifier of the subscriber associated with this 
                authentication entry.  A single subscriber may have multiple 
                authenticated users.  If this entry is only used for
                outgoing authentication, there may not be an associated
                subscriber.  Therefore, the subId may be zero."
            ::= { pppAuthenticationEntry 1 }
        
        pppAuthId OBJECT-TYPE
            SYNTAX Integer32 (1..2147483647)
            MAX-ACCESS not-accessible
            STATUS current
            DESCRIPTION
                "A unique number used to identify this authentication entry."
            ::= { pppAuthenticationEntry 2 }
        
        pppAuthIpIfIndex OBJECT-TYPE
            SYNTAX InterfaceIndexOrZero
            MAX-ACCESS read-create
            STATUS current
            DESCRIPTION
                "The ifIndex of the IP record associated with this
                set of PPP authentication data.  If this entry is to be
                used for incoming authentication, this object must be set
                to a non-zero value."
            DEFVAL { 0 }
            ::= { pppAuthenticationEntry 3 }
        
        pppAuthLgId OBJECT-TYPE
            SYNTAX InterfaceIndexOrZero
            MAX-ACCESS read-create
            STATUS current
            DESCRIPTION
                "The unique identifier of the line group on which this
                authentication data is allowed to be used.  If the value is 
                zero, this authentication data can be used on any line group."
            DEFVAL { '0'b }
            ::= { pppAuthenticationEntry 4 }
        
-- 
        pppAuthProtocol OBJECT-TYPE
            SYNTAX BITS
                {
                pap(0),
                chap(1)
                }
            MAX-ACCESS read-create
            STATUS current
            DESCRIPTION
                "The protocol used for authentication:
                      PAP  - Password Authentication Protocol
                      CHAP - Challenge Handshake Authentication Protocol
                
                A bit is set for each authentication protocol that
                is enabled.
                
                All protocols are disabled by default."
            ::= { pppAuthenticationEntry 5 }
        
        pppAuthPAPPeerID OBJECT-TYPE
            SYNTAX OCTET STRING (SIZE (0..24))
            MAX-ACCESS read-create
            STATUS current
            DESCRIPTION
                "The username used if we are authenticating with the 
                PAP protocol.  Default value is the empty string."
            ::= { pppAuthenticationEntry 6 }
        
        pppAuthPAPPassword OBJECT-TYPE
            SYNTAX OCTET STRING (SIZE (0..24))
            MAX-ACCESS read-create
            STATUS current
            DESCRIPTION
                "The password used if we are authenticating with the 
                PAP protocol.  Default value is the empty string.
                For security, an empty string will be returned on a GET."
            ::= { pppAuthenticationEntry 7 }
        
        pppAuthCHAPName OBJECT-TYPE
            SYNTAX OCTET STRING (SIZE (0..24))
            MAX-ACCESS read-create
            STATUS current
            DESCRIPTION
                "The username used if we are authenticating with the 
                CHAP protocol.  Default value is the empty string."
            ::= { pppAuthenticationEntry 8 }
        
        pppAuthCHAPSecret OBJECT-TYPE
            SYNTAX OCTET STRING (SIZE (0..24))
            MAX-ACCESS read-create
            STATUS current
            DESCRIPTION
                "The password used if we are authenticating with the 
                CHAP protocol.  Default value is the empty string.
                For security, an empty string will be returned on a GET."
            ::= { pppAuthenticationEntry 9 }
        
        pppAuthStatus OBJECT-TYPE
            SYNTAX INTEGER
                {
                valid(1),
                invalid(2)
                }
            MAX-ACCESS read-create
            STATUS current
            DESCRIPTION
                "Setting this object to 'invalid' causes the information for
                that entry to become invalidated.  Calls using the
                authentication information from an invalidated entry will not
                be accepted or initiated.  This allows an entry to be
                temporarily disabled without deleting it from the table."
            DEFVAL { valid }
            ::= { pppAuthenticationEntry 10 }
        
        pppAuthRowStatus OBJECT-TYPE
            SYNTAX ZhoneRowStatus
            MAX-ACCESS read-create
            STATUS current
            DESCRIPTION
                "This object is used to create or delete an entry in the
                table.  Setting this object to 'createAndGo' will cause an
                entry to be created.  Setting this object to 'destroy' will
                cause an entry to be deleted.  Objects required for creating
                an entry are specified in the pppAuthenticationEntry description."
            ::= { pppAuthenticationEntry 12 }
        
    
    END

--
-- comPpp.mib
--

--
-- comIua.mib
-- MIB generated by MG-SOFT Visual MIB Builder Version 3.0 Build 285
-- Tuesday, June 09, 2009 at 04:38:20
--

    ZHONE-IUA-MIB DEFINITIONS ::= BEGIN
 
        IMPORTS
            InetAddress            
                FROM INET-ADDRESS-MIB            
            applIndex            
                FROM NETWORK-SERVICES-MIB            
            Integer32, Unsigned32, OBJECT-TYPE, MODULE-IDENTITY            
                FROM SNMPv2-SMI            
            zhoneIua            
                FROM Zhone            
            ZhoneRowStatus            
                FROM Zhone-TC;
    
    
--  To Create Protection Layer header and C code (run in /vob/mibs/src):
-- /vob/zhonetools/bin/pahrser.pl INET-ADDRESS-MIB.mib comIua.mib
-- 
-- To Create Mib Handler file (run in /vob/mibs/src):
-- /vob/EPILOGUE/binaries/emissary/solaris/mibcomp Zhone.mib
--   Zhone-TC.mib INET-ADDRESS-MIB.mib rfc2571.mib rfc2788.mib
--   comIua.mib -stub -o iuaServerHdlrs.c
-- 
-- 
-- 1.3.6.1.4.1.5504.4.15.1
-- May 27, 2009 at 06:56 GMT
-- May 25, 2009 at 23:16 GMT
        -- 1.3.6.1.4.1.5504.4.15.1
        zhoneIuaModule MODULE-IDENTITY 
            LAST-UPDATED "200905270656Z"		-- May 27, 2009 at 06:56 GMT
            ORGANIZATION 
                "Zhone Technologies."
            CONTACT-INFO 
                "   Postal: 
                Zhone Technologies, Inc.
                @ Zhone Way
                7001 Oakport Street
                Oakland, CA  94621
                USA
                Toll-Free: +1 877-ZHONE20 (+1 877-946-6320)
                Tel: +1-510-777-7000
                Fax: +1-510-777-7001
                E-mail: support@zhone.com"
            DESCRIPTION 
                "IUA server configuration for Zhone products"
            REVISION "200905252316Z"		-- May 25, 2009 at 23:16 GMT
            DESCRIPTION 
                "V01.00.00 - Initial revision"
            ::= { zhoneIua 1 }

        
    
    
--
-- Node definitions
--
    
        -- 1.3.6.1.4.1.5504.4.15.1.1
        zhoneIuaServerCfg OBJECT IDENTIFIER ::= { zhoneIuaModule 1 }

        
        -- 1.3.6.1.4.1.5504.4.15.1.1.1
        zhoneIuaServerTable OBJECT-TYPE
            SYNTAX SEQUENCE OF ZhoneIuaServerEntry
            MAX-ACCESS not-accessible
            STATUS current
            DESCRIPTION
                "Table of IUA Server addresses."
            ::= { zhoneIuaServerCfg 1 }

        
        -- 1.3.6.1.4.1.5504.4.15.1.1.1.1
        zhoneIuaServerEntry OBJECT-TYPE
            SYNTAX ZhoneIuaServerEntry
            MAX-ACCESS not-accessible
            STATUS current
            DESCRIPTION
                "An entry within the table.  Indexed by applIndex, which
                is an index to voip-server-entry, and a user specified unique number."
            INDEX { applIndex, zhoneIuaServerAddressIndex }
            ::= { zhoneIuaServerTable 1 }

        
        ZhoneIuaServerEntry ::=
            SEQUENCE { 
                zhoneIuaServerAddressIndex
                    Unsigned32,
                zhoneIuaServerRowStatus
                    ZhoneRowStatus,
                zhoneIuaServerAddress
                    InetAddress,
                zhoneIuaServerPortNumber
                    Integer32
             }

--  
        -- 1.3.6.1.4.1.5504.4.15.1.1.1.1.1
        zhoneIuaServerAddressIndex OBJECT-TYPE
            SYNTAX Unsigned32
            MAX-ACCESS not-accessible
            STATUS current
            DESCRIPTION
                "A unique identifier of a server address. When
                multiple addresses are configured and if one 
                address isn't reachable, then another can
                be tried.
                "
            ::= { zhoneIuaServerEntry 1 }

        
--  
        -- 1.3.6.1.4.1.5504.4.15.1.1.1.1.2
        zhoneIuaServerRowStatus OBJECT-TYPE
            SYNTAX ZhoneRowStatus
            MAX-ACCESS read-create
            STATUS current
            DESCRIPTION
                "Row Status is used to create, modify or delete an entry."
            ::= { zhoneIuaServerEntry 2 }

        
-- 
        -- 1.3.6.1.4.1.5504.4.15.1.1.1.1.3
        zhoneIuaServerAddress OBJECT-TYPE
            SYNTAX InetAddress
            MAX-ACCESS read-create
            STATUS current
            DESCRIPTION
                "This object specifies the address of IUA server."
            ::= { zhoneIuaServerEntry 3 }

        
-- 
        -- 1.3.6.1.4.1.5504.4.15.1.1.1.1.4
        zhoneIuaServerPortNumber OBJECT-TYPE
            SYNTAX Integer32 (1..65535)
            MAX-ACCESS read-create
            STATUS current
            DESCRIPTION
                "Specifies the port number fro IUA server"
            DEFVAL { 9900 }
            ::= { zhoneIuaServerEntry 4 }

        
    
    END

--
-- comIua.mib
--

--
-- zhoneRadio-TC.mib
-- MIB generated by MG-SOFT Visual MIB Builder Version 2.1 Build 205
-- Wednesday, July 11, 2001 at 12:47:59
--

-- zhoneRadio-TC - Textual conventions for SkyZhone radio family.
-- 
-- On the Use of ifTable for Radio Layer as table indices
-- 
--         ifTable Object          Use for Radio Layer
-- ======================================================================
--         ifIndex                 Interface Index,
--         ifDescr                 'Zhone Wireless Transport Radio'
--         ifType                  propWirelessP2P (157) = Proprietary point-to-point wireless interface
--         ifMtu                   Not applicable
--         ifSpeed                 For SkyZhone45 ifSpeed = 45888000
--                                 For SkyZhone155 ifSpeed = 157500000 (est)
--         ifPhysAddress           0
--         ifAdminStatus           up(1), down(2), testing(3)
--         ifOperStatus            up(1) - operating within normal margins
--                                  down(2) - operating outside normal margins
--                                  testing(3) - maintenance mode, antenna alignment
--                                  unknown(4) - NOT SUPPORTED
--                                  dormant(5) - up but without a payload 
--                                  lowerLayerDown(7) - NOT SUPPORTED
--         ifLastChange            supported
--         ifInOctets              NOT SUPPORTED
--         ifInUcastPkts           NOT SUPPORTED
--         ifInNUcastPkts          NOT SUPPORTED-- 
--         ifInDiscards            NOT SUPPORTED
--         ifInErrors              NOT SUPPORTED
--         ifInUnknownProtos       NOT SUPPORTED
--         ifOutOctets             NOT SUPPORTED
--         ifOutUcastPkts          NOT SUPPORTED
--         ifOutNUcastPkts         NOT SUPPORTED-- 
--         ifOutDiscards           NOT SUPPORTED
--         ifOutErrors             NOT SUPPORTED
--         ifOutQLen               NOT SUPPORTED-- 
--         ifSpecific              NOT SUPPORTED -- 
-- 
-- 

    ZHONE-RADIO-TC-MIB DEFINITIONS ::= BEGIN

        IMPORTS 
            Integer32            
                FROM SNMPv2-SMI            
            TEXTUAL-CONVENTION            
                FROM SNMPv2-TC;
    
    
--
-- Textual conventions
--
    
        SinglePrecisionFloatingPoint ::= TEXTUAL-CONVENTION
            STATUS current
            DESCRIPTION
                "IEEE 754 Single Precision Floating Point format:
                -------------------------------------------------
                
                Represented as 32-bit float numbered from 0 to 31, left to right. 
                The first bit is the sign bit, S, the next eight bits are exponent 
                bits, E, and the final 23 bits are the fraction F:
                
                  S EEEEEEEE FFFFFFFFFFFFFFFFFFFFFFF
                  0 1      8 9                    31
                
                The value V represented by the word may be determined as follows:
                
                     If E=255 and F is nonzero, then V=NaN (Not a number) 
                     If E=255 and F is zero and S is 1, then V=-Infinity 
                     If E=255 and F is zero and S is 0, then V=Infinity 
                     If 0<E<255 then V=(-1)**S * 2 ** (E-127) * (1.F) where 1.F 
                is intended to represent the binary number created by 
                prefixing F with an implicit leading 1 and a binary point. 
                     If E=0 and F is nonzero, then V=(-1)**S * 2 ** (-126) * (0.F) 
                These are unnormalized values. 
                     If E=0 and F is zero and S is 1, then V=-0 
                     If E=0 and F is zero and S is 0, then V=0 
                
                In particular,
                
                  0 00000000 00000000000000000000000 = 0
                  1 00000000 00000000000000000000000 = -0
                
                  0 11111111 00000000000000000000000 = Infinity
                  1 11111111 00000000000000000000000 = -Infinity
                
                  0 11111111 00000100000000000000000 = NaN
                  1 11111111 00100010001001010101010 = NaN
                
                  0 10000000 00000000000000000000000 = +1 * 2**(128-127) * 1.0 = 2
                  0 10000001 10100000000000000000000 = +1 * 2**(129-127) * 1.101 = 6.5
                  1 10000001 10100000000000000000000 = -1 * 2**(129-127) * 1.101 = -6.5
                
                  0 00000001 00000000000000000000000 = +1 * 2**(1-127) * 1.0 = 2**(-126)
                  0 00000000 10000000000000000000000 = +1 * 2**(-126) * 0.1 = 2**(-127) 
                
                  0 00000000 00000000000000000000001  
                                        = +1 * 2**(-126) * 0.00000000000000000000001 
                                        = 2**(-149)  (Smallest positive value)
                "
            SYNTAX Integer32
            
        SkyZhoneRadioChannelNumber ::= TEXTUAL-CONVENTION
            DISPLAY-HINT
                "Optimally, the customer should be allowed to use channel numbers 
                or frequencies for channel selection. (A ZMS/NMS preference.) 
                Minimally the user should use channel numbers and be able to see
                a table of channel to frequency assignments appropriate to
                the node they are configuring."
            STATUS current
            DESCRIPTION
                "SkyZhoneRadioChannelNumber for SkyZhone45
                ----------------------------------------------
                Each SkyZhone45 pair is comprised 
                of an A type ODU, which transmits at frequencies
                5735Mhz through 5815Mhz, and a B type ODU,
                which transmits at frequencies 5260Mhz through 5340Mhz.
                Mapping from channel to exact frequency is shown below.
                
                Channel A's receive channel is Channel B's transmit frequency.
                Channel B's recieve channel is Channel A's transmit frequency.
                
                There are 17 available channels for the A type transmitter and 17 channels 
                for the B type transmitter.
                
                
                The following rules apply:  
                Primary and secondary frequencies may NOT use the same channel.
                
                Channels are assigned in fixed pairs.  There are only 17 total possible
                permutations of frequency assignments for the primary or secondary channel.
                
                 
                               Selected channel  A transmits at    B transmits at
                                ----------------  --------------    --------------
                                0                   none                none
                                1                   5735Mhz             5260Mhz 
                                2                   5740Mhz             5265Mhz 
                                3                   5745Mhz             5270Mhz 
                                4                   5750Mhz             5275Mhz 
                                5                   5755Mhz             5280Mhz 
                                6                   5760Mhz             5285Mhz 
                                7                   5765Mhz             5290Mhz 
                                8                   5770Mhz             5295Mhz 
                                9                   5775Mhz             5300Mhz 
                                10                  5780Mhz             5305Mhz 
                                11                  5785Mhz             5310Mhz 
                                12                  5790Mhz             5315Mhz 
                                13                  5795Mhz             5320Mhz 
                                14                  5800Mhz             5325Mhz 
                                15                  5805Mhz             5330Mhz 
                                16                  5810Mhz             5335Mhz 
                                17                  5815Mhz             5340Mhz
                
                The system normally transmits at the primary frequencies.
                If problems occur the system may automatically switch to 
                the secondary frequencies.
                
                Default primary channel value: 8
                Default secondary channel value: 0
                
                
                
                SkyZhoneRadioChannelNumber for 23Ghz families (155s, 8x, etc.)
                -------------------------------------------------------------------
                Channel numbers cannot be entered directly for the 23GHz family.
                Instead, the interface expects frequencies to be entered.
                
                "
            SYNTAX Integer32
            
        SkyZhoneOperatingFrequency ::= TEXTUAL-CONVENTION
            STATUS current
            DESCRIPTION
                "SkyZhoneOperatingFrequencies for 5.7GHz families (SkyZhone45, etc.)
                -------------------------------------------------------------------
                Not used for this family.  Frequencies are always derived from 
                channel number.
                
                SkyZhoneOperatingFrequencies for 23GHz families (155s, 8x, etc.)
                -------------------------------------------------------------------
                SinglePrecisionFloatingPoint representation of radio operating frequency.
                
                Channel numbers cannot be entered directly for the 23GHz family.
                Instead, the interface expects frequencies to be entered.
                The 23Ghz band (used by SkyZhone 155 and 8) does not adapt well 
                to general channel numbers.  UK has a channel plan, Germany a different 
                one, France a different one, Mexico a different one, etc.
                Channel 1, for example, means a different frequency in each plan.  
                There is no global reference, and we don't want to have to change 
                software everytime a new channel plan comes in from a new customer.  
                So we will let them Tx frequencies (in MHz) directly. 
                The Rx frequency is not written by the user, but is calculated using
                the entered Tx frequency and the channel separation.  Basically channel
                separation is how far apart the tx and rx are spaced.  Every coutnry 
                we know of uses one of 3 channel separations.   
                The rx frequency is just the sum or difference of the tx freq and the 
                separation (depending on whether you are the A or B side of the link). 
                
                It is certainly possible that ZMS or any other NMS could provide an 
                interface which allows users to select a channel according to the local
                channel plan of the unit and convert it to a frequency.  If this is desired,
                a mapping of channel to frequency is needed for the site, and as mentioned
                already, this depends upon the prevailing channel plan of the country
                where the unit is installed.
                
                Some channel plans are linear - that is calculable and evenly spaced.
                Others (e.g., French) are not linear, and so each channel to frequency 
                association would be a unique vector in a table.
                
                Also note that only 3.5MHz wide channel spacings and their multiples
                (7Mhz, 14Mhz, 28MHz) are supported at this time.  This rules out the North
                American 23GHz band (which uses 2.5MHz spacings).
                
                The following list of channel plans is by no means complete:
                
                Mexico Channels ( MHz)  
                -----------------------     
                Channel Lower   Upper 
                2	21269.5	22501.5
                3	21297.5	22529.5
                4	21325.5	22557.5
                5	21353.5	22585.5
                6	21381.5	22613.5
                7	21409.5	22641.5
                8	21437.5	22669.5
                9	21465.5	22697.5
                10	21493.5	22725.5
                11	21521.5	22753.5
                12	21549.5	22781.5
                13	21577.5	22809.5
                14	21605.5	22837.5
                15	21633.5	22865.5
                16	21661.5	22893.5
                17	21689.5	22921.5
                18	21717.5	22949.5
                19	21745.5	22977.5
                20	21773.5	23005.5
                21	21801.5	23033.5
                22	21829.5	23061.5
                23	21857.5	23089.5
                24	21885.5	23117.5
                25	21913.5	23145.5
                26	21941.5	23173.5
                27	21969.5	23201.5
                28	21997.5	23229.5
                29	22025.5	23257.5
                30	22053.5	23285.5
                31	22081.5	23313.5
                32	22109.5	23341.5
                33	22137.5	23369.5
                34	22165.5	23397.5
                35	22193.5	23425.5
                36	22221.5	23453.5
                37	22249.5	23481.5
                38	22277.5	23509.5
                39	22305.5	23537.5
                40	22333.5	23565.5
                	21213.5	22445.5
                
                UK Channels ( MHz)  
                --------------------     
                Channel Lower   Upper 
                1	21238	22470
                2	21266	22498
                3	21294	22526
                4	21322	22554
                5	21350	22582
                6	21378	22610
                7	21406	22638
                8	21434	22666
                9	21462	22694
                10	21490	22722
                11	21518	22750
                12	21546	22778
                13	21574	22806
                14	21602	22834
                15	21630	22862
                16	21658	22890
                17	21686	22918
                18	21714	22946
                19	21742	22974
                20	21770	23002
                21	21798	23030
                22	21826	23058
                23	21854	23086
                24	21882	23114
                25	21910	23142
                26	21938	23170
                27	21966	23198
                28	21994	23226
                29	22022	23254
                30	22050	23282
                31	22078	23310
                32	22106	23338
                33	22134	23366
                34	22162	23394
                35	22190	23422
                36	22218	23450
                37	22246	23478
                38	22274	23506
                39	22302	23534
                40	22330	23562
                
                Note: values are to take the form SinglePrecisionFloatingPoint,
                as described in the TEXTUAL-CONVENTION above.  The SYNTAX would
                have been SinglePrecisionFloatingPoint rather than Integer32, if
                the Pahrser (internal Zhone tool) would have been smart enough 
                to use it.  
                "
            SYNTAX Integer32
            
        SkyZhoneScientificNotation ::= TEXTUAL-CONVENTION
            STATUS current
            DESCRIPTION
                "Textual method to enter and display floating point numbers.
                Actually three different formats are acceptable:
                
                 
                   [+/-]WXYZ    -  where WXYZ is a 1 to 15 digit number
                   [+/-]WXYZ.0  -  where WXYZ is a 1 to 15 digit number
                   [+/-]W.XYZ [+/-]Ejk  
                                -  where W.XYZ is a 1 to 15 digit floating point number
                                and jk is an integer.  
                                White space between elements is OK.
                
                For example, the number 1324.0 can be represented as:
                        1234
                        1234.0
                        1.234E4
                        1.234 E4
                
                A radio frequency of 23.456Ghz, for example, may be represented as
                
                        23.456 E9
                        23456  E6
                        23456000 E3
                        23456000000
                        23456000000.0
                        
                A BER threshold of 2.5 errors per 10,000 bits can be represented as 
                
                        2.5 E-4
                        2.5E-4
                        2.5 E -4           "
            SYNTAX OCTET STRING (SIZE (0..32))
            
    
    END

--
-- zhoneRadio-TC.mib
--

-- *****************************************************************
-- STACK-MIB.mib 
--
-- 2007-5-29 9:54
-- 
--
-- Copyright (c) 1985-2007 by ZTE Corp.
-- All rights reserved.
-- *****************************************************************
--
STACK-MIB DEFINITIONS ::= BEGIN

IMPORTS
        MODULE-IDENTITY, OBJECT-TYPE, IpAddress, TimeTicks,
        Integer32, NOTIFICATION-TYPE,enterprises
                FROM SNMPv2-SMI
        MacAddress, DisplayString
                FROM SNMPv2-TC
        MODULE-COMPLIANCE, OBJECT-GROUP
                FROM SNMPv2-CONF;

    zte OBJECT IDENTIFIER ::= { enterprises 3902 }
    zxr10 OBJECT IDENTIFIER ::= { zte 3}
    
stack MODULE-IDENTITY
        LAST-UPDATED "200705280000Z"
        ORGANIZATION "ZTE Corp."
        CONTACT-INFO
               ""

        DESCRIPTION 
                ""
        REVISION "200405140000Z"
        DESCRIPTION
                ""
               
        ::= { zxr10 300 }  
        
MasterSlaveDataSynStatus ::= INTEGER
                      {
                        masterinit(11),
                        backinit(12),
                        memberinit(13),
                        masteridle(20),
                        backreg(40),
                        interaction(50),
                        masterbatchsync(60),
                        backbatchsync(70),
                        masterrealsync(80),
                        backrealsync(90),
                        mastergr(100)
                      } 
                      
StkDeviceStatus ::= INTEGER
                      {
                        master(0),
                        slave(1),
                        member(2)
                      }

-- stackMIBobjects
systemGrp           OBJECT IDENTIFIER ::= { stack 1 }
-- textual conventions

VendorIdType ::= OCTET STRING (SIZE (3))
        -- The vendor ID portion of a MacAddress (first 3 octets
        -- of the 6-octet MAC address)



-- the system group

-- Implementation of the system group is current for all Cisco Workgroup
-- Stack products.

sysNetMask OBJECT-TYPE
        SYNTAX        IpAddress
        MAX-ACCESS    read-write
        STATUS        deprecated
        DESCRIPTION   "System network mask address."
        ::= { systemGrp 1 }

sysManagIf OBJECT-TYPE
        SYNTAX  DisplayString (SIZE (0..255))          
        MAX-ACCESS  read-write       
        STATUS  current                                
        DESCRIPTION   "System management Interface of Stack device."
        ::= { systemGrp 2 } 

sysMacAddr OBJECT-TYPE
        SYNTAX        MacAddress -- OCTET STRING (SIZE (6))        
        MAX-ACCESS    read-write
        STATUS        current
        DESCRIPTION   "System mac address."
        ::= { systemGrp 3 }

sysMacChagAgingTime  OBJECT-TYPE
        SYNTAX   Integer32
        MAX-ACCESS  read-write
        STATUS  current
        DESCRIPTION
            "After the aging time system mac address must be changed."
        ::= { systemGrp 4 }

sysLastchagConfigTime  OBJECT-TYPE
        SYNTAX   DisplayString (SIZE (0..50))
        MAX-ACCESS  read-only
        STATUS  current
        DESCRIPTION
            "The lastest time when the stack system changed the configuration."
        ::= { systemGrp 5 }

sysMasterSlaveDataSynStatus OBJECT-TYPE    
        SYNTAX        MasterSlaveDataSynStatus        
        MAX-ACCESS    read-only
        STATUS        current
        DESCRIPTION   "System master and slave device data synchronization status
                      11: masterinit
                      12: backinit
                      13: memberinit
                      20: masteridle
                      40: backreg
                      50: interaction
                      60: masterbatchsync
                      70: backbatchsync
                      90: backrealsync
                      100:mastergr."
        ::= { systemGrp 6 }

sysManagIpAddr OBJECT-TYPE
        SYNTAX  IpAddress           
        MAX-ACCESS  read-write       
        STATUS  current                                
        DESCRIPTION                                    
            "Management IP Address of Stack device."
        ::= { systemGrp 7 }
                         
sysStkDeviceInfoTable OBJECT-TYPE
        SYNTAX  SEQUENCE OF SysStkDeviceInfoEntry
        MAX-ACCESS  not-accessible
        STATUS  current
        DESCRIPTION
            "A list of system member information."
        ::= { stack 2 } 
        
sysStkDeviceInfoEntry OBJECT-TYPE
        SYNTAX  SysStkDeviceInfoEntry
        MAX-ACCESS  not-accessible
        STATUS  current
        DESCRIPTION
            "An entry to system member information table."
        INDEX  { sysStkDeviceID }
        ::= { sysStkDeviceInfoTable 1 }  
        
SysStkDeviceInfoEntry ::=
     SEQUENCE {
         sysStkDeviceID
             Integer32,
         sysStkDeviceType
             Integer32,
         sysMemDeviceMacAddr
             MacAddress,
         sysMemUpTime
             TimeTicks,
         sysStkDeviceStatus
             StkDeviceStatus                                               
}               

sysStkDeviceID  OBJECT-TYPE
        SYNTAX   Integer32
        MAX-ACCESS  read-only
        STATUS  current
        DESCRIPTION
            "Stack member device ID."
        ::= { sysStkDeviceInfoEntry 1 }  

sysStkDeviceType  OBJECT-TYPE
        SYNTAX   Integer32
        MAX-ACCESS  read-only
        STATUS  current
        DESCRIPTION
            "Stack member device ID."
        ::= { sysStkDeviceInfoEntry 2 }
         
sysMemDeviceMacAddr  OBJECT-TYPE
        SYNTAX   MacAddress
        MAX-ACCESS  read-only
        STATUS  current
        DESCRIPTION
            "Stack member device mac address."
        ::= { sysStkDeviceInfoEntry 3 }

        
sysMemUpTime  OBJECT-TYPE
        SYNTAX   TimeTicks
        MAX-ACCESS  read-only
        STATUS  current
        DESCRIPTION
            "Stack member device running time."
        ::= { sysStkDeviceInfoEntry 4 } 
                
sysStkDeviceStatus OBJECT-TYPE
        SYNTAX        StkDeviceStatus        
        MAX-ACCESS    read-only
        STATUS        current
        DESCRIPTION   "System device status, such as: member device, master device and slave device 
                      0: master device
                      1: slave device
                      2: member device."
        ::= { sysStkDeviceInfoEntry 5 }               
        
        
zxr10StackStatTable OBJECT-TYPE 
        SYNTAX  SEQUENCE OF Zxr10StackStatEntry     
        MAX-ACCESS    not-accessible
        STATUS        current
        DESCRIPTION   "A list of the stack statistic information,included cpu utility and memory utility."
        ::= { stack 3 }

zxr10StackStatEntry OBJECT-TYPE
        SYNTAX  Zxr10StackStatEntry
        MAX-ACCESS  not-accessible
        STATUS  current
        DESCRIPTION
            "An entry to the stack statistic information table."
        INDEX  { zxr10StkDeviceID }
        ::= { zxr10StackStatTable 1 } 

Zxr10StackStatEntry ::=
     SEQUENCE {
         zxr10StkDeviceID
             Integer32,
         zxr10StkDeviceMacAddr
             MacAddress,        
         zxr10StkDeviceCpuUtility5s
             DisplayString,
         zxr10StkDeviceCpuUtility1m
             DisplayString,
         zxr10StkDeviceCpuUtility5m
             DisplayString, 
         zxr10StkDeviceMemUtility
             DisplayString                                           
}

zxr10StkDeviceID  OBJECT-TYPE
        SYNTAX   Integer32
        MAX-ACCESS  read-only
        STATUS  current
        DESCRIPTION
            "Stack system device index."
        ::= { zxr10StackStatEntry 1 } 

zxr10StkDeviceMacAddr  OBJECT-TYPE
        SYNTAX   MacAddress
        MAX-ACCESS  read-only
        STATUS  current
        DESCRIPTION
            "Stack system device mac address."
        ::= { zxr10StackStatEntry 2 }
 
zxr10StkDeviceCpuUtility5s  OBJECT-TYPE
        SYNTAX   DisplayString
        MAX-ACCESS  read-only
        STATUS  current
        DESCRIPTION
            "Stack system device cup utility described by percent( 5 seconds)."
        ::= { zxr10StackStatEntry 3 }

zxr10StkDeviceCpuUtility1m  OBJECT-TYPE
        SYNTAX   DisplayString
        MAX-ACCESS  read-only
        STATUS  current
        DESCRIPTION
            "Stack system device cup utility described by percent( 1 minutes)."
        ::= { zxr10StackStatEntry 4 }
        
zxr10StkDeviceCpuUtility5m  OBJECT-TYPE
        SYNTAX   DisplayString
        MAX-ACCESS  read-only
        STATUS  current
        DESCRIPTION
            "Stack system device cup utility described by percent( 5 minutes)."
        ::= { zxr10StackStatEntry 5 }
               
zxr10StkDeviceMemUtility  OBJECT-TYPE
        SYNTAX   DisplayString
        MAX-ACCESS  read-only
        STATUS  current
        DESCRIPTION
            "Stack system device memory utility."
        ::= { zxr10StackStatEntry 6 }
        
END

--  ******************************************************
--  $Id: trace.mib 2008-03$
--
--  zesr.mib: ZXR10 Access List MIB file
--  
--  Nov. 2008, Zhong Yan
--   
--  Copyright(c) 2008 by ZTE Corporaton
--  All rights reservered
--  ******************************************************
TRACE-MIB DEFINITIONS ::= BEGIN

   IMPORTS
       MODULE-IDENTITY, OBJECT-TYPE,
       Integer32,Unsigned32,Counter32,IpAddress,
       enterprises,NOTIFICATION-TYPE       FROM SNMPv2-SMI
       DisplayString,MacAddress,TruthValue FROM SNMPv2-TC
       InetAddress, InetAddressType,
       InetAddressPrefixLength             FROM INET-ADDRESS-MIB;

    trace MODULE-IDENTITY
        LAST-UPDATED "200811240000Z"
        ORGANIZATION "ZTE"
        CONTACT-INFO
               ""
        DESCRIPTION 
                ""
        REVISION "200811240000Z"
        DESCRIPTION
                ""
        ::= { zxr10 318 }
          
    zxr10LspTrace OBJECT IDENTIFIER ::= { trace 1 }
    
    zxr10MacTrace OBJECT IDENTIFIER ::= { trace 2 }
    
    lspTraceNotifications OBJECT IDENTIFIER ::= { zxr10LspTrace 4 }
    
    macTraceNotifications OBJECT IDENTIFIER ::= { zxr10MacTrace 4 }
        
    zte OBJECT IDENTIFIER ::= { enterprises 3902 }
    zxr10 OBJECT IDENTIFIER ::= { zte 3 }
    
    LspTraceType ::= INTEGER
                 {
                     ldp(0),
                     rsvp-te(1),
                     vccv(2)
                 }
                  
    LspTraceIfOption ::= INTEGER
                 {
                    none(0),
                    option(1)
                 }
                 
    TraceRosStatus ::= INTEGER
                 {
                    not-active(1),
                    start-trace(2),
                    trace-processing(3),
                    trace-completed(4)
                 }

    TraceHopsResult ::= INTEGER
                 {
                    valid(0),
                    success(1),
                    downstream-router-but-not-target(2),
                    request-not-transmitted(3),
                    timeout(4),
                    unreachable(5)
                 }
                     
    HopType ::= INTEGER
                 {
                    ingress(0),
                    downstream(1),
                    egress(2)
                 }
                 
    MacTraceIfPeOption ::= INTEGER
                 {
                    ce(0),
                    pe(1)
                 }

--  ******************************************************
--                Lsp Trace Control Table
--  ******************************************************                               
    zxr10LspTraceCtlTable OBJECT-TYPE
              SYNTAX  SEQUENCE OF Zxr10LspTraceCtlEntry
              MAX-ACCESS  not-accessible
              STATUS  current
              DESCRIPTION
                      "the description of lsp trace infomation."
               ::= { zxr10LspTrace 1 } 
              
    zxr10LspTraceCtlEntry  OBJECT-TYPE
              SYNTAX  Zxr10LspTraceCtlEntry
              MAX-ACCESS  not-accessible
              STATUS  current
              DESCRIPTION
                      ""
              INDEX { zxr10LspTraceCtlSerial }
              ::= { zxr10LspTraceCtlTable 1 }
              
    Zxr10LspTraceCtlEntry ::= SEQUENCE {
              zxr10LspTraceCtlSerial              Integer32,
              zxr10LspTraceCtlTraceType           LspTraceType,
              zxr10LspTraceCtlLdpPrefixType       InetAddressType,
              zxr10LspTraceCtlLdpPrefix           InetAddress,
              zxr10LspTraceCtlLdpPrefixLength     InetAddressPrefixLength,
              zxr10LspTraceCtlMplsTeTunnelNumber  Integer32,
              zxr10LspTraceCtlPwDestAddrType      InetAddressType,
              zxr10LspTraceCtlPwDestAddr          InetAddress,
              zxr10LspTraceCtlPwVcId              Counter32,
              zxr10LspTraceCtlPwTTL               Integer32,
              zxr10LspTraceCtlIfOption            LspTraceIfOption,
              zxr10LspTraceCtlTimeOut             Integer32,
              zxr10LspTraceCtlTTL                 Integer32,
              zxr10LspTraceCtlTrapOncompletion    TruthValue,
              zxr10LspTraceRosStatus              TraceRosStatus,
              zxr10LspTraceEntryOwner             DisplayString,
              zxr10LspTraceCtlPwName              DisplayString,
              zxr10LspTraceCtlVCTTL               Integer32
        }
    
    zxr10LspTraceCtlSerial OBJECT-TYPE
              SYNTAX  Integer32
              MAX-ACCESS  read-only
              STATUS  current
              DESCRIPTION
                      ""
              ::= { zxr10LspTraceCtlEntry 1 }
                   
    zxr10LspTraceCtlTraceType OBJECT-TYPE
              SYNTAX  LspTraceType
              MAX-ACCESS  read-write
              STATUS  current
              DESCRIPTION
                      "lsp trace type (0:ldp,1:rsvp-te,2:vccv)"
              ::= { zxr10LspTraceCtlEntry 2 }
              
    zxr10LspTraceCtlLdpPrefixType  OBJECT-TYPE
              SYNTAX     InetAddressType
              MAX-ACCESS read-write
              STATUS     current
              DESCRIPTION
                  "The type of the zxr10LspTraceCtlLdpPrefix, as defined
                  in the InetAddress MIB."
              ::= { zxr10LspTraceCtlEntry 15 }
                    
    zxr10LspTraceCtlLdpPrefix OBJECT-TYPE
              SYNTAX  InetAddress
              MAX-ACCESS  read-write
              STATUS  current
              DESCRIPTION
                      "ldp prefix"
              ::= { zxr10LspTraceCtlEntry 3 }

    zxr10LspTraceCtlLdpPrefixLength OBJECT-TYPE
              SYNTAX  InetAddressPrefixLength
              MAX-ACCESS  read-write
              STATUS  current
              DESCRIPTION
                      "ldp prefix length"
              ::= { zxr10LspTraceCtlEntry 4 }
              
    zxr10LspTraceCtlMplsTeTunnelNumber OBJECT-TYPE
              SYNTAX  Integer32 (1..8192)
              MAX-ACCESS  read-write
              STATUS  current
              DESCRIPTION
                      "tunnel number"
              ::= { zxr10LspTraceCtlEntry 5 }
              
    zxr10LspTraceCtlPwDestAddrType  OBJECT-TYPE
              SYNTAX     InetAddressType
              MAX-ACCESS read-write
              STATUS     current
              DESCRIPTION
                  "The type of the zxr10LspTraceCtlPwDestAddr, as defined
                  in the InetAddress MIB."
              ::= { zxr10LspTraceCtlEntry 16 }

    zxr10LspTraceCtlPwDestAddr OBJECT-TYPE
              SYNTAX  InetAddress
              MAX-ACCESS  read-write
              STATUS  current
              DESCRIPTION
                      "pw peer address"
              ::= { zxr10LspTraceCtlEntry 6 }

    zxr10LspTraceCtlPwVcId OBJECT-TYPE
              SYNTAX  Counter32
              MAX-ACCESS  read-write
              STATUS  current
              DESCRIPTION
                      "pw vcid"
              ::= { zxr10LspTraceCtlEntry 7 }

    zxr10LspTraceCtlPwTTL OBJECT-TYPE
              SYNTAX  Integer32 (1..255)
              MAX-ACCESS  read-write
              STATUS  current
              DESCRIPTION
                      "pw label ttl"   
              DEFVAL  { 1 }
              ::= { zxr10LspTraceCtlEntry 8 }
                                     
    zxr10LspTraceCtlIfOption OBJECT-TYPE
              SYNTAX  LspTraceIfOption
              MAX-ACCESS  read-write
              STATUS  current
              DESCRIPTION
                      "if select option,default:none"
              ::= { zxr10LspTraceCtlEntry 9 }
              
    zxr10LspTraceCtlTimeOut OBJECT-TYPE
              SYNTAX  Integer32 (1..60)
              MAX-ACCESS  read-write
              STATUS  current
              DESCRIPTION
                      "timeout,default:3"
              ::= { zxr10LspTraceCtlEntry 10 }
              
    zxr10LspTraceCtlTTL OBJECT-TYPE
              SYNTAX  Integer32 (1..255)
              MAX-ACCESS  read-write
              STATUS  current
              DESCRIPTION
                      "ttl,default:30"
              ::= { zxr10LspTraceCtlEntry 11 }
              
    zxr10LspTraceCtlTrapOncompletion OBJECT-TYPE
              SYNTAX  TruthValue
              MAX-ACCESS  read-write
              STATUS  current
              DESCRIPTION
                      "if trap"
              ::= { zxr10LspTraceCtlEntry 12 }

    zxr10LspTraceRosStatus OBJECT-TYPE
              SYNTAX  TraceRosStatus
              MAX-ACCESS  read-write
              STATUS  current
              DESCRIPTION
                      ""
              ::= { zxr10LspTraceCtlEntry 13 }
              
    zxr10LspTraceEntryOwner OBJECT-TYPE
              SYNTAX  DisplayString
              MAX-ACCESS  read-write
              STATUS  current
              DESCRIPTION
                      ""
              ::= { zxr10LspTraceCtlEntry 14 }
              
    zxr10LspTraceCtlPwName OBJECT-TYPE
              SYNTAX   DisplayString(SIZE(0..63))
              MAX-ACCESS  read-write
              STATUS  current
              DESCRIPTION
                  "Name specified for each configured MPLS L2VPN PW."
              ::= { zxr10LspTraceCtlEntry 17 }
        
    zxr10LspTraceCtlVCTTL OBJECT-TYPE
              SYNTAX  Integer32 (1..255)
              MAX-ACCESS  read-write
              STATUS  current
              DESCRIPTION
                  "Optional parameter for Pseudo-wire trace, it specified TTL
                  for the trace. If TTL is not specified, the trace will not stop
                  until reaching the destination LSR."
              ::= { zxr10LspTraceCtlEntry 18 }

-- *******************************************************
--               Lsp Trace Results Table
-- *******************************************************
    zxr10LspTraceResultsTable OBJECT-TYPE  
              SYNTAX  SEQUENCE OF Zxr10LspTraceResultsEntry
              MAX-ACCESS  not-accessible
              STATUS  current
              DESCRIPTION
                      "the description of lsp trace results infomation"
               ::= { zxr10LspTrace 2 } 
              
    zxr10LspTraceResultsEntry  OBJECT-TYPE
              SYNTAX  Zxr10LspTraceResultsEntry
              MAX-ACCESS  not-accessible
              STATUS  current
              DESCRIPTION
                      ""
              INDEX  { zxr10LspTraceResultsSerial }
              ::= { zxr10LspTraceResultsTable 1 }
              
    Zxr10LspTraceResultsEntry ::= SEQUENCE {
              zxr10LspTraceResultsSerial                 Integer32,
              zxr10LspTraceResultsCurHopCount            Integer32,
              zxr10LspTraceResultsEntryOwner             DisplayString    
              }       
                    
    zxr10LspTraceResultsSerial OBJECT-TYPE
              SYNTAX  Integer32
              MAX-ACCESS  read-only
              STATUS  current
              DESCRIPTION
                      ""
              ::= { zxr10LspTraceResultsEntry 1 }

    zxr10LspTraceResultsCurHopCount OBJECT-TYPE
              SYNTAX  Integer32
              MAX-ACCESS  read-only
              STATUS  current
              DESCRIPTION
                      "valid hops count"
              ::= { zxr10LspTraceResultsEntry 2 }

    zxr10LspTraceResultsEntryOwner OBJECT-TYPE
              SYNTAX  DisplayString
              MAX-ACCESS  read-only
              STATUS  current
              DESCRIPTION
                      ""
              ::= { zxr10LspTraceResultsEntry 3 }
                
-- *******************************************************
--               Lsp Trace Hops Table
-- *******************************************************
    zxr10LspTraceHopsTable OBJECT-TYPE  
              SYNTAX  SEQUENCE OF zxr10LspTraceHopsEntry
              MAX-ACCESS  not-accessible
              STATUS  current
              DESCRIPTION
                      "the description of lsp trace hops infomation."
               ::= { zxr10LspTrace 3 } 
                     
    zxr10LspTraceHopsEntry  OBJECT-TYPE
              SYNTAX  zxr10LspTraceHopsEntry
              MAX-ACCESS  not-accessible
              STATUS  current
              DESCRIPTION
                      ""
              INDEX  { zxr10LspTraceHopsSerial, zxr10LspTraceHopsHopIndex }
              ::= { zxr10LspTraceHopsTable 1 }

    zxr10LspTraceHopsEntry ::= SEQUENCE {
              zxr10LspTraceHopsSerial           Integer32,
              zxr10LspTraceHopsHopIndex         Integer32, 
              zxr10LspTraceHopsResultValid      TraceHopsResult,                    
              zxr10LspTraceHopsType             HopType,
              zxr10LspTraceHopsAddrType         InetAddressType,
              zxr10LspTraceHopsAddr             InetAddress,
              zxr10LspTraceHopsLabel            Integer32,
              zxr10LspTraceHopsMtu              Integer32,
              zxr10LspTraceHopsRtt              Integer32
              }       

    zxr10LspTraceHopsSerial OBJECT-TYPE
              SYNTAX  Integer32
              MAX-ACCESS  read-only
              STATUS  current
              DESCRIPTION
                      ""
              ::= { zxr10LspTraceHopsEntry 1 }
                     
    zxr10LspTraceHopsHopIndex OBJECT-TYPE
              SYNTAX  Integer32
              MAX-ACCESS  read-only
              STATUS  current
              DESCRIPTION
                      "Hop index"
              ::= { zxr10LspTraceHopsEntry 2 }

    zxr10LspTraceHopsResultValid OBJECT-TYPE
              SYNTAX  TraceHopsResult
              MAX-ACCESS  read-only
              STATUS  current
              DESCRIPTION
                  "Hop Result.
                   0:valid,
                   1:success,
                   2:downstream-router-but-not-target,
                   3:request-not-transmitted,
                   4:timeout,
                   5:unreachable"
              ::= { zxr10LspTraceHopsEntry 3 }
              
    zxr10LspTraceHopsType OBJECT-TYPE
              SYNTAX  HopType
              MAX-ACCESS  read-only
              STATUS  current
              DESCRIPTION
                      "Hop Type (0:Ingress,1:Downstream,2:Egress)"
              ::= { zxr10LspTraceHopsEntry 4 }
                     
    zxr10LspTraceHopsAddrType  OBJECT-TYPE
              SYNTAX     InetAddressType
              MAX-ACCESS read-only
              STATUS     current
              DESCRIPTION
                  "The type of the zxr10LspTraceHopsAddr, as defined
                  in the InetAddress MIB."
              ::= { zxr10LspTraceHopsEntry 9 }
                     
    zxr10LspTraceHopsAddr OBJECT-TYPE
              SYNTAX  InetAddress
              MAX-ACCESS  read-only
              STATUS  current
              DESCRIPTION
                      "Hop Address"
              ::= { zxr10LspTraceHopsEntry 5 }

    zxr10LspTraceHopsLabel OBJECT-TYPE
              SYNTAX  Integer32
              MAX-ACCESS  read-only
              STATUS  current
              DESCRIPTION
                      "Hop Label"
              ::= { zxr10LspTraceHopsEntry 6 }

    zxr10LspTraceHopsMtu OBJECT-TYPE
              SYNTAX  Integer32
              MAX-ACCESS  read-only
              STATUS  current
              DESCRIPTION
                      "Hop Mtu"
              ::= { zxr10LspTraceHopsEntry 7 }
                     
    zxr10LspTraceHopsRtt OBJECT-TYPE
              SYNTAX  Integer32
              MAX-ACCESS  read-only
              STATUS  current
              DESCRIPTION
                      "Hop Rtt"
              ::= { zxr10LspTraceHopsEntry 8 }

-- *******************************************************
--               Lsp Trace Result Trap Definitions
-- *******************************************************
    lspTraceTrapResult NOTIFICATION-TYPE
     OBJECTS  { zxr10LspTraceResultsSerial,
                zxr10LspTraceResultsCurHopCount,
                zxr10LspTraceResultsEntryOwner
              }
              STATUS  current
              DESCRIPTION
         "The newMaster trap indicates that the sending agent
         has transitioned to 'Master' state."
     ::= { lspTraceNotifications 1 }                                   

-- *******************************************************
--               Lsp Trace Hops Trap Definitions
-- *******************************************************
    lspTraceTrapHops NOTIFICATION-TYPE
     OBJECTS  { zxr10LspTraceHopsSerial,
                zxr10LspTraceHopsHopIndex,
                zxr10LspTraceHopsType,
                zxr10LspTraceHopsAddrType,
                zxr10LspTraceHopsAddr,
                zxr10LspTraceHopsLabel,
                zxr10LspTraceHopsMtu,
                zxr10LspTraceHopsRtt
              }
     STATUS  current
     DESCRIPTION
         "The newMaster trap indicates that the sending agent
         has transitioned to 'Master' state."
     ::= { lspTraceNotifications 2 }

--  ******************************************************
--                Mac Trace Control Table
--  ******************************************************                               
    zxr10MacTraceCtlTable OBJECT-TYPE
              SYNTAX  SEQUENCE OF Zxr10MacTraceCtlEntry
              MAX-ACCESS  not-accessible
              STATUS  current
              DESCRIPTION
                      "the description of mac trace infomation."
               ::= { zxr10MacTrace 1 } 
              
    zxr10MacTraceCtlEntry  OBJECT-TYPE
              SYNTAX  Zxr10MacTraceCtlEntry
              MAX-ACCESS  not-accessible
              STATUS  current
              DESCRIPTION
                      ""
              INDEX  { zxr10MacTraceCtlSerial }
              ::= { zxr10MacTraceCtlTable 1 }
              
    Zxr10MacTraceCtlEntry ::= SEQUENCE {
              zxr10MacTraceCtlSerial                    Integer32,
              zxr10MacTraceCtlDestMac                   MacAddress,
              zxr10MacTraceCtlIfPeOption                MacTraceIfPeOption,
              zxr10MacTraceCtlOutEtherIfIndex           Integer32,
              zxr10MacTraceCtlPwVcId                    Counter32,
              zxr10MacTraceCtlPeerAddress               IpAddress,
              zxr10MacTraceCtlVlanCount                 Integer32,
              zxr10MacTraceCtlInternalVlanId            Integer32,
              zxr10MacTraceCtlExternalVlanId            Integer32,
              zxr10MacTraceCtlTrapOncompletion          TruthValue,
              zxr10MacTraceCtlRosStatus                 TraceRosStatus,
              zxr10MacTraceCtlEntryOwner                DisplayString
          }      
    
    zxr10MacTraceCtlSerial OBJECT-TYPE
              SYNTAX  Integer32
              MAX-ACCESS  read-only
              STATUS  current
              DESCRIPTION
                      ""
              ::= { zxr10MacTraceCtlEntry 1 }
                   
    zxr10MacTraceCtlDestMac OBJECT-TYPE
              SYNTAX  MacAddress
              MAX-ACCESS  read-write
              STATUS  current
              DESCRIPTION
                      "destination mac address"
              ::= { zxr10MacTraceCtlEntry 2 }

    zxr10MacTraceCtlIfPeOption OBJECT-TYPE
              SYNTAX  MacTraceIfPeOption
              MAX-ACCESS  read-write
              STATUS  current
              DESCRIPTION
                      "if PE option (0:CE,1:PE)"
              ::= { zxr10MacTraceCtlEntry 3 }

    zxr10MacTraceCtlOutEtherIfIndex OBJECT-TYPE
              SYNTAX  Integer32
              MAX-ACCESS  read-write
              STATUS  current
              DESCRIPTION
                      "index of out interface on CE"
              ::= { zxr10MacTraceCtlEntry 4 }

    zxr10MacTraceCtlPwVcId OBJECT-TYPE
              SYNTAX  Counter32
              MAX-ACCESS  read-write
              STATUS  current
              DESCRIPTION
                      "pw vc id"
              ::= { zxr10MacTraceCtlEntry 5 }

    zxr10MacTraceCtlPeerAddress OBJECT-TYPE
              SYNTAX  IpAddress
              MAX-ACCESS  read-write
              STATUS  current
              DESCRIPTION
                      "Peer Address"
              ::= { zxr10MacTraceCtlEntry 6 }

    zxr10MacTraceCtlVlanCount OBJECT-TYPE
              SYNTAX  Integer32
              MAX-ACCESS  read-write
              STATUS  current
              DESCRIPTION
                      "vlan count"
              ::= { zxr10MacTraceCtlEntry 7 }

    zxr10MacTraceCtlInternalVlanId OBJECT-TYPE
              SYNTAX  Integer32
              MAX-ACCESS  read-write
              STATUS  current
              DESCRIPTION
                      "Internal VlanId"
              ::= { zxr10MacTraceCtlEntry 8 }

    zxr10MacTraceCtlExternalVlanId OBJECT-TYPE
              SYNTAX  Integer32
              MAX-ACCESS  read-write
              STATUS  current
              DESCRIPTION
                      "External VlanId"
              ::= { zxr10MacTraceCtlEntry 9 }

    zxr10MacTraceCtlTrapOncompletion OBJECT-TYPE
              SYNTAX  TruthValue
              MAX-ACCESS  read-write
              STATUS  current
              DESCRIPTION
                      "if trap"
              ::= { zxr10MacTraceCtlEntry 10 }

    zxr10MacTraceCtlRosStatus OBJECT-TYPE
              SYNTAX  TraceRosStatus
              MAX-ACCESS  read-write
              STATUS  current
              DESCRIPTION
                      ""
              ::= { zxr10MacTraceCtlEntry 11 }

    zxr10MacTraceCtlEntryOwner OBJECT-TYPE
              SYNTAX  DisplayString
              MAX-ACCESS  read-write
              STATUS  current
              DESCRIPTION
                      ""
              ::= { zxr10MacTraceCtlEntry 12 }
              
-- *******************************************************
--               Mac Trace Result Table
-- *******************************************************
    zxr10MacTraceHopsTable OBJECT-TYPE  
              SYNTAX  SEQUENCE OF Zxr10MacTraceHopsEntry
              MAX-ACCESS  not-accessible
              STATUS  current
              DESCRIPTION
                      "the description of mac trace hops infomation."
               ::= { zxr10MacTrace 2 } 
              
    zxr10MacTraceHopsEntry  OBJECT-TYPE
              SYNTAX  Zxr10MacTraceHopsEntry
              MAX-ACCESS  not-accessible
              STATUS  current
              DESCRIPTION
                      ""
              INDEX  { 
                        zxr10MacTraceHopsSerial
                     }
              ::= { zxr10MacTraceHopsTable 1 }
              
    Zxr10MacTraceHopsEntry ::=
              SEQUENCE {
                zxr10MacTraceHopsSerial
                    Integer32,
                zxr10MacTraceHopsResultValidHop0
                    TraceHopsResult,
                zxr10MacTraceHopsHostNameHop0
                    DisplayString,
                zxr10MacTraceHopsIfNameHop0
                    DisplayString,
                zxr10MacTraceHopsMacAddrHop0
                    MacAddress,
                zxr10MacTraceHopsResultValidHop1
                    TraceHopsResult,
                zxr10MacTraceHopsHostNameHop1
                    DisplayString,
                zxr10MacTraceHopsIfNameHop1
                    DisplayString,
                zxr10MacTraceHopsMacAddrHop1
                    MacAddress,
                zxr10MacTraceHopsResultValidHop2
                    TraceHopsResult,
                zxr10MacTraceHopsHostNameHop2
                    DisplayString,
                zxr10MacTraceHopsIfNameHop2
                    DisplayString,
                zxr10MacTraceHopsMacAddrHop2
                    MacAddress,
                zxr10MacTraceHopsResultValidHop3
                    TraceHopsResult,
                zxr10MacTraceHopsHostNameHop3
                    DisplayString,
                zxr10MacTraceHopsIfNameHop3
                    DisplayString,
                zxr10MacTraceHopsMacAddrHop3
                    MacAddress,
                zxr10MacTraceHopsResultValidHop4
                    TraceHopsResult,
                zxr10MacTraceHopsHostNameHop4
                    DisplayString,
                zxr10MacTraceHopsIfNameHop4
                    DisplayString,
                zxr10MacTraceHopsMacAddrHop4
                    MacAddress,
                zxr10MacTraceHopsResultValidHop5
                    TraceHopsResult,
                zxr10MacTraceHopsHostNameHop5
                    DisplayString,
                zxr10MacTraceHopsIfNameHop5
                    DisplayString,
                zxr10MacTraceHopsMacAddrHop5
                    MacAddress,
                zxr10MacTraceHopsResultValidHop6
                    TraceHopsResult,
                zxr10MacTraceHopsHostNameHop6
                    DisplayString,
                zxr10MacTraceHopsIfNameHop6
                    DisplayString,
                zxr10MacTraceHopsMacAddrHop6
                    MacAddress,
                zxr10MacTraceHopsResultValidHop7
                    TraceHopsResult,
                zxr10MacTraceHopsHostNameHop7
                    DisplayString,
                zxr10MacTraceHopsIfNameHop7
                    DisplayString,
                zxr10MacTraceHopsMacAddrHop7
                    MacAddress,
                zxr10MacTraceHopsResultValidHop8
                    TraceHopsResult,
                zxr10MacTraceHopsHostNameHop8
                    DisplayString,
                zxr10MacTraceHopsIfNameHop8
                    DisplayString,
                zxr10MacTraceHopsMacAddrHop8
                    MacAddress,
                zxr10MacTraceHopsResultValidHop9
                    TraceHopsResult,
                zxr10MacTraceHopsHostNameHop9
                    DisplayString,
                zxr10MacTraceHopsIfNameHop9
                    DisplayString,
                zxr10MacTraceHopsMacAddrHop9
                    MacAddress,
                zxr10MacTraceHopsEntryOwner
                    DisplayString
              }
                    
    zxr10MacTraceHopsSerial OBJECT-TYPE
              SYNTAX  Integer32
              MAX-ACCESS  read-only
              STATUS  current
              DESCRIPTION
                      ""
              ::= { zxr10MacTraceHopsEntry 1 }
              
    zxr10MacTraceHopsResultValidHop0 OBJECT-TYPE
              SYNTAX  TraceHopsResult
              MAX-ACCESS  read-only
              STATUS  current
              DESCRIPTION
                      "Hop0 Result (0:valid,1:invalid)"
              ::= { zxr10MacTraceHopsEntry 2 }
                
    zxr10MacTraceHopsHostNameHop0 OBJECT-TYPE
              SYNTAX  DisplayString
              MAX-ACCESS  read-only
              STATUS  current
              DESCRIPTION
                      "Hop0 Host Name"
              ::= { zxr10MacTraceHopsEntry 3 }
                     
    zxr10MacTraceHopsIfNameHop0 OBJECT-TYPE
              SYNTAX  DisplayString
              MAX-ACCESS  read-only
              STATUS  current
              DESCRIPTION
                      "Hop0 Interface Name"
              ::= { zxr10MacTraceHopsEntry 4 }

    zxr10MacTraceHopsMacAddrHop0 OBJECT-TYPE
              SYNTAX  MacAddress
              MAX-ACCESS  read-only
              STATUS  current
              DESCRIPTION
                      "Hop0 Mac Address"
              ::= { zxr10MacTraceHopsEntry 5 }

    zxr10MacTraceHopsResultValidHop1 OBJECT-TYPE
              SYNTAX  TraceHopsResult
              MAX-ACCESS  read-only
              STATUS  current
              DESCRIPTION
                      "Hop1 Result (0:valid,1:invalid)"
              ::= { zxr10MacTraceHopsEntry 6 }
                
    zxr10MacTraceHopsHostNameHop1 OBJECT-TYPE
              SYNTAX  DisplayString
              MAX-ACCESS  read-only
              STATUS  current
              DESCRIPTION
                      "Hop1 Host Name"
              ::= { zxr10MacTraceHopsEntry 7 }
                     
    zxr10MacTraceHopsIfNameHop1 OBJECT-TYPE
              SYNTAX  DisplayString
              MAX-ACCESS  read-only
              STATUS  current
              DESCRIPTION
                      "Hop1 Interface Name"
              ::= { zxr10MacTraceHopsEntry 8 }

    zxr10MacTraceHopsMacAddrHop1 OBJECT-TYPE
              SYNTAX  MacAddress
              MAX-ACCESS  read-only
              STATUS  current
              DESCRIPTION
                      "Hop1 Mac Address"
              ::= { zxr10MacTraceHopsEntry 9 }

    zxr10MacTraceHopsResultValidHop2 OBJECT-TYPE
              SYNTAX  TraceHopsResult
              MAX-ACCESS  read-only
              STATUS  current
              DESCRIPTION
                      "Hop2 Result (0:valid,1:invalid)"
              ::= { zxr10MacTraceHopsEntry 10 }
                
    zxr10MacTraceHopsHostNameHop2 OBJECT-TYPE
              SYNTAX  DisplayString
              MAX-ACCESS  read-only
              STATUS  current
              DESCRIPTION
                      "Hop2 Host Name"
              ::= { zxr10MacTraceHopsEntry 11 }
                     
    zxr10MacTraceHopsIfNameHop2 OBJECT-TYPE
              SYNTAX  DisplayString
              MAX-ACCESS  read-only
              STATUS  current
              DESCRIPTION
                      "Hop2 Interface Name"
              ::= { zxr10MacTraceHopsEntry 12 }

    zxr10MacTraceHopsMacAddrHop2 OBJECT-TYPE
              SYNTAX  MacAddress
              MAX-ACCESS  read-only
              STATUS  current
              DESCRIPTION
                      "Hop2 Mac Address"
              ::= { zxr10MacTraceHopsEntry 13 }

    zxr10MacTraceHopsResultValidHop3 OBJECT-TYPE
              SYNTAX  TraceHopsResult
              MAX-ACCESS  read-only
              STATUS  current
              DESCRIPTION
                      "Hop3 Result (0:valid,1:invalid)"
              ::= { zxr10MacTraceHopsEntry 14 }
                
    zxr10MacTraceHopsHostNameHop3 OBJECT-TYPE
              SYNTAX  DisplayString
              MAX-ACCESS  read-only
              STATUS  current
              DESCRIPTION
                      "Hop3 Host Name"
              ::= { zxr10MacTraceHopsEntry 15 }
                     
    zxr10MacTraceHopsIfNameHop3 OBJECT-TYPE
              SYNTAX  DisplayString
              MAX-ACCESS  read-only
              STATUS  current
              DESCRIPTION
                      "Hop3 Interface Name"
              ::= { zxr10MacTraceHopsEntry 16 }

    zxr10MacTraceHopsMacAddrHop3 OBJECT-TYPE
              SYNTAX  MacAddress
              MAX-ACCESS  read-only
              STATUS  current
              DESCRIPTION
                      "Hop3 Mac Address"
              ::= { zxr10MacTraceHopsEntry 17 }

    zxr10MacTraceHopsResultValidHop4 OBJECT-TYPE
              SYNTAX  TraceHopsResult
              MAX-ACCESS  read-only
              STATUS  current
              DESCRIPTION
                      "Hop4 Result (0:valid,1:invalid)"
              ::= { zxr10MacTraceHopsEntry 18 }
                
    zxr10MacTraceHopsHostNameHop4 OBJECT-TYPE
              SYNTAX  DisplayString
              MAX-ACCESS  read-only
              STATUS  current
              DESCRIPTION
                      "Hop4 Host Name"
              ::= { zxr10MacTraceHopsEntry 19 }
                     
    zxr10MacTraceHopsIfNameHop4 OBJECT-TYPE
              SYNTAX  DisplayString
              MAX-ACCESS  read-only
              STATUS  current
              DESCRIPTION
                      "Hop4 Interface Name"
              ::= { zxr10MacTraceHopsEntry 20 }

    zxr10MacTraceHopsMacAddrHop4 OBJECT-TYPE
              SYNTAX  MacAddress
              MAX-ACCESS  read-only
              STATUS  current
              DESCRIPTION
                      "Hop4 Mac Address"
              ::= { zxr10MacTraceHopsEntry 21 }

    zxr10MacTraceHopsResultValidHop5 OBJECT-TYPE
              SYNTAX  TraceHopsResult
              MAX-ACCESS  read-only
              STATUS  current
              DESCRIPTION
                      "Hop5 Result (0:valid,1:invalid)"
              ::= { zxr10MacTraceHopsEntry 22 }
                
    zxr10MacTraceHopsHostNameHop5 OBJECT-TYPE
              SYNTAX  DisplayString
              MAX-ACCESS  read-only
              STATUS  current
              DESCRIPTION
                      "Hop5 Host Name"
              ::= { zxr10MacTraceHopsEntry 23 }
                     
    zxr10MacTraceHopsIfNameHop5 OBJECT-TYPE
              SYNTAX  DisplayString
              MAX-ACCESS  read-only
              STATUS  current
              DESCRIPTION
                      "Hop5 Interface Name"
              ::= { zxr10MacTraceHopsEntry 24 }

    zxr10MacTraceHopsMacAddrHop5 OBJECT-TYPE
              SYNTAX  MacAddress
              MAX-ACCESS  read-only
              STATUS  current
              DESCRIPTION
                      "Hop5 Mac Address"
              ::= { zxr10MacTraceHopsEntry 25 }

    zxr10MacTraceHopsResultValidHop6 OBJECT-TYPE
              SYNTAX  TraceHopsResult
              MAX-ACCESS  read-only
              STATUS  current
              DESCRIPTION
                      "Hop6 Result (0:valid,1:invalid)"
              ::= { zxr10MacTraceHopsEntry 26 }
                
    zxr10MacTraceHopsHostNameHop6 OBJECT-TYPE
              SYNTAX  DisplayString
              MAX-ACCESS  read-only
              STATUS  current
              DESCRIPTION
                      "Hop6 Host Name"
              ::= { zxr10MacTraceHopsEntry 27 }
                     
    zxr10MacTraceHopsIfNameHop6 OBJECT-TYPE
              SYNTAX  DisplayString
              MAX-ACCESS  read-only
              STATUS  current
              DESCRIPTION
                      "Hop6 Interface Name"
              ::= { zxr10MacTraceHopsEntry 28 }

    zxr10MacTraceHopsMacAddrHop6 OBJECT-TYPE
              SYNTAX  MacAddress
              MAX-ACCESS  read-only
              STATUS  current
              DESCRIPTION
                      "Hop6 Mac Address"
              ::= { zxr10MacTraceHopsEntry 29 }

    zxr10MacTraceHopsResultValidHop7 OBJECT-TYPE
              SYNTAX  TraceHopsResult
              MAX-ACCESS  read-only
              STATUS  current
              DESCRIPTION
                      "Hop7 Result (0:valid,1:invalid)"
              ::= { zxr10MacTraceHopsEntry 30 }
                
    zxr10MacTraceHopsHostNameHop7 OBJECT-TYPE
              SYNTAX  DisplayString
              MAX-ACCESS  read-only
              STATUS  current
              DESCRIPTION
                      "Hop7 Host Name"
              ::= { zxr10MacTraceHopsEntry 31 }
                     
    zxr10MacTraceHopsIfNameHop7 OBJECT-TYPE
              SYNTAX  DisplayString
              MAX-ACCESS  read-only
              STATUS  current
              DESCRIPTION
                      "Hop7 Interface Name"
              ::= { zxr10MacTraceHopsEntry 32 }

    zxr10MacTraceHopsMacAddrHop7 OBJECT-TYPE
              SYNTAX  MacAddress
              MAX-ACCESS  read-only
              STATUS  current
              DESCRIPTION
                      "Hop7 Mac Address"
              ::= { zxr10MacTraceHopsEntry 33 }

    zxr10MacTraceHopsResultValidHop8 OBJECT-TYPE
              SYNTAX  TraceHopsResult
              MAX-ACCESS  read-only
              STATUS  current
              DESCRIPTION
                      "Hop8 Result (0:valid,1:invalid)"
              ::= { zxr10MacTraceHopsEntry 34 }
                
    zxr10MacTraceHopsHostNameHop8 OBJECT-TYPE
              SYNTAX  DisplayString
              MAX-ACCESS  read-only
              STATUS  current
              DESCRIPTION
                      "Hop8 Host Name"
              ::= { zxr10MacTraceHopsEntry 35 }
                     
    zxr10MacTraceHopsIfNameHop8 OBJECT-TYPE
              SYNTAX  DisplayString
              MAX-ACCESS  read-only
              STATUS  current
              DESCRIPTION
                      "Hop8 Interface Name"
              ::= { zxr10MacTraceHopsEntry 36 }

    zxr10MacTraceHopsMacAddrHop8 OBJECT-TYPE
              SYNTAX  MacAddress
              MAX-ACCESS  read-only
              STATUS  current
              DESCRIPTION
                      "Hop8 Mac Address"
              ::= { zxr10MacTraceHopsEntry 37 }
              
    zxr10MacTraceHopsResultValidHop9 OBJECT-TYPE
              SYNTAX  TraceHopsResult
              MAX-ACCESS  read-only
              STATUS  current
              DESCRIPTION
                      "Hop9 Result (0:valid,1:invalid)"
              ::= { zxr10MacTraceHopsEntry 38 }
                
    zxr10MacTraceHopsHostNameHop9 OBJECT-TYPE
              SYNTAX  DisplayString
              MAX-ACCESS  read-only
              STATUS  current
              DESCRIPTION
                      "Hop9 Host Name"
              ::= { zxr10MacTraceHopsEntry 39 }
                     
    zxr10MacTraceHopsIfNameHop9 OBJECT-TYPE
              SYNTAX  DisplayString
              MAX-ACCESS  read-only
              STATUS  current
              DESCRIPTION
                      "Hop9 Interface Name"
              ::= { zxr10MacTraceHopsEntry 40 }

    zxr10MacTraceHopsMacAddrHop9 OBJECT-TYPE
              SYNTAX  MacAddress
              MAX-ACCESS  read-only
              STATUS  current
              DESCRIPTION
                      "Hop9 Mac Address"
              ::= { zxr10MacTraceHopsEntry 41 }

    zxr10MacTraceHopsEntryOwner OBJECT-TYPE
              SYNTAX  DisplayString
              MAX-ACCESS  read-only
              STATUS  current
              DESCRIPTION
                      ""
              ::= { zxr10MacTraceHopsEntry 42 }

-- *******************************************************
--                Mac Trace Trap Definitions
-- *******************************************************
    macTraceTrapResult NOTIFICATION-TYPE
     OBJECTS  { zxr10MacTraceHopsSerial,
                zxr10MacTraceHopsResultValidHop0,
                zxr10MacTraceHopsHostNameHop0,
                zxr10MacTraceHopsIfNameHop0,
                zxr10MacTraceHopsMacAddrHop0,
                zxr10MacTraceHopsResultValidHop1,
                zxr10MacTraceHopsHostNameHop1,
                zxr10MacTraceHopsIfNameHop1,
                zxr10MacTraceHopsMacAddrHop1,
                zxr10MacTraceHopsResultValidHop2,
                zxr10MacTraceHopsHostNameHop2,
                zxr10MacTraceHopsIfNameHop2,
                zxr10MacTraceHopsMacAddrHop2,
                zxr10MacTraceHopsResultValidHop3,
                zxr10MacTraceHopsHostNameHop3,
                zxr10MacTraceHopsIfNameHop3,
                zxr10MacTraceHopsMacAddrHop3,
                zxr10MacTraceHopsResultValidHop4,
                zxr10MacTraceHopsHostNameHop4,
                zxr10MacTraceHopsIfNameHop4,
                zxr10MacTraceHopsMacAddrHop4,
                zxr10MacTraceHopsResultValidHop5,
                zxr10MacTraceHopsHostNameHop5,
                zxr10MacTraceHopsIfNameHop5,
                zxr10MacTraceHopsMacAddrHop5,
                zxr10MacTraceHopsResultValidHop6,
                zxr10MacTraceHopsHostNameHop6,
                zxr10MacTraceHopsIfNameHop6,
                zxr10MacTraceHopsMacAddrHop6,
                zxr10MacTraceHopsResultValidHop7,
                zxr10MacTraceHopsHostNameHop7,
                zxr10MacTraceHopsIfNameHop7,
                zxr10MacTraceHopsMacAddrHop7,
                zxr10MacTraceHopsResultValidHop8,
                zxr10MacTraceHopsHostNameHop8,
                zxr10MacTraceHopsIfNameHop8,
                zxr10MacTraceHopsMacAddrHop8,
                zxr10MacTraceHopsResultValidHop9,
                zxr10MacTraceHopsHostNameHop9,
                zxr10MacTraceHopsIfNameHop9,
                zxr10MacTraceHopsMacAddrHop9,
                zxr10MacTraceHopsEntryOwner
              }
     STATUS  current
     DESCRIPTION
         "The newMaster trap indicates that the sending agent
         has transitioned to 'Master' state."
     ::= { macTraceNotifications 1 }                                   

END

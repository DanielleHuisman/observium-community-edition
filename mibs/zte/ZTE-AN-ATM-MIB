--------------------------------------------------------------------------------
-- File Name : ZTE-AN-ATM-MIB.mib
-- Date      : 2008-06-30
-- Author    : ZTE Nms dept.

--
-- Zte ATM Mib for Access Node
--
--
--------------------------------------------------------------------------------
ZTE-AN-ATM-MIB DEFINITIONS ::= BEGIN     
  IMPORTS 
     MODULE-IDENTITY, OBJECT-TYPE, NOTIFICATION-TYPE,
     experimental, Integer32, Unsigned32, 
     Counter64, TimeTicks 
                                                        FROM SNMPv2-SMI
     RowStatus                                          FROM SNMPv2-TC    
     ifIndex                                            FROM IF-MIB     
     zxAn,ZxAnIfindex                                   FROM ZTE-AN-TC-MIB;      
     
     zxAnAtmMib MODULE-IDENTITY 
     LAST-UPDATED "200806301500Z"
     ORGANIZATION 
         "ZTE Corporation."
     CONTACT-INFO 
         "ZTE NMS dept.
                  Ma Jian       68897122" 

     DESCRIPTION  
         "This MIB contains managed object definitions for ATM VCX." 
     ::= { zxAn 57 } 
     
     zxAnAtmVcxObjects OBJECT IDENTIFIER ::= {zxAnAtmMib 1}

--------------------------------------------------------------------------------
-- Following objects are defined.
-- 1.zxAn AtmVcxTable 
-- 2.zxAn AtmPvcMappingIdTable
--------------------------------------------------------------------------------

------------------------------------------------------------------------------
--  1.zxAn AtmVcxTable
------------------------------------------------------------------------------ 
    zxAnAtmVcxTable OBJECT-TYPE
        SYNTAX      SEQUENCE OF ZxAnAtmVcxEntry
        MAX-ACCESS  not-accessible
        STATUS      current
        DESCRIPTION
            "The ATM VC Cross Connect table for PVCs.An entry in this table 
            models two cross-connected VCLs.Each VCL must be pvc."
        ::= { zxAnAtmVcxObjects 1 }
                       
    zxAnAtmVcxEntry OBJECT-TYPE
        SYNTAX      ZxAnAtmVcxEntry
        MAX-ACCESS  not-accessible
        STATUS      current
        DESCRIPTION
            "An entry in the ATM VC Cross Connect table.
            This entry is used to model a bi-directional ATM
            VC cross-connect cross-connecting two end points."
        INDEX       {zxAnAtmVcxUserSideIfIndex,
                    zxAnAtmVcxUserSidePvcId,
                    zxAnAtmVcxWanSideIfIndex,
                    zxAnAtmVcxWanSidePvcId}
        ::= { zxAnAtmVcxTable 1 }
    
    ZxAnAtmVcxEntry ::= SEQUENCE {
        zxAnAtmVcxUserSideIfIndex    ZxAnIfindex,
        zxAnAtmVcxUserSidePvcId      Integer32,         
        zxAnAtmVcxWanSideIfIndex     ZxAnIfindex,
        zxAnAtmVcxWanSidePvcId       Integer32,
        zxAnAtmVcxUserSideVpi        Integer32,
        zxAnAtmVcxUserSideVci        Integer32,
        zxAnAtmVcxWanSideVpi         Integer32,
        zxAnAtmVcxWanSideVci         Integer32,                  
        zxAnAtmVcxRowStatus          RowStatus
    }

    zxAnAtmVcxUserSideIfIndex OBJECT-TYPE
        SYNTAX      ZxAnIfindex
        MAX-ACCESS  not-accessible
        STATUS      current
        DESCRIPTION
            "The ifIndex value of the General interface for this
            VC cross-connect.The term UserSide implies that this 
            ATM interface has the numerically UserSide ifIndex value 
            than the other ATM interface identified in the same 
            zxAnAtmVcxEntry."
        ::= { zxAnAtmVcxEntry 1 }

    zxAnAtmVcxUserSidePvcId OBJECT-TYPE
        SYNTAX         Integer32
        MAX-ACCESS     not-accessible
        STATUS         current
        DESCRIPTION
            "Pvc port id in UserSide interface."
        ::= { zxAnAtmVcxEntry 2 }

    zxAnAtmVcxWanSideIfIndex OBJECT-TYPE
        SYNTAX      ZxAnIfindex
        MAX-ACCESS  not-accessible
        STATUS      current
        DESCRIPTION
            "The ifIndex value for the General interface for
            this VC cross-connect. The term WanSide implies
            that this ATM interface has the numerically WanSide
            ifIndex value than the other ATM interface
            identified in the same zxAnAtmVcxEntry."
        ::= { zxAnAtmVcxEntry 3 }

    zxAnAtmVcxWanSidePvcId OBJECT-TYPE
        SYNTAX      Integer32
        MAX-ACCESS  not-accessible
        STATUS      current
        DESCRIPTION
            "Pvc port id in WanSide interface."
        ::= { zxAnAtmVcxEntry 4 }    

    zxAnAtmVcxUserSideVpi OBJECT-TYPE
        SYNTAX      Integer32
        MAX-ACCESS  read-only
        STATUS      current
        DESCRIPTION
            "The VPI value at the ATM interface associated with the VC cross-connect 
            that is identified by zxAnAtmVcxUserSideIfIndex."
        ::= { zxAnAtmVcxEntry 5 }

    zxAnAtmVcxUserSideVci OBJECT-TYPE
        SYNTAX      Integer32
        MAX-ACCESS  read-only
        STATUS      current
        DESCRIPTION
            "The VCI value at the ATM interface associated with this VC cross-connect 
            that is identified by zxAnAtmVcxUserSideIfIndex."
        ::= { zxAnAtmVcxEntry 6 }
         
    zxAnAtmVcxWanSideVpi OBJECT-TYPE
        SYNTAX      Integer32
        MAX-ACCESS  read-only
        STATUS      current
        DESCRIPTION
            "The VPI value at the ATM interface associated with the VC cross-connect 
            that is identified by zxAnAtmVcxWanSideIfIndex."
        ::= { zxAnAtmVcxEntry 7 }

    zxAnAtmVcxWanSideVci OBJECT-TYPE
        SYNTAX      Integer32
        MAX-ACCESS  read-only
        STATUS      current
        DESCRIPTION
            "The VCI value at the ATM interface associated with the VC cross-connect 
            that is identified by zxAnAtmVcxWanSideIfIndex."
        ::= { zxAnAtmVcxEntry 8 }
                 
    zxAnAtmVcxRowStatus OBJECT-TYPE
        SYNTAX      RowStatus
        MAX-ACCESS  read-create
        STATUS      current
        DESCRIPTION
            "The status of this entry in the zxAnAtmVcxTable.This object is used to
            create a new cross-connect for cross-connecting Pvcs. This object must 
            be initially set to `createAndWait' or 'createAndGo'.To turn on a VC cross-connect,
            the zxAnAtmVcxAdminStatus is set to `up'."
        DEFVAL { createAndWait }
         ::= { zxAnAtmVcxEntry 50 }                

------------------------------------------------------------------------------
--  2.zxAn AtmPvcMappingIdTable
------------------------------------------------------------------------------                                       
    zxAnAtmPvcMappingIdTable OBJECT-TYPE
        SYNTAX      SEQUENCE OF ZxAnAtmPvcMappingIdEntry
        MAX-ACCESS  not-accessible
        STATUS      current
        DESCRIPTION
            "This table provides reverse mapping of the PvcId
            based on Vpi/Vci."           
        ::= { zxAnAtmVcxObjects 3 }

    zxAnAtmPvcMappingIdEntry  OBJECT-TYPE
        SYNTAX      ZxAnAtmPvcMappingIdEntry
        MAX-ACCESS  not-accessible
        STATUS      current
        DESCRIPTION
            "An entry containing pvc reverse information."         
        INDEX       {zxAnAtmIfIndex,zxAnAtmPvcVpi,zxAnAtmPvcVci}
        ::= { zxAnAtmPvcMappingIdTable 1 }
     
    ZxAnAtmPvcMappingIdEntry ::= SEQUENCE {
        zxAnAtmIfIndex            ZxAnIfindex,  
        zxAnAtmPvcVpi             Integer32,
        zxAnAtmPvcVci             Integer32,         
        zxAnAtmPvcId              Integer32
    }                        
         
    zxAnAtmIfIndex OBJECT-TYPE
        SYNTAX      ZxAnIfindex
        MAX-ACCESS  not-accessible
        STATUS      current
        DESCRIPTION
            "The ifIndex value for the General interface."
        ::= { zxAnAtmPvcMappingIdEntry 1 }
                  
    zxAnAtmPvcVpi OBJECT-TYPE
        SYNTAX      Integer32(0..255) 
        MAX-ACCESS  not-accessible
        STATUS      current
        DESCRIPTION
            "the vpi of the pvc"
        ::= { zxAnAtmPvcMappingIdEntry 2 }    
              
    zxAnAtmPvcVci OBJECT-TYPE
        SYNTAX      Integer32(0..65535) 
        MAX-ACCESS  not-accessible
        STATUS      current
        DESCRIPTION
            "the vci of the pvc"
        ::= { zxAnAtmPvcMappingIdEntry 3 } 
              
    zxAnAtmPvcId OBJECT-TYPE
        SYNTAX      Integer32
        MAX-ACCESS  read-create
        STATUS      current
        DESCRIPTION
            "the pvc Id"
        ::= { zxAnAtmPvcMappingIdEntry 4 }
        
   zxAnAtmPerfObjects OBJECT IDENTIFIER ::= {zxAnAtmMib 2}
   
------------------------------------------------------------------------------
--  1.zxAn AtmPerfTable
------------------------------------------------------------------------------ 
    zxAnAtmPerfTable OBJECT-TYPE
        SYNTAX      SEQUENCE OF ZxAnAtmPerfEntry
        MAX-ACCESS  not-accessible
        STATUS      current
        DESCRIPTION
            "The ATM VC Cross Connect table for PVCs.An entry in this table 
            models two cross-connected VCLs.Each VCL must be pvc."
        ::= { zxAnAtmPerfObjects 1 }
                       
    zxAnAtmPerfEntry OBJECT-TYPE
        SYNTAX      ZxAnAtmPerfEntry
        MAX-ACCESS  not-accessible
        STATUS      current
        DESCRIPTION
            "An entry in the ATM VC Cross Connect table.
            This entry is used to model a bi-directional ATM
            VC cross-connect cross-connecting two end points."
        INDEX       {zxAnAtmPerfIfIndex}
        ::= { zxAnAtmPerfTable 1 }
    
    ZxAnAtmPerfEntry ::= SEQUENCE {
        zxAnAtmPerfIfIndex            ZxAnIfindex,
        zxAnAtmReceiveCell            Counter64,         
        zxAnAtmTransmitCell           Counter64,
        zxAnAtmDiscardedCell          Counter64,
        zxAnAtmContinuityCell         Counter64,
        zxATMStatCounterAdminStatus   INTEGER
    }
    

    zxAnAtmPerfIfIndex OBJECT-TYPE
        SYNTAX      ZxAnIfindex
        MAX-ACCESS  not-accessible
        STATUS      current
        DESCRIPTION
            "The ifIndex value for the General interface."
        ::= { zxAnAtmPerfEntry 1 }

    zxAnAtmReceiveCell OBJECT-TYPE
        SYNTAX      Counter64
        MAX-ACCESS  read-only
        STATUS      current
        DESCRIPTION
            "Atm ReceiveCell."
        ::= { zxAnAtmPerfEntry 2 }
         
    zxAnAtmTransmitCell OBJECT-TYPE
        SYNTAX      Counter64
        MAX-ACCESS  read-only
        STATUS      current
        DESCRIPTION
            "Atm Transmit Cell."
        ::= { zxAnAtmPerfEntry 3 }

    zxAnAtmDiscardedCell OBJECT-TYPE
        SYNTAX      Counter64
        MAX-ACCESS  read-only
        STATUS      current
        DESCRIPTION
            "Atm Discarded Cell."
        ::= { zxAnAtmPerfEntry 4 }
        
    zxAnAtmContinuityCell OBJECT-TYPE
        SYNTAX      Counter64
        MAX-ACCESS  read-only
        STATUS      current
        DESCRIPTION
            "OAM continuity check."
        ::= { zxAnAtmPerfEntry 5 }
        
    zxATMStatCounterAdminStatus  OBJECT-TYPE
        SYNTAX    INTEGER{                           
                       start(1),
                       stop(2),
                       resetCounter(3)
                    }
        MAX-ACCESS  read-write
        STATUS    current
        DESCRIPTION  "Clear take count of static"
        ::={zxAnAtmPerfEntry 6}  
        
END

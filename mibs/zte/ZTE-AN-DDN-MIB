--------------------------------------------------------------------------------
-- File Name : ZTE-AN-IGMP-MIB.mib
-- Date      : 2009-07-15
-- Author    : ZTE Nms dept.

--
-- Zte DDN Mib for Access Node
--
--
--------------------------------------------------------------------------------

ZTE-AN-DDN-MIB DEFINITIONS ::= BEGIN

    IMPORTS
        MODULE-IDENTITY         FROM SNMPv2-SMI
        NOTIFICATION-TYPE       FROM SNMPv2-SMI
        OBJECT-TYPE             FROM SNMPv2-SMI 
        enterprises             FROM SNMPv2-SMI
        Counter32               FROM SNMPv2-SMI
        Integer32               FROM SNMPv2-SMI 
        Counter64               FROM SNMPv2-SMI 
        Unsigned32              FROM SNMPv2-SMI  
        Gauge32                 FROM SNMPv2-SMI
        TEXTUAL-CONVENTION      FROM SNMPv2-TC
        RowStatus               FROM SNMPv2-TC 
        DisplayString           FROM SNMPv2-TC
        TruthValue              FROM SNMPv2-TC;

    zxAnDDNMib MODULE-IDENTITY
        LAST-UPDATED    "201310100000Z"
        ORGANIZATION    "zte Telcom Co. Ltd."
        CONTACT-INFO    "E-mail: shen.yuyang@zte.com.cn,
                         E-mail: suchunshan@zte.com.cn"
        DESCRIPTION     "This MIB defines PortLocating managed objects for 
                         Access Node."
        REVISION        "201310100000Z"
        DESCRIPTION     "Extending the range of the DDN card's working mode."
        ::= { zxAn 5200 }
        
--------------------------------------------------------------------------------
-- Following objects are defined.
-- 1.ddnPortTable
-- 2.ddnConnectTable
-- 3.hdbPortConfigTable
-- 4.audbPortConfigTable
-- 5.zxAnDdnBertConfTable
-- 6.zxAnDdnBertStatsTable
-- 7.zxAnDdnModemMgmtTable
-- 8.zxAnDdnModemQueryTable
-- 9.zxAnDdnModemDiagnoseTable
-- 10.zxAnDdnGhdbCardTable
-- 100.zxAnDdnTrapObjects
--------------------------------------------------------------------------------
    
    zte                     OBJECT IDENTIFIER ::= { enterprises 3902 }
    zxAn                    OBJECT IDENTIFIER ::= { zte 1015 }

    msagmajorVersion        OBJECT IDENTIFIER ::= { zxAnDDNMib 3 }  
    
    msagDDNConfig           OBJECT IDENTIFIER ::= { msagmajorVersion 2 }      
 
    zxAnDdnBertMgmtGroup    OBJECT IDENTIFIER ::= { msagDDNConfig 5 }
    zxAnDdnModemMgmtGroup   OBJECT IDENTIFIER ::= { msagDDNConfig 7 }    
    zxAnDdnTrapObjects      OBJECT IDENTIFIER ::= { msagDDNConfig 100 } 
    
    zxAnDdnModemTrapGroup   OBJECT IDENTIFIER ::= { zxAnDdnTrapObjects 1 }

--------------------------------------------------------------------------------
-- 1.ddnPortTable
--------------------------------------------------------------------------------
    ddnPortTable OBJECT-TYPE
        SYNTAX      SEQUENCE OF DdnPortEntry
        MAX-ACCESS  not-accessible
        STATUS      current
        DESCRIPTION  ""
        ::={msagDDNConfig 1}

    ddnPortEntry OBJECT-TYPE
        SYNTAX      DdnPortEntry
        MAX-ACCESS  not-accessible
        STATUS      current
        DESCRIPTION  ""
        INDEX 
            { 
                ddnPortRack,
                ddnPortShelf,
                ddnPortSlot,
                ddnPortCircuit,
                ddnPortTs
            }
        ::={ddnPortTable 1}

    DdnPortEntry ::=
        SEQUENCE{
            ddnPortRack       INTEGER,
            ddnPortShelf      INTEGER,
            ddnPortSlot       INTEGER,
            ddnPortCircuit    INTEGER,
            ddnPortTs         INTEGER,
            ddnPortName       DisplayString,
            ddnPortMainType   INTEGER,
            ddnPortSubType    INTEGER,
            ddnPortRowStatus  RowStatus,
            ddnPortLoopback   INTEGER
        }

    ddnPortRack  OBJECT-TYPE
        SYNTAX      INTEGER(1)
        MAX-ACCESS  not-accessible
        STATUS      current
        DESCRIPTION  ""
        ::={ddnPortEntry 1}

    ddnPortShelf  OBJECT-TYPE
        SYNTAX      INTEGER(0..5)
        MAX-ACCESS  not-accessible
        STATUS      current
        DESCRIPTION  ""
        ::={ddnPortEntry 2}

    ddnPortSlot  OBJECT-TYPE
        SYNTAX      INTEGER(3..16)
        MAX-ACCESS  not-accessible
        STATUS      current
        DESCRIPTION  ""
        ::={ddnPortEntry 3}

    ddnPortCircuit  OBJECT-TYPE
        SYNTAX      INTEGER(0..31)
        MAX-ACCESS  not-accessible
        STATUS      current
        DESCRIPTION  ""
        ::={ddnPortEntry 4}

    ddnPortTs  OBJECT-TYPE
        SYNTAX      INTEGER(0..255)
        MAX-ACCESS  not-accessible
        STATUS      current
        DESCRIPTION    ""
        ::={ddnPortEntry 5}

    ddnPortName  OBJECT-TYPE
        SYNTAX      DisplayString(SIZE(1..10))
        MAX-ACCESS  read-create
        STATUS      current
        DESCRIPTION  ""
        ::={ddnPortEntry 6}

    ddnPortMainType  OBJECT-TYPE
        SYNTAX      INTEGER
            {
                type64K(0),
                type2B(1),
                typeHSB(2),
                typeSDM(3),
                typeU(4),
                typeHDB(5),
                typeE1(6),
                typePwe3(7),
                typeShdsl(8)
            }
        MAX-ACCESS  read-create
        STATUS      current
        DESCRIPTION  ""
        ::={ddnPortEntry 7}

    ddnPortSubType  OBJECT-TYPE
        SYNTAX      INTEGER
            {
                type1X64K(1),
                type2X64K(2),
                type3X64K(3),
                type4X64K(4),
                type5X64K(5),
                type6X64K(6),
                type7X64K(7),
                type8X64K(8),
                type9X64K(9),
                type10X64K(10),
                type11X64K(11),
                type12X64K(12),
                type13X64K(13),
                type14X64K(14),
                type15X64K(15),
                type16X64K(16),
                type17X64K(17),
                type18X64K(18),
                type19X64K(19),
                type20X64K(20),
                type21X64K(21),
                type22X64K(22),
                type23X64K(23),
                type24X64K(24),
                type25X64K(25),
                type26X64K(26),
                type27X64K(27),
                type28X64K(28),
                type29X64K(29),
                type30X64K(30),
                type31X64K(31),
                type32X64K(32),
                type24(33),
                type48(34),
                type96(35),
                type192(36)
            }
        MAX-ACCESS  read-create
        STATUS      current
        DESCRIPTION  ""
        ::={ddnPortEntry 8}

    ddnPortRowStatus  OBJECT-TYPE
        SYNTAX      RowStatus
        MAX-ACCESS  read-create
        STATUS      current
        DESCRIPTION  ""
        ::={ddnPortEntry 9}

    ddnPortLoopback  OBJECT-TYPE
        SYNTAX      INTEGER {
            noLoopback(1),
            localLoopback(2),
            remoteLineLoopback(3),
            unsupported(255)
        }
        MAX-ACCESS  read-create
        STATUS      current
        DESCRIPTION  
            "This variable represents the loopback configuration of DDN port.
            The values mean:
            noLoopback
                Not in the loopback state.
            localLoopback
                The DDN port can transmit packets to the LE, but receives its 
                own transmission back again and ignores data from the LE.
            remoteLineLoopback
                With remote line loopback ,packets sent from the LE are 
                received by the DDN port but also are immediately retransmitted
                to the LE.
            unsupported
                The DDN port doesn't support loopback."
        ::={ddnPortEntry 10}

--------------------------------------------------------------------------------
-- 2.ddnConnectTable
--------------------------------------------------------------------------------
    ddnConnectTable OBJECT-TYPE
        SYNTAX      SEQUENCE OF DdnConnectEntry
        MAX-ACCESS  not-accessible
        STATUS      current
        DESCRIPTION  ""
        ::={msagDDNConfig 2}

    ddnConnectEntry OBJECT-TYPE
        SYNTAX      DdnConnectEntry
        MAX-ACCESS  not-accessible
        STATUS      current
        DESCRIPTION  ""
        INDEX 
            { 
                ddnConPort1Rack,
                ddnConPort1Shelf,
                ddnConPort1Slot,
                ddnConPort1Circuit,
                ddnConPort1Ts
            }
        ::={ddnConnectTable 1}

    DdnConnectEntry ::=
        SEQUENCE{
            ddnConPort1Rack        INTEGER,
            ddnConPort1Shelf       INTEGER,
            ddnConPort1Slot        INTEGER,
            ddnConPort1Circuit     INTEGER,
            ddnConPort1Ts          INTEGER,
            ddnConPort1Name        DisplayString,
            ddnConPort2Rack        INTEGER,
            ddnConPort2Shelf       INTEGER,
            ddnConPort2Slot        INTEGER,
            ddnConPort2Circuit     INTEGER,
            ddnConPort2Ts          INTEGER,
            ddnConPort2Name        DisplayString,
            ddnConName             DisplayString,
            ddnConnExOperType      INTEGER,
            ddnConRowStatus        RowStatus
        }

    ddnConPort1Rack  OBJECT-TYPE
        SYNTAX      INTEGER(1)
        MAX-ACCESS  not-accessible
        STATUS      current
        DESCRIPTION  ""
        ::={ddnConnectEntry 1}

    ddnConPort1Shelf  OBJECT-TYPE
        SYNTAX      INTEGER(0..5)
        MAX-ACCESS  not-accessible
        STATUS      current
        DESCRIPTION  ""
        ::={ddnConnectEntry 2}

    ddnConPort1Slot  OBJECT-TYPE
        SYNTAX      INTEGER(3..16)
        MAX-ACCESS  not-accessible
        STATUS      current
        DESCRIPTION  ""
        ::={ddnConnectEntry 3}

    ddnConPort1Circuit  OBJECT-TYPE
        SYNTAX      INTEGER(0..31)
        MAX-ACCESS  not-accessible
        STATUS      current
        DESCRIPTION  ""
        ::={ddnConnectEntry 4}

    ddnConPort1Ts  OBJECT-TYPE
        SYNTAX      INTEGER(0..255)
        MAX-ACCESS  not-accessible
        STATUS      current
        DESCRIPTION ""
        ::={ddnConnectEntry 5}

    ddnConPort1Name  OBJECT-TYPE
        SYNTAX      DisplayString(SIZE(1..10))
        MAX-ACCESS  read-create
        STATUS      current
        DESCRIPTION  ""
        ::={ddnConnectEntry 6}

    ddnConPort2Rack  OBJECT-TYPE
        SYNTAX      INTEGER(1)
        MAX-ACCESS  read-create
        STATUS      current
        DESCRIPTION  ""
        ::={ddnConnectEntry 7}

    ddnConPort2Shelf  OBJECT-TYPE
        SYNTAX      INTEGER(0..5)
        MAX-ACCESS  read-create
        STATUS      current
        DESCRIPTION  ""
        ::={ddnConnectEntry 8}

    ddnConPort2Slot  OBJECT-TYPE
        SYNTAX      INTEGER(3..16)
        MAX-ACCESS  read-create
        STATUS      current
        DESCRIPTION  ""
        ::={ddnConnectEntry 9}

    ddnConPort2Circuit  OBJECT-TYPE
        SYNTAX      INTEGER(0..31)
        MAX-ACCESS  read-create
        STATUS      current
        DESCRIPTION  ""
        ::={ddnConnectEntry 10}

    ddnConPort2Ts  OBJECT-TYPE
        SYNTAX      INTEGER(0..255)
        MAX-ACCESS  read-create
        STATUS      current
        DESCRIPTION ""
        ::={ddnConnectEntry 11}

    ddnConPort2Name  OBJECT-TYPE
        SYNTAX      DisplayString(SIZE(1..10))
        MAX-ACCESS  read-create
        STATUS      current
        DESCRIPTION  ""
        ::={ddnConnectEntry 12}

    ddnConName  OBJECT-TYPE
        SYNTAX      DisplayString(SIZE(1..30))
        MAX-ACCESS  read-create
        STATUS      current
        DESCRIPTION  ""
        ::={ddnConnectEntry 13}

    ddnConnExOperType  OBJECT-TYPE
        SYNTAX      INTEGER(1..2)
        MAX-ACCESS  read-create
        STATUS      current
        DESCRIPTION "use SPN"
        ::={ddnConnectEntry 14}

    ddnConRowStatus  OBJECT-TYPE
        SYNTAX      RowStatus
        MAX-ACCESS  read-create
        STATUS      current
        DESCRIPTION  ""
        ::={ddnConnectEntry 15}
  
--------------------------------------------------------------------------------
-- 3.hdbPortConfigTable
--------------------------------------------------------------------------------
    hdbPortConfigTable OBJECT-TYPE
        SYNTAX      SEQUENCE OF HdbPortConfigEntry
        MAX-ACCESS  not-accessible
        STATUS      current
        DESCRIPTION  ""
        ::={msagDDNConfig 3}

    hdbPortConfigEntry OBJECT-TYPE
        SYNTAX    HdbPortConfigEntry
        MAX-ACCESS  not-accessible
        STATUS    current
        DESCRIPTION  ""
        INDEX { hdbPCRack,hdbPCShelf,hdbPCSlot }
        ::={hdbPortConfigTable 1}

    HdbPortConfigEntry ::=
        SEQUENCE{
            hdbPCRack        INTEGER,
            hdbPCShelf       INTEGER,
            hdbPCSlot        INTEGER,
            hdbPCPortNumber  INTEGER
        }

    hdbPCRack  OBJECT-TYPE
        SYNTAX      INTEGER(1)
        MAX-ACCESS  not-accessible
        STATUS      current
        DESCRIPTION  ""
        ::={hdbPortConfigEntry 1}

    hdbPCShelf  OBJECT-TYPE
        SYNTAX      INTEGER(0..5)
        MAX-ACCESS  not-accessible
        STATUS      current
        DESCRIPTION  ""
        ::={hdbPortConfigEntry 2}

    hdbPCSlot  OBJECT-TYPE
        SYNTAX      INTEGER(3..16)
        MAX-ACCESS  not-accessible
        STATUS      current
        DESCRIPTION  ""
        ::={hdbPortConfigEntry 3}

    hdbPCPortNumber  OBJECT-TYPE
        SYNTAX      INTEGER(1..4)
        MAX-ACCESS  read-write
        STATUS      current
        DESCRIPTION  ""
        ::={hdbPortConfigEntry 4}

--------------------------------------------------------------------------------
-- 4.audbPortConfigTable
--------------------------------------------------------------------------------
    audbPortConfigTable OBJECT-TYPE
        SYNTAX      SEQUENCE OF AudbPortConfigEntry
        MAX-ACCESS  not-accessible
        STATUS      current
        DESCRIPTION  ""
        ::={msagDDNConfig 4}

    audbPortConfigEntry OBJECT-TYPE
        SYNTAX    AudbPortConfigEntry
        MAX-ACCESS  not-accessible
        STATUS    current
        DESCRIPTION  ""
        INDEX { audbPCRack,audbPCShelf,audbPCSlot,audbPCCircuit,audbPCTs }
        ::={audbPortConfigTable 1}

    AudbPortConfigEntry ::=
        SEQUENCE{
            audbPCRack         INTEGER,
            audbPCShelf        INTEGER,
            audbPCSlot         INTEGER,
            audbPCCircuit      INTEGER,
            audbPCTs           INTEGER,
            audbPortLineType   INTEGER,
            audbPortInputGain  DisplayString,
            audbPortOutputGain DisplayString,
            audbPortLoopState  INTEGER
        }

    audbPCRack  OBJECT-TYPE
        SYNTAX      INTEGER(1)
        MAX-ACCESS  not-accessible
        STATUS      current
        DESCRIPTION  ""
        ::={audbPortConfigEntry 1}

    audbPCShelf  OBJECT-TYPE
        SYNTAX      INTEGER(0..5)
        MAX-ACCESS  not-accessible
        STATUS      current
        DESCRIPTION  ""
        ::={audbPortConfigEntry 2}

    audbPCSlot  OBJECT-TYPE
        SYNTAX      INTEGER(3..16)
        MAX-ACCESS  not-accessible
        STATUS      current
        DESCRIPTION  ""
        ::={audbPortConfigEntry 3}

    audbPCCircuit  OBJECT-TYPE
        SYNTAX      INTEGER(0..7)
        MAX-ACCESS  not-accessible
        STATUS      current
        DESCRIPTION  ""
        ::={audbPortConfigEntry 4}


    audbPCTs  OBJECT-TYPE
        SYNTAX      INTEGER(255)
        MAX-ACCESS  not-accessible
        STATUS      current
        DESCRIPTION  "filled with 255"
        ::={audbPortConfigEntry 5}


    audbPortLineType  OBJECT-TYPE
        SYNTAX      INTEGER{twolinetrans(1),fourlinetrans(2)}
        MAX-ACCESS  read-write
        STATUS      current
        DESCRIPTION  ""
        ::={audbPortConfigEntry 9}

    audbPortInputGain  OBJECT-TYPE
        SYNTAX      DisplayString(SIZE(1..10))
        MAX-ACCESS  read-write
        STATUS      current
        DESCRIPTION  ""
        ::={audbPortConfigEntry 10}

    audbPortOutputGain  OBJECT-TYPE
        SYNTAX      DisplayString(SIZE(1..10))
        MAX-ACCESS  read-write
        STATUS      current
        DESCRIPTION  ""
        ::={audbPortConfigEntry 11}


    audbPortLoopState  OBJECT-TYPE
        SYNTAX      INTEGER{loop(1),notloop(2)}
        MAX-ACCESS  read-write
        STATUS      current
        DESCRIPTION  ""
        ::={audbPortConfigEntry 12}
--------------------------------------------------------------------------------
-- 5.zxAnDdnBertConfTable
--------------------------------------------------------------------------------
    zxAnDdnBertConfTable OBJECT-TYPE
        SYNTAX      SEQUENCE OF ZxAnDdnBertConfEntry
        MAX-ACCESS  not-accessible
        STATUS      current
        DESCRIPTION  
            "The BERT function configuration table"
        ::={zxAnDdnBertMgmtGroup 1}

    zxAnDdnBertConfEntry OBJECT-TYPE
        SYNTAX       ZxAnDdnBertConfEntry
        MAX-ACCESS   not-accessible
        STATUS       current
        DESCRIPTION  
            "An entry in the BERT function configuration table."
        INDEX 
            { 
                zxAnDdnBertConfRack,
                zxAnDdnBertConfShelf,
                zxAnDdnBertConfSlot,
                zxAnDdnBertConfCircuit,
                zxAnDdnBertConfTs
            }
        ::={zxAnDdnBertConfTable 1}

    ZxAnDdnBertConfEntry ::=
        SEQUENCE{
            zxAnDdnBertConfRack           Integer32,
            zxAnDdnBertConfShelf          Integer32,
            zxAnDdnBertConfSlot           Integer32,
            zxAnDdnBertConfCircuit        Integer32,
            zxAnDdnBertConfTs             Integer32,
            zxAnDdnBertAction             INTEGER,
            zxAnDdnBertTestPattern        INTEGER,
            zxAnDdnBertUserPattern        OCTET STRING,
            zxAnDdnBertMode               INTEGER,
            zxAnDdnBertDuration           Integer32,
            zxAnDdnBertStartDateAndTime   DisplayString,
            zxAnDdnBertOperStatus         INTEGER,
            zxAnDdnBertTargetType         INTEGER,
            zxAnDdnBertRowStatus          RowStatus
    }

    zxAnDdnBertConfRack  OBJECT-TYPE
        SYNTAX       Integer32
        MAX-ACCESS   not-accessible
        STATUS       current
        DESCRIPTION  "Rack of DDN BERT"
        ::={zxAnDdnBertConfEntry 1}

    zxAnDdnBertConfShelf  OBJECT-TYPE
        SYNTAX      Integer32
        MAX-ACCESS  not-accessible
        STATUS      current
        DESCRIPTION  "Shelf of DDN BERT"
        ::={zxAnDdnBertConfEntry 2}

    zxAnDdnBertConfSlot  OBJECT-TYPE
        SYNTAX       Integer32
        MAX-ACCESS   not-accessible
        STATUS       current
        DESCRIPTION  "Slot of DDN BERT"
        ::={zxAnDdnBertConfEntry 3}

    zxAnDdnBertConfCircuit  OBJECT-TYPE
        SYNTAX      Integer32
        MAX-ACCESS  not-accessible
        STATUS      current
        DESCRIPTION  "Port of DDN BERT"
        ::={zxAnDdnBertConfEntry 4}

    zxAnDdnBertConfTs  OBJECT-TYPE
        SYNTAX      Integer32
        MAX-ACCESS  not-accessible
        STATUS      current
        DESCRIPTION  "Time slot of DDN BERT"
        ::={zxAnDdnBertConfEntry 5}

    zxAnDdnBertAction  OBJECT-TYPE
        SYNTAX      INTEGER
           {
               start(1),
               stop(2)
           }
        MAX-ACCESS  read-create
        STATUS      current
        DESCRIPTION  
            "The action type of DDN BERT function."
        ::={zxAnDdnBertConfEntry 6}
   
    zxAnDdnBertTestPattern  OBJECT-TYPE
        SYNTAX      INTEGER
            {
                twoE9MinusOne(1),
                twoE11MinusOne(2),
                twoE15MinusOne(3),
                twoE20MinusOne(4),
                twoE23MinusOne(5),
                userPattern(20)
            }
        MAX-ACCESS  read-create
        STATUS      current
        DESCRIPTION  
            "The BERT pattern to be sent and expected to be received.
      
            twoE9MinusOne(1): This is 2^9-1(511 bits in length)
            pattern specified in ITU O.153.
            It has the maximum of 8(non-inverted)
            sequential zeros and 9 sequential ones.
            
            twoE11MinusOne(2): This is the 2^11-1(2047 bits in length)
            pattern specified in ITU O.152, O.153.
            It has a maximum of 10(non-inverted) 
            sequential zeros and 11 sequential ones.
            This pattern is primarily intended for
            error measurements at bit rates of 64kbit/s
            and N*64 kbit/s.
            
            twoE15MinusOne(3): This is the 2^15-1(32767 bits in length)
            pattern as specified in ITU O.151.
            It has the maximum of 15(inverted) 
            sequential zeros.
            This sequence is primarily intended for
            error and jitter measurements at bit
            rates of 1544, 2048, 6312, 8448, 32064 and 
            44736 kbit/s.
            
            twoE20MinusOne(4): This the 2^20-1(1048575 bits in length)
            pattern specified in ITU O.153.It has
            the maximum of 19(non-inverted) sequential
            zeros.  This pattern is primarily intended 
            for error measurements at bit rates up to 
            73kbit/s.  This pattern stresses the 
            equalization and timing recovery circuitry 
            of line repeaters.

            twoE23MinusOne(5): This is the 2^23-1(8388607 bit length)
            pattern specified in ITU O.151.
            Highest stress pseudo-random pattern, with 
            a maximum of 23 (inverted) sequential zeros 
            and 23 sequential ones.
            This sequence is primarily intended for
            error and jitter measurements at bit rates
            of 34368 and 139264 kbit/s.
            
            userPattern(20): This is any user defined pattern."
        DEFVAL      {twoE15MinusOne}
        ::={zxAnDdnBertConfEntry 7}

    zxAnDdnBertUserPattern  OBJECT-TYPE
        SYNTAX      OCTET STRING (SIZE(1..4))
        MAX-ACCESS  read-create
        STATUS      current
        DESCRIPTION
            "The object used for configuring the user defined pattern
            for BERT.  This is the fixed repeating BERT pattern sent
            and expected to be received when the zxAnDdnBertTestPattern
            object is set to 'userPattern'.  The maximum length of this
            pattern is 32 bits.  Depending on the hardware, the patterns
            are transmitted with least significant first or most 
            significant bit, until pattern length is reached.
            This object can not be modified when the BERT is running."
        ::={zxAnDdnBertConfEntry 8}

    zxAnDdnBertMode  OBJECT-TYPE
        SYNTAX      INTEGER
            {
                break(1),
                monitor(2)
            }
        MAX-ACCESS  read-create
        STATUS      current
        DESCRIPTION  
            "The BERT mode to be sent.
      
            In break mode, the Quality Loop Tester(QLT) shall transmit
            a test pattern into the channel under test and another QLT
            or same QLT (a loopback is activated earlier in the channel)
            shall receive the test pattern and performance measurement.
      
            In monitor mode,the QLT shall be able to read the status
            of test pattern transmitted by another QLT non-intrusively."
        DEFVAL      {break}
        ::={zxAnDdnBertConfEntry 9}

    zxAnDdnBertDuration  OBJECT-TYPE
        SYNTAX      Integer32(1..2880)
        UNITS       "Minutes"
        MAX-ACCESS  read-create
        STATUS      current
        DESCRIPTION  
            "The duration for which BERT is to be run."
        DEFVAL     {1}
        ::={zxAnDdnBertConfEntry 10}

    zxAnDdnBertStartDateAndTime  OBJECT-TYPE
        SYNTAX      DisplayString(SIZE(1..32))
        MAX-ACCESS  read-only
        STATUS      current
        DESCRIPTION  
            "The date and time when the last BERT testing is started."
        ::={zxAnDdnBertConfEntry 11}

    zxAnDdnBertOperStatus  OBJECT-TYPE
        SYNTAX      INTEGER
           {
               notStarted(1),
               inProgress(2),
               success(3),
               failed(4)
           }
        MAX-ACCESS  read-only
        STATUS      current
        DESCRIPTION  
            "The operation status of DDN BERT."
        DEFVAL      {notStarted}
        ::={zxAnDdnBertConfEntry 12}

    zxAnDdnBertTargetType  OBJECT-TYPE
        SYNTAX      INTEGER
            {
                port(1),
                link(2)
            }
        MAX-ACCESS  read-create
        STATUS      current
        DESCRIPTION  
            "The BERT target type to be sent."
        DEFVAL      {port}
        ::={zxAnDdnBertConfEntry 13}


    zxAnDdnBertRowStatus OBJECT-TYPE
        SYNTAX      RowStatus
        MAX-ACCESS  read-create
        STATUS      current
        DESCRIPTION
           "The status of this conceptual row.  This object is used for
            creating or deleting an entry from this table.
            To create a row in this table, a manager must set this
            object to either createAndGo(4).
            An entry can be deleted by setting this object to destroy(6)."
        ::= {zxAnDdnBertConfEntry 20}

--------------------------------------------------------------------------------
-- 6.zxAnDdnBertStatsTable
--------------------------------------------------------------------------------
    zxAnDdnBertStatsTable OBJECT-TYPE
        SYNTAX      SEQUENCE OF ZxAnDdnBertStatsEntry
        MAX-ACCESS  not-accessible
        STATUS      current
        DESCRIPTION  
            "The BERT function statistic table"
        ::={zxAnDdnBertMgmtGroup 2}

    zxAnDdnBertStatsEntry OBJECT-TYPE
        SYNTAX       ZxAnDdnBertStatsEntry
        MAX-ACCESS   not-accessible
        STATUS       current
        DESCRIPTION  
            "An entry in the BERT function statistic table."
            INDEX 
                { 
                    zxAnDdnBertStatsRack,
                    zxAnDdnBertStatsShelf,
                    zxAnDdnBertStatsSlot,
                    zxAnDdnBertStatsCircuit,
                    zxAnDdnBertStatsTs
                }
        ::={zxAnDdnBertStatsTable 1}

    ZxAnDdnBertStatsEntry ::=
        SEQUENCE{
            zxAnDdnBertStatsRack          Integer32,
            zxAnDdnBertStatsShelf         Integer32,
            zxAnDdnBertStatsSlot          Integer32,
            zxAnDdnBertStatsCircuit       Integer32,
            zxAnDdnBertStatsTs            Integer32,
            zxAnDdnBertRxTotalBits        Counter64,
            zxAnDdnBertRxErrorBits        Counter32,
            zxAnDdnBertRxBitErrorRatio    Unsigned32,
            zxAnDdnBertTimeElapsed        Integer32,
            zxAnDdnBertEs                 Counter32,
            zxAnDdnBertSes                Counter32,
            zxAnDdnBertUas                Counter32,
            zxAnDdnBertDm                 Counter32,
            zxAnDdnBertBbe                Counter32,
            zxAnDdnBertCses               Counter32
    }

    zxAnDdnBertStatsRack  OBJECT-TYPE
        SYNTAX       Integer32
        MAX-ACCESS   not-accessible
        STATUS       current
        DESCRIPTION  "Rack of DDN BERT"
        ::={zxAnDdnBertStatsEntry 1}

    zxAnDdnBertStatsShelf  OBJECT-TYPE
        SYNTAX      Integer32
        MAX-ACCESS  not-accessible
        STATUS      current
        DESCRIPTION  "Shelf of DDN BERT"
        ::={zxAnDdnBertStatsEntry 2}

    zxAnDdnBertStatsSlot  OBJECT-TYPE
        SYNTAX       Integer32
        MAX-ACCESS   not-accessible
        STATUS       current
        DESCRIPTION  "Slot of DDN BERT"
        ::={zxAnDdnBertStatsEntry 3}

    zxAnDdnBertStatsCircuit  OBJECT-TYPE
        SYNTAX      Integer32
        MAX-ACCESS  not-accessible
        STATUS      current
        DESCRIPTION  "Port of DDN BERT"
        ::={zxAnDdnBertStatsEntry 4}

    zxAnDdnBertStatsTs  OBJECT-TYPE
        SYNTAX      Integer32
        MAX-ACCESS  not-accessible
        STATUS      current
        DESCRIPTION  "Time slot of DDN BERT"
        ::={zxAnDdnBertStatsEntry 5}

    zxAnDdnBertRxTotalBits  OBJECT-TYPE
        SYNTAX      Counter64
        MAX-ACCESS  read-only
        STATUS      current
        DESCRIPTION  "The total number of bits be transmitted in the BERT."
        ::={zxAnDdnBertStatsEntry 6}

    zxAnDdnBertRxErrorBits  OBJECT-TYPE
        SYNTAX      Counter32
        MAX-ACCESS  read-only
        STATUS      current
        DESCRIPTION  "The number of error bits to be received in the BERT."
        ::={zxAnDdnBertStatsEntry 7}

    zxAnDdnBertRxBitErrorRatio  OBJECT-TYPE
        SYNTAX      Unsigned32(0..100)
        UNITS       "percents"
        MAX-ACCESS  read-only
        STATUS      current
        DESCRIPTION  "The ratio of received bit error in the BERT."
        ::={zxAnDdnBertStatsEntry 8}

    zxAnDdnBertTimeElapsed  OBJECT-TYPE
        SYNTAX      Integer32
        UNITS       "seconds"
        MAX-ACCESS  read-only
        STATUS      current
        DESCRIPTION  "The elapsed time in the BERT."        
        ::={zxAnDdnBertStatsEntry 9}

    zxAnDdnBertEs  OBJECT-TYPE
        SYNTAX      Counter32
        MAX-ACCESS  read-only
        STATUS      current
        DESCRIPTION  
            "Errored seconds.
            The number of 1 second intervals during the BERT that at least
            one bit error was detected in the received data pattern. "
        ::={zxAnDdnBertStatsEntry 10}

    zxAnDdnBertSes  OBJECT-TYPE
        SYNTAX      Counter32
        MAX-ACCESS  read-only
        STATUS      current
        DESCRIPTION  
            "Severely errored seconds.
            The number of 1 second intervals during the BERT that the
            bit error rate was greater than 10^-3."
        ::={zxAnDdnBertStatsEntry 11}

    zxAnDdnBertUas  OBJECT-TYPE
        SYNTAX      Counter32
        MAX-ACCESS  read-only
        STATUS      current
        DESCRIPTION  
            "The number of unavailable seconds."
        ::={zxAnDdnBertStatsEntry 12}

    zxAnDdnBertDm  OBJECT-TYPE
        SYNTAX      Counter32
        MAX-ACCESS  read-only
        STATUS      current
        DESCRIPTION  
            "The number of degraded minutes."
        ::={zxAnDdnBertStatsEntry 13}

    zxAnDdnBertBbe  OBJECT-TYPE
        SYNTAX      Counter32
        MAX-ACCESS  read-only
        STATUS      current
        DESCRIPTION  
            "The number of background block errors."
        ::={zxAnDdnBertStatsEntry 14}

    zxAnDdnBertCses  OBJECT-TYPE
        SYNTAX      Counter32
        MAX-ACCESS  read-only
        STATUS      current
        DESCRIPTION  
            "The number of consecutive severely errored seconds."
        ::={zxAnDdnBertStatsEntry 15}

--------------------------------------------------------------------------------
-- 7.zxAnDdnModemMgmtTable
--------------------------------------------------------------------------------   
    zxAnDdnModemMgmtTable OBJECT-TYPE
        SYNTAX       SEQUENCE OF ZxAnDdnModemMgmtEntry
        MAX-ACCESS   not-accessible
        STATUS       current
        DESCRIPTION  "This table includes the DDN modem information."
        ::={zxAnDdnModemMgmtGroup 1}
        
    zxAnDdnModemMgmtEntry OBJECT-TYPE
        SYNTAX       ZxAnDdnModemMgmtEntry
        MAX-ACCESS   not-accessible
        STATUS       current
        DESCRIPTION  "An entry in zxAnDdnModemMgmtTable."
        INDEX { zxAnDdnModemRack,zxAnDdnModemShelf,zxAnDdnModemSlot,
                zxAnDdnModemPort }
        ::={zxAnDdnModemMgmtTable 1}

    ZxAnDdnModemMgmtEntry  ::=  SEQUENCE {
        zxAnDdnModemRack                              Integer32,
        zxAnDdnModemShelf                             Integer32,
        zxAnDdnModemSlot                              Integer32,
        zxAnDdnModemPort                              Integer32,
        zxAnDdnModemOperStatus                        INTEGER,
        zxAnDdnModemConfigData                        DisplayString,                
        zxAnDdnModemReset                             INTEGER,
        zxAnDdnModemSaveData                          INTEGER,
        zxAnDdnModemLineStatus                        INTEGER
        }

    zxAnDdnModemRack          OBJECT-TYPE
        SYNTAX          Integer32
        MAX-ACCESS      not-accessible
        STATUS          current
        DESCRIPTION     "Rack No. of the DDN modem."
        ::=  {  zxAnDdnModemMgmtEntry  1  }

     zxAnDdnModemShelf         OBJECT-TYPE
        SYNTAX          Integer32
        MAX-ACCESS      not-accessible
        STATUS          current
        DESCRIPTION     "Shelf No. of the DDN modem."
        ::=  {  zxAnDdnModemMgmtEntry  2  }
        
     zxAnDdnModemSlot          OBJECT-TYPE
        SYNTAX          Integer32
        MAX-ACCESS      not-accessible
        STATUS          current
        DESCRIPTION     "Slot No. of the DDN modem."
        ::=  {  zxAnDdnModemMgmtEntry  3  }
        
     zxAnDdnModemPort          OBJECT-TYPE
        SYNTAX          Integer32
        MAX-ACCESS      not-accessible
        STATUS          current
        DESCRIPTION     "Port No. of the DDN modem."
        ::=  {  zxAnDdnModemMgmtEntry  4  }       
        
    zxAnDdnModemOperStatus     OBJECT-TYPE
        SYNTAX          INTEGER
        {
            online(1),
            offline(2)
        }
        MAX-ACCESS      read-only
        STATUS          current
        DESCRIPTION     "The operation status of DDN Modem."
        ::=  {  zxAnDdnModemMgmtEntry  5  }
        
    zxAnDdnModemConfigData     OBJECT-TYPE
        SYNTAX          DisplayString
        MAX-ACCESS      read-write
        STATUS          current
        DESCRIPTION     "The config data of DDN modem which set in text 
                         format."
        ::=  {  zxAnDdnModemMgmtEntry  6  }        
        
    zxAnDdnModemReset          OBJECT-TYPE
        SYNTAX          INTEGER
        {
            reset(1)
        }
        MAX-ACCESS      read-write
        STATUS          current
        DESCRIPTION     "Request a DDN modem reset to occur."
        ::=  {  zxAnDdnModemMgmtEntry  7  }
        
    zxAnDdnModemSaveData          OBJECT-TYPE
        SYNTAX          INTEGER
        {
            saveData(1)
        }
        MAX-ACCESS      read-write
        STATUS          current
        DESCRIPTION     "Request a DDN modem to save config data."
        ::=  {  zxAnDdnModemMgmtEntry  8  }
        
   zxAnDdnModemLineStatus         OBJECT-TYPE
        SYNTAX          INTEGER
        {
            shdslSnrMarginCrossing(1),
            shdslLoopAttenCrossing(2),
            shdslLossOfSyncWord(3),
            e1LossOfSignal(11),
            e1LossOfFrame(12),
            e1CrcError(13),
            v35IfConnectionBroken(14),
            dteIfConnectionBroken(21)
        }
        MAX-ACCESS      read-only
        STATUS          current
        DESCRIPTION     "DDN Modem SHDSL Line Status.
                         snrMarginCrossing  indicates that the SNR margin 
                         threshold has been reached/exceeded.
                         loopAttenCrossing indicates that the loop attenuation
                         threshold has been reached/exceeded.
                         loswsThresh indicates that the LOSW seconds threshold
                         has been reached/exceeded.
                         e1LossOfSignal(LOS)-The loss of signal alarm occurs 
                         and a failure is declared (for E1 links) when more
                         than ten consecutive zeroes are detected. 
                         e1LossOfFrame(LOF)-The loss of frame alarm occurs 
                         and a failure is declared (for E1 links) when an 
                         out-of-frame (OOF) defect has persisted for T seconds,
                         where 2 &eth; T &eth; 10. This failure is cleared 
                         when there have been no OOF defects during a period 
                         T seconds, where 0 &eth; T &eth; 20. 
                         e1CrcError(13) is declared when crc error has been 
                         detected.
                         v35IfConnectionBroken(14) is declared when the
                         DTE interface not connected the DCE device.
                         dteIfConnectionBroken(21) is declared when the 
                         DTE interface not connected the DCE device."
        ::=  {  zxAnDdnModemMgmtEntry  9  }
        
--------------------------------------------------------------------------------
-- 8.zxAnDdnModemQueryTable
--------------------------------------------------------------------------------  
    zxAnDdnModemQueryTable OBJECT-TYPE
        SYNTAX       SEQUENCE OF ZxAnDdnModemQueryEntry
        MAX-ACCESS   not-accessible
        STATUS       current
        DESCRIPTION  "This table is defined to query the DDN modem information."
        ::={zxAnDdnModemMgmtGroup 2}
        
    zxAnDdnModemQueryEntry OBJECT-TYPE
        SYNTAX       ZxAnDdnModemQueryEntry
        MAX-ACCESS   not-accessible
        STATUS       current
        DESCRIPTION  "An entry in zxAnDdnModemQueryTable."
        INDEX { zxAnDdnModemQueryRack,zxAnDdnModemQueryShelf,
                zxAnDdnModemQuerySlot,zxAnDdnModemQueryPort }
        ::={zxAnDdnModemQueryTable 1}

    ZxAnDdnModemQueryEntry  ::=  SEQUENCE {
        zxAnDdnModemQueryRack                         Integer32,
        zxAnDdnModemQueryShelf                        Integer32,
        zxAnDdnModemQuerySlot                         Integer32,
        zxAnDdnModemQueryPort                         Integer32,                
        zxAnDdnModemQueryType                         INTEGER,
        zxAnDdnModemQueryStatus                       INTEGER,
        zxAnDdnModemQueryResult                       DisplayString
        }

    zxAnDdnModemQueryRack          OBJECT-TYPE
        SYNTAX          Integer32
        MAX-ACCESS      not-accessible
        STATUS          current
        DESCRIPTION     "Rack No. of the DDN modem."
        ::=  {  zxAnDdnModemQueryEntry  1  }

     zxAnDdnModemQueryShelf         OBJECT-TYPE
        SYNTAX          Integer32
        MAX-ACCESS      not-accessible
        STATUS          current
        DESCRIPTION     "Shelf No. of the DDN modem."
        ::=  {  zxAnDdnModemQueryEntry  2  }
        
     zxAnDdnModemQuerySlot          OBJECT-TYPE
        SYNTAX          Integer32
        MAX-ACCESS      not-accessible
        STATUS          current
        DESCRIPTION     "Slot No. of the DDN modem."
        ::=  {  zxAnDdnModemQueryEntry  3  }
        
     zxAnDdnModemQueryPort          OBJECT-TYPE
        SYNTAX          Integer32
        MAX-ACCESS      not-accessible
        STATUS          current
        DESCRIPTION     "Port No. of the DDN modem."
        ::=  {  zxAnDdnModemQueryEntry  4  }
     
    zxAnDdnModemQueryType      OBJECT-TYPE
        SYNTAX          INTEGER
        {
            config(1),
            perf(2)
        }
        MAX-ACCESS      read-write
        STATUS          current
        DESCRIPTION     "It is defined getting a DDN modem's config data 
                         or perf data.                         
                         A query will be started by setting this mib variable, 
                         and variable zxAnDdnModemQueryStatus will be set. 
                         During the query, the value is inProgress(2). 
                         If modem returned a result, the 
                         zxAnDdnModemQueryStatus value is success(3),
                         else the value is failed(4). 
                         The mib variable zxAnDdnModemQueryResult can be read
                         to get the result if query successfully, 
                         while if query failed, the reading is meaningless."
        ::=  {  zxAnDdnModemQueryEntry  5  }
        
    zxAnDdnModemQueryStatus    OBJECT-TYPE
        SYNTAX          INTEGER
        {
            notStarted(1),
            inProgress(2),
            success(3),
            failed(4)
        }
        MAX-ACCESS      read-only
        STATUS          current
        DESCRIPTION     "The status of getting DDN modem's config data or perf
                         data.
                         The details could refer to the zxAnDdnModemQueryType's
                         description."
        ::=  {  zxAnDdnModemQueryEntry  6  }

    zxAnDdnModemQueryResult          OBJECT-TYPE
        SYNTAX          DisplayString
        MAX-ACCESS      read-only
        STATUS          current
        DESCRIPTION     "The result of getting DDN modem's config data or perf
                         data which returns in text format.
                         The details could refer to the zxAnDdnModemQueryType's
                         description."
        ::=  {  zxAnDdnModemQueryEntry  7  }        
        
--------------------------------------------------------------------------------
-- 9.zxAnDdnModemDiagnoseTable
--------------------------------------------------------------------------------     
    zxAnDdnModemDiagnoseTable OBJECT-TYPE
        SYNTAX       SEQUENCE OF ZxAnDdnModemDiagnoseEntry
        MAX-ACCESS   not-accessible
        STATUS       current
        DESCRIPTION  "This table includes the DDN modem information."
        ::={zxAnDdnModemMgmtGroup 3}
        
    zxAnDdnModemDiagnoseEntry OBJECT-TYPE
        SYNTAX       ZxAnDdnModemDiagnoseEntry
        MAX-ACCESS   not-accessible
        STATUS       current
        DESCRIPTION  "An entry in zxAnDdnModemMgmtTable."
        INDEX { zxAnDdnModemDiagnoseRack,zxAnDdnModemDiagnoseShelf,
                zxAnDdnModemDiagnoseSlot,zxAnDdnModemDiagnosePort }
        ::={zxAnDdnModemDiagnoseTable 1}

    ZxAnDdnModemDiagnoseEntry  ::=  SEQUENCE {
        zxAnDdnModemDiagnoseRack                      Integer32,
        zxAnDdnModemDiagnoseShelf                     Integer32,
        zxAnDdnModemDiagnoseSlot                      Integer32,
        zxAnDdnModemDiagnosePort                      Integer32,
        zxAnDdnModemDiagnoseType                      INTEGER,
        zxAnDdnModemDiagnoseStatus                    INTEGER
        }

    zxAnDdnModemDiagnoseRack          OBJECT-TYPE
        SYNTAX          Integer32
        MAX-ACCESS      not-accessible
        STATUS          current
        DESCRIPTION     "Rack No. of the DDN modem."
        ::=  {  zxAnDdnModemDiagnoseEntry  1  }

     zxAnDdnModemDiagnoseShelf         OBJECT-TYPE
        SYNTAX          Integer32
        MAX-ACCESS      not-accessible
        STATUS          current
        DESCRIPTION     "Shelf No. of the DDN modem."
        ::=  {  zxAnDdnModemDiagnoseEntry  2  }
        
     zxAnDdnModemDiagnoseSlot          OBJECT-TYPE
        SYNTAX          Integer32
        MAX-ACCESS      not-accessible
        STATUS          current
        DESCRIPTION     "Slot No. of the DDN modem."
        ::=  {  zxAnDdnModemDiagnoseEntry  3  }
        
     zxAnDdnModemDiagnosePort          OBJECT-TYPE
        SYNTAX          Integer32
        MAX-ACCESS      not-accessible
        STATUS          current
        DESCRIPTION     "Port No. of the DDN modem."
        ::=  {  zxAnDdnModemDiagnoseEntry  4  }   
        
    zxAnDdnModemDiagnoseType          OBJECT-TYPE
        SYNTAX          INTEGER
        {
            selfDiagnose(1)
        }
        MAX-ACCESS      read-write
        STATUS          current
        DESCRIPTION     "Request a DDN modem self diagnose to occur.
                         During the diagnose, the variable 
                         zxAnDdnModemDiagnoseStatus value is inProgress(2).
                         And zxAnDdnModemDiagnoseStatus will be set 
                         success(3) or failed(4) after diagnose."
        ::=  {  zxAnDdnModemDiagnoseEntry  5  }
        
    zxAnDdnModemDiagnoseStatus       OBJECT-TYPE
        SYNTAX          INTEGER
        {
            notStarted(1),
            inProgress(2),
            success(3),
            failed(4)
        }
        MAX-ACCESS      read-only
        STATUS          current
        DESCRIPTION     "The result of DDN modem's self diagnose.
                         The details could refer to the zxAnDdnModemDiagnose's
                         description."        
        ::=  {  zxAnDdnModemDiagnoseEntry  6  }  

--------------------------------------------------------------------------------
-- 10.zxAnDdnGhdbCardTable
--------------------------------------------------------------------------------  
    zxAnDdnGhdbCardTable OBJECT-TYPE
        SYNTAX       SEQUENCE OF ZxAnDdnGhdbCardEntry
        MAX-ACCESS   not-accessible
        STATUS       current
        DESCRIPTION  "GHDB card configuration table."
        ::={msagDDNConfig 8}

    zxAnDdnGhdbCardEntry OBJECT-TYPE
        SYNTAX       ZxAnDdnGhdbCardEntry
        MAX-ACCESS   not-accessible
        STATUS       current
        DESCRIPTION  "Entry of GHDB card configuration table."
        INDEX { zxAnDdnGhdbRack,zxAnDdnGhdbShelf,zxAnDdnGhdbSlot }
        ::={zxAnDdnGhdbCardTable 1}

    ZxAnDdnGhdbCardEntry ::=
        SEQUENCE{
            zxAnDdnGhdbRack        Integer32,
            zxAnDdnGhdbShelf       Integer32,
            zxAnDdnGhdbSlot        Integer32,
            zxAnDdnGhdbWorkMode    INTEGER
        }

    zxAnDdnGhdbRack  OBJECT-TYPE
        SYNTAX       Integer32
        MAX-ACCESS   not-accessible
        STATUS       current
        DESCRIPTION  "Rack of GHDB card."
        ::={zxAnDdnGhdbCardEntry 1}

    zxAnDdnGhdbShelf  OBJECT-TYPE
        SYNTAX       Integer32
        MAX-ACCESS   not-accessible
        STATUS       current
        DESCRIPTION  "Shelf of GHDB card."
        ::={zxAnDdnGhdbCardEntry 2}

    zxAnDdnGhdbSlot  OBJECT-TYPE
        SYNTAX       Integer32
        MAX-ACCESS   not-accessible
        STATUS       current
        DESCRIPTION  "Slot of GHDB card."
        ::={zxAnDdnGhdbCardEntry 3}

    zxAnDdnGhdbWorkMode  OBJECT-TYPE
        SYNTAX       INTEGER
            {
                tdm(1),
                e1Transparent(2),
                narrowbandConvergence(3),
                cesopsn(4),
                satop(5),
                mixed(6)
            }
        MAX-ACCESS   read-write
        STATUS       current
        DESCRIPTION  
            "Working mode of GHDB card.
             tdm(1): 
                    The all E1 chips and the all SHDSL chips are structured, the
                    CES is not working. It means traditional DDN service.
             e1Transparent(2): 
                    The all E1 chips and the all SHDSL chips are unstructured, 
                    the CES is not working. 
                    It means that the E1 transmits data transparently.
             narrowbandConvergence(3): 
                    The first E1 chip and the first SHDSL chip are structured, 
                    the second E1 chip and the second SHDSL chip are 
                    unstructured. 
                    It means that the narrowband service is converged on the E1.
             cesopsn(4): 
                    The CES is structured, the all E1 chips and the all SHDSL
                    chips are unstructured. 
                    It means that it supports the structured PWE3 service 
                    configuration.
             satop(5): 
                    The CES is unstructured, the all E1 chips and the all SHDSL 
                    chips are unstructured. 
                    It means that it supports the unstructured PWE3 service
                    configuration.
             mixed(6):
                    The CES is unstructured, the first E1 chip is unstructured
                    and connected with CES, the second E1 chip and the all SHDSL 
                    chips are structured. 
                    It means that the data is transmitted transparently by the
                    unstructured E1 connected with the CES."
        DEFVAL { tdm }
        ::={zxAnDdnGhdbCardEntry 4}  
--------------------------------------------------------------------------------
-- 100.zxAnDdnTrapObjects
--------------------------------------------------------------------------------  
    zxAnDdnModemLineStatusAbnormal         NOTIFICATION-TYPE
        OBJECTS        { zxAnDdnModemLineStatus }
        STATUS         current
        DESCRIPTION    "DDN modem SHDSL line status abnormal."
        ::= { zxAnDdnModemTrapGroup 1 }
       
    zxAnDdnModemLineStatusNormal           NOTIFICATION-TYPE
        OBJECTS        { zxAnDdnModemLineStatus }
        STATUS         current
        DESCRIPTION    "It indicates that the DDN modem SHDSL line status 
                        abnormal fault is cleared."
        ::= { zxAnDdnModemTrapGroup 2 }  

    zxAnDdnPortLinkDown         NOTIFICATION-TYPE
        OBJECTS        { zxAnDdnModemOperStatus }
        STATUS         current
        DESCRIPTION    "It indicates that the DDN port is down."
        ::= { zxAnDdnModemTrapGroup 3 }
       
    zxAnDdnPortLinkUp        NOTIFICATION-TYPE
        OBJECTS        { zxAnDdnModemOperStatus }
        STATUS         current
        DESCRIPTION    "It indicates that the DDN port is up."
        ::= { zxAnDdnModemTrapGroup 4 }               
END

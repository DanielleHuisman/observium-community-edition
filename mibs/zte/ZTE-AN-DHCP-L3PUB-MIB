ZTE-AN-DHCP-L3PUB-MIB DEFINITIONS ::= BEGIN

IMPORTS 
      OBJECT-TYPE, MODULE-IDENTITY                            FROM SNMPv2-SMI
    zxAn, ZxAnIfindex                                       FROM ZTE-AN-TC-MIB;

    zxAnDhcpL3PubMIB MODULE-IDENTITY
    LAST-UPDATED "200705080000Z"
    ORGANIZATION "zte Telcom Co. Ltd."
    CONTACT-INFO
        "E-mail: shen.yuyang@zte.com.cn,
         E-mail: suchunshan@zte.com.cn"
    DESCRIPTION
        "The MIB module is for configuration of DHCP L3 public 
         feature."
    ::= { zxAn 52 }

    zxAnDhcpL3PubMIBNotifs
        OBJECT IDENTIFIER ::= { zxAnDhcpL3PubMIB 0 }
    zxAnDhcpL3PubMIBObjects
        OBJECT IDENTIFIER ::= { zxAnDhcpL3PubMIB 1 }

    zxAnDlGlobal
        OBJECT IDENTIFIER ::= { zxAnDhcpL3PubMIBObjects 1 }
    zxAnDlVlanInterface
        OBJECT IDENTIFIER ::= { zxAnDhcpL3PubMIBObjects 2 }
    
-- the global group

    zxAnDlGlobalEnable OBJECT-TYPE
        SYNTAX      INTEGER
            {   
                enable(1),
                disable(2)
            }
        MAX-ACCESS  read-write
        STATUS      current
        DESCRIPTION
        "dhcp L3 global status"             
        REFERENCE "Used by MAP"
        DEFVAL { disable }

        ::= { zxAnDlGlobal 1 }
        
    zxAnDlLog OBJECT-TYPE
        SYNTAX      INTEGER
            {   
                enable(1),
                disable(2)
            }
        MAX-ACCESS  read-write
        STATUS      current
        DESCRIPTION
        "dhcp loggin on status"
        DEFVAL { disable }
        ::= { zxAnDlGlobal 2 }

-- the vlan interface group

    zxAnDlVlanIntTable OBJECT-TYPE 
        SYNTAX      SEQUENCE OF ZxAnDlVlanIntEntry 
        MAX-ACCESS  not-accessible 
        STATUS      current 
        DESCRIPTION 
        " dhcp vlan interface relay table. " 
        ::= { zxAnDlVlanInterface 1 }
    
    zxAnDlVlanIntEntry OBJECT-TYPE 
        SYNTAX      ZxAnDlVlanIntEntry
        MAX-ACCESS  not-accessible 
        STATUS      current 
        DESCRIPTION 
        " dhcp vlan interface L3 public entry. "
        INDEX { zxAnDlIntIndex }
        ::= { zxAnDlVlanIntTable 1 }
    
    ZxAnDlVlanIntEntry ::= SEQUENCE {
        zxAnDlIntIndex        ZxAnIfindex,
        zxAnDlMode            INTEGER
        }
    
    zxAnDlIntIndex OBJECT-TYPE
      SYNTAX      ZxAnIfindex
      MAX-ACCESS  not-accessible 
      STATUS      current
      DESCRIPTION
          "set the vlan interface." 
      ::= { zxAnDlVlanIntEntry 1 }
      
    zxAnDlMode OBJECT-TYPE
      SYNTAX      INTEGER
            {   
                nowork(0),
                server(1),
                relay(2),
                proxy(3)
            }
      MAX-ACCESS  read-write 
      STATUS      current
      DESCRIPTION
          "set the vlan interface dhcp work mode." 
      ::= { zxAnDlVlanIntEntry 2 }
END

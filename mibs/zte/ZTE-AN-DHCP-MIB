ZTE-AN-DHCP-MIB DEFINITIONS ::= BEGIN 
IMPORTS 
    OBJECT-TYPE, MODULE-IDENTITY,Integer32      FROM SNMPv2-SMI
    zxAnPortLocatingMib                         FROM ZTE-AN-PORT-LOCATING-MIB
    ZxAnIfindex,zxAn                            FROM ZTE-AN-TC-MIB
    RowStatus                                   FROM SNMPv2-TC;
    
    zxAnDhcpMib   MODULE-IDENTITY 
         LAST-UPDATED    "0608140000Z"  -- july. 23, 2005
        ORGANIZATION    "zte Telcom Co. Ltd."
        CONTACT-INFO    "E-mail: shen.yuyang@zte.com.cn,
                         E-mail: suchunshan@zte.com.cn"
        DESCRIPTION     "This MIB defines DHCP managed objects for Access Node."
        ::= { zxAnPortLocatingMib 21 }



    zxAnDhcpV4L2RAEnable OBJECT-TYPE
        SYNTAX      INTEGER
            {   
                enable(1),
                disable(2)
            }
        MAX-ACCESS  read-write
        STATUS      current
        DESCRIPTION
        "enable = 1, disable = 2"
        DEFVAL { disable }
        ::= { zxAnDhcpMib 1 }
    
    zxAnPortLocatingDhcp128Enable OBJECT-TYPE
        SYNTAX      INTEGER
            {   
                enable(1),
                disable(2)
            }
        MAX-ACCESS  read-write
        STATUS      current
        DESCRIPTION
        "enable = 1, disable = 2"
        DEFVAL { disable }
        ::= { zxAnDhcpMib 2 }
        
    zxAnDhcpV6L2RAEnable OBJECT-TYPE
        SYNTAX      INTEGER
            {   
                enable(1),
                disable(2)
            }
        MAX-ACCESS  read-write
        STATUS      current
        DESCRIPTION
        "enable = 1, disable = 2"
        DEFVAL { disable }
        ::= { zxAnDhcpMib 3 }     
        
    zxAnPortLocatingDhcpVmacEnable OBJECT-TYPE
        SYNTAX      INTEGER
            {   
                enable(1),
                disable(2)
            }
        MAX-ACCESS  read-write
        STATUS      current
        DESCRIPTION
        "enable = 1 disable = 2 config the port status for virtual mac function"
        DEFVAL { disable }
        ::= { zxAnDhcpMib 4 }      

    zxAnDhcpv6PortLocatingWorkMode OBJECT-TYPE
        SYNTAX      INTEGER
            {   
                tcMode(1),
                layer2Mode(2),
                layer3Mode(3)
            }
        MAX-ACCESS  read-write
        STATUS      current
        DESCRIPTION
        "DHCPv6 work mode."
        DEFVAL { layer2Mode }
        ::= { zxAnDhcpMib 5 }
    
    --table
    
    zxAnPortLocatingDhcpTable OBJECT-TYPE 
        SYNTAX SEQUENCE OF ZxAnPortLocatingDhcpEntry 
        MAX-ACCESS not-accessible 
        STATUS current 
        DESCRIPTION 
        "port Locating dhcp table" 
        ::= { zxAnDhcpMib 20 }
    
    zxAnPortLocatingDhcpEntry OBJECT-TYPE 
        SYNTAX ZxAnPortLocatingDhcpEntry
        MAX-ACCESS not-accessible 
        STATUS current 
        DESCRIPTION 
        " port Locating dhcp entry. "
        INDEX { zxAnPortLocatingDhcpIndex } 
        ::= { zxAnPortLocatingDhcpTable 1 }
    
    ZxAnPortLocatingDhcpEntry ::= SEQUENCE {
        zxAnPortLocatingDhcpIndex          ZxAnIfindex,
        zxAnDhcpV4L2RAIfConfEnable   INTEGER, 
        zxAnPortLocatingPortDhcp128Enable  INTEGER,
        zxAnDhcpV4L2RAIfConfTrust          INTEGER,
        zxAnDhcpV4L2RAIfConfPolicy         INTEGER,
        zxAnPortLocatingPortDhcpSnoopEnable  INTEGER }
        
    zxAnPortLocatingDhcpIndex     OBJECT-TYPE
        SYNTAX             ZxAnIfindex
        MAX-ACCESS         not-accessible
        STATUS          current
        DESCRIPTION
            "The ifindex of the port pppoe location."
        ::= { zxAnPortLocatingDhcpEntry 1 }        
        
    zxAnDhcpV4L2RAIfConfEnable OBJECT-TYPE 
        SYNTAX INTEGER 
            {   
                enable(1),
                disable(2)
            }
        MAX-ACCESS read-write 
        STATUS current 
        DESCRIPTION 
        "enable = 1, disable = 2"
        DEFVAL { disable }
        ::= { zxAnPortLocatingDhcpEntry 2 }
    
    zxAnPortLocatingPortDhcp128Enable OBJECT-TYPE 
        SYNTAX INTEGER 
            {   
                enable(1),
                disable(2)
            }
        MAX-ACCESS read-write 
        STATUS current 
        DESCRIPTION 
        "enable = 1, disable = 2"
        DEFVAL { disable }
        ::= { zxAnPortLocatingDhcpEntry 3 }
    
    zxAnDhcpV4L2RAIfConfTrust OBJECT-TYPE 
        SYNTAX INTEGER 
            {   
                true(1),
                false(2)
            }
        MAX-ACCESS read-write 
        STATUS current 
        DESCRIPTION 
        "true = 1, false = 2"
        DEFVAL { false }
        ::= { zxAnPortLocatingDhcpEntry 4 }
        
    zxAnDhcpV4L2RAIfConfPolicy OBJECT-TYPE 
        SYNTAX INTEGER 
            {
                keep(1), 
                replace(2), 
                discard(3), 
                add(4)
            }
        MAX-ACCESS read-write 
        STATUS current 
        DESCRIPTION 
        "keep = 1, replace = 2, discard = 3, add = 4, when port = trust, policy
        can set keep ort replace, when port = untrust, policy can set discard or
        add"
        DEFVAL { add }
        ::= { zxAnPortLocatingDhcpEntry 5 }
    zxAnPortLocatingPortDhcpSnoopEnable OBJECT-TYPE 
        SYNTAX INTEGER 
            {   
                enable(1),
                disable(2)
            }
        MAX-ACCESS read-write 
        STATUS current 
        DESCRIPTION 
        "enable = 1, disable = 2"
        DEFVAL { disable }
        ::= { zxAnPortLocatingDhcpEntry 6 }
        
    --dhcpv6 table        
    zxAnDhcpv6PortLocatingDhcpTable OBJECT-TYPE 
        SYNTAX SEQUENCE OF ZxAnDhcpv6PortLocatingDhcpEntry 
        MAX-ACCESS not-accessible 
        STATUS current 
        DESCRIPTION 
        "port Locating dhcpv6 table" 
        ::= { zxAnDhcpMib 21 }
    
    zxAnDhcpv6PortLocatingDhcpEntry OBJECT-TYPE 
        SYNTAX ZxAnDhcpv6PortLocatingDhcpEntry
        MAX-ACCESS not-accessible 
        STATUS current 
        DESCRIPTION 
        " port Locating dhcpv6 entry. "
        INDEX { zxAnDhcpv6PortLocatingDhcpIndex } 
        ::= { zxAnDhcpv6PortLocatingDhcpTable 1 }
    
    ZxAnDhcpv6PortLocatingDhcpEntry ::= SEQUENCE {
        zxAnDhcpv6PortLocatingDhcpIndex          ZxAnIfindex,
        zxAnDhcpV6L2RAIfConfEnable          INTEGER,         
        zxAnDhcpV6L2RAIfConfTrust           INTEGER,
        zxAnDhcpV6L2RAIfConfPolicy          INTEGER,
        zxAnDhcpv6PortLocatingPortDhcpSnoopEnable  INTEGER 
        }
        
    zxAnDhcpv6PortLocatingDhcpIndex     OBJECT-TYPE
        SYNTAX             ZxAnIfindex
        MAX-ACCESS         not-accessible
        STATUS          current
        DESCRIPTION
            "The ifindex of the port pppoe location."
        ::= { zxAnDhcpv6PortLocatingDhcpEntry 1 }        
        
    zxAnDhcpV6L2RAIfConfEnable OBJECT-TYPE 
        SYNTAX INTEGER 
            {   
                enable(1),
                disable(2)
            }
        MAX-ACCESS read-write 
        STATUS current 
        DESCRIPTION 
        "enable = 1, disable = 2"
        DEFVAL { disable }
        ::= { zxAnDhcpv6PortLocatingDhcpEntry 2 }
          
    zxAnDhcpV6L2RAIfConfTrust OBJECT-TYPE 
        SYNTAX INTEGER 
            {   
                true(1),
                false(2)
            }
        MAX-ACCESS read-write 
        STATUS current 
        DESCRIPTION 
        "true = 1, false = 2"
        DEFVAL { false }
        ::= { zxAnDhcpv6PortLocatingDhcpEntry 3 }
        
    zxAnDhcpV6L2RAIfConfPolicy OBJECT-TYPE 
        SYNTAX INTEGER 
            {
                keep(1), 
                replace(2), 
                discard(3), 
                add(4)
            }
        MAX-ACCESS read-write 
        STATUS current 
        DESCRIPTION 
        "keep = 1, replace = 2, discard = 3, add = 4, when port = trust, policy
        can set keep ort replace, when port = untrust, policy can set discard or
        add"
        DEFVAL { add }
        ::= { zxAnDhcpv6PortLocatingDhcpEntry 4 }
    zxAnDhcpv6PortLocatingPortDhcpSnoopEnable OBJECT-TYPE 
        SYNTAX INTEGER 
            {   
                enable(1),
                disable(2)
            }
        MAX-ACCESS read-write 
        STATUS current 
        DESCRIPTION 
        "enable = 1, disable = 2"
        DEFVAL { disable }
        ::= { zxAnDhcpv6PortLocatingDhcpEntry 5 }        
        
    --Virtual MAC VLAN table
    
    zxAnPortIdDhcpVmacTable OBJECT-TYPE 
        SYNTAX SEQUENCE OF ZxAnPortIdDhcpVmacEntry 
        MAX-ACCESS  not-accessible 
        STATUS      current 
        DESCRIPTION 
            "This table is to enable DHCP virtual MAC on the inteface VLAN."
        ::= { zxAnDhcpMib 22 }
    
    zxAnPortIdDhcpVmacEntry OBJECT-TYPE 
        SYNTAX ZxAnPortIdDhcpVmacEntry
        MAX-ACCESS not-accessible 
        STATUS current 
        DESCRIPTION 
            "Port identification DHCP virtual MAC VLAN entry. "
        INDEX { zxAnPortIdDhcpVmacIfIndex, zxAnPortIdDhcpVmacVid} 
        ::= { zxAnPortIdDhcpVmacTable 1 }
    
    ZxAnPortIdDhcpVmacEntry ::= SEQUENCE {
        zxAnPortIdDhcpVmacIfIndex    ZxAnIfindex,
        zxAnPortIdDhcpVmacVid        Integer32, 
        zxAnPortIdDhcpVmacRowStatus  RowStatus 
    }
        
    zxAnPortIdDhcpVmacIfIndex     OBJECT-TYPE
        SYNTAX      ZxAnIfindex
        MAX-ACCESS  not-accessible
        STATUS      current
        DESCRIPTION
            "The ifindex of the DHCP virtual MAC table."
        ::= { zxAnPortIdDhcpVmacEntry 1 }        
        
    zxAnPortIdDhcpVmacVid OBJECT-TYPE 
        SYNTAX        Integer32(1..4094)
        MAX-ACCESS    not-accessible 
        STATUS        current 
        DESCRIPTION   
            "Interface VLAN ID."
        ::= { zxAnPortIdDhcpVmacEntry 2 }   
        
    zxAnPortIdDhcpVmacRowStatus    OBJECT-TYPE    
        SYNTAX          RowStatus 
        MAX-ACCESS      read-create
        STATUS          current
        DESCRIPTION     
            "The status of this conceptual row.                      
             The supported actions of this conceptual row only include:
             'createAndGo' and 'destroy'. 
             
             To create a row in this table, a manager must set this object to 
             createAndGo(4), and must comply with the rule described in 
             zxAnPortIdDhcpVmacEntry.    
             To delete a row in this table, a manager must set this object to 
             destroy(6).             
             To get this object, the agent always returns active(1)."
        ::=  {  zxAnPortIdDhcpVmacEntry  50  }   
        
END

ZTE-AN-DHCP-SERVER-MIB DEFINITIONS ::= BEGIN

IMPORTS
      OBJECT-TYPE, MODULE-IDENTITY, IpAddress                 FROM SNMPv2-SMI
    RowStatus, DisplayString, MacAddress                    FROM SNMPv2-TC
    zxAn, ZxAnIfindex                                       FROM ZTE-AN-TC-MIB;

    zxAnDhcpServerMIB MODULE-IDENTITY
    LAST-UPDATED "200612110000Z"
    ORGANIZATION "zte Inc."
    CONTACT-INFO
        "        zte corporation Systems
                 Customer Service

         Postal: E3030, bibo road 889#
                 pudong, shanghai,
                 CHINA

            Tel: +86 021-68895439

         E-mail: shen.yuyang@zte.com.cn"
    DESCRIPTION
        "The MIB module is for configuration of DHCP server
         feature."
    REVISION    "200612110000Z"
    DESCRIPTION
        "Initial revision of this MIB module."
    ::= { zxAn 54 }

    zxAnDhcpServerMIBNotifs
        OBJECT IDENTIFIER ::= { zxAnDhcpServerMIB 0 }
    zxAnDhcpServerMIBObjects
        OBJECT IDENTIFIER ::= { zxAnDhcpServerMIB 1 }

    zxAnDvGlobal
        OBJECT IDENTIFIER ::= { zxAnDhcpServerMIBObjects 1 }
    zxAnDvIpPool
        OBJECT IDENTIFIER ::= { zxAnDhcpServerMIBObjects 2 }
    zxAnDvVlanInterface
        OBJECT IDENTIFIER ::= { zxAnDhcpServerMIBObjects 3 }
    zxAnDvShowUsers
        OBJECT IDENTIFIER ::= { zxAnDhcpServerMIBObjects 4 }

-- the global group

    zxAnDvPrimaryDns OBJECT-TYPE
        SYNTAX      IpAddress
        MAX-ACCESS  read-write
        STATUS      current
        DESCRIPTION
        "the primary dns ip address."
        ::= { zxAnDvGlobal 1 }

    zxAnDvSecondDns OBJECT-TYPE
        SYNTAX      IpAddress
        MAX-ACCESS  read-write
        STATUS      current
        DESCRIPTION
        "the second dns ip address."
        ::= { zxAnDvGlobal 2 }

    zxAnDvLeaseTime OBJECT-TYPE
        SYNTAX      INTEGER(60..18000)
        MAX-ACCESS  read-write
        STATUS      current
        DESCRIPTION
        "the dhcp server leasetime."
        DEFVAL { 3600 }
        ::= { zxAnDvGlobal 3 }

    zxAnDvUpdateArp OBJECT-TYPE
        SYNTAX      INTEGER
            {
                enable(1),
                disable(2)
            }
        MAX-ACCESS  read-write
        STATUS      current
        DESCRIPTION
        "enable = 1, disable = 2."
        DEFVAL { disable }
        ::= { zxAnDvGlobal 4 }

-- the ip pool group

    zxAnDvIpPoolTable OBJECT-TYPE
        SYNTAX      SEQUENCE OF ZxAnDvIpPoolEntry
        MAX-ACCESS  not-accessible
        STATUS      current
        DESCRIPTION
        " dhcp server ip pool table. "
        ::= { zxAnDvIpPool 1 }

    zxAnDvIpPoolEntry OBJECT-TYPE
        SYNTAX      ZxAnDvIpPoolEntry
        MAX-ACCESS  not-accessible
        STATUS      current
        DESCRIPTION
        " dhcp server ip pool entry. "
        INDEX { zxAnDvIpPoolName, zxAnDvBeginIp }
        ::= { zxAnDvIpPoolTable 1 }

    ZxAnDvIpPoolEntry ::= SEQUENCE {
        zxAnDvIpPoolName     DisplayString,
        zxAnDvBeginIp        IpAddress,
        zxAnDvEndIp          IpAddress,
        zxAnDvMask           IpAddress,
        zxAnDvRow            RowStatus
        }
        
    zxAnDvIpPoolName OBJECT-TYPE
      SYNTAX      DisplayString(SIZE (1..16))
      MAX-ACCESS  not-accessible
      STATUS      current
      DESCRIPTION
          "the ip pool name, used for dhcp server assign ip."
      ::= { zxAnDvIpPoolEntry 1 }

    zxAnDvBeginIp OBJECT-TYPE
      SYNTAX      IpAddress
      MAX-ACCESS  not-accessible
      STATUS      current
      DESCRIPTION
          "the begin ip of ip pool."
      ::= { zxAnDvIpPoolEntry 2 }

    zxAnDvEndIp OBJECT-TYPE
      SYNTAX      IpAddress
      MAX-ACCESS  read-create
      STATUS      current
      DESCRIPTION
          "the end ip of ip pool."
      ::= { zxAnDvIpPoolEntry 3 }

    zxAnDvMask OBJECT-TYPE
      SYNTAX      IpAddress
      MAX-ACCESS  read-create
      STATUS      current
      DESCRIPTION
          "the mask of ip pool."
      ::= { zxAnDvIpPoolEntry 4 }

    zxAnDvRow OBJECT-TYPE
      SYNTAX      RowStatus
      MAX-ACCESS  read-create
      STATUS      current
      DESCRIPTION
          "only support createAndGo and destroy."
      ::= { zxAnDvIpPoolEntry 5 }

-- the vlan interface group

    zxAnDvVlanIntTable OBJECT-TYPE
        SYNTAX      SEQUENCE OF ZxAnDvVlanIntEntry
        MAX-ACCESS  not-accessible
        STATUS      current
        DESCRIPTION
        " dhcp vlan interface server table. "
        ::= { zxAnDvVlanInterface 1 }

    zxAnDvVlanIntEntry OBJECT-TYPE
        SYNTAX      ZxAnDvVlanIntEntry
        MAX-ACCESS  not-accessible
        STATUS      current
        DESCRIPTION
        " dhcp vlan interface server entry. "
        INDEX { zxAnDvIntIndex }
        ::= { zxAnDvVlanIntTable 1 }

    ZxAnDvVlanIntEntry ::= SEQUENCE {
        zxAnDvIntIndex        ZxAnIfindex,
        zxAnDvIntIpPoolName   DisplayString
        }

    zxAnDvIntIndex OBJECT-TYPE
      SYNTAX      ZxAnIfindex
      MAX-ACCESS  not-accessible
      STATUS      current
      DESCRIPTION
          "set the vlan interface."
      ::= { zxAnDvVlanIntEntry 1 }

    zxAnDvIntIpPoolName OBJECT-TYPE
      SYNTAX      DisplayString(SIZE (1..16))
      MAX-ACCESS  read-write
      STATUS      current
      DESCRIPTION
          "set ip pool name which the dhcp server used."
      ::= { zxAnDvVlanIntEntry 2 }

-- the vlan interface gateway group

    zxAnDvVlanIntGateWayTable OBJECT-TYPE
        SYNTAX      SEQUENCE OF ZxAnDvVlanIntGateWayEntry
        MAX-ACCESS  not-accessible
        STATUS      current
        DESCRIPTION
        " dhcp vlan interface gateway table. "
        ::= { zxAnDvVlanInterface 2 }

    zxAnDvVlanIntGateWayEntry OBJECT-TYPE
        SYNTAX      ZxAnDvVlanIntGateWayEntry
        MAX-ACCESS  not-accessible
        STATUS      current
        DESCRIPTION
        " dhcp vlan interface gateway entry. "
        INDEX { zxAnDvIntIndex, zxAnDvGateway }
        ::= { zxAnDvVlanIntGateWayTable 1 }

    ZxAnDvVlanIntGateWayEntry ::= SEQUENCE {
        zxAnDvGateway         IpAddress,
        zxAnDvGatewayRow      RowStatus
        }

    zxAnDvGateway OBJECT-TYPE
      SYNTAX      IpAddress
      MAX-ACCESS  not-accessible
      STATUS      current
      DESCRIPTION
          "set the dhcp server assign client's gateway."
      ::= { zxAnDvVlanIntGateWayEntry 1 }
    
    zxAnDvGatewayRow OBJECT-TYPE
      SYNTAX      RowStatus
      MAX-ACCESS  read-create
      STATUS      current
      DESCRIPTION
        "create or destroy the dhcp server assign client's gateway, 
                   only support createAndWait + Active and destroy"
      ::= { zxAnDvVlanIntGateWayEntry 2 }

-- the show users group

    zxAnDvUserViewTable OBJECT-TYPE 
        SYNTAX      SEQUENCE OF ZxAnDvUserViewEntry 
        MAX-ACCESS  not-accessible 
        STATUS      current 
        DESCRIPTION 
        "show dhcp server users by interface. " 
        ::= { zxAnDvShowUsers 1 }
    
    zxAnDvUserViewEntry OBJECT-TYPE 
        SYNTAX      ZxAnDvUserViewEntry
        MAX-ACCESS  not-accessible 
        STATUS      current 
        DESCRIPTION 
        "show dhcp server users entry. "
        INDEX { zxAnDvIntIndex,
                zxAnDvUserViewMac } 
        ::= { zxAnDvUserViewTable 1 }
    
    ZxAnDvUserViewEntry ::= SEQUENCE {
        zxAnDvUserViewMac           MacAddress,
        zxAnDvUserViewIp            IpAddress,
        zxAnDvUserViewState         DisplayString,
        zxAnDvUserViewTime          DisplayString }
        
    zxAnDvUserViewMac OBJECT-TYPE
        SYNTAX      MacAddress
        MAX-ACCESS  not-accessible
        STATUS      current
        DESCRIPTION
        ""
        ::= { zxAnDvUserViewEntry 1 }
        
    zxAnDvUserViewIp OBJECT-TYPE
        SYNTAX      IpAddress
        MAX-ACCESS  read-only
        STATUS      current
        DESCRIPTION
        ""
        ::= { zxAnDvUserViewEntry 2 }
        
    zxAnDvUserViewState OBJECT-TYPE
        SYNTAX      DisplayString (SIZE (0..9))
        MAX-ACCESS  read-only
        STATUS      current
        DESCRIPTION
        ""
        ::= { zxAnDvUserViewEntry 3 }
    
    zxAnDvUserViewTime OBJECT-TYPE
        SYNTAX      DisplayString (SIZE (0..50))
        MAX-ACCESS  read-only
        STATUS      current
        DESCRIPTION
        ""
        ::= { zxAnDvUserViewEntry 4 }
END

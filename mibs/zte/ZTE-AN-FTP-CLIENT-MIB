--------------------------------------------------------------------------------
-- 
-- File Name : ZTE-AN-FTP-CLIENT-MIB.mib
-- Date      : 2006-09-25
-- Author    : ZTE Nms dept.
--
-- Zte Ftp Client Mib for Access Node
-- 
-- 
--------------------------------------------------------------------------------


ZTE-AN-FTP-CLIENT-MIB DEFINITIONS ::= BEGIN
 
IMPORTS
    MODULE-IDENTITY, OBJECT-TYPE,
    IpAddress                            FROM SNMPv2-SMI 
    DisplayString                        FROM SNMPv2-TC
    zxAnSysObjects                       FROM ZTE-AN-SYS-MIB;
 
    zxAnFtpClientMIB MODULE-IDENTITY
        LAST-UPDATED "200611150900Z"
        ORGANIZATION "ZTE Corporation"
        CONTACT-INFO "ZTE NMS dept. 
                      Guo Jun       68896247,
                      Su Chunshan   68896292,
                      Zeng Nanxi    68896250 "
        DESCRIPTION  "This MIB defines managed objects of zte ftp client mgmt.
            The related functions include uploading agent's configuration files 
        and performance files to NMS ftp server,downloading the agent's version 
        to agent.       
        "
         ::= {zxAnSysObjects 50}
         

    zxAnFtpClientMIBObjects OBJECT IDENTIFIER ::= { zxAnFtpClientMIB 1 }



--------------------------------------------------------------------------------
--  
-- 
-- 1 FTP Control
--------------------------------------------------------------------------------
-- 1 FTP Control
--------------------------------------------------------------------------------
    zxAnFileFtpFileType  OBJECT-TYPE 
        SYNTAX          INTEGER
                    {
                        sys_conf_startup(1),  -- 0x0001  system file
                        sys_conf_running(2),  -- 0x0002  system file
                        sys-conf-onu(3),      -- 0x0003  ONU conf file
                        sys-version-onu(4),   -- 0x0004  ONU version file
                        sys-conf-narrowband(5),   -- 0x0005  narrowband conf file
                        sys-license-narrowband(6), -- 0x0006  narrowband license file
                        sys-log-debugging(7), -- 0x0007   Debugging Log file
                        sys-log-snmp(8), -- 0x0008  SNMP Log file
                        sys-log-running(9), -- 0x0009 Running Log file
                        sys-log-clioperation(10), -- 0x0010 Cli Operation Log file
                        xmlForPmMeasurementPoints(51),
                         -- 0x000B xml file for performance measurement points
                        xmlForThresholdCrossingAlert(52),
                         -- 0x000C xml file for threshold crossing alert
                        csvForPmData(53),
                         -- 0x000D xml file for performance data
                        adsl_port_log(257),    -- 0x0101  adsl file
                        gpon_port_log(258)     -- 0x0102  gpon file
                        dataBulkMeasurement(259),           -- 0x0103  Bulk measurement file
                        selfswitchTelFile(513) -- 0x0201  selfswitch telephone
                    }
        MAX-ACCESS      read-write
        STATUS          current
        DESCRIPTION     "
             The ftp client function is used to implement the transmission of 
         data or statics file between an agent and a manager.
             This object is to indicate the type of being transmitted object,such as
         data,file. 
         
         Different operations have different ManagedObjectType as followings.
         System configure file include:startup file,running file.
         Statistic file inclued:adsl port log file,gpon port log file,and so on.
                                               
         NOTE:
              Perf Log or Mib Data File Format
            -------------------------------------
          The performance data or some mib data in an agent may be mass.So 
          using ftp mode to transfer the data is necessary.
          In this case,following format should be used in the transfered file.
           
           1.The title for this file should be added to the file. And the title
           is just the mib variable name.
           
           2.The fields in the file should be seperated by '||'.
                      
           Example:
           
           ifIndex||ifOutOctets||ifInOctets||ifAdinstatus
           12||1400||342||1||1    
           13||238||264||1||1    
           14||8602||2565||2||2    
                                               
         "
        ::=  {  zxAnFtpClientMIBObjects  1  }

    zxAnFileFtpOperType OBJECT-TYPE 
        SYNTAX      INTEGER
                {
                    upload(1),
                    download(2)
                }
        MAX-ACCESS  read-write
        STATUS      current
        DESCRIPTION " 
        The operation type is based on ManagedMainType and ManagedSubType.
         UpLoad:   put file to NMS ftp server.Used for SubType: PORT_LINK_INFO,STARTUP_FILE,RUNNING_FILE,SAVED_FILE.
                 DownLoad: get file from NMS ftp server.Used for SubType: STARTUP_FILE,RUNNING_FILE,SAVED_FILE.
           "
        ::=  {  zxAnFtpClientMIBObjects  2  }

    zxAnFileFtpSvrIpAddress  OBJECT-TYPE 
        SYNTAX          IpAddress
        MAX-ACCESS      read-write
        STATUS          current
        DESCRIPTION     "
             The IP Address for the FTP server used for downloading
             and/or uploading files."
        ::=  {  zxAnFtpClientMIBObjects  3  }

    zxAnFileFtpSvrUserName   OBJECT-TYPE 
        SYNTAX          DisplayString  ( SIZE ( 1 .. 32  ) ) 
        MAX-ACCESS      read-write
        STATUS          current
        DESCRIPTION     "The FTP username."
        ::=  {  zxAnFtpClientMIBObjects  4  }

    zxAnFileFtpSvrUserPwd    OBJECT-TYPE 
        SYNTAX          DisplayString  ( SIZE ( 1 .. 32  ) ) 
        MAX-ACCESS      read-write
        STATUS          current
        DESCRIPTION     "The FTP User Password."
        ::=  {  zxAnFtpClientMIBObjects  5  }

    zxAnFileFtpSvrFilePath   OBJECT-TYPE 
        SYNTAX          DisplayString  ( SIZE ( 1 .. 64  ) ) 
        MAX-ACCESS      read-write
        STATUS          current
        DESCRIPTION     " The FTP File Path, start from the root directory."
        ::=  {  zxAnFtpClientMIBObjects  6 }

    zxAnFileFtpSvrFileName   OBJECT-TYPE 
        SYNTAX          DisplayString  ( SIZE ( 1 .. 128  ) ) 
        MAX-ACCESS      read-write
        STATUS          current
        DESCRIPTION     "The FTP file name."
        ::=  {  zxAnFtpClientMIBObjects  7  }

    zxAnFileFtpAction  OBJECT-TYPE 
        SYNTAX      INTEGER  
                    { 
                        cancleCurrentFtpSession (1) 
                    } 
        MAX-ACCESS  read-write
        STATUS      current
        DESCRIPTION " Ftp administrative status."
        ::=  {  zxAnFtpClientMIBObjects  8 }

    zxAnFileFtpOperStatus   OBJECT-TYPE 
        SYNTAX          INTEGER  
                        { 
                          notstarted (1) , 
                          inprogress (2) , 
                          success (3) , 
                          failed (4) 
                        } 
        MAX-ACCESS  read-only
        STATUS      current
        DESCRIPTION     " Ftp operational status."
        ::=  {  zxAnFtpClientMIBObjects  9  }


    zxAnFileFtpFailedReason OBJECT-TYPE 
        SYNTAX      DisplayString  ( SIZE ( 1 .. 64  ) )   
        MAX-ACCESS  read-only
        STATUS      current
        DESCRIPTION " Ftp failed reason."
        ::=  {  zxAnFtpClientMIBObjects  10  }
        
    zxAnFileFtpSvrProtocolType       OBJECT-TYPE     
        SYNTAX          INTEGER 
                    {
                        ftp(1),
                        sftp(2)
                    } 
        MAX-ACCESS      read-write
        STATUS          current
        DESCRIPTION     " The  flag is used for 
        indicating the ftp protocol when downing versions between EMS and NE .
        It include two protocols:one is ftp and another is sftp.
        "
        ::=  {  zxAnFtpClientMIBObjects  11 }    
        
    zxAnFileFtpProgress       OBJECT-TYPE     
        SYNTAX          INTEGER  (0..100)
        UNITS           "%"
        MAX-ACCESS      read-only
        STATUS          current
        DESCRIPTION     "The total progress of upload or download file."
        ::=  {  zxAnFtpClientMIBObjects  12  }  
        
    zxAnFileFtpPerfLogType       OBJECT-TYPE 
        SYNTAX          INTEGER  
        {
            for15Minutes(1), 
            for24Hours(2)
        }
        MAX-ACCESS    read-write
        STATUS        current
        DESCRIPTION   "The time granularity of performance data 
                       files retrieval."
        ::=  {  zxAnFtpClientMIBObjects  13  }
        
    zxAnFileFtpFileRetrieveStartTime   OBJECT-TYPE     
        SYNTAX      DisplayString 
        MAX-ACCESS  read-write
        STATUS      current
        DESCRIPTION
        "Specifies the start of the time for which the 
         selected PM measurements shall be retrieved (this parameter 
         only applies for the retrieval of historical PM data). "
        ::=  {  zxAnFtpClientMIBObjects  14 }        
        
    zxAnFileFtpFileRetrieveEndTime     OBJECT-TYPE     
        SYNTAX      DisplayString 
        MAX-ACCESS  read-write
        STATUS      current
        DESCRIPTION
        "Specifies the end of the time for which the selected 
         PM measurements shall be retrieved (this parameter only 
         applies for the retrieval of historical PM data). "
        ::=  {  zxAnFtpClientMIBObjects  15 } 
              
END

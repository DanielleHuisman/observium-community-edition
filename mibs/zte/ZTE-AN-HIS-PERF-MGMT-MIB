------------------------------------------------------------------------------- 
-- File Name : ZTE-AN-HIS-PERF-MGMT-MIB.mib
-- Date      : 2011-11-07
-- Author    : ZTE Shanghai NMS Dept.
--
-- Zte History Performance Mgmt Mib for Access Node.
-- 
------------------------------------------------------------------------------- 
ZTE-AN-HIS-PERF-MGMT-MIB DEFINITIONS ::= BEGIN 

    IMPORTS 
    MODULE-IDENTITY,NOTIFICATION-TYPE,OBJECT-TYPE,
    Integer32,Unsigned32,Counter64                  FROM SNMPv2-SMI  
    
    RowStatus,DisplayString,TEXTUAL-CONVENTION,
    TruthValue,DateAndTime                          FROM SNMPv2-TC  
    
    MODULE-COMPLIANCE, OBJECT-GROUP                 FROM SNMPv2-CONF 
    zxAn                                            FROM ZTE-AN-TC-MIB;

    zxAnHisPerfMgmtMib MODULE-IDENTITY
        LAST-UPDATED "201111070000Z"
        ORGANIZATION "ZTE Corporation"
        CONTACT-INFO "jinyongbin ZTE Corporation
                      Mail: jing.younbin@zte.com.cn 
                      Tel : 021-68897626"
        DESCRIPTION  "This MIB defines managed objects of ZTE historical 
                      performance management."
        REVISION     "201111070000Z"
        DESCRIPTION  "The initial revision of this MIB module."
        ::= {zxAn 168}
-------------------------------------------------------------------------------
-- Following management objects are defined.
-- 1.Historical performance management objects 
-- Following notification objects are defined.
-- 3.Historical performance management threshold cross alarm trap
-- Following conformance information is defined.
-- 4.Historical performance management compliance 
-------------------------------------------------------------------------------
    zxAnHisPerfMgmtObjects        
        OBJECT IDENTIFIER  ::= { zxAnHisPerfMgmtMib 1 }
    zxAnHisPerfMgmtTrapObjects    
        OBJECT IDENTIFIER  ::= { zxAnHisPerfMgmtMib 3 }
    zxAnHisPerfMgmtConformance
        OBJECT IDENTIFIER  ::= { zxAnHisPerfMgmtMib 4 }
  
-------------------------------------------------------------------------------
-- 1.Historical performance management objects
-------------------------------------------------------------------------------
    zxAnHisPerfMgmtThreshAlmObjects  
        OBJECT IDENTIFIER   ::= { zxAnHisPerfMgmtObjects 1 }  
    zxAnHisPerfMgmtGlobalObjects
        OBJECT IDENTIFIER   ::= { zxAnHisPerfMgmtObjects 2 }

-------------------------------------------------------------------------------
-- 1.1 Historical performance management threshold alarm objects
-------------------------------------------------------------------------------
    zxAnHisPmMetricInstIndex  OBJECT-TYPE
        SYNTAX      DisplayString( SIZE ( 1 .. 128  ) ) 
        MAX-ACCESS  accessible-for-notify
        STATUS      current
        DESCRIPTION
            "The historical performance metric instance identification. 
             It identifies types of data for which historical performance
             item was collected."
        ::= { zxAnHisPerfMgmtThreshAlmObjects 1 }
             
    zxAnHisPmThresholdMetric    OBJECT-TYPE
        SYNTAX      OBJECT IDENTIFIER
        MAX-ACCESS  accessible-for-notify
        STATUS      current
        DESCRIPTION
            "A mib variable's instance of historcal performance,such as an 
             ether port monitored object,it may be 
             1.3.6.1.4.1.3902.1082.30.31.2.2.1.1"
        ::= { zxAnHisPerfMgmtThreshAlmObjects 2 }
 
    zxAnHisPmStatisticalValue OBJECT-TYPE
        SYNTAX     Counter64 
        MAX-ACCESS accessible-for-notify
        STATUS     current
        DESCRIPTION
            "Statistical value for specified metric instance."
        ::= { zxAnHisPerfMgmtThreshAlmObjects 3 }             

    zxAnHisPmRisingWarningThreshold OBJECT-TYPE
        SYNTAX      Counter64
        MAX-ACCESS  accessible-for-notify
        STATUS      current
        DESCRIPTION
            "A binding object for rising threshold cross alarm.
             When a rising warning event is generated,
             it identifies rising warning threshold value.
             When a clear rising warning event is generated,
             It identifies rising warning restore threshold value."                  
        ::= { zxAnHisPerfMgmtThreshAlmObjects 4 }

    zxAnHisPmRisingAlarmThreshold OBJECT-TYPE
        SYNTAX      Counter64
        MAX-ACCESS  accessible-for-notify
        STATUS      current
        DESCRIPTION
            "A binding object for rising threshold cross alarm.
             When a rising alarm event is generated,
             it identifies rising alarm threshold value.
             When a clear rising alarm event is generated,
             It identifies rising alarm restore threshold value."      
        ::= { zxAnHisPerfMgmtThreshAlmObjects 5 }        

    zxAnHisPmFallingWarningThreshold  OBJECT-TYPE
        SYNTAX     Counter64
        MAX-ACCESS accessible-for-notify
        STATUS     current
        DESCRIPTION
            "A binding object for falling threshold cross alarm.
             When a falling warning event is generated,
             it identifies falling warning threshold value.
             When a clear falling warning event is generated,
             It identifies falling warning restore threshold value."
        ::= { zxAnHisPerfMgmtThreshAlmObjects 6 }  

    zxAnHisPmFallingAlarmThreshold  OBJECT-TYPE
        SYNTAX     Counter64
        MAX-ACCESS accessible-for-notify
        STATUS     current
        DESCRIPTION
            "A binding object for falling threshold cross alarm.
             When a falling alarm event is generated,
             it identifies falling alarm threshold value.
             When a clear falling alarm event is generated,
             It identifies falling alarm restore threshold value."
        ::= { zxAnHisPerfMgmtThreshAlmObjects 7 } 
        
-------------------------------------------------------------------------------
-- 1.2 History Performance management global control
-------------------------------------------------------------------------------
    zxAnHisPerfMgmtSampleEnable       OBJECT-TYPE 
        SYNTAX          INTEGER
        {
            enable(1),
            disable(2)
        }
        MAX-ACCESS    read-write
        STATUS        current
        DESCRIPTION   
            "Enable or disable historical performance data sample 
             function,default value is enable.Disable operation 
             will also disable threshold check for historical performance 
             data, and performance threshold cross alarm can't be 
             generated any more,but previous alarm won't be cleared."
        DEFVAL { enable }
        ::=  {  zxAnHisPerfMgmtGlobalObjects  1  }  

    zxAnHisPerfMgmtAlarmEnable       OBJECT-TYPE     
        SYNTAX          INTEGER
        {
            enable(1),
            disable(2)
        }
        MAX-ACCESS  read-write
        STATUS      current
        DESCRIPTION
            "Enable or disable historical performance threshold cross 
             alarm function,default value is enable.Disable operation
             will clear all previous threshold cross alarm."
        DEFVAL { enable }
        ::=  {  zxAnHisPerfMgmtGlobalObjects  2 }     

    zxAnHisPerfMgmtAutoUploadEnable       OBJECT-TYPE     
        SYNTAX          INTEGER
        {
            enable(1),
            disable(2)
        }
        MAX-ACCESS  read-write
        STATUS      current
        DESCRIPTION
            "Enable or disable data files of historical performance automatic
             upload function,default value is disable.For upload data files 
             successfully,performance upload file server must be configured
             before."
        DEFVAL { disable }
        ::=  {  zxAnHisPerfMgmtGlobalObjects  3 }   
        
-------------------------------------------------------------------------------
-- 3.Historical performance management threshold cross alarm trap
-------------------------------------------------------------------------------
    zxAnPm15minRisingWarning NOTIFICATION-TYPE
        OBJECTS { 
            zxAnHisPmMetricInstIndex, 
            zxAnHisPmThresholdMetric,
            zxAnHisPmStatisticalValue, 
            zxAnHisPmRisingWarningThreshold 
        }
        STATUS       current
        DESCRIPTION
            "The 15 minutes performance SNMP trap that is generated when an 
             alarm entry crosses its rising warning threshold and generates
             an event that is configured for sending SNMP traps."
        ::= { zxAnHisPerfMgmtTrapObjects 1 }     

    zxAnPm15minRisingWarningRestore NOTIFICATION-TYPE
        OBJECTS { 
            zxAnHisPmMetricInstIndex, 
            zxAnHisPmThresholdMetric,
            zxAnHisPmStatisticalValue, 
            zxAnHisPmRisingWarningThreshold
        }
        STATUS       current
        DESCRIPTION
            "The 15 minutes performance restore SNMP trap that is generated 
             when an alarm entry restore to normal range."
        ::= { zxAnHisPerfMgmtTrapObjects 2 }

    zxAnPm15minRisingAlarm NOTIFICATION-TYPE
        OBJECTS { 
            zxAnHisPmMetricInstIndex,
            zxAnHisPmThresholdMetric, 
            zxAnHisPmStatisticalValue,
            zxAnHisPmRisingAlarmThreshold
        }
        STATUS      current
        DESCRIPTION
            "The 15 minutes performance SNMP trap that is generated when an 
             alarm entry crosses its rising alarm threshold and generates
             an event that is configured for sending SNMP traps."
        ::= { zxAnHisPerfMgmtTrapObjects 3 }  

    zxAnPm15minRisingAlarmRestore NOTIFICATION-TYPE
        OBJECTS { 
            zxAnHisPmMetricInstIndex, 
            zxAnHisPmThresholdMetric, 
            zxAnHisPmStatisticalValue,
            zxAnHisPmRisingAlarmThreshold
        }
        STATUS             current
        DESCRIPTION
            "The 15 minutes performance restore SNMP trap that is generated 
             when an alarm entry restore to normal range."
        ::= { zxAnHisPerfMgmtTrapObjects 4 }                                

    zxAnPm24hRisingWarning NOTIFICATION-TYPE
        OBJECTS {  
            zxAnHisPmMetricInstIndex, 
            zxAnHisPmThresholdMetric,
            zxAnHisPmStatisticalValue, 
            zxAnHisPmRisingWarningThreshold
        }
        STATUS             current
        DESCRIPTION
            "The 24 hours performance SNMP trap that is generated when an 
             alarm entry crosses its rising warning threshold and generates
             an event that is configured for sending SNMP traps."
        ::= { zxAnHisPerfMgmtTrapObjects 5 }            

    zxAnPm24hRisingWarningRestore NOTIFICATION-TYPE
        OBJECTS { 
            zxAnHisPmMetricInstIndex,
            zxAnHisPmThresholdMetric,
            zxAnHisPmStatisticalValue,
            zxAnHisPmRisingWarningThreshold
        }
        STATUS             current
        DESCRIPTION
            "The 24 hours performance restore SNMP trap that is generated 
             when an alarm entry restore to normal range."
        ::= { zxAnHisPerfMgmtTrapObjects 6 }

    zxAnPm24hRisingAlarm NOTIFICATION-TYPE
        OBJECTS { 
            zxAnHisPmMetricInstIndex, 
            zxAnHisPmThresholdMetric, 
            zxAnHisPmStatisticalValue,
            zxAnHisPmRisingAlarmThreshold
        }
        STATUS             current
        DESCRIPTION
            "The 24 hours performance SNMP trap that is generated when an 
             alarm entry crosses its rising alarm threshold and generates
             an event that is configured for sending SNMP traps."
        ::= { zxAnHisPerfMgmtTrapObjects 7 }            

    zxAnPm24hRisingAlarmRestore NOTIFICATION-TYPE
        OBJECTS { 
            zxAnHisPmMetricInstIndex, 
            zxAnHisPmThresholdMetric, 
            zxAnHisPmStatisticalValue,
            zxAnHisPmRisingAlarmThreshold
        }
        STATUS             current
        DESCRIPTION
            "The 24 hours performance restore SNMP trap that is generated 
             when an alarm entry restore to normal range."
        ::= { zxAnHisPerfMgmtTrapObjects 8 }                                

    zxAnPm15minFallingWarning NOTIFICATION-TYPE
        OBJECTS {  
            zxAnHisPmMetricInstIndex, 
            zxAnHisPmThresholdMetric,
            zxAnHisPmStatisticalValue, 
            zxAnHisPmFallingWarningThreshold
        }
        STATUS             current
        DESCRIPTION
            "The 15 minutes performance SNMP trap that is generated 
             when an alarm entry crosses its falling warning threshold 
             and generates an event that is configured for sending 
             SNMP traps."
        ::= { zxAnHisPerfMgmtTrapObjects 9 }            

    zxAnPm15minFallingWarningRestore NOTIFICATION-TYPE
        OBJECTS { 
            zxAnHisPmMetricInstIndex, 
            zxAnHisPmThresholdMetric,
            zxAnHisPmStatisticalValue, 
            zxAnHisPmFallingWarningThreshold
        }
        STATUS             current
        DESCRIPTION
            "The 15 minutes performance restore SNMP trap that is generated 
             when an alarm entry restore to normal range."
        ::= { zxAnHisPerfMgmtTrapObjects 10 }

    zxAnPm15minFallingAlarm NOTIFICATION-TYPE
        OBJECTS { 
            zxAnHisPmMetricInstIndex, 
            zxAnHisPmThresholdMetric, 
            zxAnHisPmStatisticalValue,
            zxAnHisPmFallingAlarmThreshold
        }
        STATUS             current
        DESCRIPTION
            "The 15 minutes performance SNMP trap that is generated 
             when an alarm entry crosses its falling alarm threshold 
             and generates an event that is configured for sending 
             SNMP traps."
        ::= { zxAnHisPerfMgmtTrapObjects 11 }            

    zxAnPm15minFallingAlarmRestore NOTIFICATION-TYPE
        OBJECTS { 
            zxAnHisPmMetricInstIndex, 
            zxAnHisPmThresholdMetric, 
            zxAnHisPmStatisticalValue,
            zxAnHisPmFallingAlarmThreshold
        }
        STATUS             current
        DESCRIPTION
            "The 15 minutes performance restore SNMP trap that is generated 
             when an alarm entry restore to normal range."
        ::= { zxAnHisPerfMgmtTrapObjects 12 }                                

    zxAnPm24hFallingWarning NOTIFICATION-TYPE
        OBJECTS {  
            zxAnHisPmMetricInstIndex, 
            zxAnHisPmThresholdMetric,
            zxAnHisPmStatisticalValue,
            zxAnHisPmFallingWarningThreshold
        }
        STATUS             current
        DESCRIPTION
            "The 24 hours performance SNMP trap that is generated 
             when an alarm entry crosses its falling warning threshold 
             and generates an event that is configured for sending 
             SNMP traps."
        ::= { zxAnHisPerfMgmtTrapObjects 13 }            

    zxAnPm24hFallingWarningRestore NOTIFICATION-TYPE
        OBJECTS { 
            zxAnHisPmMetricInstIndex, 
            zxAnHisPmThresholdMetric,
            zxAnHisPmStatisticalValue,
            zxAnHisPmFallingWarningThreshold
        }
        STATUS             current
        DESCRIPTION
            "The 24 hours performance restore SNMP trap that is generated 
             when an alarm entry restore to normal range."
        ::= { zxAnHisPerfMgmtTrapObjects 14 }

    zxAnPm24hFallingAlarm NOTIFICATION-TYPE
        OBJECTS { 
            zxAnHisPmMetricInstIndex, 
            zxAnHisPmThresholdMetric, 
            zxAnHisPmStatisticalValue,
            zxAnHisPmFallingAlarmThreshold
        }
        STATUS             current
        DESCRIPTION
            "The 24 hours performance SNMP trap that is generated 
             when an alarm entry crosses its falling alarm threshold 
             and generates an event that is configured for sending 
             SNMP traps."
        ::= { zxAnHisPerfMgmtTrapObjects 15 }            


    zxAnPm24hFallingAlarmRestore NOTIFICATION-TYPE
        OBJECTS { 
            zxAnHisPmMetricInstIndex, 
            zxAnHisPmThresholdMetric, 
            zxAnHisPmStatisticalValue,
            zxAnHisPmFallingAlarmThreshold
        }
        STATUS             current
        DESCRIPTION
            "The 24 hours performance restore SNMP trap that is generated 
             when an alarm entry restore to normal range."
        ::= { zxAnHisPerfMgmtTrapObjects 16 }  
        
-------------------------------------------------------------------------------
-- 4 History Performance management Conformance Information 
-------------------------------------------------------------------------------
    zxAnHisPerfMIBCompliances   
        OBJECT IDENTIFIER   ::= { zxAnHisPerfMgmtConformance 1 }
    zxAnHisPerfMIBGroups  
        OBJECT IDENTIFIER   ::= { zxAnHisPerfMgmtConformance 2 }
        
-------------------------------------------------------------------------------
-- 4.1 History Performance management Compliance  
-------------------------------------------------------------------------------
    zxAnHisPerfMIBCompliance MODULE-COMPLIANCE
        STATUS      current
        DESCRIPTION 
            "The compliance statement for ZTE-AN-HIS-PERF-MGMT-MIB."
        MODULE             -- this module
        MANDATORY-GROUPS  { 
            zxAnHisPerfThreshAlmGroup,
            zxAnHisPerfGlobalGroup  
        }
        ::= { zxAnHisPerfMIBCompliances 1 }
        
-------------------------------------------------------------------------------
-- 4.2 History Performance units of compliance  
-------------------------------------------------------------------------------
    zxAnHisPerfThreshAlmGroup OBJECT-GROUP
        OBJECTS     {
            zxAnHisPmMetricInstIndex,
            zxAnHisPmThresholdMetric,        
            zxAnHisPmStatisticalValue,  
            zxAnHisPmRisingWarningThreshold,        
            zxAnHisPmRisingAlarmThreshold, 
            zxAnHisPmFallingWarningThreshold, 
            zxAnHisPmFallingAlarmThreshold
        }
        STATUS      current
        DESCRIPTION 
            "A collection of binding objects for sending historical
             performance threshold cross alarm trap."
        ::= { zxAnHisPerfMIBGroups 1 }  

    zxAnHisPerfGlobalGroup OBJECT-GROUP
        OBJECTS     {
            zxAnHisPerfMgmtSampleEnable,
            zxAnHisPerfMgmtAlarmEnable,
            zxAnHisPerfMgmtAutoUploadEnable
        }
        STATUS      current
        DESCRIPTION 
            "A collection of objects providing for performance 
             global control."
        ::= { zxAnHisPerfMIBGroups 2 }                                 
END

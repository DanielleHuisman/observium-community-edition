ZTE-AN-IPOA-MIB DEFINITIONS ::= BEGIN 
IMPORTS 
    OBJECT-TYPE, MODULE-IDENTITY, IpAddress,
    Counter32, Integer32                    FROM SNMPv2-SMI 
    TruthValue, MacAddress, RowStatus       FROM SNMPv2-TC
    ifIndex                                 FROM RFC1213-MIB
    ZxAnIfindex, zxAn                       FROM ZTE-AN-TC-MIB;
    
zxAnIpoaMib   MODULE-IDENTITY 
        LAST-UPDATED    "200701241600Z"
        ORGANIZATION    "Zhongxing Telcom Co. Ltd."
        CONTACT-INFO    "E-mail: yao.huayin@zte.com.cn"
        DESCRIPTION     "IPOA MIB definition."        
        ::= { zxAn 33 }  
        
        
zxAnIpoaMibObjects     OBJECT IDENTIFIER  ::= { zxAnIpoaMib 1 }  



--------------------------------------------------------------------------------
-- Following objects are defined.
-- 1.Ipoa Global Mgmt
-- 2.Ipoa User Config Table
-- 3.Ipoa User info Table
------------------------------------------------------------------------------



------------------------------------------------------------------------------
-- 1.Ipoa Global Mgmt
------------------------------------------------------------------------------
zxAnIpoaDefGateway OBJECT-TYPE
    SYNTAX      IpAddress
    MAX-ACCESS  read-write
    STATUS      current
    DESCRIPTION
      "IPOA user's default gateway"
    ::= { zxAnIpoaMibObjects 1 }

zxAnIpoaQueryInterval OBJECT-TYPE
    SYNTAX      Integer32
    MAX-ACCESS  read-write
    STATUS      current
    DESCRIPTION
      "IPOA InATMARP query interval"
    ::= { zxAnIpoaMibObjects 2 }
    
zxAnIpoaGatewayARPInterval OBJECT-TYPE
    SYNTAX      Integer32
    MAX-ACCESS  read-write
    STATUS      current
    DESCRIPTION
      "IPOA gateway arp query interval"
    ::= { zxAnIpoaMibObjects 3 }



------------------------------------------------------------------------------
-- 2.Ipoa User Config Table
------------------------------------------------------------------------------

zxAnIpoaUserConfTable OBJECT-TYPE
    SYNTAX SEQUENCE OF ZxAnIpoaUserConfEntry
    MAX-ACCESS not-accessible
    STATUS current
    DESCRIPTION
    "IPOA user table"
    ::= { zxAnIpoaMibObjects 10 }    
    
zxAnIpoaUserConfEntry OBJECT-TYPE
    SYNTAX ZxAnIpoaUserConfEntry
    MAX-ACCESS not-accessible
    STATUS current
    DESCRIPTION
    "IPOA user entry "
    INDEX { zxAnIpoaIfIndex }
    ::= { zxAnIpoaUserConfTable 1 }
        
ZxAnIpoaUserConfEntry ::= SEQUENCE {
    zxAnIpoaIfIndex                ZxAnIfindex,
    zxAnIpoaUserConfIp             IpAddress,
    zxAnIpoaUserConfInAtmArp       INTEGER,
    zxAnIpoaUserConfLayer          INTEGER,
    zxAnIpoaUserConfL2gatewayIp    IpAddress,
    zxAnIpoaUserConfL2gatewayMac   MacAddress,
    zxAnIpoaUserConfRowStatus      RowStatus
    }    

zxAnIpoaIfIndex OBJECT-TYPE
    SYNTAX         ZxAnIfindex
    MAX-ACCESS     not-accessible
    STATUS         current       
    DESCRIPTION
      "User port's ifIndex. 
       
       NOTES: It means physical port only now.So the filed of interface type in 
       ZxAnIfindex should be 0x1.       
       
       "
    ::= { zxAnIpoaUserConfEntry 1 }
    
zxAnIpoaUserConfIp OBJECT-TYPE
    SYNTAX         IpAddress
    MAX-ACCESS     read-create
    STATUS         current       
    DESCRIPTION
    "IPOA user's ip address"
    ::= { zxAnIpoaUserConfEntry 2 }
  
zxAnIpoaUserConfInAtmArp OBJECT-TYPE
    SYNTAX        INTEGER
        {   
          enable(1),
          disable(2)
        }
    MAX-ACCESS  read-create
    STATUS      current
    DESCRIPTION
      "Enable or disable getting IPOA user's ip address by InAtmARP"
    DEFVAL { enable }
    ::= { zxAnIpoaUserConfEntry 3 }

zxAnIpoaUserConfLayer OBJECT-TYPE
     SYNTAX        INTEGER
        {   
            layer2(1),
            layer3(2)
            }
     MAX-ACCESS  read-create
     STATUS      current
     DESCRIPTION
     "Layer 2 IPOA user or Layer 3 IPOA user"
     DEFVAL { layer2 }
     ::= { zxAnIpoaUserConfEntry 4 }

zxAnIpoaUserConfL2gatewayIp OBJECT-TYPE
    SYNTAX         IpAddress
    MAX-ACCESS     read-create
    STATUS         current       
    DESCRIPTION
    "Layer 2 IPOA user's gateway ip address"
    ::= { zxAnIpoaUserConfEntry 5 }

          
zxAnIpoaUserConfL2gatewayMac OBJECT-TYPE
    SYNTAX         MacAddress
    MAX-ACCESS     read-create
    STATUS         current       
    DESCRIPTION
    "Layer 2 IPOA user's gateway mac address"
    ::= { zxAnIpoaUserConfEntry 6 }  
      
zxAnIpoaUserConfRowStatus  OBJECT-TYPE 
    SYNTAX          RowStatus
    MAX-ACCESS      read-create
    STATUS          current
    DESCRIPTION     "The row status of this entry."
    ::=  {  zxAnIpoaUserConfEntry 7 }   


------------------------------------------------------------------------------
-- 3.Ipoa User info Table
------------------------------------------------------------------------------

zxAnIpoaUserInfoTable OBJECT-TYPE
  SYNTAX SEQUENCE OF ZxAnIpoaUserInfoEntry
  MAX-ACCESS not-accessible
  STATUS current
  DESCRIPTION
  "IPOA user table"
  ::= { zxAnIpoaMibObjects 11 }    
    
zxAnIpoaUserInfoEntry OBJECT-TYPE
  SYNTAX ZxAnIpoaUserInfoEntry
  MAX-ACCESS not-accessible
  STATUS current
  DESCRIPTION
  "IPOA user entry "
  INDEX { zxAnIpoaIfIndex }

  ::= { zxAnIpoaUserInfoTable 1 }
        
ZxAnIpoaUserInfoEntry ::= SEQUENCE {
    zxAnIpoaUserInfoVlan        Integer32,
    zxAnIpoaUserInfoIp          IpAddress,
    zxAnIpoaUserInfoMac        MacAddress,
    zxAnIpoaUserInfoGatewayIp   IpAddress,
    zxAnIpoaUserInfoGatewayMac  MacAddress
    }    

zxAnIpoaUserInfoVlan OBJECT-TYPE
    SYNTAX        Integer32
    MAX-ACCESS  read-only
    STATUS      current
    DESCRIPTION
    "IPOA user's vlan ID"
    ::= { zxAnIpoaUserInfoEntry 1 }

zxAnIpoaUserInfoIp OBJECT-TYPE
  SYNTAX         IpAddress
  MAX-ACCESS     read-only
  STATUS         current       
  DESCRIPTION
  "IPOA user's ip address"
  ::= { zxAnIpoaUserInfoEntry 2 }
  
zxAnIpoaUserInfoMac OBJECT-TYPE
    SYNTAX         MacAddress
    MAX-ACCESS     read-only
    STATUS         current       
    DESCRIPTION
    "IPOA user's mac address"
    ::= { zxAnIpoaUserInfoEntry 3 }  

zxAnIpoaUserInfoGatewayIp OBJECT-TYPE
          SYNTAX         IpAddress
          MAX-ACCESS     read-only
          STATUS         current       
          DESCRIPTION
          "IPOA user's gateway ip address"
          ::= { zxAnIpoaUserInfoEntry 4 }
          
zxAnIpoaUserInfoGatewayMac OBJECT-TYPE
    SYNTAX         MacAddress
    MAX-ACCESS     read-only
    STATUS         current       
    DESCRIPTION
    "IPOA user's gateway mac address"
    ::= { zxAnIpoaUserInfoEntry 5 }  
END

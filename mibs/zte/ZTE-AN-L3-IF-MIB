--------------------------------------------------------------------------
-- File Name : ZTE-AN-L3-IF-MIB.mib
-- Date      : 2006-12-25
-- Author    : ZTE Nms dept.

--
-- Zte Layer 3 Interface Mib for Access Node
-- 
-- 
--------------------------------------------------------------------------


ZTE-AN-L3-IF-MIB DEFINITIONS ::= BEGIN

    IMPORTS
          MODULE-IDENTITY, OBJECT-TYPE, NOTIFICATION-TYPE,
        Integer32, IpAddress                    FROM SNMPv2-SMI        
        DisplayString,RowStatus                 FROM SNMPv2-TC
        MODULE-COMPLIANCE, OBJECT-GROUP         FROM SNMPv2-CONF
        InetAddress,InetAddressPrefixLength     FROM INET-ADDRESS-MIB           
        zxAn,ZxAnIfindex                        FROM ZTE-AN-TC-MIB;
        
    zxAnL3InterfaceMib    MODULE-IDENTITY
        LAST-UPDATED    "0612070000Z"  -- Dec 7, 2006
        ORGANIZATION    "ZTE Corporation"
        CONTACT-INFO    "
                        Mail: suchunshan@zte.com.cn,
                              guo.jun@zte.com.cn
                        Tel : 021-68896292"
        DESCRIPTION     "This MIB defines zte Access Node managed objects for
        layer 3 interfaces."
        ::=  {  zxAn  4  }  
        


    zxAnL3InterfaceObjects     OBJECT IDENTIFIER  ::=  { zxAnL3InterfaceMib 1 }
    zxAnL3InterfaceTrapObjects OBJECT IDENTIFIER  ::=  { zxAnL3InterfaceMib 2 }

        
------------------------------------------------------------------------------
-- Following objects are defined.
--  1.L3 Interface Table
--  2.L3 Interface's SuperVlan Table
--  3.L3 Interface IpAddress Table
--  4.L3 Interface IpAddress Table For IPv6
------------------------------------------------------------------------------

------------------------------------------------------------------------------
--  1.L3 Interface Table
------------------------------------------------------------------------------
 
    zxAnL3IfTable OBJECT-TYPE
        SYNTAX SEQUENCE OF ZxAnL3IfEntry
        MAX-ACCESS not-accessible
        STATUS current
        DESCRIPTION
        "zx an L3 interface table."
        ::= { zxAnL3InterfaceObjects  1 }
      
    zxAnL3IfEntry OBJECT-TYPE
        SYNTAX ZxAnL3IfEntry
        MAX-ACCESS not-accessible
        STATUS current
        DESCRIPTION
        "L3 interface create entry.It is used to create or remove a L3 interface."
        INDEX { zxAnL3IfIndex}
        ::= { zxAnL3IfTable 1 }
  
    ZxAnL3IfEntry ::= 
        SEQUENCE {
        zxAnL3IfIndex                 ZxAnIfindex,
        zxAnL3IfName                  DisplayString,
        zxAnIfReferIndex              Integer32,
        zxAnL3IfArpProxyEnable        INTEGER,
        zxAnL3IfRowStatus             RowStatus,
        zxAnL3IfArpAgingTime          INTEGER
        }

    zxAnL3IfIndex OBJECT-TYPE
        SYNTAX  ZxAnIfindex
        MAX-ACCESS  not-accessible
        STATUS  current
        DESCRIPTION
        "A unique value for each interface. The field of interface type in 
        ZxAnIfindex for L3 is 0x6(Layer 3 interface)."
        ::= { zxAnL3IfEntry 1 }

    zxAnL3IfName OBJECT-TYPE
        SYNTAX  DisplayString (SIZE (0..64))
        MAX-ACCESS  read-only
        STATUS  current
        DESCRIPTION
        "A textual string refer to an interface,it also contain information about the 
        interface."
        ::= { zxAnL3IfEntry 2 }

    zxAnIfReferIndex OBJECT-TYPE
        SYNTAX  Integer32
        MAX-ACCESS  read-only
        STATUS  current
        DESCRIPTION
        "The index dynamically assigned by zte ROS Platform for inner port."
        ::= { zxAnL3IfEntry 3 }
        
    zxAnL3IfArpProxyEnable OBJECT-TYPE
        SYNTAX  INTEGER
            {
              enable(1),
              disable(2)
            }
        MAX-ACCESS  read-create
        STATUS  current
        DESCRIPTION
        "Enable/disable Arp Proxy functionality ."
        ::= { zxAnL3IfEntry 4 }

    zxAnL3IfRowStatus    OBJECT-TYPE
        SYNTAX         RowStatus
        MAX-ACCESS     read-create
        STATUS         current
        DESCRIPTION
        "This object is used to create, delete the l3 interface 
        in this table."
        ::= {zxAnL3IfEntry 5}

    zxAnL3IfArpAgingTime  OBJECT-TYPE 
        SYNTAX          INTEGER(1..4294967) 
        UNITS           "second" 
        MAX-ACCESS      read-write
        STATUS          current
        DESCRIPTION     "ARP aging time ."
        DEFVAL { 300 }
        ::=  {  zxAnL3IfEntry  6  }         


------------------------------------------------------------------------------
--  2.L3 Interface's SuperVlan Table
------------------------------------------------------------------------------
 
    zxAnL3IfSuperVlanTable OBJECT-TYPE
        SYNTAX SEQUENCE OF ZxAnL3IfSuperVlanEntry
        MAX-ACCESS not-accessible
        STATUS current
        DESCRIPTION
        "An L3 super vlan interface table."
        ::= { zxAnL3InterfaceObjects  2 }

    zxAnL3IfSuperVlanEntry OBJECT-TYPE
          SYNTAX ZxAnL3IfSuperVlanEntry
          MAX-ACCESS not-accessible
          STATUS current
          DESCRIPTION
          "L3 supervlan interface entry.The creating and deleting of this entry
          is related to the operation of zxAnL3IfEntry."
          INDEX { zxAnL3IfIndex }
          ::= { zxAnL3IfSuperVlanTable 1 }
  
    ZxAnL3IfSuperVlanEntry ::=
          SEQUENCE {
          zxAnL3IfSubvlanRoutingEnable    INTEGER,
          zxAnL3IfSubvlanList             OCTET STRING
        }
   

    zxAnL3IfSubvlanRoutingEnable OBJECT-TYPE
        SYNTAX  INTEGER
        {
          enable(1),
          disable(2)
        }
        MAX-ACCESS  read-write
        STATUS  current
        DESCRIPTION
        "Enable/disable inter sub vlan routing."
        ::= { zxAnL3IfSuperVlanEntry 1 }

    zxAnL3IfSubvlanList OBJECT-TYPE
        SYNTAX  OCTET STRING (SIZE (0..5472))
        MAX-ACCESS  read-write
        STATUS  current
        DESCRIPTION
        "Configure sub vlan list of supervlan.
                     for example:1-10,13"
        ::= { zxAnL3IfSuperVlanEntry 2 }




------------------------------------------------------------------------------
--  3.L3 Interface IpAddress Table
------------------------------------------------------------------------------
    zxAnL3IfIpAddressTable OBJECT-TYPE
        SYNTAX SEQUENCE OF ZxAnL3IfIpAddressEntry
        MAX-ACCESS not-accessible
        STATUS current
        DESCRIPTION
        "An L3 interface ip Address table"
        ::= { zxAnL3InterfaceObjects  3 }

    zxAnL3IfIpAddressEntry OBJECT-TYPE
        SYNTAX ZxAnL3IfIpAddressEntry
        MAX-ACCESS not-accessible
        STATUS current
        DESCRIPTION
        "L3 interface ip address entry"
        INDEX { zxAnL3IfIndex,zxAnL3IfIpAddress }
        ::= { zxAnL3IfIpAddressTable 1 }  
        
    ZxAnL3IfIpAddressEntry ::=
        SEQUENCE {
        zxAnL3IfIpAddress     IpAddress,
        zxAnL3IfIpAddressMask IpAddress,
        zxAnL3IfIpCategory    INTEGER,
        zxAnL3IfIpRowStatus   RowStatus
        }


    zxAnL3IfIpAddress OBJECT-TYPE
        SYNTAX  IpAddress
        MAX-ACCESS  not-accessible
        STATUS  current
        DESCRIPTION
        "Ip address of L3 interface."                         
        ::= { zxAnL3IfIpAddressEntry 1 }
        
    zxAnL3IfIpAddressMask OBJECT-TYPE
        SYNTAX  IpAddress
        MAX-ACCESS  read-create
        STATUS  current
        DESCRIPTION
        "Ip address mask of L3 interface."                          
        ::= { zxAnL3IfIpAddressEntry 2 }

    zxAnL3IfIpCategory OBJECT-TYPE
        SYNTAX  INTEGER
        {
            single(1),
            primary(2),
            secondary(3)
        }
        MAX-ACCESS  read-create
        STATUS  current
        DESCRIPTION
        " Represents the IP address category. 
          single(1)     - Indicates that the IP addressing information for 
                       this interface, has no primary/secondary category.
          primary(2)    - Indicates that this interface provides primary IP 
                       addressing information.
          secondary(3)  - Indicates that this interface provides a secondary
                       IP addressing information. There may be more than one 
                       secondary IP addressing information for an interface. 
        "
        ::= { zxAnL3IfIpAddressEntry 3 }

    zxAnL3IfIpRowStatus      OBJECT-TYPE
        SYNTAX         RowStatus
        MAX-ACCESS     read-create
        STATUS         current
        DESCRIPTION
        "Only creating or deleting this entry is used now."
        ::= {zxAnL3IfIpAddressEntry 4}


------------------------------------------------------------------------------
--  4.L3 Interface IpAddress Table For IPv6
------------------------------------------------------------------------------
    zxAnL3IfIpv6IpAddressTable OBJECT-TYPE
        SYNTAX SEQUENCE OF ZxAnL3IfIpv6IpAddressEntry
        MAX-ACCESS not-accessible
        STATUS current
        DESCRIPTION
        "L3 interface IP address table for IPv6"
        ::= { zxAnL3InterfaceObjects  4 }

    zxAnL3IfIpv6IpAddressEntry OBJECT-TYPE
        SYNTAX ZxAnL3IfIpv6IpAddressEntry
        MAX-ACCESS not-accessible
        STATUS current
        DESCRIPTION
        "L3 interface IP address entry for IPv6"
        INDEX { zxAnL3IfIndex,zxAnL3IfIpv6IpAddress }
        ::= { zxAnL3IfIpv6IpAddressTable 1 }  
        
    ZxAnL3IfIpv6IpAddressEntry ::=
        SEQUENCE {
        zxAnL3IfIpv6IpAddress     InetAddress,
        zxAnL3IfIpv6IpPfxLen      InetAddressPrefixLength,
        zxAnL3IfIpv6Enable        INTEGER,
        zxAnL3IfIpv6Mtu           INTEGER,
        zxAnL3IfIpv6DadAttemps    INTEGER,
        zxAnL3IfIpv6RowStatus     RowStatus
        }


    zxAnL3IfIpv6IpAddress OBJECT-TYPE
        SYNTAX  InetAddress
        MAX-ACCESS  not-accessible
        STATUS  current
        DESCRIPTION
        "IP address of L3 interface for IPv6."                         
        ::= { zxAnL3IfIpv6IpAddressEntry 1 }
        
    zxAnL3IfIpv6IpPfxLen OBJECT-TYPE
        SYNTAX  InetAddressPrefixLength
        MAX-ACCESS  read-create
        STATUS  current
        DESCRIPTION
        "Prefix length of the IPv6 IP address of this L3 interface."                          
        ::= { zxAnL3IfIpv6IpAddressEntry 2 }

    zxAnL3IfIpv6Enable OBJECT-TYPE
        SYNTAX  INTEGER
        {
            enable(1),
            disable(2)
        }
        MAX-ACCESS  read-create
        STATUS  current
        DESCRIPTION
        "Enable status of the IPv6 IP address of this L3 interface."                          
        DEFVAL { disable }   
        ::= { zxAnL3IfIpv6IpAddressEntry 3 }

    zxAnL3IfIpv6Mtu OBJECT-TYPE
        SYNTAX  INTEGER(1280..1500)
        MAX-ACCESS  read-create
        STATUS  current
        DESCRIPTION
        "MTU of this L3 interface."
        DEFVAL { 1500 }   
        ::= { zxAnL3IfIpv6IpAddressEntry 4 }

    zxAnL3IfIpv6DadAttemps OBJECT-TYPE
        SYNTAX  INTEGER(1..60)
        MAX-ACCESS  read-create
        STATUS  current
        DESCRIPTION
        "The DAD(Duplicate Address Detection) attemps of this L3 interface."
        DEFVAL { 1 }   
        ::= { zxAnL3IfIpv6IpAddressEntry 5 }

    zxAnL3IfIpv6RowStatus      OBJECT-TYPE
        SYNTAX         RowStatus
        MAX-ACCESS     read-create
        STATUS         current
        DESCRIPTION
        "The rowstatus which is used to create or delete this entry."
        ::= {zxAnL3IfIpv6IpAddressEntry 20}
   END

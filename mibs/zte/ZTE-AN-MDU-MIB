-------------------------------------------------------------------------------
-- File Name : ZTE-AN-MDU-MIB.mib
-- Date      : 2008-12-08
-- Author    : ZTE Nms dept.

--
-- Zte Mdu Mib for Access Node
-- 
-- 
-------------------------------------------------------------------------------


ZTE-AN-MDU-MIB DEFINITIONS ::= BEGIN

    IMPORTS
        MODULE-IDENTITY     FROM SNMPv2-SMI
        NOTIFICATION-TYPE   FROM SNMPv2-SMI
        OBJECT-TYPE         FROM SNMPv2-SMI
        Integer32           FROM SNMPv2-SMI
        RowStatus           FROM SNMPv2-TC
        DisplayString       FROM SNMPv2-TC
        MacAddress          FROM SNMPv2-TC
        zxAn                FROM ZTE-AN-TC-MIB
        VlanId              FROM ZTE-AN-TC-MIB
        ZxAnIfindex         FROM ZTE-AN-TC-MIB;

       
    zxAnMduMib MODULE-IDENTITY
        LAST-UPDATED "200812080000Z"  -- Dec 08, 2008"
        ORGANIZATION "ZTE Corp."
        CONTACT-INFO 
            "ZTE PON Working Group: 
            http://www.zte.com.cn
            e-mail:zhang.ling@zte.com.cn"
        DESCRIPTION
            "Mdu Mangement with SNMP protocol"       
        ::= { zxAn 1016 }

    zxAnMduSysCtrlObjects        OBJECT IDENTIFIER ::= { zxAnMduMib 2}
    zxAnMduServiceObjects        OBJECT IDENTIFIER ::= { zxAnMduMib 3}
    zxAnMduEquipObjects          OBJECT IDENTIFIER ::= { zxAnMduMib 10}
    zxAnMduTrapObjects           OBJECT IDENTIFIER ::= { zxAnMduMib 20}
    
-------------------------------------------------------------------------------
-- Following objects are defined.
-- 1 zxAnMduGlobalObjects
-- 2 zxAnMduSysCtrlObjects
-- 3 zxAnMduServiceObjects
-- 3.1 Config Mdu Global Attibutes
-- 3.2 Config Hg Report Status & Hg online trap info
-- 10 zxAnMduEquipObjects
-- 10.21 zxAnMduEnvBattMgmt
-- 20 zxAnMduTrapObjects
-- 20.3 zxAnMduServiceTrapObjects
-- 20.10 zxAnMduEquipTrapObjects
-------------------------------------------------------------------------------    
-- 100.zxAnMduMibEnd
-------------------------------------------------------------------------------

-------------------------------------------------------------------------------
-- 1 zxAnMduGlobalObjects
-------------------------------------------------------------------------------


-------------------------------------------------------------------------------
-- 2 zxAnMduSysCtrlObjects
-------------------------------------------------------------------------------
    zxAnMduSysDataMgmt  OBJECT IDENTIFIER ::= { zxAnMduSysCtrlObjects 1}
    
    zxAnMduSaveModifiedToNvmInterval  OBJECT-TYPE
        SYNTAX          Integer32(0..1440)
        UNITS           "minutes" 
        MAX-ACCESS      read-write
        STATUS          current
        DESCRIPTION     
            "The interval to save flash if running configuration of  agent 
            modified, value 0 means disable the auto save flash operation.
            This variable only for F820."
        DEFVAL          { 0 }
        ::=  {  zxAnMduSysDataMgmt  1  }
        
    zxAnMduSaveToNvmInterval  OBJECT-TYPE 
        SYNTAX          Integer32(0..8760)
        UNITS           "hours" 
        MAX-ACCESS      read-write
        STATUS          current
        DESCRIPTION     
          "The interval to force saving flash , value 0 means disable the force 
          save saving operation.This variable only for F820."
        DEFVAL          { 0 }
        ::=  {  zxAnMduSysDataMgmt  2  }

-------------------------------------------------------------------------------
-- 3.1 Config Mdu Global Attibutes
-------------------------------------------------------------------------------
    zxAnMduHgMacFeatureCodeTable OBJECT-TYPE
        SYNTAX       SEQUENCE OF ZxAnMduHgMacFeatureCodeEntry 
        MAX-ACCESS   not-accessible 
        STATUS       current 
        DESCRIPTION 
            "Mdu HomeGateway Mac Feature Codes Table."
        ::= { zxAnMduServiceObjects 1 } 
   
    zxAnMduHgMacFeatureCodeEntry OBJECT-TYPE 
        SYNTAX      ZxAnMduHgMacFeatureCodeEntry 
        MAX-ACCESS  not-accessible 
        STATUS      current 
        DESCRIPTION 
            " " 
        INDEX   {zxAnMduHgMacFeatureCodeId}
        ::= { zxAnMduHgMacFeatureCodeTable 1 } 
   
    ZxAnMduHgMacFeatureCodeEntry ::=
        SEQUENCE {
                zxAnMduHgMacFeatureCodeId         Integer32,
                zxAnMduHgMacFeatureCode           DisplayString
                }
                
    zxAnMduHgMacFeatureCodeId OBJECT-TYPE
        SYNTAX      Integer32
        MAX-ACCESS  not-accessible
        STATUS      current
        DESCRIPTION
            "The sequence number of Mac Feature Code.The max count of these
             codes is 32."
        ::= {zxAnMduHgMacFeatureCodeEntry 1}
            
    zxAnMduHgMacFeatureCode OBJECT-TYPE
        SYNTAX      DisplayString(SIZE(1..20))
        MAX-ACCESS  read-write
        STATUS      current
        DESCRIPTION
            "This is one of the MAC Feature codes that used to identify the 
            productor of HomeGateway by Mac Addr."
        ::= {zxAnMduHgMacFeatureCodeEntry 2}     

    zxAnMduHgMgmtVlan OBJECT-TYPE     
       SYNTAX      Integer32 
       MAX-ACCESS  read-write
       STATUS      current
       DESCRIPTION 
           "HomeGateway EMS management vlan.For Beijing CNC, the default value 
           is 3999."
       ::=  {  zxAnMduServiceObjects  2  }  

     zxAnMduConfigFileCRC32    
       OBJECT-TYPE     
       SYNTAX      DisplayString(SIZE(1..100))
       MAX-ACCESS  read-only
       STATUS      current
       DESCRIPTION 
           "The CRC32 codes are generated from the latest Configuration file by 
           MDU."
       ::=  {  zxAnMduServiceObjects  3  }

     zxAnMduLoadSettings    
       OBJECT-TYPE
       SYNTAX      INTEGER {
                    loadFactoryDefaults(1)
                   }
       MAX-ACCESS  read-write
       STATUS      current
       DESCRIPTION 
           "User this parameter to load settings. 
            It will take effect after MDU system reboot.
           "
       DEFVAL      { loadFactoryDefaults }
       ::=  {  zxAnMduServiceObjects  4  }
                   
-------------------------------------------------------------------------------
--  3.2 Config Hg Report Status & Hg online trap info 
------------------------------------------------------------------------------- 
  
    zxAnMduHgTable OBJECT-TYPE
        SYNTAX       SEQUENCE OF ZxAnMduHgEntry 
        MAX-ACCESS   not-accessible 
        STATUS       current 
        DESCRIPTION 
            "Mdu HomeGateway Management table."
        ::= { zxAnMduServiceObjects 21 } 
   
    zxAnMduHgEntry OBJECT-TYPE 
        SYNTAX      ZxAnMduHgEntry 
        MAX-ACCESS  not-accessible 
        STATUS      current 
        DESCRIPTION 
            " " 
        INDEX   {zxAnMduPortIfIndex,zxAnMduHgMac}
        ::= { zxAnMduHgTable 1 } 
   
    ZxAnMduHgEntry ::=
        SEQUENCE {
                zxAnMduPortIfIndex                ZxAnIfindex,
                zxAnMduHgMac                        MacAddress,
                zxAnMduHgReportStatus             INTEGER,
                zxAnMduHgDataVlan                   Integer32,
                zxAnMduHgVideoVlan                Integer32,
                zxAnMduHgVoiceVlan                   Integer32,
                zxAnMduType                         DisplayString
                }
                
    zxAnMduPortIfIndex OBJECT-TYPE
        SYNTAX      ZxAnIfindex
        MAX-ACCESS  not-accessible
        STATUS      current
        DESCRIPTION
            "Port Id"
        ::= {zxAnMduHgEntry 1}
            
    zxAnMduHgMac OBJECT-TYPE
        SYNTAX      MacAddress
        MAX-ACCESS  not-accessible
        STATUS      current
        DESCRIPTION
            "HomeGateway MAC Addr."
        ::= {zxAnMduHgEntry 2}    
                 
    zxAnMduHgReportStatus OBJECT-TYPE
        SYNTAX      INTEGER{failed(0),success(1)}
        MAX-ACCESS  read-write
        STATUS      current
        DESCRIPTION
            "EMS report the Hg to RMS, 1 means the operation is successful, 
            0 is the initial value, also means the operation is failed."
        ::= {zxAnMduHgEntry 3}      

    zxAnMduHgDataVlan OBJECT-TYPE
        SYNTAX      Integer32
        MAX-ACCESS  read-only
        STATUS      current
        DESCRIPTION
            "Data vlan of the port to which this Hg is belong."
        ::= {zxAnMduHgEntry 4}    
        
    zxAnMduHgVideoVlan OBJECT-TYPE
        SYNTAX      Integer32
        MAX-ACCESS  read-only
        STATUS      current
        DESCRIPTION
            "Video vlan of the port. For Beijing CNC, the value is 
            (DataVlan+1200)"
        ::= {zxAnMduHgEntry 5}    
                
    zxAnMduHgVoiceVlan OBJECT-TYPE
        SYNTAX      Integer32
        MAX-ACCESS  read-only
        STATUS      current
        DESCRIPTION
            "Voice vlan of the port, For Beijing CNC, the value is 
            (DataVlan+2400)"
        ::= {zxAnMduHgEntry 6}    

    zxAnMduType    
       OBJECT-TYPE     
       SYNTAX      DisplayString(SIZE(1..30))
       MAX-ACCESS  read-only
       STATUS      current
       DESCRIPTION 
           "The type of MDU, eg.ZTE-F820"
       ::=  {zxAnMduHgEntry 7}
       
-------------------------------------------------------------------------------
-- 10.21 zxAnMduEnvBattMgmt
-------------------------------------------------------------------------------
    zxAnMduEnvSwitchMgmt      OBJECT IDENTIFIER ::= { zxAnMduEquipObjects 21}
    
    zxAnMduEnvDeviceTable OBJECT-TYPE
       SYNTAX      SEQUENCE OF ZxAnMduEnvDeviceEntry 
       MAX-ACCESS  not-accessible
       STATUS      current
       DESCRIPTION
           "The table of environment monitor Device."
       ::= { zxAnMduEnvSwitchMgmt 11 }

    zxAnMduEnvDeviceEntry  OBJECT-TYPE
       SYNTAX      ZxAnMduEnvDeviceEntry 
       MAX-ACCESS  not-accessible
       STATUS      current
       DESCRIPTION
           "a entry of this table."
       INDEX       { zxAnMduEnvEnvDeviceIndex }
       ::= { zxAnMduEnvDeviceTable 1 }

    ZxAnMduEnvDeviceEntry ::= SEQUENCE {
        zxAnMduEnvEnvDeviceIndex               Integer32,
        zxAnMduEnvEnvDeviceName                DisplayString,
        zxAnMduEnvDeviceRowStatus              RowStatus
    }
        
    zxAnMduEnvEnvDeviceIndex OBJECT-TYPE
        SYNTAX     Integer32 
        MAX-ACCESS not-accessible
        STATUS     current
        DESCRIPTION
            "The index of this environment monitor Device. "
        ::= { zxAnMduEnvDeviceEntry 1 }   
       
    zxAnMduEnvEnvDeviceName OBJECT-TYPE 
        SYNTAX      DisplayString  (SIZE(0..32))                 
        MAX-ACCESS  read-create
        STATUS      current
        DESCRIPTION     
            "the name of environment monitor Device."        
        ::= { zxAnMduEnvDeviceEntry 2 }

    zxAnMduEnvDeviceRowStatus OBJECT-TYPE 
        SYNTAX      RowStatus
        MAX-ACCESS  read-create
        STATUS      current
        DESCRIPTION   "The status of this table."
        ::=  { zxAnMduEnvDeviceEntry 3 }    

    zxAnMduSwitchTable OBJECT-TYPE
        SYNTAX  SEQUENCE OF ZxAnMduSwitchEntry
        MAX-ACCESS  not-accessible
        STATUS  current
        DESCRIPTION
           "The table of switch's managed objects.Each row instance represents 
            a device connected with this switch."
       ::= { zxAnMduEnvSwitchMgmt 12 }

    zxAnMduSwitchEntry OBJECT-TYPE
        SYNTAX  ZxAnMduSwitchEntry
        MAX-ACCESS  not-accessible
        STATUS  current
        DESCRIPTION
           "a entry of this table."
        INDEX   { zxAnMduEnvSwitchIndex }
       ::= { zxAnMduSwitchTable 1 }

    ZxAnMduSwitchEntry ::= SEQUENCE 
        {
            zxAnMduEnvSwitchIndex               Integer32,
            zxAnMduEnvDeviceId                  Integer32,
            zxAnMduEnvSwitchNormalStatus        INTEGER,
            zxAnMduEnvSwitchEnable              INTEGER,
            zxAnMduEnvSwitchCurrentStatus       INTEGER
        }

    zxAnMduEnvSwitchIndex OBJECT-TYPE
        SYNTAX     Integer32 
        MAX-ACCESS not-accessible
        STATUS     current
        DESCRIPTION
            "The index of this Switch."
        ::= { zxAnMduSwitchEntry 1 }   
       
    zxAnMduEnvDeviceId    OBJECT-TYPE 
        SYNTAX          Integer32
        MAX-ACCESS      read-write
        STATUS          current
        DESCRIPTION     
            "The device id.If this switch can't connect with any device,
            zxAnMduEnvDeviceId set to 0."
        DEFVAL { 0 }
        ::= { zxAnMduSwitchEntry 2 }             
        
    zxAnMduEnvSwitchNormalStatus  OBJECT-TYPE 
        SYNTAX      INTEGER
        { 
            low(0),
            high(1)
        } 
        MAX-ACCESS  read-write
        STATUS      current
        DESCRIPTION   
            "The Threshold of this environment monitor Device."
        ::= { zxAnMduSwitchEntry 3 }
   
    zxAnMduEnvSwitchEnable  OBJECT-TYPE 
        SYNTAX      INTEGER  
        { 
            enable(1),
            disable(2)
        } 
        MAX-ACCESS  read-write
        STATUS      current
        DESCRIPTION   
            "Enables and disables Trap of this environment monitor Device."
        ::= { zxAnMduSwitchEntry 4 }        
     
    zxAnMduEnvSwitchCurrentStatus  OBJECT-TYPE 
        SYNTAX      INTEGER  
        { 
            low(0),
            high(1)
        } 
        MAX-ACCESS  read-only
        STATUS      current
        DESCRIPTION   
            "The current status of this environment monitor Device."
        ::= { zxAnMduSwitchEntry 5 }     
         
       
-------------------------------------------------------------------------------
-- 20.3 zxAnMduServiceTrapObjects
-------------------------------------------------------------------------------
    zxAnMduServiceTrapObjects     OBJECT IDENTIFIER ::= { zxAnMduTrapObjects 3}
    
    zxAnMduNetworkAccessRequest NOTIFICATION-TYPE
        OBJECTS { zxAnMduPortIfIndex,  zxAnMduHgMac, zxAnMduHgDataVlan, 
        zxAnMduHgVideoVlan, zxAnMduHgVoiceVlan, zxAnMduType}
        STATUS             current
        DESCRIPTION
           "It indicate Hg Network Access Request,The variable 
           zxAnMduPortIfIndex indicate trap position,it's type is ZxAnIfindex,
           detail info about ZxAnIfindex please
           refer to ZTE-AN-TC-MIB.mib file."
       ::= { zxAnMduServiceTrapObjects 1 }  

    zxAnMduUploadConfigFileRequest NOTIFICATION-TYPE
        OBJECTS { zxAnMduPortIfIndex, zxAnMduConfigFileCRC32 }
        STATUS             current
        DESCRIPTION
           "It indicate Upload Configuraton File Request,The variable 
           zxAnMduPortIfIndex indicate trap position,it's type is ZxAnIfindex,
           detail info about ZxAnIfindex please refer to ZTE-AN-TC-MIB.mib 
           file."
       ::= { zxAnMduServiceTrapObjects 2 }     

       
-------------------------------------------------------------------------------
-- 20.10 zxAnMduEquipTrapObjects
-------------------------------------------------------------------------------
    zxAnMduEquipTrapObjects      OBJECT IDENTIFIER ::= { zxAnMduTrapObjects 10}
    
    zxAnMduEnvSwitchFailed NOTIFICATION-TYPE
         OBJECTS {
             zxAnMduEnvDeviceId,zxAnMduEnvEnvDeviceName,
             zxAnMduEnvSwitchNormalStatus,zxAnMduEnvSwitchCurrentStatus
         }   
         STATUS      current
         DESCRIPTION
            "It is generated when the switch is Faild."
         ::= { zxAnMduEquipTrapObjects 1 }

    zxAnMduEnvSwitchRecovered NOTIFICATION-TYPE
         OBJECTS {
             zxAnMduEnvDeviceId,zxAnMduEnvEnvDeviceName,
             zxAnMduEnvSwitchNormalStatus,zxAnMduEnvSwitchCurrentStatus
         }    
         STATUS      current
         DESCRIPTION
            "It is generated when the switch is Recovered."
         ::= { zxAnMduEquipTrapObjects 2 }
        
       
-------------------------------------------------------------------------------
--  100.zxAnMduMibEnd 
-------------------------------------------------------------------------------
    zxAnMduMibEnd OBJECT-TYPE
        SYNTAX      Integer32
        MAX-ACCESS  read-only
        STATUS      current
        DESCRIPTION
                "The dummy object indicats the end of Mdu mib."
        ::= { zxAnMduMib 100 }
                                                                                                         
END

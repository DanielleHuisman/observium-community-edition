ZTE-AN-OFD-SMI DEFINITIONS ::= BEGIN

IMPORTS
    MODULE-IDENTITY, OBJECT-IDENTITY, enterprises    FROM SNMPv2-SMI;

    zxAnOfd  MODULE-IDENTITY
        LAST-UPDATED    "201302250000Z"
        ORGANIZATION    "ZTE Corporation"
        CONTACT-INFO    "wangbingyu
                         Mail: wang.bingyu@zte.com.cn
                         Tel : 021-68897359"
        DESCRIPTION     "The mib architecture for management of ZTE optical 
                         fiber diagnosis nodes.
                         The OID of zxAnOfd is assigned by zhang.jingshu,
                         tech. depart of ZTE China."
        REVISION        "201302250000Z"
        DESCRIPTION     "Initial version of this MIB module."
        ::= { zte 1083 }

    zte     OBJECT IDENTIFIER ::= { enterprises 3902 }
    
END

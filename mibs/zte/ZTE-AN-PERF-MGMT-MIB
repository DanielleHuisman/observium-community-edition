--------------------------------------------------------------------------
-- File Name : ZTE-AN-PERF-MGMT-MIB.mib
-- Date      : 2007-01-04
-- Author    : ZTE Nms dept.

--
-- Zte Performance Mgmt Mib for Access Node
-- 
-- 
--------------------------------------------------------------------------


ZTE-AN-PERF-MGMT-MIB DEFINITIONS ::= BEGIN

    IMPORTS
        MODULE-IDENTITY,NOTIFICATION-TYPE,OBJECT-TYPE,Integer32
        ,Unsigned32,Counter64
                                                    FROM SNMPv2-SMI
        RowStatus,DisplayString,TEXTUAL-CONVENTION,TruthValue
                                                    FROM SNMPv2-TC
        zxAn                                        FROM ZTE-AN-TC-MIB;


    zxAnPerfMgmtMib MODULE-IDENTITY
        LAST-UPDATED    "200703271030Z"
        ORGANIZATION "ZTE Corporation"
        CONTACT-INFO "ZTE NMS dept. 
                      Su Chunshan   68896292,
                      Xu Lirong     68896481 "
        DESCRIPTION  "This MIB defines managed objects of zte system mgmt."
         ::= { zxAn 189 }
         
         
    zxAnPerfMgmtObjects        OBJECT IDENTIFIER ::= { zxAnPerfMgmtMib 1 }
    zxAnPerfLogMgmtObjects     OBJECT IDENTIFIER ::= { zxAnPerfMgmtMib 2 }
    zxAnPerfFileMgmtObjects    OBJECT IDENTIFIER ::= { zxAnPerfMgmtMib 3 }
    zxAnPerfMgmtTrapObjects    OBJECT IDENTIFIER ::= { zxAnPerfMgmtMib 100 }
   


--------------------------------------------------------------------------------
-- Following objects are defined.
-- 1.performance control table
-- 2.performance threshold table
-- 3.performance file mgmt
--------------------------------------------------------------------------------



--------------------------------------------------------------------------------
-- 1.performance control table
--------------------------------------------------------------------------------   
    zxAnPmCtrlTable   OBJECT-TYPE
        SYNTAX      SEQUENCE  OF  ZxAnPmCtrlEntry
        MAX-ACCESS  not-accessible
        STATUS      current
        DESCRIPTION "This table includes performance control information."
        ::=  { zxAnPerfMgmtObjects  1 }

    zxAnPmCtrlEntry   OBJECT-TYPE
        SYNTAX      ZxAnPmCtrlEntry
        MAX-ACCESS  not-accessible
        STATUS      current
        DESCRIPTION "An entry in zxAnPmCtrlTable.It defines performance 
        metrics to be monitored."
        
          INDEX { zxAnPmCtrlIndex }
        ::=  { zxAnPmCtrlTable 1 }

    ZxAnPmCtrlEntry  ::=  SEQUENCE {
        zxAnPmCtrlIndex                      Integer32,
        zxAnPmCtrlDesc                       DisplayString,
        zxAnPmCtrlMetric                     OBJECT IDENTIFIER,
        zxAnPmCtrlMetricInstIndex            OBJECT IDENTIFIER,
        zxAnPmCtrlAdminStatus                INTEGER,
        zxAnPmCtrlBucketsRequested           Integer32, -- reserved now 2007-01-04
        zxAnPmCtrlBucketsGranted             Integer32, -- reserved now 2007-01-04
        zxAnPmCtrlSamplingInterval           Integer32,
        zxAnPmCtrlRowStatus                  RowStatus,
        zxAnPmCtrlSamplingType               INTEGER,
        zxAnPmCtrlStatisticalInterval        Integer32
        }

    zxAnPmCtrlIndex     OBJECT-TYPE
        SYNTAX      Integer32
        MAX-ACCESS  not-accessible
        STATUS      current
        DESCRIPTION
            "An index that uniquely identifies an entry in the
             zxAnPmCtrl table."
        ::= { zxAnPmCtrlEntry 1 }


    zxAnPmCtrlDesc    OBJECT-TYPE
        SYNTAX      DisplayString
        MAX-ACCESS  read-create
        STATUS      current
        DESCRIPTION
            "Description for this performance metric."
        ::= { zxAnPmCtrlEntry 2 }

    zxAnPmCtrlMetric    OBJECT-TYPE
        SYNTAX      OBJECT IDENTIFIER
        MAX-ACCESS  read-create
        STATUS      current
        DESCRIPTION
            "The performance metric identification.It identifies the type of 
         the performance data for which historical data was collected .  

         -- IMPORTANT!!
             This metric can be any leaf node,ie. variable or virtual object 
         identifier in the mib. 
             When it is leaf node, ie. variable, It means only this variable will be 
         monitored by a agent.
             When it isn't a leaf node,ie. a virtual object identifier, It means 
         all variables subject to this node will be monitored by a agent.

             This object indicates the monitored metric only, but no a monitored 
         instance.So if the monitored instance should be told to a agent,
         the zxAnPmCtrlMetricInstIndex must be specified. For example,
            If the instance 'ifInOctets.15' will be monitered,then zxAnPmCtrlMetric
         should be 1.3.6.1.2.1.2.2.1.10, and then, zxAnPmCtrlMetricInstIndex 
         should be 15.         
            "
        ::= { zxAnPmCtrlEntry 3 }
        
        
    zxAnPmCtrlMetricInstIndex  OBJECT-TYPE
        SYNTAX      OBJECT IDENTIFIER
        MAX-ACCESS  read-create
        STATUS      current
        DESCRIPTION
            "A mib variable's instance.When the monitored object is only a 
        specified variable's instance,such as a port's ifInOctets,the 
        zxAnPmCtrlMetricInstIndex should be specified.For example,
            If the instance 'ifInOctets.15' will be monitered,then zxAnPmCtrlMetric
         should be 1.3.6.1.2.1.2.2.1.10, and then, zxAnPmCtrlMetricInstIndex 
         should be 15.
            If no instance should be specified,zxAnPmCtrlMetricInstIndex should 
         be 0.   
                    
            "
        ::= { zxAnPmCtrlEntry 4 }
        
    zxAnPmCtrlAdminStatus  OBJECT-TYPE
        SYNTAX      INTEGER{                           
                       start(1),
                       stop(2),
                       resetCounter(3)
                    }
        MAX-ACCESS  read-create
        STATUS      current
        DESCRIPTION
            "The performance metric operation mode."
        ::= { zxAnPmCtrlEntry 5 }
  
  
    zxAnPmCtrlBucketsRequested OBJECT-TYPE
         SYNTAX     Integer32 (1..65535)
         MAX-ACCESS read-create
         STATUS     current
         DESCRIPTION
             "The requested number of discrete time intervals.
    
             When this object is created or modified, the probe
             should set zxAnPmCtrlBucketsGranted as closely to
             this object as is possible for the particular probe
             implementation and available resources."
         DEFVAL { 50 }
         ::= { zxAnPmCtrlEntry 6 }
    
     zxAnPmCtrlBucketsGranted OBJECT-TYPE
         SYNTAX     Integer32 (1..65535)
         MAX-ACCESS read-only
         STATUS     current
         DESCRIPTION
             "The number of discrete sampling intervals.
       
             When the associated zxAnPmCtrlBucketsRequested
             object is created or modified, the probe
             should set this object as closely to the requested
             value as is possible for the particular
             probe implementation and available resources.  The
             probe must not lower this value except as a result
             of a modification to the associated
             zxAnPmCtrlBucketsRequested object.
    
             There will be times when the actual number of
             buckets associated with this entry is less than
             the value of this object.  In this case, at the
             end of each sampling interval, a new bucket will
             be added to the media-specific table.
    
             When the number of buckets reaches the value of
             this object and a new bucket is to be added to the
             media-specific table, the oldest bucket associated
             with this zxAnPmCtrlEntry shall be deleted by
             the agent so that the new bucket can be added.
    
             When the value of this object changes to a value less
             than the current value, entries are deleted
             from the media-specific table associated with this
             zxAnPmCtrlEntry.  Enough of the oldest of these
             entries shall be deleted by the agent so that their
             number remains less than or equal to the new value of
             this object.
    
             When the value of this object changes to a value greater
             than the current value, the number of associated media-
             specific entries may be allowed to grow."
         ::= { zxAnPmCtrlEntry 7 }
    
     zxAnPmCtrlSamplingInterval OBJECT-TYPE
         SYNTAX     Integer32 (1..3600)
         UNITS      "Seconds"
         MAX-ACCESS read-create
         STATUS     current
         DESCRIPTION
             "The interval in seconds over which the data is
             sampled for each bucket in the part of the
             media-specific table associated with this
             zxAnPmCtrlEntry.  This interval can
             be set to any number of seconds between 1 and
             3600 (1 hour).
    
             Because the counters in a bucket may overflow at their
    
    
             maximum value with no indication, a prudent manager will
             take into account the possibility of overflow in any of
             the associated counters.  It is important to consider the
             minimum time in which any counter could overflow on a
             particular media type and set the zxAnPmCtrlInterval
             object to a value less than this interval.  This is
             typically most important for the 'octets' counter in any
             media-specific table.  For example, on an Ethernet
             network, the etherHistoryOctets counter could overflow
             in about one hour at the Ethernet's maximum
             utilization.
    
             This object may not be modified if the associated
             zxAnPmCtrlStatus object is equal to valid(1)."
         DEFVAL { 1800 }
         ::= { zxAnPmCtrlEntry 8 }
         
             
    zxAnPmCtrlRowStatus OBJECT-TYPE
        SYNTAX      RowStatus
        MAX-ACCESS  read-create
        STATUS      current
        DESCRIPTION
            "The row status of this entry."
        ::= { zxAnPmCtrlEntry 9 }
       
    zxAnPmCtrlSamplingType   OBJECT-TYPE
        SYNTAX     INTEGER {
                  absoluteValue(1),
                  deltaValue(2)
                }
        MAX-ACCESS read-create
        STATUS     current
        DESCRIPTION
            "The method of sampling the selected variable and
            calculating the value to be compared against the
            thresholds.  If the value of this object is
            absoluteValue(1), the value of the selected variable
            will be compared directly with the thresholds at the
            end of the sampling interval.  If the value of this
            object is deltaValue(2), the value of the selected
            variable at the last sample will be subtracted from
            the current value, and the difference compared with
            the thresholds."
        ::= { zxAnPmCtrlEntry 10 }
                        
     zxAnPmCtrlStatisticalInterval OBJECT-TYPE
         SYNTAX     Integer32 (1..1440)
         UNITS      "Minutes"
         MAX-ACCESS read-create
         STATUS     current
         DESCRIPTION
             "The interval in minutes over which the data is
             statistical for each bucket in the part of the
             media-specific table associated with this
             zxAnPmCtrlEntry.  This interval can
             be set to any number of seconds between 1 and
             1400 (24 hour)."
         DEFVAL { 15 }
         ::= { zxAnPmCtrlEntry 11 }        
        

    zxAnPmSpareIndex   OBJECT-TYPE
        SYNTAX      Integer32
        MAX-ACCESS  read-only
        STATUS      current
        DESCRIPTION "Query Pm free index."
        ::=  { zxAnPerfMgmtObjects  2 }
        
--------------------------------------------------------------------------------
-- 31.performance history table
-------------------------------------------------------------------------------- 
    zxAnPmHisTable   OBJECT-TYPE
        SYNTAX      SEQUENCE  OF  ZxAnPmHisEntry
        MAX-ACCESS  not-accessible
        STATUS      current
        DESCRIPTION "This table includes performance history information."
        ::=  { zxAnPerfMgmtObjects  31 }

    zxAnPmHisEntry   OBJECT-TYPE
        SYNTAX      ZxAnPmHisEntry
        MAX-ACCESS  not-accessible
        STATUS      current
        DESCRIPTION "An entry in zxAnPmHisTable.It defines history performance metrics."
        
          INDEX { zxAnPmHisMetric,zxAnPmHisMetricInstIndex }
        ::=  { zxAnPmHisTable 1 }

    ZxAnPmHisEntry  ::=  SEQUENCE {
        zxAnPmHisMetric                OBJECT IDENTIFIER,
        zxAnPmHisMetricInstIndex       OBJECT IDENTIFIER,
        zxAnPmHisStatisticalValue      Counter64
        }         
         
    zxAnPmHisMetric    OBJECT-TYPE
        SYNTAX      OBJECT IDENTIFIER
        MAX-ACCESS  not-accessible
        STATUS      current
        DESCRIPTION
            "The performance metric identification.It identifies the type of 
         the performance data for which historical data was collected . "
        ::= { zxAnPmHisEntry 1 }
        
        
    zxAnPmHisMetricInstIndex  OBJECT-TYPE
        SYNTAX      OBJECT IDENTIFIER
        MAX-ACCESS  not-accessible
        STATUS      current
        DESCRIPTION
            "A mib variable's instance.When the monitored object is only a 
        specified variable's instance,such as a port's ifInOctets,the 
        zxAnPmThresholdMetricPointInstIndex should be specified.For example,
            If the instance 'ifInOctets.15' will be monitered,then zxAnPmCtrlMetric
         should be 1.3.6.1.2.1.2.2.1.10, and then, zxAnPmThresholdMetricPointInstIndex 
         should be 15.
            If no instance should be specified,zxAnPmThresholdMetricPointInstIndex should 
         be 0.   
                    
            "
        ::= { zxAnPmHisEntry 2 }
        
         
     zxAnPmHisStatisticalValue OBJECT-TYPE
         SYNTAX     Counter64
         MAX-ACCESS read-only
         STATUS     current
         DESCRIPTION
             "The value of history performance metric."
         ::= { zxAnPmHisEntry 3 }              
        
--------------------------------------------------------------------------------
-- 32.performance threshold table
--------------------------------------------------------------------------------   
    zxAnPmThresholdTable   OBJECT-TYPE
        SYNTAX      SEQUENCE  OF  ZxAnPmThresholdEntry
        MAX-ACCESS  not-accessible
        STATUS      current
        DESCRIPTION "This table includes performance threshold information."
        ::=  { zxAnPerfMgmtObjects  32 }

    zxAnPmThresholdEntry   OBJECT-TYPE
        SYNTAX      ZxAnPmThresholdEntry
        MAX-ACCESS  not-accessible
        STATUS      current
        DESCRIPTION "An entry in zxAnPmThresholdTable.It defines performance 
        metrics threshold to be monitored."
        
          INDEX { zxAnPmThresholdMetricInstIndex,zxAnPmThresholdMetric }
        ::=  { zxAnPmThresholdTable 1 }

    ZxAnPmThresholdEntry  ::=  SEQUENCE {
        zxAnPmThresholdMetricInstIndex       OBJECT IDENTIFIER,
        zxAnPmThresholdMetric                OBJECT IDENTIFIER,
        zxAnPmEventTrapEnable                INTEGER,
        zxAnPmRisingWarningThreshold         Counter64,
        zxAnPmRisingAlarmThreshold           Counter64,
        zxAnPmFallingWarningThreshold        Counter64,
        zxAnPmFallingAlarmThreshold           Counter64,
        zxAnPmThresholdRowStatus             RowStatus
        }         
         
         
    zxAnPmThresholdMetricInstIndex  OBJECT-TYPE
        SYNTAX      OBJECT IDENTIFIER
        MAX-ACCESS  not-accessible
        STATUS      current
        DESCRIPTION
            "A mib variable's instance.When the monitored object is only a 
        specified variable's instance,such as a port's ifInOctets,the 
        zxAnPmThresholdMetricPointInstIndex should be specified.For example,
            If the instance 'ifInOctets.15' will be monitered,then zxAnPmCtrlMetric
         should be 1.3.6.1.2.1.2.2.1.10, and then, zxAnPmThresholdMetricPointInstIndex 
         should be 15.
            If no instance should be specified,zxAnPmThresholdMetricPointInstIndex should 
         be 0."
        ::= { zxAnPmThresholdEntry 1 }
             
    zxAnPmThresholdMetric    OBJECT-TYPE
        SYNTAX      OBJECT IDENTIFIER
        MAX-ACCESS  not-accessible
        STATUS      current
        DESCRIPTION
            "The performance metric identification.It identifies the type of 
         the performance data for which historical data was collected . "
        ::= { zxAnPmThresholdEntry 2 }
        
        
     zxAnPmEventTrapEnable  OBJECT-TYPE
        SYNTAX INTEGER
                {
                  enable(1), 
                  disable(2)
                }
        MAX-ACCESS read-create
        STATUS current
        DESCRIPTION
            "enable/disable this performance trap."
        ::= { zxAnPmThresholdEntry 3 }


    zxAnPmRisingWarningThreshold OBJECT-TYPE
        SYNTAX Counter64
        MAX-ACCESS read-create
        STATUS current
        DESCRIPTION
                  "A threshold for the sampled statistic.  When the
                  current sampled value is greater than or equal to
                  this threshold, and the value at the last sampling
                  interval was less than this threshold, a single
                  warning event will be generated. 

                  After a rising event is generated, another such event
                  will not be generated until the sampled value
                  falls below this threshold and reaches the
                  zxAnPmEventFallingWarningThreshold."
                  
        ::= { zxAnPmThresholdEntry 4 }
        
    zxAnPmRisingAlarmThreshold OBJECT-TYPE
        SYNTAX Counter64
        MAX-ACCESS read-create
        STATUS current
        DESCRIPTION
                  "A threshold for the sampled statistic.  When the
                  current sampled value is greater than or equal to
                  this threshold, and the value at the last sampling
                  interval was less than this threshold, a single
                  alarm event will be generated. 

                  After a rising event is generated, another such event
                  will not be generated until the sampled value
                  falls below this threshold and reaches the
                  zxAnPmEventFallingAlarmThreshold."
                  
        ::= { zxAnPmThresholdEntry 5 }        

    zxAnPmFallingWarningThreshold  OBJECT-TYPE
        SYNTAX Counter64
        MAX-ACCESS read-create
        STATUS current
        DESCRIPTION
                  "A threshold for the sampled statistic.  When the
                  current sampled value is less than or equal to this
                  threshold, and the value at the last sampling
                  interval was greater than this threshold, a single
                  warning event will be generated. 

                  After a falling event is generated, another such event
                  will not be generated until the sampled value
                  rises above this threshold and reaches the
                  zxAnPmEventRisingWarningThreshold."
        ::= { zxAnPmThresholdEntry 6 }  
        
    zxAnPmFallingAlarmThreshold  OBJECT-TYPE
        SYNTAX Counter64
        MAX-ACCESS read-create
        STATUS current
        DESCRIPTION
                  "A threshold for the sampled statistic.  When the
                  current sampled value is less than or equal to this
                  threshold, and the value at the last sampling
                  interval was greater than this threshold, a single
                  alarm event will be generated. 

                  After a falling event is generated, another such event
                  will not be generated until the sampled value
                  rises above this threshold and reaches the
                  zxAnPmEventRisingAlarmThreshold."
        ::= { zxAnPmThresholdEntry 7 }  
         
             
    zxAnPmThresholdRowStatus OBJECT-TYPE
        SYNTAX      RowStatus
        MAX-ACCESS  read-create
        STATUS      current
        DESCRIPTION
            "The row status of this entry."
        ::= { zxAnPmThresholdEntry 31 }
        

--------------------------------------------------------------------------------
-- 2.performance log mgmt
--------------------------------------------------------------------------------
    zxAnPmLogAdminStatus   OBJECT-TYPE
        SYNTAX INTEGER
                {
                  enable(1), 
                  disable(2)
                }
        MAX-ACCESS  read-write
        STATUS      current
        DESCRIPTION "It indicate whether NE record performance metric static value to log file.
        If is enable,NE will record performance metric static value to log file."
        ::=  { zxAnPerfLogMgmtObjects  1 }


    zxAnPmLogMaxRecordRows   OBJECT-TYPE
         SYNTAX     Integer32 
         MAX-ACCESS read-write
         STATUS     current
         DESCRIPTION
             "Performance metric log record rows.More than the max record number,the log file will be re-writted circulatory.
             It means when reache max record number,some performance metric static records will be losted."
         ::= { zxAnPerfLogMgmtObjects 2 } 
         
         
    zxAnPmLogManualReportAction   OBJECT-TYPE
         SYNTAX INTEGER
                {
                  report(1)
                }
         MAX-ACCESS read-write
         STATUS     current
         DESCRIPTION
             "If report,NE will FTP performance metric log file to EMS immediately."
         ::= { zxAnPerfLogMgmtObjects 3 }
         
    zxAnPmLogManualReportStatus   OBJECT-TYPE
         SYNTAX TruthValue
         MAX-ACCESS read-only
         STATUS     current
         DESCRIPTION
             "If true,NE has reported file to FTP path.It related with zxAnPmLogManualReportAction.
             If zxAnPmLogManualReportAction set report,NE first set zxAnPmLogManualReportStatus false,
             when log file has been uploaded to EMS,then NE set zxAnPmLogManualReportStatus true."
         ::= { zxAnPerfLogMgmtObjects 4 }         
         
         
    zxAnPmLogAutoReportMetric   OBJECT-TYPE
        SYNTAX  TruthValue
        MAX-ACCESS  read-write
        STATUS      current
        DESCRIPTION "It indicate whether NE report log file automatic to EMS by FTP."
        ::=  { zxAnPerfLogMgmtObjects  5 }
        
        
       zxAnPmLogAutoReportInterval   OBJECT-TYPE
         SYNTAX     Integer32 
         UNITS      "Minute"
         MAX-ACCESS read-write
         STATUS     current
         DESCRIPTION
             "NE FTP performance metric log file to EMS interval time."
         ::= { zxAnPerfLogMgmtObjects 6 }
               
               
    zxAnPmLogReportFtpHost   OBJECT-TYPE
         SYNTAX     DisplayString 
         MAX-ACCESS read-write
         STATUS     current
         DESCRIPTION
             "EMS FTP Host IP Address. "
         ::= { zxAnPerfLogMgmtObjects 7 }
         
         
    zxAnPmLogReportFtpPath   OBJECT-TYPE
         SYNTAX     DisplayString 
         MAX-ACCESS read-write
         STATUS     current
         DESCRIPTION
             "EMS FTP Path,there EMS will upload log files."
         ::= { zxAnPerfLogMgmtObjects 8 }
         
         
    zxAnPmLogReportFtpUser   OBJECT-TYPE
         SYNTAX     DisplayString 
         MAX-ACCESS read-write
         STATUS     current
         DESCRIPTION
             "The user name of zxAnPmLogReportFtpUrl."
         ::= { zxAnPerfLogMgmtObjects 9 }
         
         
   zxAnPmLogReportFtpPassword   OBJECT-TYPE
         SYNTAX     DisplayString 
         MAX-ACCESS read-write
         STATUS     current
         DESCRIPTION
             "The password of of zxAnPmLogReportFtpUrl."
         ::= { zxAnPerfLogMgmtObjects 10 }
         
         
    zxAnPmLogCtrlTable   OBJECT-TYPE
        SYNTAX      SEQUENCE  OF  ZxAnPmLogCtrlEntry
        MAX-ACCESS  not-accessible
        STATUS      current
        DESCRIPTION "This table includes performance log control information."
        ::=  { zxAnPerfLogMgmtObjects  31 }


    zxAnPmLogCtrlEntry   OBJECT-TYPE
        SYNTAX      ZxAnPmLogCtrlEntry
        MAX-ACCESS  not-accessible
        STATUS      current
        DESCRIPTION "An entry in zxAnPmLogCtrlTable.It defines which performance 
        metrics add to log file."
        
          INDEX { zxAnPmLogCtrlMetric, zxAnPmLogCtrlMetricInstIndex}
        ::=  { zxAnPmLogCtrlTable 1 }


    ZxAnPmLogCtrlEntry  ::=  SEQUENCE {
        zxAnPmLogCtrlMetric                     OBJECT IDENTIFIER,
        zxAnPmLogCtrlMetricInstIndex            OBJECT IDENTIFIER,
        zxAnPmLoggingMetricAdminStatus          INTEGER,
        zxAnPmLogCtrlRowStatus                  RowStatus
        }
         
         
    zxAnPmLogCtrlMetric    OBJECT-TYPE
        SYNTAX      OBJECT IDENTIFIER
        MAX-ACCESS  not-accessible
        STATUS      current
        DESCRIPTION
            "The performance metric identification.It identifies the type of 
         the performance data for which historical data was collected .  

         -- IMPORTANT!!
             This metric can be any leaf node,ie. variable or virtual object 
         identifier in the mib. 
             When it is leaf node, ie. variable, It means only this variable will be 
         monitored by a agent.
             When it isn't a leaf node,ie. a virtual object identifier, It means 
         all variables subject to this node will be monitored by a agent.

             This object indicates the monitored metric only, but no a monitored 
         instance.So if the monitored instance should be told to a agent,
         the zxAnPmCtrlMetricInstIndex must be specified. For example,
            If the instance 'ifInOctets.15' will be monitered,then zxAnPmCtrlMetric
         should be 1.3.6.1.2.1.2.2.1.10, and then, zxAnPmCtrlMetricInstIndex 
         should be 15.         
            "
        ::= { zxAnPmLogCtrlEntry 1 }
        
        
    zxAnPmLogCtrlMetricInstIndex  OBJECT-TYPE
        SYNTAX      OBJECT IDENTIFIER
        MAX-ACCESS  not-accessible
        STATUS      current
        DESCRIPTION
            "A mib variable's instance.When the monitored object is only a 
        specified variable's instance,such as a port's ifInOctets,the 
        zxAnPmCtrlMetricInstIndex should be specified.For example,
            If the instance 'ifInOctets.15' will be monitered,then zxAnPmCtrlMetric
         should be 1.3.6.1.2.1.2.2.1.10, and then, zxAnPmCtrlMetricInstIndex 
         should be 15.
            If no instance should be specified,zxAnPmCtrlMetricInstIndex should 
         be 0.   
                    
            "
        ::= { zxAnPmLogCtrlEntry 2 }
        
    zxAnPmLoggingMetricAdminStatus   OBJECT-TYPE
        SYNTAX INTEGER
                {
                  enable(1), 
                  disable(2)
                }
        MAX-ACCESS  read-create
        STATUS      current
        DESCRIPTION "It indicate whether NE record this performance metric static value to log file.
        It also depend zxAnPmLogAdminStatus.Only zxAnPmLogAdminStatus and zxAnPmCtrlLogAdminStatus are enable,
        NE records performance metric static value to log file."
        ::=  { zxAnPmLogCtrlEntry  3 }
        
        
     zxAnPmLogCtrlRowStatus OBJECT-TYPE
        SYNTAX      RowStatus
        MAX-ACCESS  read-create
        STATUS      current
        DESCRIPTION
            "The row status of this entry."
        ::= { zxAnPmLogCtrlEntry 31 }                 
                
--------------------------------------------------------------------------------
-- 3.performance file mgmt
--------------------------------------------------------------------------------
    zxAnPerfRetrievalControlObjects  OBJECT IDENTIFIER   
        ::=  {  zxAnPerfFileMgmtObjects  1  }
    
    zxAnPerfRetrievalTimeGranularity       OBJECT-TYPE 
        SYNTAX          INTEGER  
        {
            for15Minutes(1), 
            for24Hours(2)
        }
        MAX-ACCESS      read-write
        STATUS          current
        DESCRIPTION     "The time granularity  of performance data retrieval."
        ::=  {  zxAnPerfRetrievalControlObjects  1  }   
    
    zxAnPerfRetrievalStartTime       OBJECT-TYPE     
        SYNTAX      DisplayString (SIZE (1..19))
        MAX-ACCESS  read-write
        STATUS      current
        DESCRIPTION
        "Specifies the start of the time for which the 
         selected PM measurements shall be retrieved (this parameter 
         only applies for the retrieval of historical PM data). 
         The format is  yyyy-mm-dd HH:MM:SS.
         For example,  2001-01-01 02:22:33. "
        ::=  {  zxAnPerfRetrievalControlObjects  2 }        
        
    zxAnPerfRetrievalEndTime       OBJECT-TYPE     
        SYNTAX      DisplayString (SIZE (1..19))
        MAX-ACCESS  read-write
        STATUS      current
        DESCRIPTION
        "Specifies the end of the time for which the selected 
         PM measurements shall be retrieved (this parameter only 
         applies for the retrieval of historical PM data). 
         The format is  yyyy-mm-dd HH:MM:SS.
         For example,  2001-01-01 02:22:33. "
        ::=  {  zxAnPerfRetrievalControlObjects  3 }  
--------------------------------------------------------------------------------
-- 100.Trap
--------------------------------------------------------------------------------
    zxAnPmMetricOverWarning NOTIFICATION-TYPE
        OBJECTS {  zxAnPmThresholdMetricInstIndex, zxAnPmThresholdMetric, zxAnPmHisStatisticalValue,  zxAnPmCtrlStatisticalInterval, zxAnPmCtrlSamplingType,zxAnPmRisingWarningThreshold,zxAnPmFallingWarningThreshold}
        STATUS             current
        DESCRIPTION
           "It indicate current statistical metric over threshold,if zxAnPmEventRisingThreshold has valid value,
           it means over upper threshold,inversely it means below lower threshold."
       ::= { zxAnPerfMgmtTrapObjects 1 }            

    zxAnPmMetricOverWarningRestore NOTIFICATION-TYPE
        OBJECTS { zxAnPmThresholdMetricInstIndex,zxAnPmThresholdMetric, zxAnPmHisStatisticalValue, zxAnPmCtrlStatisticalInterval, zxAnPmCtrlSamplingType,zxAnPmRisingWarningThreshold,zxAnPmFallingWarningThreshold}
        STATUS             current
        DESCRIPTION
           "It indicate current statistical metric restore to normal range."
       ::= { zxAnPerfMgmtTrapObjects 2 }   
  
    zxAnPmMetricOverAlarm NOTIFICATION-TYPE
        OBJECTS { zxAnPmThresholdMetricInstIndex, zxAnPmThresholdMetric, zxAnPmHisStatisticalValue, zxAnPmCtrlStatisticalInterval, zxAnPmCtrlSamplingType,zxAnPmRisingAlarmThreshold,zxAnPmFallingAlarmThreshold}
        STATUS             current
        DESCRIPTION
           "It indicate current statistical metric over threshold,if zxAnPmEventRisingAlarmThreshold has valid value,
           it means over upper threshold,inversely it means below lower threshold."
       ::= { zxAnPerfMgmtTrapObjects 3 }            

    zxAnPmMetricOverAlarmRestore NOTIFICATION-TYPE
        OBJECTS { zxAnPmThresholdMetricInstIndex, zxAnPmThresholdMetric,  zxAnPmHisStatisticalValue, zxAnPmCtrlStatisticalInterval, zxAnPmCtrlSamplingType,zxAnPmRisingAlarmThreshold,zxAnPmFallingAlarmThreshold}
        STATUS             current
        DESCRIPTION
           "It indicate current statistical metric restore to normal range."
       ::= { zxAnPerfMgmtTrapObjects 4 }    
    
END

--------------------------------------------------------------------------
-- File Name : ZTE-AN-PPPOA-MIB.mib
-- Date      : 2007-06-07
-- Author    : ZTE Nms dept.

--
-- Zte PPPOA Mib for Access Node
-- 
-- 
--------------------------------------------------------------------------

ZTE-AN-PPPOA-MIB  DEFINITIONS ::= BEGIN
  IMPORTS
        MODULE-IDENTITY, OBJECT-TYPE, NOTIFICATION-TYPE,
        Integer32, IpAddress,Counter32          FROM SNMPv2-SMI        
        DisplayString,MacAddress                FROM SNMPv2-TC
        MODULE-COMPLIANCE, OBJECT-GROUP         FROM SNMPv2-CONF
        zxAn,ZxAnIfindex                        FROM ZTE-AN-TC-MIB;
              

  zxAnPppoaMib  MODULE-IDENTITY
    LAST-UPDATED  "200706071600Z"
    ORGANIZATION  "ZTE Corporation"
    CONTACT-INFO  "suchunshan
                  Mail: suchunshan@zte.com.cn
                  Tel : 021-68896292"
    DESCRIPTION   "This MIB defines managed objects of PPPOA for DSLAM."
    ::=  {  zxAn 35  }


    zxAnPppoaGlobal OBJECT IDENTIFIER ::= { zxAnPppoaMib 1 }
  
   

--------------------------------------------------------------------------------
-- Following objects are defined.
-- 1.PPPoA Global
-- 2.PPPoA Interface Table
--------------------------------------------------------------------------------



------------------------------------------------------------------------------
-- 1.PPPoA Global
------------------------------------------------------------------------------

  zxAnPppoaEchoTimeout OBJECT-TYPE
        SYNTAX      Integer32(60..1800)
        UNITS       "sec"
        MAX-ACCESS  read-write
        STATUS      current
        DESCRIPTION
            "The timeout of PPPOA echo ."
        DEFVAL { 180 }    
          ::= { zxAnPppoaGlobal 1}   
         

------------------------------------------------------------------------------
-- 2.PPPoA Interface Table
------------------------------------------------------------------------------


  zxAnPppoaInterfaceTable OBJECT-TYPE
        SYNTAX SEQUENCE OF ZxAnPppoaInterfaceEntry
        MAX-ACCESS not-accessible
        STATUS current
        DESCRIPTION
            "PPPoA Interface information table"
        ::= { zxAnPppoaMib 2 }
        
   zxAnPppoaInterfaceEntry OBJECT-TYPE
        SYNTAX ZxAnPppoaInterfaceEntry
        MAX-ACCESS not-accessible
        STATUS current
        DESCRIPTION
            "PPPoA Interface information table"
      INDEX { zxAnPppoaIfIndex }
        ::= { zxAnPppoaInterfaceTable 1 }
            
    ZxAnPppoaInterfaceEntry ::= SEQUENCE 
    {
        zxAnPppoaIfIndex                 ZxAnIfindex,
        zxAnPppoaIfAdminStatus           INTEGER,
        zxAnPppoaIfMgmtOperstatus        INTEGER,
        zxAnPppoaIfSessionId             Integer32,
        zxAnPppoaIfServerMac             MacAddress,
        zxAnPppoaIfLcpCfgReqPkts         Counter32,
        zxAnPppoaIfEchoAckPkts           Counter32,
        zxAnPppoaIfLcpTerminateReqPkts   Counter32,
        zxAnPppoaIfPadoPkts              Counter32,
        zxAnPppoaIfPadsPkts              Counter32,
        zxAnPppoaIfPadtPkts              Counter32

    }   



     zxAnPppoaIfIndex OBJECT-TYPE
        SYNTAX      ZxAnIfindex
        MAX-ACCESS  not-accessible
        STATUS      current
        DESCRIPTION
            "The interface index of user port or bridge port."
          ::= { zxAnPppoaInterfaceEntry 1}   


     zxAnPppoaIfAdminStatus OBJECT-TYPE
        SYNTAX      INTEGER
             {
                    enable(1), 
                    disable(2)
             }
        MAX-ACCESS  read-write
        STATUS      current
        DESCRIPTION
            "The administrative status of the port PPPoA."
          ::= { zxAnPppoaInterfaceEntry 2}  

       
       
    zxAnPppoaIfMgmtOperstatus  OBJECT-TYPE
        SYNTAX      INTEGER
             {
                  invalidState(1) ,
                  waitLcpCfgreq(2),
                  waitPado(3),
                  waitPads(4),
                  waitRetry(5),
                  pppoeConnnect(6)
             }
        MAX-ACCESS  read-only
        STATUS      current
        DESCRIPTION
            "The PPPOA management operatinal status."
          ::= { zxAnPppoaInterfaceEntry 3}   
           


     zxAnPppoaIfSessionId OBJECT-TYPE
        SYNTAX      Integer32
        MAX-ACCESS  read-only
        STATUS      current
        DESCRIPTION
            "The SeesionId that the port obtained from server."
          ::= { zxAnPppoaInterfaceEntry 4}      
          
          
          
     zxAnPppoaIfServerMac OBJECT-TYPE
        SYNTAX      MacAddress
        MAX-ACCESS  read-only
        STATUS      current
        DESCRIPTION
            "The Server MacAddress that the port obtained from server."
          ::= { zxAnPppoaInterfaceEntry 5}   
       

     zxAnPppoaIfLcpCfgReqPkts OBJECT-TYPE
        SYNTAX      Counter32
        MAX-ACCESS  read-only
        STATUS      current
        DESCRIPTION
            "The recieved LcpCfgReqPkts from userside."
          ::= { zxAnPppoaInterfaceEntry 6}   



     zxAnPppoaIfEchoAckPkts OBJECT-TYPE
        SYNTAX      Counter32
        MAX-ACCESS  read-only
        STATUS      current
        DESCRIPTION
            "The recieved LcpCfgReqPkts from userside."
          ::= { zxAnPppoaInterfaceEntry 7}   




     zxAnPppoaIfLcpTerminateReqPkts OBJECT-TYPE
        SYNTAX      Counter32
        MAX-ACCESS  read-only
        STATUS      current
        DESCRIPTION
            "The recieved LcpTerminateReqPkts from userside."
          ::= { zxAnPppoaInterfaceEntry 8}   



     zxAnPppoaIfPadoPkts OBJECT-TYPE
        SYNTAX      Counter32
        MAX-ACCESS  read-only
        STATUS      current
        DESCRIPTION
            "The recieved PadoPkts from server."
          ::= { zxAnPppoaInterfaceEntry 9}   



     zxAnPppoaIfPadsPkts OBJECT-TYPE
        SYNTAX      Counter32
        MAX-ACCESS  read-only
        STATUS      current
        DESCRIPTION
            "The recieved PadsPkt from server."
          ::= { zxAnPppoaInterfaceEntry 10}   


     zxAnPppoaIfPadtPkts OBJECT-TYPE
        SYNTAX      Counter32
        MAX-ACCESS  read-only
        STATUS      current
        DESCRIPTION
            "The recieved PadtPkts from server."
          ::= { zxAnPppoaInterfaceEntry 11}   

END

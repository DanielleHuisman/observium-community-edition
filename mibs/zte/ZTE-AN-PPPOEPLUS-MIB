ZTE-AN-PPPOEPLUS-MIB DEFINITIONS ::= BEGIN 
IMPORTS 
    OBJECT-TYPE, MODULE-IDENTITY                FROM SNMPv2-SMI
    zxAnPortLocatingMib                         FROM ZTE-AN-PORT-LOCATING-MIB
    ZxAnIfindex,zxAn                              FROM ZTE-AN-TC-MIB;
    
    zxAnPppoePlusMib   MODULE-IDENTITY 
         LAST-UPDATED    "0608140000Z"  -- july. 23, 2005
        ORGANIZATION    "zte Telcom Co. Ltd."
        CONTACT-INFO    "E-mail: shen.yuyang@zte.com.cn"
        DESCRIPTION     "his MIB defines PPPoE+ managed objects for Access Node."
        ::= { zxAnPortLocatingMib 40 }

    
    zxAnPppoeIAEnable OBJECT-TYPE
        SYNTAX      INTEGER
            {   
                enable(1),
                disable(2)
            }
        MAX-ACCESS  read-write
        STATUS      current
        DESCRIPTION
        "enable = 1, disable = 2"
        DEFVAL { disable }
        ::= { zxAnPppoePlusMib 1 }
    
    --table
    
    zxAnPortLocatingPppoePlusTable OBJECT-TYPE 
        SYNTAX SEQUENCE OF ZxAnPortLocatingPppoePlusEntry 
        MAX-ACCESS not-accessible 
        STATUS current 
        DESCRIPTION 
        "port Locating pppoe+ table" 
        ::= { zxAnPppoePlusMib 10 }
    
    zxAnPortLocatingPppoePlusEntry OBJECT-TYPE 
        SYNTAX ZxAnPortLocatingPppoePlusEntry
        MAX-ACCESS not-accessible 
        STATUS current 
        DESCRIPTION 
        " port Locating pppoe+ entry. "
        INDEX { zxAnPortLocatingPppoePlusifIndex } 
        ::= { zxAnPortLocatingPppoePlusTable 1 }
    
    ZxAnPortLocatingPppoePlusEntry ::= SEQUENCE {
        zxAnPortLocatingPppoePlusifIndex       ZxAnIfindex,
        zxAnPppoeIAIfConfEnable   INTEGER,
        zxAnPppoeIAIfConfTrust    INTEGER,
        zxAnPppoeIAIfConfPolicy   INTEGER }

    zxAnPortLocatingPppoePlusifIndex     OBJECT-TYPE
        SYNTAX             ZxAnIfindex
        MAX-ACCESS         not-accessible
        STATUS          current
        DESCRIPTION
            "The ifindex of the port pppoe location."
        ::= { zxAnPortLocatingPppoePlusEntry 1 }
        
    zxAnPppoeIAIfConfEnable OBJECT-TYPE 
        SYNTAX INTEGER
            {   
                enable(1),
                disable(2)
            }        
        MAX-ACCESS read-write 
        STATUS current 
        DESCRIPTION 
        "enable = 1, disable = 2"
        DEFVAL { disable }
        ::= { zxAnPortLocatingPppoePlusEntry 2 }
        
    zxAnPppoeIAIfConfTrust OBJECT-TYPE 
        SYNTAX INTEGER 
            {   
                true(1),
                false(2)
            }
        MAX-ACCESS read-write 
        STATUS current 
        DESCRIPTION 
        "Port locating PPPoE plus trust flag."
        DEFVAL { false }
        ::= { zxAnPortLocatingPppoePlusEntry 3 }

    zxAnPppoeIAIfConfPolicy OBJECT-TYPE 
        SYNTAX INTEGER 
            {
                keep(1), 
                replace(2), 
                discard(3), 
                add(4)
            }
        MAX-ACCESS read-write 
        STATUS current 
        DESCRIPTION 
        "Port locating PPPoE plus trust policy.
         when port = trust, policy can set keep or replace, 
         when port = untrust, policy can set discard or    add"
        DEFVAL { add }
        ::= { zxAnPortLocatingPppoePlusEntry 4 }

END

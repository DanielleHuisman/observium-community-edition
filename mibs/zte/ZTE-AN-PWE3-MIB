--------------------------------------------------------------------------------
-- File Name : ZTE-AN-PWE3-MIB.mib
-- Date      : 2008-06-30
-- Author    : ZTE Nms dept.

--
-- Zte PWE3 Mib for Access Node
--
--
--------------------------------------------------------------------------------
ZTE-AN-PWE3-MIB DEFINITIONS ::= BEGIN
  IMPORTS 
     MODULE-IDENTITY, OBJECT-TYPE, NOTIFICATION-TYPE,
     experimental, Integer32, Unsigned32, 
     Counter64, TimeTicks, IpAddress
                                                        FROM SNMPv2-SMI      
     ifIndex                                            FROM IF-MIB
     RowStatus,DisplayString                            FROM SNMPv2-TC   
     zxAn, ZxAnIfindex                                  FROM ZTE-AN-TC-MIB; 

  zxAnPwe3Mib MODULE-IDENTITY 
     LAST-UPDATED "200806301500Z"
     ORGANIZATION 
         "ZTE Corporation."
     CONTACT-INFO 
         "ZTE NMS dept.
                  Ma Jian       68897122" 

     DESCRIPTION 
         "This MIB contains managed object definitions for Pseudo 
         Wire operation." 
     ::= { zxAn 56 } 
     
     zxAnPwe3GlobalObjects  OBJECT IDENTIFIER ::= {zxAnPwe3Mib 1}          
     zxAnPwe3Objects        OBJECT IDENTIFIER ::= {zxAnPwe3Mib 2}

--------------------------------------------------------------------------------
-- Following objects are defined.
-- 1.zxAn PWE3 global mgmt objects
-- 2.zxAn PWE3 Bridge Port Atm Encapsulation Table
-- 3.zxAn PWE3 Port VCMapping Table
-- 4.zxAn PWE3 Pseudo Wires query Table
------------------------------------------------------------------------------     
--------------------------------------------------------------------------------

------------------------------------------------------------------------------
--  1.zxAn PWE3 global mgmt objects
------------------------------------------------------------------------------
    zxAnPwe3McptTimer1 OBJECT-TYPE
        SYNTAX      Integer32(10..4095)
        UNITS       "millisecond"        
        MAX-ACCESS  read-write
        STATUS      current
        DESCRIPTION
            "Mcpt timer 1,define the time threshold that the router uses to collect and 
             concatenate ATM cells in a single VCC cell relay-encapsulated packet and 
             transmit the packet on an MPLS pseudowire connection. 
             When the timer expires, the router forwards the packet even if the number of 
             concatenated ATM cells in the packet is fewer than the specified maximum number 
             of cells per packet. 
             "
        DEFVAL { 100 }
        ::= { zxAnPwe3GlobalObjects 1 }
        
    zxAnPwe3McptTimer2 OBJECT-TYPE
        SYNTAX      Integer32(10..4095)
        UNITS       "millisecond"        
        MAX-ACCESS  read-write
        STATUS      current
        DESCRIPTION
            "Mcpt timer 2."
        DEFVAL { 500 }
        ::= { zxAnPwe3GlobalObjects 2 }
        
    zxAnPwe3McptTimer3 OBJECT-TYPE
        SYNTAX      Integer32(10..4095)
        UNITS       "millisecond"        
        MAX-ACCESS  read-write
        STATUS      current
        DESCRIPTION
            "Mcpt timer 3."
        DEFVAL { 1000 }
        ::= { zxAnPwe3GlobalObjects 3 }              
          
--------------------------------------------------------------------------------
-- 2.zxAn PWE3 Bridge Port Atm Encapsulation Table
--------------------------------------------------------------------------------
    zxAnPwe3PortAtmEncapTable OBJECT-TYPE
        SYNTAX      SEQUENCE OF ZxAnPwe3PortAtmEncapEntry
        MAX-ACCESS  not-accessible
        STATUS      current
        DESCRIPTION 
            "This table includes the bridge port user-side encapsulation infomation."
        ::=  { zxAnPwe3Objects 1 }

    zxAnPwe3PortAtmEncapEntry OBJECT-TYPE
        SYNTAX      ZxAnPwe3PortAtmEncapEntry
        MAX-ACCESS  not-accessible
        STATUS      current
        DESCRIPTION 
            "An entry in zxAnPwe3PortAtmEncapTable."
        INDEX       {ifIndex, zxAnPwe3PvcId }
        ::=  { zxAnPwe3PortAtmEncapTable 1 }

    ZxAnPwe3PortAtmEncapEntry ::= SEQUENCE {
        zxAnPwe3PvcId                  Integer32,
        zxAnPwe3PortMaxCellsPerPacket  Integer32,
        zxAnPwe3PortMcptTimer          INTEGER,
        zxAnPwe3PortEncapsulationType  INTEGER
    }

    zxAnPwe3PvcId OBJECT-TYPE 
        SYNTAX      Integer32
        MAX-ACCESS  not-accessible
        STATUS      current
        DESCRIPTION     
            "pvc id in this interface."
        ::= { zxAnPwe3PortAtmEncapEntry 1 }
        
    zxAnPwe3PortMaxCellsPerPacket OBJECT-TYPE 
        SYNTAX      Integer32(0..28)
        MAX-ACCESS  read-write
        STATUS      current
        DESCRIPTION    
            "Maximum number of ATM cells that the router 
             can concatenate in a single VCC cell relay-encapsulated 
             packet and transmit on an MPLS pseudowire connection."
        DEFVAL { 0 }
        ::= { zxAnPwe3PortAtmEncapEntry  2 }

    zxAnPwe3PortMcptTimer OBJECT-TYPE 
        SYNTAX     INTEGER 
        {
            noUse(0),            
            zxAnPwe3McptTimer1(1),
            zxAnPwe3McptTimer2(2),
            zxAnPwe3McptTimer3(3)
        }        
        MAX-ACCESS read-write
        STATUS     current
        DESCRIPTION     
            "define the time threshold that the router uses to collect and 
            concatenate ATM cells in a single VCC cell relay-encapsulated packet and 
            transmit the packet on an MPLS pseudowire connection."
        DEFVAL { noUse }     
        ::=  { zxAnPwe3PortAtmEncapEntry 3 }
        
    zxAnPwe3PortEncapsulationType  OBJECT-TYPE
        SYNTAX     INTEGER 
        {
            encapUnknown(0),
            encapAtmAal01to1(1),
            encapAtmAal0nto1(2),
            encapAtmAal5pdu(3),
            encapEthAal5sdu(4)
        }
        MAX-ACCESS read-write
        STATUS     current
        DESCRIPTION
            "Encapsulation type of the VPWS configuration interface."
        DEFVAL { encapUnknown }
         ::= { zxAnPwe3PortAtmEncapEntry 4 }             
               
------------------------------------------------------------------------------
--  3.zxAn PWE3 Port VCMapping Table
------------------------------------------------------------------------------
    zxAnPwe3PortToVCMappingTable  OBJECT-TYPE
        SYNTAX      SEQUENCE OF ZxAnPwe3PortToVCMappingEntry
        MAX-ACCESS  not-accessible
        STATUS      current
        DESCRIPTION
            "Mpls xconnect table"
        ::= { zxAnPwe3Objects 2 }

    zxAnPwe3PortToVCMappingEntry  OBJECT-TYPE
        SYNTAX      ZxAnPwe3PortToVCMappingEntry
        MAX-ACCESS  not-accessible
        STATUS      current
        DESCRIPTION
            "An entry in zxAnPwe3PortToVCMappingTable."
        INDEX       { zxAnPwe3PortIndex, zxAnPwe3Vcid }
        ::= { zxAnPwe3PortToVCMappingTable 1 }

    ZxAnPwe3PortToVCMappingEntry ::= SEQUENCE {
        zxAnPwe3PortIndex              ZxAnIfindex,                                
        zxAnPwe3Vcid                   Unsigned32,              
        zxAnPwe3PeerAddress            IpAddress,      
        zxAnPwe3ControlWordEnable      INTEGER,
        zxAnPwe3SequenceEnable         INTEGER,
        zxAnPwe3PortVCMappingRowStatus RowStatus                
    }

    zxAnPwe3PortIndex  OBJECT-TYPE
        SYNTAX      ZxAnIfindex
        MAX-ACCESS  not-accessible
        STATUS      current
        DESCRIPTION
            "Index of a interface."
        ::= { zxAnPwe3PortToVCMappingEntry 1 }

    zxAnPwe3Vcid  OBJECT-TYPE
        SYNTAX      Unsigned32(1..4294967295)
        MAX-ACCESS  not-accessible
        STATUS      current
        DESCRIPTION
            "Vcid of the VPWS configured on this interface."
        ::= { zxAnPwe3PortToVCMappingEntry 2 }
         
    zxAnPwe3PeerAddress  OBJECT-TYPE
        SYNTAX      IpAddress
        MAX-ACCESS  read-create
        STATUS      current
        DESCRIPTION
            "Peer Address of VC affected."
         ::= { zxAnPwe3PortToVCMappingEntry 3 }        
         
    zxAnPwe3ControlWordEnable  OBJECT-TYPE
        SYNTAX      INTEGER
        {
            enable(1),
            disable(2)
        }
        MAX-ACCESS  read-create
        STATUS      current
        DESCRIPTION
            "enable(1): enable Control Word.
            disable(2): disable Control Word. "
        DEFVAL { disable }
        ::= { zxAnPwe3PortToVCMappingEntry 4 }
        
    zxAnPwe3SequenceEnable  OBJECT-TYPE
        SYNTAX      INTEGER
        {
            enable(1),
            disable(2)
        }
        MAX-ACCESS  read-create
        STATUS      current
        DESCRIPTION
            "enable(1):  enable Sequence.
            disable(2): disable Sequence. "
        DEFVAL { disable }
        ::= { zxAnPwe3PortToVCMappingEntry 5 }          
        
    zxAnPwe3PortVCMappingRowStatus    OBJECT-TYPE    
        SYNTAX        RowStatus
        MAX-ACCESS  read-create
        STATUS      current
        DESCRIPTION     
            "RowStatus of this table."
        ::= { zxAnPwe3PortToVCMappingEntry 50 }          

------------------------------------------------------------------------------
--  4.zxAn PWE3 Pseudo Wires query Table
------------------------------------------------------------------------------                                      
    zxAnPwe3PwTable OBJECT-TYPE
        SYNTAX      SEQUENCE OF ZxAnPwe3PwEntry
        MAX-ACCESS  not-accessible
        STATUS      current
        DESCRIPTION
            "PWE3 Pseudo Wires query table."
        ::= { zxAnPwe3Objects 4 }

    zxAnPwe3PwEntry  OBJECT-TYPE
        SYNTAX      ZxAnPwe3PwEntry
        MAX-ACCESS  not-accessible
        STATUS      current
        DESCRIPTION
            "Informatin of PWE3 Pseudo Wires configured on a PE."
        INDEX       { zxAnPwe3PwVcId }
        ::= { zxAnPwe3PwTable 1 }

    ZxAnPwe3PwEntry ::= SEQUENCE 
    {
        zxAnPwe3PwVcId                 Unsigned32,
        zxAnPwe3PwType                 INTEGER,
        zxAnPwe3PwEncapType            INTEGER,
        zxAnPwe3PwVlanid               Integer32,
        zxAnPwe3PwPsnType              INTEGER,
        zxAnPwe3PwTunnelid             Unsigned32,
        zxAnPwe3PwInlabel              Unsigned32,
        zxAnPwe3PwOutlabel             Unsigned32,
        zxAnPwe3PwCbit                 INTEGER,
        zxAnPwe3PwStatus               INTEGER,
        zxAnPwe3PwLocalGroupId         Unsigned32,
        zxAnPwe3PwLocalEncapType       INTEGER,
        zxAnPwe3PwLocalLabel           Unsigned32,
        zxAnPwe3PwLocalCbit            INTEGER,
        zxAnPwe3PwLocalPortName        DisplayString,
        zxAnPwe3PwLocalRouterId        IpAddress,
        zxAnPwe3PwLocalIfMtu           Unsigned32,
        zxAnPwe3PwRemoteGroupId        Unsigned32,
        zxAnPwe3PwRemoteEncapType      INTEGER,
        zxAnPwe3PwRemoteLabel          Unsigned32,
        zxAnPwe3PwRemoteCbit           INTEGER,
        zxAnPwe3PwRemotePortName       DisplayString,
        zxAnPwe3PwRemoteRouterId       IpAddress,
        zxAnPwe3PwRemoteIfMtu          Unsigned32
    }

    zxAnPwe3PwVcId  OBJECT-TYPE
        SYNTAX      Unsigned32 (1..4294967295)
        MAX-ACCESS  not-accessible
        STATUS      current
        DESCRIPTION
            "VcId of that PW belongs to.It can't be zero."
        ::= { zxAnPwe3PwEntry 1 }

    zxAnPwe3PwType OBJECT-TYPE
        SYNTAX      INTEGER 
        {
            pwUnknown(0),
            pwSpoke(1),
            pwHub(2)
        }
        MAX-ACCESS  read-only
        STATUS      current
        DESCRIPTION
            "Type of PW:hub or spoke,used in H-VPLS."
        ::= { zxAnPwe3PwEntry 2 }

    zxAnPwe3PwEncapType OBJECT-TYPE
        SYNTAX      INTEGER 
        {
            encapUnknown(0),
            encapFrDlci(1),
            encapAtmAal5(2),
            encapAtmTranscell(3),
            encapEthVlan(4),
            encapEth(5),
            encapHdlc(6),
            encapPpp(7),
            encapCem(8),
            encapAtmVcc(9),
            encapAtmVpc(10)
        }
        MAX-ACCESS  read-only
        STATUS      current
        DESCRIPTION
            "PW encapsulation type."
        ::= { zxAnPwe3PwEntry 3 }

    zxAnPwe3PwVlanid OBJECT-TYPE
        SYNTAX      Integer32
        MAX-ACCESS  read-only
        STATUS      current
        DESCRIPTION
            "if zxAnPwe3PWEncapType is eth-vlan type,this value represents
            vlan id encapsulated for L2vpn interface.It will be zero otherwise."
        ::= { zxAnPwe3PwEntry 4 }

    zxAnPwe3PwPsnType OBJECT-TYPE
        SYNTAX      INTEGER 
        {
            unknownTunnel(0),
            mplsTunnel(1),
            teTunnel(2)
        }
        MAX-ACCESS  read-only
        STATUS      current
        DESCRIPTION
            "Type of external tunnel for this PW to be carried on."
        ::= { zxAnPwe3PwEntry 5 }

    zxAnPwe3PwTunnelid OBJECT-TYPE
        SYNTAX      Unsigned32
        MAX-ACCESS  read-only
        STATUS      current
        DESCRIPTION
            "If zxAnPwe3PWPsnType is TE tunnel,this value represents Id of TE tunnel
            for this PW to be carried on. It will be zero otherwise."
        ::= { zxAnPwe3PwEntry 6 }

    zxAnPwe3PwInlabel OBJECT-TYPE
        SYNTAX      Unsigned32(16..1048575)
        MAX-ACCESS  read-only
        STATUS      current
        DESCRIPTION
            "The PW internal label used in the inbound direction,ie label locally allocated.
            If the label is not yet known,the object should return a value of 0xFFFFFFFF."
         ::= { zxAnPwe3PwEntry 7 }

    zxAnPwe3PwOutlabel OBJECT-TYPE
        SYNTAX      Unsigned32(16..1048575)
        MAX-ACCESS  read-only
        STATUS      current
        DESCRIPTION
            "The PW internal label used in the outbound direction,ie label allocated by remote
            peer.If the label is not yet known,the object should return a value of 0xFFFFFFFF."
        ::= { zxAnPwe3PwEntry 8 }

    zxAnPwe3PwCbit OBJECT-TYPE
        SYNTAX      INTEGER 
        {
            cwordDisable(0),
            cwordEnable(1)
        }
        MAX-ACCESS  read-only
        STATUS      current
        DESCRIPTION
            "Defines if the control word will be sent with each packet by the local node."
        ::= { zxAnPwe3PwEntry 9 }

    zxAnPwe3PwStatus OBJECT-TYPE
        SYNTAX      INTEGER 
        {
            notEstablished(0),
            established(1)
        }
        MAX-ACCESS  read-only
        STATUS      current
        DESCRIPTION
            "If PW has finished negotiation with remote peer including internal label and
            other parameters,then PW will be in established status."
        ::= { zxAnPwe3PwEntry 10 }

    zxAnPwe3PwLocalGroupId  OBJECT-TYPE
        SYNTAX      Unsigned32
        MAX-ACCESS  read-only
        STATUS      current
        DESCRIPTION
            "Used in the Group ID field sent to peer within the maintenance protocol used
            for PW setup."
        ::= { zxAnPwe3PwEntry 11 }

    zxAnPwe3PwLocalEncapType OBJECT-TYPE
        SYNTAX      INTEGER 
        {
            encapUnknown(0),
            encapFrDlci(1),
            encapAtmAal5(2),
            encapAtmTranscell(3),
            encapEthVlan(4),
            encapEth(5),
            encapHdlc(6),
            encapPpp(7),
            encapCem(8),
            encapAtmVcc(9),
            encapAtmVpc(10)
        }
        MAX-ACCESS  read-only
        STATUS      current
        DESCRIPTION
            "Local PW  encapsulation type."
        ::= { zxAnPwe3PwEntry 12 }

    zxAnPwe3PwLocalLabel OBJECT-TYPE
        SYNTAX      Unsigned32(16..1048575)
        MAX-ACCESS  read-only
        STATUS      current
        DESCRIPTION
            "PW internal label locally allocated.If the label is not yet known,
            the object should return a value of 0xFFFFFFFF. "
        ::= { zxAnPwe3PwEntry 13 }

    zxAnPwe3PwLocalCbit OBJECT-TYPE
        SYNTAX      INTEGER 
        {
            cwordDisable(0),
            cwordEnable(1)
        }
        MAX-ACCESS  read-only
        STATUS      current
        DESCRIPTION
            "Local configuration of the control word."
        ::= { zxAnPwe3PwEntry 14 }

    zxAnPwe3PwLocalPortName OBJECT-TYPE
        SYNTAX      DisplayString(SIZE(0..32))
        MAX-ACCESS  read-only
        STATUS      current
        DESCRIPTION
            "Name of local interface that PW has been configured on."
        ::= { zxAnPwe3PwEntry 15 }

    zxAnPwe3PwLocalRouterId OBJECT-TYPE
        SYNTAX      IpAddress
        MAX-ACCESS  read-only
        STATUS      current
        DESCRIPTION
            "Router ID of local PE."
        ::= { zxAnPwe3PwEntry 16 }

    zxAnPwe3PwLocalIfMtu OBJECT-TYPE
        SYNTAX      Unsigned32(0..65535)
        MAX-ACCESS  read-only
        STATUS      current
        DESCRIPTION
            "Locally supported MTU size over the interface associated with the PW."
        ::= { zxAnPwe3PwEntry 17 }

    zxAnPwe3PwRemoteGroupId  OBJECT-TYPE
        SYNTAX      Unsigned32
        MAX-ACCESS  read-only
        STATUS      current
        DESCRIPTION
            "Obtained from the Group ID field as received via the signaling protocol
            used for PW setup."
        ::= { zxAnPwe3PwEntry 18 }

    zxAnPwe3PwRemoteEncapType OBJECT-TYPE
        SYNTAX      INTEGER 
        {
            encapUnknown(0),
            encapFrDlci(1),
            encapAtmAal5(2),
            encapAtmTranscell(3),
            encapEthVlan(4),
            encapEth(5),
            encapHdlc(6),
            encapPpp(7),
            encapCem(8),
            encapAtmVcc(9),
            encapAtmVpc(10)
        }
        MAX-ACCESS  read-only
        STATUS      current
        DESCRIPTION
            "Remote PW  encapsulation type."
        ::= { zxAnPwe3PwEntry 19 }

    zxAnPwe3PwRemoteLabel OBJECT-TYPE
        SYNTAX      Unsigned32
        MAX-ACCESS  read-only
        STATUS      current
        DESCRIPTION
            "PW internal label allocated by remote peer.If the label is not yet known,
            the object should return a value of 0xFFFFFFFF. "
        ::= { zxAnPwe3PwEntry 20 }

    zxAnPwe3PwRemoteCbit OBJECT-TYPE
        SYNTAX       INTEGER 
        {
            cwordDisable(0),
            cwordEnable(1)
        }
        MAX-ACCESS  read-only
        STATUS      current
        DESCRIPTION
            "Remote configuration of the control word."
        ::= { zxAnPwe3PwEntry 21 }

    zxAnPwe3PwRemotePortName OBJECT-TYPE
        SYNTAX      DisplayString(SIZE(0..32))
        MAX-ACCESS  read-only
        STATUS      current
        DESCRIPTION
            "Name of remote interface that PW has been configured on."
        ::= { zxAnPwe3PwEntry 22 }

    zxAnPwe3PwRemoteRouterId OBJECT-TYPE
        SYNTAX      IpAddress
        MAX-ACCESS  read-only
        STATUS      current
        DESCRIPTION
            "Router ID of remote PE."
        ::= { zxAnPwe3PwEntry 23 }

    zxAnPwe3PwRemoteIfMtu OBJECT-TYPE
        SYNTAX      Unsigned32
        MAX-ACCESS  read-only
        STATUS      current
        DESCRIPTION
            "Supported MTU size of remote peer over the interface associated with the PW."
        ::= { zxAnPwe3PwEntry 24 }                                      
END

--------------------------------------------------------------------------
-- File Name : ZTE-AN-SIP-MIB.mib
-- Date      : 2009-07-15
-- Author    : ZTE Nms dept.

--
-- Zte SIP Mib for Access Node
-- 
--------------------------------------------------------------------------

ZTE-AN-SIP-MIB DEFINITIONS ::= BEGIN

    IMPORTS
        MODULE-IDENTITY,NOTIFICATION-TYPE,OBJECT-TYPE,Counter32,
        Integer32,Counter64,Unsigned32,Gauge32,IpAddress,enterprises
                                                                FROM SNMPv2-SMI
        TEXTUAL-CONVENTION,RowStatus,DisplayString,TruthValue   FROM SNMPv2-TC
        InetAddress,InetAddressType    FROM INET-ADDRESS-MIB;

    zxAnSipMib MODULE-IDENTITY
        LAST-UPDATED    "0608140000Z"  -- july. 23, 2005
        ORGANIZATION    "zte Telcom Co. Ltd."
        CONTACT-INFO    "E-mail: shen.yuyang@zte.com.cn,
                         E-mail: suchunshan@zte.com.cn"
        DESCRIPTION     "This MIB defines SIP management objects for Access Node."

    ::= { zxAn 5200 }
    
    zte OBJECT IDENTIFIER ::= { enterprises 3902 }
    zxAn OBJECT IDENTIFIER ::= { zte 1015 }
    zxAnVoiceMgmt OBJECT IDENTIFIER ::= { zxAnSipMib 3 }
    zxAnSipConfig OBJECT IDENTIFIER ::= { zxAnVoiceMgmt 8 }
    zxAnSipTrap  OBJECT IDENTIFIER  ::= { zxAnVoiceMgmt  100}  

--------------------------------------------------------------------------------
-- Following objects are defined.
-- 1.SIP User Table
-- 2.SIP Access Code Table
-- 3.SIP Service Code Table
-- 4.SIP Generate Format Table
-- 5.SIP Capability Table
-- 6.SIP Global Objects
-- 7.SIP Proxy Server Table
-- 8.SIP User Agent Table
-- 20.SIP Group Table
-- 22.SIP ISDN DLink Table
-- 22.SIP ISDN User Table
-- 23.SIP ISDN Phone Number Table
-- 24.SIP ISDN PBX B Channel Table
-- 50.SIP Performance Table
-- 51.zxAnSipHisPerfObjects

-- SIP Trap
--------------------------------------------------------------------------------

--------------------------------------------------------------------------------
-- 1.SIP User Table
--------------------------------------------------------------------------------

    zxMsagSipUserTable OBJECT-TYPE
        SYNTAX   SEQUENCE OF ZxMsagSipUserEntry
        MAX-ACCESS   not-accessible
        STATUS   current
        DESCRIPTION  "Sip user table"
        ::={zxAnSipConfig 1}
    
    zxMsagSipUserEntry OBJECT-TYPE
        SYNTAX    ZxMsagSipUserEntry
        MAX-ACCESS   not-accessible
        STATUS   current
        DESCRIPTION  "Sip user entry"
        INDEX {zxMsagSipUserRack, zxMsagSipUserShelf,
            zxMsagSipUserSlot, zxMsagSipUserIndex}
        ::={zxMsagSipUserTable 1}
   
    ZxMsagSipUserEntry ::=
        SEQUENCE{
            zxMsagSipUserRack              INTEGER,
            zxMsagSipUserShelf             INTEGER, 
            zxMsagSipUserSlot              INTEGER,     
            zxMsagSipUserIndex             INTEGER, 
            zxMsagSipUserOperNum           INTEGER,
            zxMsagSipUserSipDigit          DisplayString,
            zxMsagSipUserAuthusername      DisplayString,
            zxMsagSipUserId                DisplayString,   
            zxMsagSipUserType              INTEGER,
            zxMsagSipUserBeginNo           INTEGER,
            zxMsagSipUserDigitLen          INTEGER,   
            zxMsagSipUserPassword          DisplayString,     
            zxMsagSipUserDstngRing         INTEGER,
            zxMsagSipUserHotlineType       INTEGER,
            zxMsagSipUserHotlineNum        DisplayString,   
            zxMsagSipUserDigitMap          DisplayString,   
            zxMsagSipUserOperType          INTEGER, 
            zxMsagSipUserGroupId           INTEGER,
            zxMsagSipUserAdminStatus       INTEGER,
            zxMsagSipUserSessionLimit      TruthValue,
            zxMsagSipUserRegisterStatus    INTEGER,
            zxMsagSipUserRowStatus         RowStatus
        }
    
    zxMsagSipUserRack  OBJECT-TYPE
        SYNTAX       INTEGER(1..3)
        MAX-ACCESS   not-accessible
        STATUS   current
        DESCRIPTION  "Rack of sip user"
        DEFVAL{1}
        ::={zxMsagSipUserEntry 1}
       
    zxMsagSipUserShelf  OBJECT-TYPE
        SYNTAX       INTEGER(1..5)
        MAX-ACCESS  not-accessible
        STATUS   current
        DESCRIPTION  "Shelf of sip user"
        DEFVAL{1}
        ::={zxMsagSipUserEntry 2}
    
    zxMsagSipUserSlot  OBJECT-TYPE
        SYNTAX       INTEGER(1..23)
        MAX-ACCESS   not-accessible
        STATUS   current
        DESCRIPTION  "Slot of sip user"
        DEFVAL{3}
        ::={zxMsagSipUserEntry 3}
    
    zxMsagSipUserIndex  OBJECT-TYPE
        SYNTAX       INTEGER(1..64)
        MAX-ACCESS  not-accessible
        STATUS   current
        DESCRIPTION  "Index of sip user"
        DEFVAL{1}
        ::={zxMsagSipUserEntry 4}

    zxMsagSipUserOperNum  OBJECT-TYPE
        SYNTAX       INTEGER(1..64)
        MAX-ACCESS  read-create
        STATUS   current
        DESCRIPTION  "Sip user operaton number"
        DEFVAL{32}
        ::={zxMsagSipUserEntry 5}
    
    zxMsagSipUserSipDigit  OBJECT-TYPE
        SYNTAX       DisplayString(SIZE(1..32))
        MAX-ACCESS  read-create
        STATUS   current
        DESCRIPTION  "Sip user digit"
        ::={zxMsagSipUserEntry 6}
    
    zxMsagSipUserAuthusername  OBJECT-TYPE
        SYNTAX   DisplayString(SIZE(0..64))
        MAX-ACCESS  read-create
        STATUS   current
        DESCRIPTION  "Sip user name"
        ::={zxMsagSipUserEntry 7}
    
    zxMsagSipUserId   OBJECT-TYPE
        SYNTAX   DisplayString(SIZE(1..64))
        MAX-ACCESS  read-create
        STATUS   current
        DESCRIPTION  "Sip user id"
        ::={zxMsagSipUserEntry 8}
    
    zxMsagSipUserType  OBJECT-TYPE
        SYNTAX      INTEGER{type1(1),type2(2),type3(3)}
        MAX-ACCESS  read-create
        STATUS   current
        DESCRIPTION  "   Type 1:USER00100100000-USER00100100031,
        type 2:USER0-USER31
        type 3:User000-USER031"
        DEFVAL{1}
        ::={zxMsagSipUserEntry 9}
    
    zxMsagSipUserBeginNo   OBJECT-TYPE
        SYNTAX       INTEGER(0..65535)
        MAX-ACCESS  read-create
        STATUS   current
        DESCRIPTION  "Sip user begin no"
        DEFVAL{0}
        ::={zxMsagSipUserEntry 10}
    
    zxMsagSipUserDigitLen  OBJECT-TYPE
        SYNTAX       INTEGER(0..64)
        MAX-ACCESS  read-create
        STATUS   current
        DESCRIPTION  "Sip user digit length"
        DEFVAL{3}
        ::={zxMsagSipUserEntry 11}
    
    zxMsagSipUserPassword  OBJECT-TYPE
        SYNTAX       DisplayString(SIZE(0..16))
        MAX-ACCESS  read-create
        STATUS   current
        DESCRIPTION  "User password"
        ::={zxMsagSipUserEntry 12}
    
    zxMsagSipUserDstngRing  OBJECT-TYPE
        SYNTAX       INTEGER(0..15)
        MAX-ACCESS  read-create
        STATUS   current
        DESCRIPTION  "Ring type"
        DEFVAL{15}
        ::={zxMsagSipUserEntry 13}
    
    zxMsagSipUserHotlineType  OBJECT-TYPE
        SYNTAX       INTEGER{
                      noneHotline(1),
                      instantHotline(2),
                      delayHotline(3)
                      }
        MAX-ACCESS  read-create
        STATUS   current
        DESCRIPTION  "Hotline type"
        DEFVAL{1}    
        ::={zxMsagSipUserEntry 14}
    
    zxMsagSipUserHotlineNum  OBJECT-TYPE
        SYNTAX       DisplayString(SIZE(0..16))
        MAX-ACCESS  read-create
        STATUS   current
        DESCRIPTION  "Hotline number"
        ::={zxMsagSipUserEntry 15}
    
    zxMsagSipUserDigitMap  OBJECT-TYPE
        SYNTAX       DisplayString(SIZE(0..20))
        MAX-ACCESS  read-create
        STATUS   current
        DESCRIPTION  "Digital map name"
        ::={zxMsagSipUserEntry 16}
    
    zxMsagSipUserOperType  OBJECT-TYPE
        SYNTAX      INTEGER{sipuser(1),sipuserid(2)}
        MAX-ACCESS  read-create
        STATUS   current
        DESCRIPTION  "Operation type"
        ::={zxMsagSipUserEntry 17}  

    zxMsagSipUserGroupId  OBJECT-TYPE
        SYNTAX       INTEGER(1..500)
        MAX-ACCESS  read-create
        STATUS   current
        DESCRIPTION  "Sip user group id"        
        ::={zxMsagSipUserEntry 18}
        
    zxMsagSipUserAdminStatus OBJECT-TYPE
        SYNTAX      INTEGER {
            enable(1),
            disable(2)
            }
        MAX-ACCESS  read-create
        STATUS      current
        DESCRIPTION
            "The administrative status of the sip user."
        DEFVAL { enable }        
        ::={zxMsagSipUserEntry 19}  

    zxMsagSipUserSessionLimit    OBJECT-TYPE
        SYNTAX      TruthValue
        MAX-ACCESS  read-create
        STATUS      current
        DESCRIPTION 
            "Session limit.
             Whether one user only has one session at the same time or not."
        DEFVAL { false }
        ::={zxMsagSipUserEntry 20}     
  
    zxMsagSipUserRegisterStatus OBJECT-TYPE
        SYNTAX      INTEGER {
            success(1),
            failed(2)
            }
        MAX-ACCESS  read-only
        STATUS      current
        DESCRIPTION
            "The registered status of the SIP user."
        DEFVAL { failed }        
        ::={zxMsagSipUserEntry 21} 
        
    zxMsagSipUserRowStatus  OBJECT-TYPE
        SYNTAX       RowStatus
        MAX-ACCESS  read-create
        STATUS   current
        DESCRIPTION  "Row status"
        ::={zxMsagSipUserEntry 50}

--------------------------------------------------------------------------------
-- 2.SIP Access Code Table
--------------------------------------------------------------------------------
    
    zxMsagSipAccessCodeTable OBJECT-TYPE
        SYNTAX  SEQUENCE OF ZxMsagSipAccessCodeEntry
        MAX-ACCESS  not-accessible
        STATUS      current
        DESCRIPTION "Sip access code table"
        ::={zxAnSipConfig 2}
   
    zxMsagSipAccessCodeEntry OBJECT-TYPE
        SYNTAX    ZxMsagSipAccessCodeEntry
        MAX-ACCESS  not-accessible
        STATUS      current
        DESCRIPTION "Sip access code table"
        INDEX {zxMsagSipAccessCodeMgId, zxMsagSipAccessCodeId}
        ::={zxMsagSipAccessCodeTable 1}
    
    ZxMsagSipAccessCodeEntry ::=
        SEQUENCE{
            zxMsagSipAccessCodeMgId           INTEGER,
            zxMsagSipAccessCodeId             INTEGER, 
            zxMsagSipAccessCodecode           DisplayString,     
            zxMsagSipAccessCodeRowStatus      RowStatus
        }
    
    zxMsagSipAccessCodeMgId  OBJECT-TYPE
        SYNTAX  INTEGER(1)
        MAX-ACCESS  not-accessible
        STATUS      current
        DESCRIPTION "MG ID"
        DEFVAL{1}
        ::={zxMsagSipAccessCodeEntry 1}
       
    zxMsagSipAccessCodeId  OBJECT-TYPE
        SYNTAX  INTEGER(0..14)
        MAX-ACCESS  not-accessible
        STATUS      current
        DESCRIPTION "Sip access code id"        
        ::={zxMsagSipAccessCodeEntry 2}
    
    zxMsagSipAccessCodecode  OBJECT-TYPE
        SYNTAX  DisplayString(SIZE(1..6))
        MAX-ACCESS  read-create
        STATUS      current
        DESCRIPTION "Sip access code"
        ::={zxMsagSipAccessCodeEntry 3}
    
    zxMsagSipAccessCodeRowStatus  OBJECT-TYPE
        SYNTAX  RowStatus
        MAX-ACCESS  read-create
        STATUS      current
        DESCRIPTION "Sip access code row status"
        ::={zxMsagSipAccessCodeEntry 20}
    
--------------------------------------------------------------------------------
-- 3.SIP Service Code Table
--------------------------------------------------------------------------------    
    
    zxMsagSipServiceCodeTable OBJECT-TYPE
        SYNTAX  SEQUENCE OF ZxMsagSipServiceCodeEntry
        MAX-ACCESS  not-accessible
        STATUS      current
        DESCRIPTION "Sip Service code table"
        ::={zxAnSipConfig 3}
    
    zxMsagSipServiceCodeEntry OBJECT-TYPE
        SYNTAX    ZxMsagSipServiceCodeEntry
        MAX-ACCESS  not-accessible
        STATUS      current
        DESCRIPTION "Sip Service code table entry"
        INDEX {zxMsagSipServiceCodeMgId, zxMsagSipServiceCodeType}
        ::={zxMsagSipServiceCodeTable 1}
    
    ZxMsagSipServiceCodeEntry ::=
        SEQUENCE{
            zxMsagSipServiceCodeMgId           INTEGER,
            zxMsagSipServiceCodeType           INTEGER, 
            zxMsagSipServiceCode               DisplayString,     
            zxMsagSipServiceCodeRowStatus      RowStatus
        }
    
    zxMsagSipServiceCodeMgId  OBJECT-TYPE
        SYNTAX  INTEGER(1)
        MAX-ACCESS  not-accessible
        STATUS      current
        DESCRIPTION "MG ID"
        DEFVAL{1}
        ::={zxMsagSipServiceCodeEntry 1}
       
    zxMsagSipServiceCodeType   OBJECT-TYPE
        SYNTAX  INTEGER{conference(1),threeWayConference(2),refere(3)}
        MAX-ACCESS  not-accessible
        STATUS      current
        DESCRIPTION "Sip service code type"             
        ::={zxMsagSipServiceCodeEntry 2}
    
    zxMsagSipServiceCode  OBJECT-TYPE
        SYNTAX  DisplayString(SIZE(1..64))
        MAX-ACCESS  read-create
        STATUS      current
        DESCRIPTION "Sip service code"
        ::={zxMsagSipServiceCodeEntry 3}
    
    zxMsagSipServiceCodeRowStatus  OBJECT-TYPE
        SYNTAX  RowStatus
        MAX-ACCESS  read-create
        STATUS      current
        DESCRIPTION "Sip service code row status"
        ::={zxMsagSipServiceCodeEntry 20}
    
--------------------------------------------------------------------------------
-- 4.SIP Generate Format Table
--------------------------------------------------------------------------------    
    
    zxMsagSipGenFmtTable OBJECT-TYPE
        SYNTAX  SEQUENCE OF ZxMsagSipGenFmtEntry
        MAX-ACCESS  not-accessible
        STATUS      current
        DESCRIPTION "Sip generate format table"
        ::={zxAnSipConfig 4}
    
    zxMsagSipGenFmtEntry OBJECT-TYPE
        SYNTAX    ZxMsagSipGenFmtEntry
        MAX-ACCESS  not-accessible
        STATUS      current
        DESCRIPTION "Sip generate format table entry"
        INDEX {zxMsagSipGenFmtMgId, zxMsagSipGenFmtField}
        ::={zxMsagSipGenFmtTable 1}
    
    ZxMsagSipGenFmtEntry ::=
        SEQUENCE{
            zxMsagSipGenFmtMgId      INTEGER,
            zxMsagSipGenFmtField     INTEGER, 
            zxMsagSipGenFmtValue     INTEGER    
        }
    
    zxMsagSipGenFmtMgId  OBJECT-TYPE
        SYNTAX  INTEGER(1)
        MAX-ACCESS  not-accessible
        STATUS      current
        DESCRIPTION "MG ID"
        DEFVAL{1}
        ::={zxMsagSipGenFmtEntry 1}
       
    zxMsagSipGenFmtField   OBJECT-TYPE
        SYNTAX  INTEGER{from(1),to(2),requireline(3)}
        MAX-ACCESS  not-accessible
        STATUS      current
        DESCRIPTION "Sip generate format field"        
        ::={zxMsagSipGenFmtEntry 2}
    
    zxMsagSipGenFmtValue  OBJECT-TYPE
        SYNTAX  INTEGER{sipuserid(1),telephone(2)}
        MAX-ACCESS  read-create
        STATUS      current
        DESCRIPTION "Sip generate format value"
        DEFVAL{1}
        ::={zxMsagSipGenFmtEntry 3}
    
--------------------------------------------------------------------------------
-- 5.SIP Capability Table
--------------------------------------------------------------------------------    

    zxMsagSipCapTable OBJECT-TYPE
        SYNTAX  SEQUENCE OF ZxMsagSipCapEntry
        MAX-ACCESS  not-accessible
        STATUS      current
        DESCRIPTION "Sip capability table"
        ::={zxAnSipConfig 5}
    
    zxMsagSipCapEntry OBJECT-TYPE
        SYNTAX    ZxMsagSipCapEntry
        MAX-ACCESS  not-accessible
        STATUS      current
        DESCRIPTION "Sip capability table entry"
        INDEX {zxMsagSipCapMgId}
        ::={zxMsagSipCapTable 1}
    
    ZxMsagSipCapEntry ::=
        SEQUENCE{
            zxMsagSipCapMgId                   INTEGER,
            zxMsagSipCapSpPrecondition         TruthValue,
            zxMsagSipCapNeedReserveRes         TruthValue,
            zxMsagSipCapSpEarlySession         TruthValue,
            zxMsagSipCapSp100Rel               TruthValue,
            zxMsagSipCapSpPath                 TruthValue,
            zxMsagSipCapSpReplaces             TruthValue,
            zxMsagSipCapSpTimer                TruthValue,
            zxMsagSipCapAudioCodePri1          INTEGER,
            zxMsagSipCapAudioCodePri2          INTEGER,
            zxMsagSipCapAudioCodePri3          INTEGER,
            zxMsagSipCapAudioCodePri4          INTEGER,
            zxMsagSipCapAudioCodePri5          INTEGER,
            zxMsagSipCapAudioCodePri6          INTEGER,
            zxMsagSipCapAudioCodePri7          INTEGER,
            zxMsagSipCapDtmfRelayPri1          INTEGER,
            zxMsagSipCapDtmfRelayPri2          INTEGER,
            zxMsagSipCapFaxPri1                INTEGER,
            zxMsagSipCapFaxPri2                INTEGER,
            zxMsagSipCapSpFaxModem             TruthValue,
            zxMsagSipCapSessionMaxExpire       INTEGER,
            zxMsagSipCapSessionMinExpire       INTEGER,
            zxMsagSipCapSessionRefresher       INTEGER,
            zxMsagSipCapDisplayFrom            INTEGER,
            zxMsagSipCapRegisterExpire         INTEGER,
            zxMsagSipCapReqMsgAuth             TruthValue,
            zxMsagSipCapPPreService            TruthValue,
            zxMsagSipCapAuthWithDomain         TruthValue,
            zxMsagSipCapPackageInterval        INTEGER,
            zxMsagSipCapSessionLimit           TruthValue,
            zxMsagSipCapUserParam              INTEGER,
            zxMsagSipCapDtmfSendingType        INTEGER,
            zxMsagSipCapEarlyMedia             TruthValue,
            zxMsagSipCapEchoCancel             TruthValue,
            zxMsagSipCapHistoryInfo            TruthValue,
            zxMsagSipCapThreePartySvrCode      DisplayString,
            zxMsagSipCapUserRegisterType       INTEGER,
            zxMsagSipCapHeartbeatEnable        INTEGER,
            zxMsagSipCapHeartbeatInterval      INTEGER,
            
            zxMsagSipCapSelfswitch             INTEGER,
            zxMsagSipCapCallProtection         INTEGER,
            zxAnSipCapVideoMediaNegotiation    TruthValue,
            
            zxAnSipCapUserPhoneAppendEnable    INTEGER,
            zxAnSipCapSendSubscribeMsgEnable   INTEGER,
            zxAnSipCapFaxCodePri1              INTEGER,
            zxAnSipCapFaxCodePri2              INTEGER,
            zxAnSipCapFaxCodePri3              INTEGER,
            zxAnSipCapFaxCodePri4              INTEGER,
            zxAnSipCapFaxPacketInterval        Integer32,
            zxAnSipCapAutoRefreshEnable        INTEGER,
            zxAnSipCapImsHotlineValidTime      Integer32,
            zxAnSipCapDnsRequestInterval       Integer32,
            
            zxAnSipCapCallWaitInvite18xRsp     Integer32,
            zxAnSipCapSubscribeUaProfileEn     INTEGER,
            zxAnSipCapSubscribeMsgSummaryEn    INTEGER,
            zxAnSipCapCallerControlEnable      INTEGER,
            zxAnSipCapNoDialSendInviteEnable   INTEGER,
            zxAnSipCapProxySvrAutoDrEnable     INTEGER,
            zxAnSipCapProxySvrDrMode           INTEGER
        }
    
    zxMsagSipCapMgId  OBJECT-TYPE
        SYNTAX  INTEGER(1)
        MAX-ACCESS  not-accessible
        STATUS      current
        DESCRIPTION "MG ID"
        DEFVAL{1}
        ::={zxMsagSipCapEntry 1}
       
    zxMsagSipCapSpPrecondition  OBJECT-TYPE
        SYNTAX  TruthValue
        MAX-ACCESS  read-write
        STATUS      current
        DESCRIPTION "Support precondition"
        DEFVAL{2}
        ::={zxMsagSipCapEntry 2}
    
    zxMsagSipCapNeedReserveRes   OBJECT-TYPE
        SYNTAX  TruthValue
        MAX-ACCESS  read-write
        STATUS      current
        DESCRIPTION "Need reserve resource"
        DEFVAL{2}
        ::={zxMsagSipCapEntry 3}
    
    zxMsagSipCapSpEarlySession   OBJECT-TYPE
        SYNTAX  TruthValue
        MAX-ACCESS  read-write
        STATUS      current
        DESCRIPTION "Support early-session"
        DEFVAL{2}
        ::={zxMsagSipCapEntry 4}
    
    zxMsagSipCapSp100Rel   OBJECT-TYPE
        SYNTAX  TruthValue
        MAX-ACCESS  read-write
        STATUS      current
        DESCRIPTION "Support 100rel"
        DEFVAL{2}
        ::={zxMsagSipCapEntry 5}
    
    zxMsagSipCapSpPath   OBJECT-TYPE
        SYNTAX  TruthValue
        MAX-ACCESS  read-write
        STATUS      current
        DESCRIPTION "Support path"
        DEFVAL{2}
        ::={zxMsagSipCapEntry 6}
    
    zxMsagSipCapSpReplaces   OBJECT-TYPE
        SYNTAX  TruthValue
        MAX-ACCESS  read-write
        STATUS      current
        DESCRIPTION "Support replaces"
        DEFVAL{1}
        ::={zxMsagSipCapEntry 7}
    
    zxMsagSipCapSpTimer   OBJECT-TYPE
        SYNTAX  TruthValue
        MAX-ACCESS  read-write
        STATUS      current
        DESCRIPTION "Support timer"
        DEFVAL{1}
        ::={zxMsagSipCapEntry 8}
    
    zxMsagSipCapAudioCodePri1   OBJECT-TYPE
        SYNTAX  INTEGER
            {
                pcma(1),
                pcmu(2),
                g722(3),
                g723(4),
                g726(5),
                g728(6),
                g729(7),
                unconfig(255)
            }
        MAX-ACCESS  read-write
        STATUS      current
        DESCRIPTION "Audio code priority 1"
        DEFVAL{1}
        ::={zxMsagSipCapEntry 9}
    
   zxMsagSipCapAudioCodePri2   OBJECT-TYPE
        SYNTAX  INTEGER
            {
                pcma(1),
                pcmu(2),
                g722(3),
                g723(4),
                g726(5),
                g728(6),
                g729(7),
                unconfig(255)
            }
        MAX-ACCESS  read-write
        STATUS      current
        DESCRIPTION "Audio code priority 2"
        DEFVAL{2}
        ::={zxMsagSipCapEntry 10}
    
    zxMsagSipCapAudioCodePri3   OBJECT-TYPE
        SYNTAX  INTEGER
            {
                pcma(1),
                pcmu(2),
                g722(3),
                g723(4),
                g726(5),
                g728(6),
                g729(7),
                unconfig(255)
            }
        MAX-ACCESS  read-write
        STATUS      current
        DESCRIPTION "Audio code priority 3"
        DEFVAL{255}
        ::={zxMsagSipCapEntry 11}
    
    zxMsagSipCapAudioCodePri4   OBJECT-TYPE
        SYNTAX  INTEGER
            {
                pcma(1),
                pcmu(2),
                g722(3),
                g723(4),
                g726(5),
                g728(6),
                g729(7),
                unconfig(255)
            }
        MAX-ACCESS  read-write
        STATUS      current
        DESCRIPTION "Audio code priority 4"
        DEFVAL{255}
        ::={zxMsagSipCapEntry 12}
    
    zxMsagSipCapAudioCodePri5   OBJECT-TYPE
        SYNTAX  INTEGER
            {
                pcma(1),
                pcmu(2),
                g722(3),
                g723(4),
                g726(5),
                g728(6),
                g729(7),
                unconfig(255)
            }
        MAX-ACCESS  read-write
        STATUS      current
        DESCRIPTION "Audio code priority 5"
        DEFVAL{255}
        ::={zxMsagSipCapEntry 13}
    
    zxMsagSipCapAudioCodePri6   OBJECT-TYPE
        SYNTAX  INTEGER
            {
                pcma(1),
                pcmu(2),
                g722(3),
                g723(4),
                g726(5),
                g728(6),
                g729(7),
                unconfig(255)
            }
        MAX-ACCESS  read-write
        STATUS      current
        DESCRIPTION "Audio code priority 6"
        DEFVAL{255}
        ::={zxMsagSipCapEntry 14}
    
    zxMsagSipCapAudioCodePri7   OBJECT-TYPE
        SYNTAX  INTEGER
            {
                pcma(1),
                pcmu(2),
                g722(3),
                g723(4),
                g726(5),
                g728(6),
                g729(7),
                unconfig(255)
            }
        MAX-ACCESS  read-write
        STATUS      current
        DESCRIPTION "Audio code priority 7"
        DEFVAL{255}
        ::={zxMsagSipCapEntry 15}
    
    zxMsagSipCapDtmfRelayPri1   OBJECT-TYPE
        SYNTAX  INTEGER
            {
                redunt2833(1),
                noRedunt2833(2),               
                unconfig(255)
            }
        MAX-ACCESS  read-write
        STATUS      current
        DESCRIPTION "DTMF relay priority 1"
        DEFVAL{1}
        ::={zxMsagSipCapEntry 16}
    
    zxMsagSipCapDtmfRelayPri2   OBJECT-TYPE
        SYNTAX  INTEGER
            {
                redunt2833(1),
                noRedunt2833(2),               
                unconfig(255)
            }
        MAX-ACCESS  read-write
        STATUS      current
        DESCRIPTION "DTMF relay priority 2"
        DEFVAL{2}
        ::={zxMsagSipCapEntry 17}
    
    zxMsagSipCapFaxPri1   OBJECT-TYPE
        SYNTAX  INTEGER
            {
                t30(1),
                t38(2),               
                unconfig(255)
            }
        MAX-ACCESS  read-write
        STATUS      current
        DESCRIPTION "Fax priority 1"
        DEFVAL{1}
        ::={zxMsagSipCapEntry 18}
    
    zxMsagSipCapFaxPri2   OBJECT-TYPE
        SYNTAX  INTEGER
            {
                t30(1),
                t38(2),               
                unconfig(255)
            }
        MAX-ACCESS  read-write
        STATUS      current
        DESCRIPTION "Fax priority 2"
        DEFVAL{2}
        ::={zxMsagSipCapEntry 19}
    
    zxMsagSipCapSpFaxModem   OBJECT-TYPE
        SYNTAX  TruthValue
        MAX-ACCESS  read-write
        STATUS      current
        DESCRIPTION "Support fax modem"
        DEFVAL{2}
        ::={zxMsagSipCapEntry 20}
    
    zxMsagSipCapSessionMaxExpire   OBJECT-TYPE
        SYNTAX  INTEGER(0..65535)
        MAX-ACCESS  read-write
        STATUS      current
        DESCRIPTION "Session max expire(s)."
        DEFVAL{1800}
        ::={zxMsagSipCapEntry 21}
    
    zxMsagSipCapSessionMinExpire   OBJECT-TYPE
        SYNTAX  INTEGER(0..65535)
        MAX-ACCESS  read-write
        STATUS      current
        DESCRIPTION "Session min expire(s)."
        DEFVAL{90}
        ::={zxMsagSipCapEntry 22}
    
    zxMsagSipCapSessionRefresher   OBJECT-TYPE
        SYNTAX  INTEGER{local(1),remote(2)}
        MAX-ACCESS  read-write
        STATUS      current
        DESCRIPTION "Session refresher."
        DEFVAL{1}        
        ::={zxMsagSipCapEntry 23}
    
    zxMsagSipCapDisplayFrom   OBJECT-TYPE
        SYNTAX  INTEGER{from(1),pai(2)}
        MAX-ACCESS  read-write
        STATUS      current
        DESCRIPTION "Sip number display source"
        DEFVAL{1}
        ::={zxMsagSipCapEntry 24}
    
    zxMsagSipCapRegisterExpire   OBJECT-TYPE
        SYNTAX  INTEGER(0..65535)
        MAX-ACCESS  read-write
        STATUS      current
        DESCRIPTION "Register expire(s)"
        DEFVAL{3600}
        ::={zxMsagSipCapEntry 25}
    
    zxMsagSipCapReqMsgAuth   OBJECT-TYPE
        SYNTAX  TruthValue
        MAX-ACCESS  read-write
        STATUS      current
        DESCRIPTION "Request message authentication"
        DEFVAL{2}
        ::={zxMsagSipCapEntry 26}
    
    zxMsagSipCapPPreService   OBJECT-TYPE
        SYNTAX  TruthValue
        MAX-ACCESS  read-write
        STATUS      current
        DESCRIPTION "Request with preferred servic"
        DEFVAL{1}
        ::={zxMsagSipCapEntry 27}
    
    zxMsagSipCapAuthWithDomain   OBJECT-TYPE
        SYNTAX  TruthValue
        MAX-ACCESS  read-write
        STATUS      current
        DESCRIPTION "Authentication username with domain"
        DEFVAL{2}
        ::={zxMsagSipCapEntry 28}
    
    zxMsagSipCapPackageInterval   OBJECT-TYPE
        SYNTAX  INTEGER(20..50)
        MAX-ACCESS  read-write
        STATUS      current
        DESCRIPTION "Package interval(ms). The value must be 20,30,40,50."
        DEFVAL{20}
        ::={zxMsagSipCapEntry 29}  

    zxMsagSipCapSessionLimit    OBJECT-TYPE
        SYNTAX  TruthValue
        MAX-ACCESS  read-write
        STATUS      current
        DESCRIPTION "Session limit.One user only has one session at the same time."
        DEFVAL{2}
        ::={zxMsagSipCapEntry 30} 

    zxMsagSipCapUserParam   OBJECT-TYPE
        SYNTAX  INTEGER{null(1),phone(2),ip(3),other(4)}
        MAX-ACCESS  read-write
        STATUS      current
        DESCRIPTION "User-param of SIP URL."
        DEFVAL{2}
        ::={zxMsagSipCapEntry 31}       

    zxMsagSipCapDtmfSendingType   OBJECT-TYPE
        SYNTAX  INTEGER
        {
            rtp(1),
            sipinfo(2),
            broadSoftInfo(3),
            ibx1000Info(4)
        }
        MAX-ACCESS  read-write
        STATUS      current
        DESCRIPTION "DTMF sending type."
        DEFVAL{1}
        ::={zxMsagSipCapEntry 32}

    zxMsagSipCapEarlyMedia  OBJECT-TYPE
        SYNTAX  TruthValue
        MAX-ACCESS  read-write
        STATUS      current
        DESCRIPTION "Support early media."
        DEFVAL{2}
        ::={zxMsagSipCapEntry 33}      

    zxMsagSipCapEchoCancel  OBJECT-TYPE
        SYNTAX  TruthValue
        MAX-ACCESS  read-write
        STATUS      current
        DESCRIPTION "Echo cancel."
        DEFVAL{2}
        ::={zxMsagSipCapEntry 34}  

    zxMsagSipCapHistoryInfo  OBJECT-TYPE
        SYNTAX  TruthValue
        MAX-ACCESS  read-write
        STATUS      current
        DESCRIPTION "Support history-info."
        DEFVAL{2}
        ::={zxMsagSipCapEntry 35} 

    zxMsagSipCapThreePartySvrCode  OBJECT-TYPE
        SYNTAX  DisplayString(SIZE(0..16))
        MAX-ACCESS  read-write
        STATUS      current
        DESCRIPTION "Three party serive code. The character must be 0-9,E,F."        
        ::={zxMsagSipCapEntry 36} 

    zxMsagSipCapUserRegisterType       OBJECT-TYPE
        SYNTAX  INTEGER{explicit(1),implicit(2)}
        MAX-ACCESS  read-write
        STATUS      current
        DESCRIPTION "User register type.
            explicit(1):users register respectively,
            implicit(2):groups register"
        DEFVAL{1}
        ::={zxMsagSipCapEntry 37}                  
        
    zxMsagSipCapHeartbeatEnable   OBJECT-TYPE
        SYNTAX  INTEGER{off(1),on(2)}
        MAX-ACCESS  read-write
        STATUS      current
        DESCRIPTION "Sip heartbeat enable"
        DEFVAL{1}
        ::={zxMsagSipCapEntry 51}
    
    zxMsagSipCapHeartbeatInterval  OBJECT-TYPE
        SYNTAX  INTEGER(1..65535)
        MAX-ACCESS  read-write
        STATUS      current
        DESCRIPTION "Sip heartbeat interval(100ms)"
        DEFVAL{3000}
        ::={zxMsagSipCapEntry 52}
        
    zxMsagSipCapSelfswitch  OBJECT-TYPE
        SYNTAX      INTEGER{enable(1),disable(2)}
        MAX-ACCESS  read-write
        STATUS      current
        DESCRIPTION "Sip user agent selfswitch function enable status"
        REFERENCE   "Used by MAP"
        DEFVAL{2}
        ::={zxMsagSipCapEntry 53}

    zxMsagSipCapCallProtection   OBJECT-TYPE
        SYNTAX      INTEGER{enable(1),disable(2)}
        MAX-ACCESS  read-write
        STATUS      current
        DESCRIPTION "Sip user agent call protection function enable status" 
        REFERENCE   "Used by MAP"
        DEFVAL{2}      
        ::={zxMsagSipCapEntry 54}  
        
    zxAnSipCapVideoMediaNegotiation  OBJECT-TYPE
        SYNTAX      TruthValue
        MAX-ACCESS  read-write
        STATUS      current
        DESCRIPTION 
            "Supports video media negotiation or not."
        DEFVAL {false}
        ::={zxMsagSipCapEntry 55}
        
    zxAnSipCapUserPhoneAppendEnable   OBJECT-TYPE
        SYNTAX      INTEGER
            {
                enable(1),
                disable(2)
            }
        MAX-ACCESS  read-write
        STATUS      current
        DESCRIPTION 
            "Enable/disable to append SIP account with 'user=phone'." 
        REFERENCE   "Used by MAP"
        ::={zxMsagSipCapEntry 56}
        
    zxAnSipCapSendSubscribeMsgEnable   OBJECT-TYPE
        SYNTAX      INTEGER
            {
                enable(1),
                disable(2)
            }
        MAX-ACCESS  read-write
        STATUS      current
        DESCRIPTION 
            "Enable/disable to send subscribe message to SIP server after
             registering successfully." 
        REFERENCE   "Used by MAP"
        DEFVAL      {disable}
        ::={zxMsagSipCapEntry 57}
    
    zxAnSipCapFaxCodePri1   OBJECT-TYPE
        SYNTAX      INTEGER
            {
                pcma(1),
                pcmu(2),
                unconfig(255)
            }
        MAX-ACCESS  read-write
        STATUS      current
        DESCRIPTION 
            "Fax coding priority 1." 
        REFERENCE   "Used by MAP"
        DEFVAL      {pcma}
        ::={zxMsagSipCapEntry 58}
        
    zxAnSipCapFaxCodePri2   OBJECT-TYPE
        SYNTAX      INTEGER
            {
                pcma(1),
                pcmu(2),
                unconfig(255)
            }
        MAX-ACCESS  read-write
        STATUS      current
        DESCRIPTION 
            "Fax coding priority 2." 
        REFERENCE   "Used by MAP"
        DEFVAL      {pcmu}
        ::={zxMsagSipCapEntry 59}
        
    zxAnSipCapFaxCodePri3   OBJECT-TYPE
        SYNTAX      INTEGER
            {
                pcma(1),
                pcmu(2),
                unconfig(255)
            }
        MAX-ACCESS  read-write
        STATUS      current
        DESCRIPTION 
            "Fax coding priority 3." 
        REFERENCE   "Used by MAP"
        DEFVAL      {unconfig}
        ::={zxMsagSipCapEntry 60}
        
    zxAnSipCapFaxCodePri4   OBJECT-TYPE
        SYNTAX      INTEGER
            {
                pcma(1),
                pcmu(2),
                unconfig(255)
            }
        MAX-ACCESS  read-write
        STATUS      current
        DESCRIPTION 
            "Fax coding priority 4." 
        REFERENCE   "Used by MAP"
        DEFVAL      {unconfig}
        ::={zxMsagSipCapEntry 61}
    
    zxAnSipCapFaxPacketInterval   OBJECT-TYPE
        SYNTAX      Integer32(20..50)
        UNITS       "ms"
        MAX-ACCESS  read-write
        STATUS      current
        DESCRIPTION 
            "Fax packet interval. The value must be 20,30,40,50." 
        REFERENCE   "Used by MAP"
        DEFVAL      {20}
        ::={zxMsagSipCapEntry 62}
    
    zxAnSipCapAutoRefreshEnable   OBJECT-TYPE
        SYNTAX      INTEGER
            {
                enable(1),
                disable(2)
            }
        MAX-ACCESS  read-write
        STATUS      current
        DESCRIPTION 
            "Enable/disable to refresh terminal automatically when server does 
             not support to refresh session." 
        REFERENCE   "Used by MAP"
        DEFVAL      {disable}
        ::={zxMsagSipCapEntry 63}
        
    zxAnSipCapImsHotlineValidTime   OBJECT-TYPE
        SYNTAX      Integer32(90..900000)
        UNITS       "seconds"
        MAX-ACCESS  read-write
        STATUS      current
        DESCRIPTION 
            "Valid time of IMS hotline service." 
        REFERENCE   "Used by MAP"
        DEFVAL      {86400}
        ::={zxMsagSipCapEntry 64}
        
    zxAnSipCapDnsRequestInterval   OBJECT-TYPE
        SYNTAX      Integer32(10..65535)
        UNITS       "seconds"
        MAX-ACCESS  read-write
        STATUS      current
        DESCRIPTION 
            "DNS request interval." 
        REFERENCE   "Used by MAP"
        DEFVAL      {300}
        ::={zxMsagSipCapEntry 65}
        
   zxAnSipCapCallWaitInvite18xRsp  OBJECT-TYPE
        SYNTAX      Integer32(180..182)
        MAX-ACCESS  read-write
        STATUS      current
        DESCRIPTION 
            "Response value for sending INVITE request on call waiting."
        DEFVAL      {180}
        ::={zxMsagSipCapEntry 66}
   
   zxAnSipCapSubscribeUaProfileEn  OBJECT-TYPE
        SYNTAX      INTEGER
            {
                enabled(1),
                disabled(2)
            }
        MAX-ACCESS  read-write
        STATUS      current
        DESCRIPTION 
            "Enable/disable the function of subscribing the ua-profile event."
        DEFVAL      {enabled}
        ::={zxMsagSipCapEntry 67}
   
   zxAnSipCapSubscribeMsgSummaryEn  OBJECT-TYPE
        SYNTAX      INTEGER
            {
                enabled(1),
                disabled(2)
            }
        MAX-ACCESS  read-write
        STATUS      current
        DESCRIPTION 
            "Enable/disable the function of subscribing the message-summary 
            event." 
        DEFVAL      {enabled}
        ::={zxMsagSipCapEntry 68}
        
   zxAnSipCapCallerControlEnable  OBJECT-TYPE
        SYNTAX      INTEGER
            {
                enabled(1),
                disabled(2)
            }
        MAX-ACCESS  read-write
        STATUS      current
        DESCRIPTION 
            "Enable/disable the caller control service." 
        DEFVAL      {enabled}
        ::={zxMsagSipCapEntry 69}
        
    zxAnSipCapNoDialSendInviteEnable   OBJECT-TYPE
        SYNTAX      INTEGER
            {
                enabled(1),
                disabled(2)
            }
        MAX-ACCESS  read-write
        STATUS      current
        DESCRIPTION 
            "Enable/disable the function of sending INVITE request 
            without dialing." 
        DEFVAL      {disabled}
        ::={zxMsagSipCapEntry 70}
        
    zxAnSipCapProxySvrAutoDrEnable   OBJECT-TYPE
        SYNTAX      INTEGER
            {
                enabled(1),
                disabled(2)
            }
        MAX-ACCESS  read-write
        STATUS      current
        DESCRIPTION "Enables or disables the SIP proxy server automatic disaster 
                    recovery."
        DEFVAL      { enabled }
        ::={zxMsagSipCapEntry 71}
        
    zxAnSipCapProxySvrDrMode   OBJECT-TYPE
        SYNTAX      INTEGER
            {
                primaryFirst(1),
                roundRobin(2)
            }
        MAX-ACCESS  read-write
        STATUS      current
        DESCRIPTION "SIP proxy server disaster recovery mode.
                    primaryFirst(1):the current SIP proxy server is primary 
                    server when primary server works well, and it swap to 
                    secondary server when primary server is down.
                    roundRobin(2):the current SIP proxy server works in a 
                    round-robin manner."
        DEFVAL      { primaryFirst }
        ::={zxMsagSipCapEntry 72}

--------------------------------------------------------------------------------
-- 6.SIP Global Objects
--------------------------------------------------------------------------------

    zxAnSipGlobalObjects    OBJECT IDENTIFIER   ::=  {  zxAnSipConfig  6  }

    zxAnSipMgmtCapabilities OBJECT-TYPE
        SYNTAX     BITS
        {
            group(0),
            sipUaIp(1),
            proxySvrDomainName(2),
            nbPlatform(3),
            userAdminStatus(4),
            userSessionLimit(5)
        }
        MAX-ACCESS  read-only
        STATUS      current
        DESCRIPTION
            "The SIP management capabilities of this equipment.
            The bit value 1 means the function represented by this bit is
            supported by this equipment.            
            group(0): value 1 means support SIP user group ID.
            sipUaIp(1): value 1 means support SIP user agent IP(zxAnSipUaIp).
            proxySvrDomainName(2): value 1 means support zxAnSipProxySvrNamingType and 
                   zxAnSipProxySvrDomainName.
            nbPlatform(3): value 1 means support narrowband platform.
            userAdminStatus(4): value 1 means support zxMsagSipUserAdminStatus.
            userSessionLimit(5): value 1 means support zxMsagSipUserSessionLimit.
            NOTE: No recommended to display it in NMS."
        ::= { zxAnSipGlobalObjects 1 }
    
    zxAnSipProcessReboot OBJECT-TYPE 
       SYNTAX             INTEGER  
          { 
              reboot (1)
          } 
       MAX-ACCESS       read-write
       STATUS           current
       DESCRIPTION      "Reboot sip process."
       ::=  {  zxAnSipGlobalObjects  2  }
        
        

--------------------------------------------------------------------------------
-- 7.SIP Proxy Server Table
--------------------------------------------------------------------------------    
    
    zxAnSipProxyServerTable OBJECT-TYPE
        SYNTAX  SEQUENCE OF ZxAnSipProxyServerEntry
        MAX-ACCESS  not-accessible
        STATUS      current
        DESCRIPTION "Sip proxy server table"
        ::={zxAnSipConfig 7}
    
    zxAnSipProxyServerEntry OBJECT-TYPE
        SYNTAX    ZxAnSipProxyServerEntry
        MAX-ACCESS  not-accessible
        STATUS      current
        DESCRIPTION "Sip proxy server table entry"
        INDEX {zxAnSipProxySvrId}
        ::={zxAnSipProxyServerTable 1}
    
    ZxAnSipProxyServerEntry ::=
        SEQUENCE{
            zxAnSipProxySvrId             INTEGER,
            zxAnSipProxySvrIp             IpAddress, 
            zxAnSipProxySvrPort           Integer32,  
            zxAnSipProxySvrNamingType     INTEGER,
            zxAnSipProxySvrDomainName     DisplayString,      
            zxAnSipProxySvrRowStatus      RowStatus
        }
    
    zxAnSipProxySvrId  OBJECT-TYPE
        SYNTAX  INTEGER(1..255)
        MAX-ACCESS  not-accessible
        STATUS      current
        DESCRIPTION "Sip proxy server ID"
        DEFVAL{1}
        ::={zxAnSipProxyServerEntry 1}
       
    zxAnSipProxySvrIp   OBJECT-TYPE
        SYNTAX  IpAddress
        MAX-ACCESS  read-create
        STATUS      current
        DESCRIPTION 
            "Sip proxy server IP address.
            When zxAnSipProxySvrNamingType is dhcpOption120(3), 
            it is read only."             
        ::={zxAnSipProxyServerEntry 2}
    
    zxAnSipProxySvrPort  OBJECT-TYPE
        SYNTAX  Integer32(0..65535)
        MAX-ACCESS  read-create
        STATUS      current
        DESCRIPTION "Sip proxy server port"
        DEFVAL{5060}
        ::={zxAnSipProxyServerEntry 3}

    zxAnSipProxySvrNamingType  OBJECT-TYPE
        SYNTAX  INTEGER{useIp(1),useDomainName(2),dhcpOption120(3)}
        MAX-ACCESS  read-create
        STATUS      current
        DESCRIPTION "Sip proxy server naming type."
        DEFVAL{useIp}
        ::={zxAnSipProxyServerEntry 4}

    zxAnSipProxySvrDomainName  OBJECT-TYPE
        SYNTAX  DisplayString(SIZE(0..32))
        MAX-ACCESS  read-create
        STATUS      current
        DESCRIPTION 
            "Sip proxy server domain name.
             When zxAnSipProxySvrNamingType is dhcpOption120(3), 
             it is read only."
        ::={zxAnSipProxyServerEntry 5}
    
    zxAnSipProxySvrRowStatus  OBJECT-TYPE
        SYNTAX  RowStatus
        MAX-ACCESS  read-create
        STATUS      current
        DESCRIPTION "Sip proxy server row status"
        ::={zxAnSipProxyServerEntry 20}

--------------------------------------------------------------------------------
-- 8.SIP User Agent Table
--------------------------------------------------------------------------------    
    
    zxAnSipUserAgentTable OBJECT-TYPE
        SYNTAX  SEQUENCE OF ZxAnSipUserAgentEntry
        MAX-ACCESS  not-accessible
        STATUS      current
        DESCRIPTION "Sip user agent table"
        ::={zxAnSipConfig 8}
    
    zxAnSipUserAgentEntry OBJECT-TYPE
        SYNTAX    ZxAnSipUserAgentEntry
        MAX-ACCESS  not-accessible
        STATUS      current
        DESCRIPTION "Sip user agent table entry"
        INDEX {zxAnSipUaId}
        ::={zxAnSipUserAgentTable 1}
    
    ZxAnSipUserAgentEntry ::=
        SEQUENCE{
            zxAnSipUaId                    INTEGER,            
            zxAnSipUaPort                  Integer32,   
            zxAnSipUaDomainName            DisplayString,            
            zxAnSipUaProxySvrId1           Integer32,
            zxAnSipUaProxySvrId2           Integer32,
            zxAnSipUaProxySvrId3           Integer32,
            zxAnSipUaProxySvrId4           Integer32,
            zxAnSipUaSelfswitch            INTEGER,
            zxAnSipUaCallProtection        INTEGER,
            zxAnSipUaIpType                InetAddressType,
            zxAnSipUaIp                    InetAddress,  
            zxAnSipUaSwitchProxySvrId      Integer32,
            zxAnSipUaCurrentProxySvrId     Integer32,            
            zxAnSipUaRowStatus             RowStatus
        }
    
    zxAnSipUaId  OBJECT-TYPE
        SYNTAX  INTEGER(1)
        MAX-ACCESS  not-accessible
        STATUS      current
        DESCRIPTION "Sip user agent ID"
        REFERENCE   "Used by MAP"
        DEFVAL{1}
        ::={zxAnSipUserAgentEntry 1}
    
    zxAnSipUaPort  OBJECT-TYPE
        SYNTAX  Integer32(0..65535)
        MAX-ACCESS  read-create
        STATUS      current
        DESCRIPTION "Sip user agent port"
        REFERENCE   "Used by MAP"
        DEFVAL{5060}
        ::={zxAnSipUserAgentEntry 2}

    zxAnSipUaDomainName  OBJECT-TYPE
        SYNTAX      DisplayString(SIZE(0..32))
        MAX-ACCESS  read-create
        STATUS      current
        DESCRIPTION "Sip user agent domain name"
        REFERENCE   "Used by MAP"
        ::={zxAnSipUserAgentEntry 3}    

    zxAnSipUaProxySvrId1  OBJECT-TYPE
        SYNTAX  Integer32(1..255)
        MAX-ACCESS  read-create
        STATUS      current
        DESCRIPTION "Sip proxy server ID 1"
        REFERENCE   "Used by MAP"
        DEFVAL{1}
        ::={zxAnSipUserAgentEntry 4}

    zxAnSipUaProxySvrId2  OBJECT-TYPE
        SYNTAX  Integer32(0..255)
        MAX-ACCESS  read-create
        STATUS      current
        DESCRIPTION
            "Sip proxy server ID 2.
             Value 0 means SIP proxy server ID 2 is not used in SIP user agent.
            "
        REFERENCE   "Used by MAP"
        ::={zxAnSipUserAgentEntry 5}

    zxAnSipUaProxySvrId3  OBJECT-TYPE
        SYNTAX  Integer32(0..255)
        MAX-ACCESS  read-create
        STATUS      current
        DESCRIPTION
            "Sip proxy server ID 3.
             Value 0 means SIP proxy server ID 3 is not used in SIP user agent.
            "
        REFERENCE   "Used by MAP"    
        ::={zxAnSipUserAgentEntry 6}
    
    zxAnSipUaProxySvrId4  OBJECT-TYPE
        SYNTAX  Integer32(0..255)
        MAX-ACCESS  read-create
        STATUS      current
        DESCRIPTION 
            "Sip proxy server ID 4.
             Value 0 means SIP proxy server ID 4 is not used in SIP user agent.
            "
        REFERENCE   "Used by MAP"    
        ::={zxAnSipUserAgentEntry 7}

    zxAnSipUaSelfswitch  OBJECT-TYPE
        SYNTAX      INTEGER{enable(1),disable(2)}
        MAX-ACCESS  read-create
        STATUS      current
        DESCRIPTION "Sip user agent selfswitch function enable status"
        REFERENCE   "Used by MAP"
        DEFVAL{2}
        ::={zxAnSipUserAgentEntry 8}

    zxAnSipUaCallProtection   OBJECT-TYPE
        SYNTAX      INTEGER{enable(1),disable(2)}
        MAX-ACCESS  read-create
        STATUS      current
        DESCRIPTION "Sip user agent call protection function enable status" 
        REFERENCE   "Used by MAP"
        DEFVAL{2}      
        ::={zxAnSipUserAgentEntry 9}
    
    zxAnSipUaIpType    OBJECT-TYPE 
        SYNTAX       InetAddressType
        MAX-ACCESS   read-only 
        STATUS       current 
        DESCRIPTION 
            "SIP user agent IP address type." 
        ::= { zxAnSipUserAgentEntry 10} 
            
    zxAnSipUaIp   OBJECT-TYPE
        SYNTAX      InetAddress
        MAX-ACCESS  read-only
        STATUS      current
        DESCRIPTION "Sip user agent IP address." 
        REFERENCE   "Used by MAP"
        ::={zxAnSipUserAgentEntry 11}
        
    zxAnSipUaSwitchProxySvrId  OBJECT-TYPE
        SYNTAX      Integer32(1..4)
        MAX-ACCESS  read-create
        STATUS      current
        DESCRIPTION "Switchover SIP proxy server ID."
        ::={zxAnSipUserAgentEntry 12}  
    
    zxAnSipUaCurrentProxySvrId  OBJECT-TYPE
        SYNTAX      Integer32(1..4)
        MAX-ACCESS  read-only
        STATUS      current
        DESCRIPTION "Current SIP proxy server ID."
        ::={zxAnSipUserAgentEntry 13}   

    zxAnSipUaRowStatus  OBJECT-TYPE
        SYNTAX  RowStatus
        MAX-ACCESS  read-create
        STATUS      current
        DESCRIPTION "Sip user agent row status"
        REFERENCE   "Used by MAP"
        ::={zxAnSipUserAgentEntry 50}

--------------------------------------------------------------------------------
-- 20.SIP Group Table
--------------------------------------------------------------------------------

    zxAnSipGroupTable OBJECT-TYPE
        SYNTAX  SEQUENCE OF ZxAnSipGroupEntry 
        MAX-ACCESS  not-accessible
        STATUS      current
        DESCRIPTION "SIP group table"
        ::={zxAnSipConfig 20}
    
    zxAnSipGroupEntry OBJECT-TYPE
        SYNTAX    ZxAnSipGroupEntry 
        MAX-ACCESS  not-accessible
        STATUS      current
        DESCRIPTION "Entry of SIP group table"
        INDEX {zxAnSipGroupMgId, zxAnSipGroupId}
        ::={zxAnSipGroupTable 1}
    
    ZxAnSipGroupEntry ::=
        SEQUENCE{
            zxAnSipGroupMgId              INTEGER,    
            zxAnSipGroupId                Integer32,
            zxAnSipGroupName              DisplayString,
            zxAnSipGroupType              INTEGER,
            zxAnSipGroupOperNum           Integer32,
            zxAnSipGroupPhoneNumber       DisplayString,
            zxAnSipGroupUserId            DisplayString,
            zxAnSipGroupAuthUserName      DisplayString,
            zxAnSipGroupOperType          INTEGER,
            zxAnSipGroupUserType          INTEGER,
            zxAnSipGroupUserStartNumber   Integer32,
            zxAnSipGroupUserDigitLen      Integer32,
            zxAnSipGroupPassword          DisplayString,
            zxAnSipGroupRowStatus         RowStatus
        }
    
    zxAnSipGroupMgId  OBJECT-TYPE
        SYNTAX      INTEGER(1)
        MAX-ACCESS  not-accessible
        STATUS      current
        DESCRIPTION "MG ID"
        DEFVAL{1}
        ::={zxAnSipGroupEntry 1}
    
    zxAnSipGroupId   OBJECT-TYPE
        SYNTAX      Integer32(1..500)
        MAX-ACCESS   not-accessible
        STATUS      current
        DESCRIPTION "Group ID"
        ::={zxAnSipGroupEntry 2}
    
    zxAnSipGroupName   OBJECT-TYPE
        SYNTAX      DisplayString(SIZE(1..16))
        MAX-ACCESS   read-create
        STATUS      current
        DESCRIPTION "Group name"
        ::={zxAnSipGroupEntry 3}
    
    zxAnSipGroupType   OBJECT-TYPE
        SYNTAX      INTEGER{pstn(1),isdnbri(2),isdnpri(3)}
        MAX-ACCESS   read-create
        STATUS      current
        DESCRIPTION "Group type. ISDN BRI for 2B+D. ISDN PRI for 30B+D and 23B+D."
        ::={zxAnSipGroupEntry 4}
    
    zxAnSipGroupOperNum   OBJECT-TYPE
        SYNTAX      Integer32(1..500)
        MAX-ACCESS   read-create
        STATUS      current
        DESCRIPTION "Batch operation number"
        ::={zxAnSipGroupEntry 5}

    zxAnSipGroupPhoneNumber  OBJECT-TYPE
        SYNTAX      DisplayString(SIZE(1..32))
        MAX-ACCESS  read-create
        STATUS      current
        DESCRIPTION "SIP group phone number"
        ::={zxAnSipGroupEntry 6}

    zxAnSipGroupUserId   OBJECT-TYPE
        SYNTAX  DisplayString(SIZE(1..64))
        MAX-ACCESS  read-create
        STATUS      current
        DESCRIPTION "Sip group user ID"
        ::={zxAnSipGroupEntry 7}

    zxAnSipGroupAuthUserName  OBJECT-TYPE
        SYNTAX  DisplayString(SIZE(0..64))
        MAX-ACCESS  read-create
        STATUS      current
        DESCRIPTION "SIP group authentication name"
        ::={zxAnSipGroupEntry 8}   
        
    zxAnSipGroupOperType  OBJECT-TYPE
        SYNTAX     INTEGER{username(1),userid(2),all(3),none(4)}
        MAX-ACCESS  read-create
        STATUS      current
        DESCRIPTION "Operation type.
            username(1):Only create or modify authentication name,
            userid(2):Only create or modify user ID,
            all(3):create or modify authentication name and user ID at the same time.
            none(4):not create or modify authentication name and user ID. 
            Note: No recomanded to display it in NMS."
        ::={zxAnSipGroupEntry 9} 
        
    zxAnSipGroupUserType  OBJECT-TYPE
        SYNTAX     INTEGER{type2(2),type3(3)}
        MAX-ACCESS  read-create
        STATUS      current
        DESCRIPTION "SIP group user ID or authentication name type.            
            Type 2:USER0-USER31,
            Type 3:User000-USER031"
        DEFVAL{2}
        ::={zxAnSipGroupEntry 10}
        
    zxAnSipGroupUserStartNumber   OBJECT-TYPE
        SYNTAX      Integer32(0..65535)
        MAX-ACCESS  read-create
        STATUS      current
        DESCRIPTION "SIP group user ID or authentication name start number"
        DEFVAL{0}
        ::={zxAnSipGroupEntry 11}
        
    zxAnSipGroupUserDigitLen  OBJECT-TYPE
        SYNTAX      Integer32(0..64)
        MAX-ACCESS  read-create
        STATUS      current
        DESCRIPTION "SIP group user ID or authentication name digit length"
        DEFVAL{3}
        ::={zxAnSipGroupEntry 12}
        
    zxAnSipGroupPassword  OBJECT-TYPE
        SYNTAX      DisplayString(SIZE(0..16))
        MAX-ACCESS  read-create
        STATUS      current
        DESCRIPTION "SIP group user password"
        ::={zxAnSipGroupEntry 13}    
    
    zxAnSipGroupRowStatus  OBJECT-TYPE
        SYNTAX      RowStatus
        MAX-ACCESS  read-create
        STATUS      current
        DESCRIPTION "Row status of SIP group table"
        ::= { zxAnSipGroupEntry 30 }

--------------------------------------------------------------------------------
-- 21.SIP ISDN Link Table
--------------------------------------------------------------------------------

    zxAnSipIsdnDLinkTable OBJECT-TYPE
        SYNTAX    SEQUENCE OF ZxAnSipIsdnDLinkEntry
        MAX-ACCESS not-accessible
        STATUS     current
        DESCRIPTION "SIP ISDN Dlink table"
        ::={zxAnSipConfig 21}
    
    zxAnSipIsdnDLinkEntry OBJECT-TYPE
        SYNTAX    ZxAnSipIsdnDLinkEntry
        MAX-ACCESS not-accessible
        STATUS     current
        DESCRIPTION "Entry of SIP ISDN Dlink table"
        INDEX {zxAnSipIsdnDLinkMgId,zxAnSipIsdnDLinkGroupId,zxAnSipIsdnDLinkLinkId}
        ::={zxAnSipIsdnDLinkTable 1}
    
    ZxAnSipIsdnDLinkEntry ::=
        SEQUENCE{
            zxAnSipIsdnDLinkMgId       INTEGER,
            zxAnSipIsdnDLinkGroupId    Integer32,
            zxAnSipIsdnDLinkLinkId     Integer32,
            zxAnSipIsdnDLinkRack       Integer32,
            zxAnSipIsdnDLinkShelf      Integer32,
            zxAnSipIsdnDLinkSlot       Integer32,
            zxAnSipIsdnDLinkIndex      Integer32,
            zxAnSipIsdnDLinkDChanTs    Integer32,
            zxAnSipIsdnDLinkOperNum    Integer32,
            zxAnSipIsdnDLinkType       INTEGER,                    
            zxAnSipIsdnDLinkRowStatus  RowStatus
        }
    
    zxAnSipIsdnDLinkMgId  OBJECT-TYPE
        SYNTAX      INTEGER(1)
        MAX-ACCESS  not-accessible
        STATUS      current
        DESCRIPTION "MG ID"
        DEFVAL{1}
        ::={zxAnSipIsdnDLinkEntry 1}
    
    zxAnSipIsdnDLinkGroupId      OBJECT-TYPE
        SYNTAX      Integer32(1..500)
        MAX-ACCESS  not-accessible
        STATUS      current
        DESCRIPTION "Group ID"
        ::= { zxAnSipIsdnDLinkEntry 2 }
    
    zxAnSipIsdnDLinkLinkId  OBJECT-TYPE
        SYNTAX      Integer32(1..512)
        MAX-ACCESS  not-accessible
        STATUS      current
        DESCRIPTION "Link ID"
        ::= { zxAnSipIsdnDLinkEntry 3 }
    
    zxAnSipIsdnDLinkRack    OBJECT-TYPE
        SYNTAX      Integer32(1..3)
        MAX-ACCESS  read-create
        STATUS      current
        DESCRIPTION "Rack of the link"
        ::= { zxAnSipIsdnDLinkEntry 4 }
    
    zxAnSipIsdnDLinkShelf   OBJECT-TYPE
        SYNTAX      Integer32(1..5)
        MAX-ACCESS  read-create
        STATUS      current
        DESCRIPTION "Shelf of the link"
        ::= { zxAnSipIsdnDLinkEntry 5 }
    
    zxAnSipIsdnDLinkSlot    OBJECT-TYPE
        SYNTAX      Integer32(1..23)
        MAX-ACCESS  read-create
        STATUS      current
        DESCRIPTION "Slot of the link"
        ::= { zxAnSipIsdnDLinkEntry 6 }
    
    zxAnSipIsdnDLinkIndex   OBJECT-TYPE
        SYNTAX      Integer32(1..8)
        MAX-ACCESS  read-create
        STATUS      current
        DESCRIPTION "2B+D No or E1/T1 No"
        DEFVAL{1}
        ::= { zxAnSipIsdnDLinkEntry 7 }
    
    zxAnSipIsdnDLinkDChanTs OBJECT-TYPE
        SYNTAX      Integer32(1..31)
        MAX-ACCESS  read-create
        STATUS      current
        DESCRIPTION "D channel time slot of the link. Only configured for E1/T1. 255 means not configured."        
        ::= { zxAnSipIsdnDLinkEntry 8 }    
    
    zxAnSipIsdnDLinkOperNum  OBJECT-TYPE
        SYNTAX      Integer32(1..8)
        MAX-ACCESS  read-create
        STATUS      current
        DESCRIPTION "Operation number. For 2B+D it must be 1."
        DEFVAL{1}
        ::= { zxAnSipIsdnDLinkEntry 9 }
    
    zxAnSipIsdnDLinkType  OBJECT-TYPE
        SYNTAX      INTEGER{link2BplusD(1),link30BplusD(2),link23BplusD(3)}
        MAX-ACCESS  read-only
        STATUS      current
        DESCRIPTION "Link type"
        ::= { zxAnSipIsdnDLinkEntry 10 }   
    
    zxAnSipIsdnDLinkRowStatus     OBJECT-TYPE
        SYNTAX      RowStatus
        MAX-ACCESS  read-create
        STATUS      current
        DESCRIPTION "Row status of SIP ISDN Dlink table"
        ::= { zxAnSipIsdnDLinkEntry 20 }

--------------------------------------------------------------------------------
-- 22.SIP ISDN User Table
--------------------------------------------------------------------------------

    zxAnSipIsdnUserTable OBJECT-TYPE
        SYNTAX  SEQUENCE OF ZxAnSipIsdnUserEntry
        MAX-ACCESS  not-accessible
        STATUS      current
        DESCRIPTION "SIP ISDN user table"
        ::={zxAnSipConfig 22}
        
    zxAnSipIsdnUserEntry OBJECT-TYPE
        SYNTAX    ZxAnSipIsdnUserEntry
        MAX-ACCESS  not-accessible
        STATUS      current
        DESCRIPTION "Entry of SIP ISDN user table"
        INDEX {zxAnSipIsdnUserMgId, zxAnSipIsdnUserGroupId,zxAnSipIsdnUserSipPhoneNumber}
        ::={zxAnSipIsdnUserTable 1}
        
    ZxAnSipIsdnUserEntry ::=
        SEQUENCE{
            zxAnSipIsdnUserMgId              INTEGER,
            zxAnSipIsdnUserGroupId           Integer32,
            zxAnSipIsdnUserSipPhoneNumber    DisplayString,
            zxAnSipIsdnUserOperNum           Integer32,
            zxAnSipIsdnUserOperType          INTEGER,
            zxAnSipIsdnUserAuthUsername      DisplayString,
            zxAnSipIsdnUserAuthType          INTEGER,
            zxAnSipIsdnUserAuthStartNumber   Integer32,
            zxAnSipIsdnUserAuthDigitLen      Integer32,   
            zxAnSipIsdnUserPassword          DisplayString,     
            zxAnSipIsdnUserId                DisplayString, 
            zxAnSipIsdnUserIdType            INTEGER,
            zxAnSipIsdnUserIdStartNumber     Integer32,
            zxAnSipIsdnUserIdDigitLen        Integer32,
            zxAnSipIsdnUserRowStatus         RowStatus
        }
        
    zxAnSipIsdnUserMgId  OBJECT-TYPE
        SYNTAX      INTEGER(1)
        MAX-ACCESS   not-accessible
        STATUS      current
        DESCRIPTION "MG ID"
        DEFVAL{1}
        ::={zxAnSipIsdnUserEntry 1}
        
    zxAnSipIsdnUserGroupId  OBJECT-TYPE
        SYNTAX      Integer32(1..500)
        MAX-ACCESS  not-accessible
        STATUS      current
        DESCRIPTION "Group ID of SIP user"        
        ::={zxAnSipIsdnUserEntry 2}  
        
    zxAnSipIsdnUserSipPhoneNumber  OBJECT-TYPE
        SYNTAX      DisplayString(SIZE(1..32))
        MAX-ACCESS  not-accessible
        STATUS      current
        DESCRIPTION "SIP user phone number"
        ::={zxAnSipIsdnUserEntry 3}
        
    zxAnSipIsdnUserOperNum  OBJECT-TYPE
        SYNTAX      Integer32(1..2000)
        MAX-ACCESS  read-create
        STATUS      current
        DESCRIPTION "SIP user operaton number"        
        ::={zxAnSipIsdnUserEntry 4}
        
    zxAnSipIsdnUserOperType  OBJECT-TYPE
        SYNTAX     INTEGER{sipuser(1),sipuserid(2)}
        MAX-ACCESS  read-create
        STATUS      current
        DESCRIPTION "Operation type"
        ::={zxAnSipIsdnUserEntry 5}  
        
    zxAnSipIsdnUserAuthUsername  OBJECT-TYPE
        SYNTAX  DisplayString(SIZE(0..64))
        MAX-ACCESS  read-create
        STATUS      current
        DESCRIPTION "SIP user name"
        ::={zxAnSipIsdnUserEntry 6}   
        
    zxAnSipIsdnUserAuthType  OBJECT-TYPE
        SYNTAX     INTEGER{type2(2),type3(3)}
        MAX-ACCESS  read-create
        STATUS      current
        DESCRIPTION "SIP user name type.            
            Type 2:USER0-USER31,
            Type 3:User000-USER031"
        DEFVAL{2}
        ::={zxAnSipIsdnUserEntry 7}
        
    zxAnSipIsdnUserAuthStartNumber   OBJECT-TYPE
        SYNTAX      Integer32(0..65535)
        MAX-ACCESS  read-create
        STATUS      current
        DESCRIPTION "SIP user name begin no"
        DEFVAL{0}
        ::={zxAnSipIsdnUserEntry 8}
        
    zxAnSipIsdnUserAuthDigitLen  OBJECT-TYPE
        SYNTAX      Integer32(0..64)
        MAX-ACCESS  read-create
        STATUS      current
        DESCRIPTION "SIP user name digit length"
        DEFVAL{3}
        ::={zxAnSipIsdnUserEntry 9}
        
    zxAnSipIsdnUserPassword  OBJECT-TYPE
        SYNTAX      DisplayString(SIZE(0..16))
        MAX-ACCESS  read-create
        STATUS      current
        DESCRIPTION "User password"
        ::={zxAnSipIsdnUserEntry 10}
        
    zxAnSipIsdnUserId   OBJECT-TYPE
        SYNTAX  DisplayString(SIZE(1..64))
        MAX-ACCESS  read-create
        STATUS      current
        DESCRIPTION "Sip user ID"
        ::={zxAnSipIsdnUserEntry 11}
        
    zxAnSipIsdnUserIdType  OBJECT-TYPE
        SYNTAX     INTEGER{type2(2),type3(3)}
        MAX-ACCESS  read-create
        STATUS      current
        DESCRIPTION "SIP user ID type.            
            Type 2:USER0-USER31,
            Type 3:User000-USER031"
        DEFVAL{2}
        ::={zxAnSipIsdnUserEntry 12}
        
    zxAnSipIsdnUserIdStartNumber   OBJECT-TYPE
        SYNTAX      Integer32(0..65535)
        MAX-ACCESS  read-create
        STATUS      current
        DESCRIPTION "Sip user ID begin no"
        DEFVAL{0}
        ::={zxAnSipIsdnUserEntry 13}
        
    zxAnSipIsdnUserIdDigitLen  OBJECT-TYPE
        SYNTAX      Integer32(0..64)
        MAX-ACCESS  read-create
        STATUS      current
        DESCRIPTION "Sip user ID digit length"
        DEFVAL{3}
        ::={zxAnSipIsdnUserEntry 14}
        
    zxAnSipIsdnUserRowStatus  OBJECT-TYPE
        SYNTAX      RowStatus
        MAX-ACCESS  read-create
        STATUS      current
        DESCRIPTION "Row status of SIP ISDN user table"
        ::={zxAnSipIsdnUserEntry 50}

--------------------------------------------------------------------------------
-- 23.SIP ISDN Phone Number Table
--------------------------------------------------------------------------------

    zxAnSipIsdnPhoneTable OBJECT-TYPE
        SYNTAX    SEQUENCE OF ZxAnSipIsdnPhoneEntry
        MAX-ACCESS not-accessible
        STATUS     current
        DESCRIPTION "SIP ISDN phone number table"
        ::={zxAnSipConfig 23}
        
    zxAnSipIsdnPhoneEntry OBJECT-TYPE
        SYNTAX    ZxAnSipIsdnPhoneEntry
        MAX-ACCESS not-accessible
        STATUS     current
        DESCRIPTION "Entry of SIP ISDN phone number table"
        INDEX {zxAnSipIsdnPhoneSipPhone,zxAnSipIsdnPhoneIsdnPhone}
        ::={zxAnSipIsdnPhoneTable 1}
        
    ZxAnSipIsdnPhoneEntry ::=
        SEQUENCE{
            zxAnSipIsdnPhoneSipPhone       DisplayString,
            zxAnSipIsdnPhoneIsdnPhone      DisplayString,          
            zxAnSipIsdnPhoneOperNum        Integer32,                        
            zxAnSipIsdnPhoneRowStatus      RowStatus
        }
        
    zxAnSipIsdnPhoneSipPhone  OBJECT-TYPE
        SYNTAX      DisplayString(SIZE(1..16))
        MAX-ACCESS  not-accessible
        STATUS      current
        DESCRIPTION "SIP phone number"
        ::={zxAnSipIsdnPhoneEntry 1}
        
    zxAnSipIsdnPhoneIsdnPhone  OBJECT-TYPE
        SYNTAX      DisplayString(SIZE(1..16))
        MAX-ACCESS  not-accessible
        STATUS      current
        DESCRIPTION "ISDN phone number"
        ::= { zxAnSipIsdnPhoneEntry 2 }  
        
    zxAnSipIsdnPhoneOperNum  OBJECT-TYPE
        SYNTAX      Integer32(1..2000)
        MAX-ACCESS  read-create
        STATUS      current
        DESCRIPTION "Operation number"
        ::= { zxAnSipIsdnPhoneEntry 3 }
        
    zxAnSipIsdnPhoneRowStatus     OBJECT-TYPE
        SYNTAX      RowStatus
        MAX-ACCESS  read-create
        STATUS      current
        DESCRIPTION "Row status of SIP ISDN phone number table"
        ::= { zxAnSipIsdnPhoneEntry 10 }

--------------------------------------------------------------------------------
-- 24.SIP ISDN PBX B Channel Table
--------------------------------------------------------------------------------

    zxAnSipIsdnBChanTable OBJECT-TYPE
        SYNTAX    SEQUENCE OF ZxAnSipIsdnBChanEntry
        MAX-ACCESS not-accessible
        STATUS     current
        DESCRIPTION "SIP ISDN PBX B channel table"
        ::={zxAnSipConfig 24}
        
    zxAnSipIsdnBChanEntry OBJECT-TYPE
        SYNTAX    ZxAnSipIsdnBChanEntry
        MAX-ACCESS not-accessible
        STATUS     current
        DESCRIPTION "Entry of SIP ISDN PBX B channel table"
        INDEX {zxAnSipIsdnBChanRack,zxAnSipIsdnBChanShelf,zxAnSipIsdnBChanSlot,zxAnSipIsdnBChanIndex,zxAnSipIsdnBChanTimeSlot}
        ::={zxAnSipIsdnBChanTable 1}
        
    ZxAnSipIsdnBChanEntry ::=
        SEQUENCE{         
            zxAnSipIsdnBChanRack       Integer32,
            zxAnSipIsdnBChanShelf      Integer32,
            zxAnSipIsdnBChanSlot       Integer32,
            zxAnSipIsdnBChanIndex      Integer32,
            zxAnSipIsdnBChanTimeSlot   Integer32,          
            zxAnSipIsdnBChanGroupId    Integer32,
            zxAnSipIsdnBChanPbxBChan   Integer32,   
            zxAnSipIsdnBChanOperNum    Integer32
        }
        
    zxAnSipIsdnBChanRack    OBJECT-TYPE
        SYNTAX      Integer32(1..3)
        MAX-ACCESS  not-accessible
        STATUS      current
        DESCRIPTION "Rack of ISDN B channel"
        ::= { zxAnSipIsdnBChanEntry 1 }
        
    zxAnSipIsdnBChanShelf   OBJECT-TYPE
        SYNTAX      Integer32(1..5)
        MAX-ACCESS  not-accessible
        STATUS      current
        DESCRIPTION "Shelf of ISDN B channel"
        ::= { zxAnSipIsdnBChanEntry 2 }
        
    zxAnSipIsdnBChanSlot    OBJECT-TYPE
        SYNTAX      Integer32(1..23)
        MAX-ACCESS  not-accessible
        STATUS      current
        DESCRIPTION "Slot of ISDN B channel"
        ::= { zxAnSipIsdnBChanEntry 3 }
        
    zxAnSipIsdnBChanIndex   OBJECT-TYPE
        SYNTAX      Integer32(1..8)
        MAX-ACCESS  not-accessible
        STATUS      current
        DESCRIPTION "E1/T1 No"
        ::= { zxAnSipIsdnBChanEntry 4 }
        
    zxAnSipIsdnBChanTimeSlot OBJECT-TYPE
        SYNTAX      Integer32(1..31)
        MAX-ACCESS  not-accessible
        STATUS      current
        DESCRIPTION "Time slot of E1/T1"
        ::= { zxAnSipIsdnBChanEntry 5 }
        
    zxAnSipIsdnBChanGroupId      OBJECT-TYPE
        SYNTAX      Integer32(1..500)
        MAX-ACCESS  read-only
        STATUS      current
        DESCRIPTION "Group ID"
        ::= { zxAnSipIsdnBChanEntry 6 }   
        
    zxAnSipIsdnBChanPbxBChan OBJECT-TYPE
        SYNTAX      Integer32(1..900)
        MAX-ACCESS  read-write
        STATUS      current
        DESCRIPTION "PBX B channel No"
        ::= { zxAnSipIsdnBChanEntry 7 }    
        
    zxAnSipIsdnBChanOperNum  OBJECT-TYPE
        SYNTAX      Integer32(1..31)
        MAX-ACCESS  read-write
        STATUS      current
        DESCRIPTION "Operation number"
        ::= { zxAnSipIsdnBChanEntry 8 }   

        


--------------------------------------------------------------------------------
-- 50.SIP Performance Table
--------------------------------------------------------------------------------

    zxAnSipCallPerfTable  OBJECT IDENTIFIER  ::= { zxAnSipConfig 50 }
    

    zxAnSipRegCurrentUsers   OBJECT-TYPE
        SYNTAX          Gauge32
        MAX-ACCESS      read-only
        STATUS          current
        DESCRIPTION     "Count of registered users successfully."
        ::= { zxAnSipCallPerfTable 1 }

    zxAnSipSuccessContactRegs   OBJECT-TYPE
        SYNTAX          Counter32
        MAX-ACCESS      read-only
        STATUS          current
        DESCRIPTION     "Count of regist successfully."
        ::= { zxAnSipCallPerfTable 2 }

    zxAnSipFailedContactRegs   OBJECT-TYPE
        SYNTAX          Counter32
        MAX-ACCESS      read-only
        STATUS          current
        DESCRIPTION     "Count of regist unsuccessfully."
        ::= { zxAnSipCallPerfTable 3 }

    zxAnSipSuccessIncomingCalls   OBJECT-TYPE
        SYNTAX          Counter32
        MAX-ACCESS      read-only
        STATUS          current
        DESCRIPTION     "Count of the successful session incomming calls."
        ::= { zxAnSipCallPerfTable 4 }
  
    zxAnSipFailedIncomingCalls   OBJECT-TYPE
        SYNTAX          Counter32
        MAX-ACCESS      read-only
        STATUS          current
        DESCRIPTION     "Count of the unsuccessful session incomming calls."
        ::= { zxAnSipCallPerfTable 5 }

    zxAnSipSuccessOutgoingCalls   OBJECT-TYPE
        SYNTAX          Counter32
        MAX-ACCESS      read-only
        STATUS          current
        DESCRIPTION     "Count of the successful session outgoing calls."
        ::= { zxAnSipCallPerfTable 6 }

    zxAnSipFailedOutgoingCalls   OBJECT-TYPE
        SYNTAX          Counter32
        MAX-ACCESS      read-only
        STATUS          current
        DESCRIPTION     "Count of the unsuccessful session outgoing calls."
        ::= { zxAnSipCallPerfTable 7 }
  

    zxAnSipPrev15MinSuccessContactRegs   OBJECT-TYPE
        SYNTAX          Counter32
        MAX-ACCESS      read-only
        STATUS          current
        DESCRIPTION     "Count of regist successfully within the most 
                         recent previous 15-min period."
        ::= { zxAnSipCallPerfTable 8 }

    zxAnSipPrev15MinFailedContactRegs   OBJECT-TYPE
        SYNTAX          Counter32
        MAX-ACCESS      read-only
        STATUS          current
        DESCRIPTION     "Count of regist unsuccessfully within the most 
                         recent previous 15-min period."
        ::= { zxAnSipCallPerfTable 9 }

    zxAnSipPrev15MinSuccessIncomingCalls   OBJECT-TYPE
        SYNTAX          Counter32
        MAX-ACCESS      read-only
        STATUS          current
        DESCRIPTION     "Count of the successful session incomming call within the most 
                         recent previous 15-min period."
        ::= { zxAnSipCallPerfTable 10 }
  
    zxAnSipPrev15MinFailedIncomingCalls   OBJECT-TYPE
        SYNTAX          Counter32
        MAX-ACCESS      read-only
        STATUS          current
        DESCRIPTION     "Count of the unsuccessful session incomming call within the most 
                         recent previous 15-min period."
        ::= { zxAnSipCallPerfTable 11 }  

    zxAnSipPrev15MinSuccessOutgoingCalls   OBJECT-TYPE
        SYNTAX          Counter32
        MAX-ACCESS      read-only
        STATUS          current
        DESCRIPTION     "Count of the successful session outgoing call within the most 
                         recent previous 15-min period."
        ::= { zxAnSipCallPerfTable 12 }

    zxAnSipPrev15MinFailedOutgoingCalls   OBJECT-TYPE
        SYNTAX          Counter32
        MAX-ACCESS      read-only
        STATUS          current
        DESCRIPTION     "Count of the unsuccessful session outgoing call within the most 
                         recent previous 15-min period."
        ::= { zxAnSipCallPerfTable 13 }  

    zxAnSipActiveIncomingCalls   OBJECT-TYPE
        SYNTAX          Counter32
        MAX-ACCESS      read-only
        STATUS          current
        DESCRIPTION     "Current count of the session incomming calls ."
        ::= { zxAnSipCallPerfTable 14 } 

    zxAnSipActiveOutgoingCalls   OBJECT-TYPE
        SYNTAX          Counter32
        MAX-ACCESS      read-only
        STATUS          current
        DESCRIPTION     "Current count of the session outgoing calls."
        ::= { zxAnSipCallPerfTable 15 } 

    zxAnSipOutgoingCallTraffic   OBJECT-TYPE
        SYNTAX          Integer32
        UNITS           "erl"        
        MAX-ACCESS      read-only
        STATUS          current
        DESCRIPTION     "Current traffic of the session outgoing calls."
        ::= { zxAnSipCallPerfTable 16 } 

    zxAnSipIncomingCallTraffic   OBJECT-TYPE
        SYNTAX          Integer32
        UNITS           "erl"        
        MAX-ACCESS      read-only
        STATUS          current
        DESCRIPTION     "Current traffic of the session incoming calls."
        ::= { zxAnSipCallPerfTable 17 } 

    zxAnSipTotalCallTraffic   OBJECT-TYPE
        SYNTAX          Integer32
        UNITS           "erl"
        MAX-ACCESS      read-only
        STATUS          current
        DESCRIPTION     "Current traffic of the total calls."
        ::= { zxAnSipCallPerfTable 18 }

    zxAnSipOutgoingCallKeepingTime   OBJECT-TYPE
        SYNTAX          Counter32
        UNITS           "seconds"        
        MAX-ACCESS      read-only
        STATUS          current
        DESCRIPTION     "Current outgoing call keeping time."
        ::= { zxAnSipCallPerfTable 19 } 

    zxAnSipIncomingCallKeepingTime   OBJECT-TYPE
        SYNTAX          Counter32
        UNITS           "seconds"        
        MAX-ACCESS      read-only
        STATUS          current
        DESCRIPTION     "Current incoming call keeping time."
        ::= { zxAnSipCallPerfTable 20 } 

    zxAnSipTotalCallKeepingTime   OBJECT-TYPE
        SYNTAX          Counter32
        UNITS           "seconds"
        MAX-ACCESS      read-only
        STATUS          current
        DESCRIPTION     "Current total call keeping time."
        ::= { zxAnSipCallPerfTable 21 } 

    zxAnSipOutgoingCallAttempts   OBJECT-TYPE
        SYNTAX          Counter32
        MAX-ACCESS      read-only
        STATUS          current
        DESCRIPTION     "Current count of outgoing call attempts."
        ::= { zxAnSipCallPerfTable 22 } 

    zxAnSipOutgoingCallCompletions   OBJECT-TYPE
        SYNTAX          Counter32
        MAX-ACCESS      read-only
        STATUS          current
        DESCRIPTION     "Current count of outgoing call completions."
        ::= { zxAnSipCallPerfTable 23 } 

    zxAnSipOutgoingCallLosses   OBJECT-TYPE
        SYNTAX          Counter32
        MAX-ACCESS      read-only
        STATUS          current
        DESCRIPTION     "Current count of outgoing call losses."
        ::= { zxAnSipCallPerfTable 24 }
        
    zxAnSipIncomingCallAttempts   OBJECT-TYPE
        SYNTAX          Counter32
        MAX-ACCESS      read-only
        STATUS          current
        DESCRIPTION     "Current count of incoming call attempts."
        ::= { zxAnSipCallPerfTable 25 } 

    zxAnSipIncomingCallCompletions   OBJECT-TYPE
        SYNTAX          Counter32
        MAX-ACCESS      read-only
        STATUS          current
        DESCRIPTION     "Current count of incoming call completions."
        ::= { zxAnSipCallPerfTable 26 } 

    zxAnSipIncomingCallLosses   OBJECT-TYPE
        SYNTAX          Counter32
        MAX-ACCESS      read-only
        STATUS          current
        DESCRIPTION     "Current count of incoming call losses."
        ::= { zxAnSipCallPerfTable 27 }

    zxAnSipOutgoingCallCompleteRatio   OBJECT-TYPE
        SYNTAX          Integer32(0..100)
        UNITS           "percent"
        MAX-ACCESS      read-only
        STATUS          current
        DESCRIPTION     "Current ratio of complete outgoing calls."
        ::= { zxAnSipCallPerfTable 28 } 

    zxAnSipIncomingCallCompleteRatio   OBJECT-TYPE
        SYNTAX          Integer32(0..100)
        UNITS           "percent"
        MAX-ACCESS      read-only
        STATUS          current
        DESCRIPTION     "Current ratio of complete incoming calls."
        ::= { zxAnSipCallPerfTable 29 } 

    zxAnSipTotalCallCompleteRatio   OBJECT-TYPE
        SYNTAX          Integer32(0..100)
        UNITS           "percent"
        MAX-ACCESS      read-only
        STATUS          current
        DESCRIPTION     "Current ratio of total complete calls."
        ::= { zxAnSipCallPerfTable 30 } 
                                
    zxAnSipTotalCallLossRatio   OBJECT-TYPE
        SYNTAX          Integer32(0..100)
        UNITS           "percent"
        MAX-ACCESS      read-only
        STATUS          current
        DESCRIPTION     "Current ratio of call losses."
        ::= { zxAnSipCallPerfTable 31 }
        
--------------------------------------------------------------------------------        
-- 51.zxAnSipHisPerfObjects
--------------------------------------------------------------------------------         

    zxAnSipHisPerfObjects     OBJECT IDENTIFIER ::= { zxAnSipConfig 51 } 

    zxAnSipHisPerfGlobalObjects OBJECT IDENTIFIER 
        ::= { zxAnSipHisPerfObjects 1 }
      
    zxAnSipHisPerfIntervalType   OBJECT-TYPE
        SYNTAX INTEGER {
            fifteenMinutes(1), 
            oneHour(2)
        }
        MAX-ACCESS      read-write
        STATUS          current
        DESCRIPTION     "Sip call history performance monitor interval."
        DEFVAL          { fifteenMinutes }
        ::= { zxAnSipHisPerfGlobalObjects 1 }   

    zxAnSipHisPerfIntervalTable OBJECT-TYPE
        SYNTAX          SEQUENCE  OF  ZxAnSipHisPerfIntervalEntry
        MAX-ACCESS      not-accessible
        STATUS          current
        DESCRIPTION     
            "SIP call interval performance table."
        ::=  { zxAnSipHisPerfObjects 2 }  

    zxAnSipHisPerfIntervalEntry OBJECT-TYPE
        SYNTAX          ZxAnSipHisPerfIntervalEntry
        MAX-ACCESS      not-accessible
        STATUS          current
        DESCRIPTION     
            "SIP call interval performance entry."
        INDEX   { zxAnSipHisPerfIntervalNumber }
        ::=  { zxAnSipHisPerfIntervalTable 1 }
            
    ZxAnSipHisPerfIntervalEntry ::=
        SEQUENCE{    
            zxAnSipHisPerfIntervalNumber        Integer32,
            zxAnSipHisValidData                 TruthValue,  
            zxAnSipHisSuccessContactRegs        Counter32,
            zxAnSipHisFailedContactRegs         Counter32,
            zxAnSipHisSuccessInCalls            Counter32,
            zxAnSipHisFailedInCalls             Counter32,
            zxAnSipHisSuccessOutCalls           Counter32,
            zxAnSipHisFailedOutCalls            Counter32,
            zxAnSipHisOutCallTraffic            Integer32,
            zxAnSipHisInCallTraffic             Integer32,
            zxAnSipHisTotalCallTraffic          Integer32,
            zxAnSipHisOutCallKeepTime           Counter32,          
            zxAnSipHisInCallKeepTime            Counter32,
            zxAnSipHisTotalCallKeepTime         Counter32,   
            zxAnSipHisOutCallAttempts           Counter32,
            zxAnSipHisOutCallCompletions        Counter32,
            zxAnSipHisOutCallLosses             Counter32,
            zxAnSipHisInCallAttempts            Counter32,
            zxAnSipHisInCallCompletions         Counter32,
            zxAnSipHisInCallLosses              Counter32,
            zxAnSipHisOutCallCompleteRatio      Integer32,
            zxAnSipHisInCallCompleteRatio       Integer32,
            zxAnSipHisTotalCallCompleteRatio    Integer32,
            zxAnSipHisTotalCallLossRatio        Integer32
        }
    
    zxAnSipHisPerfIntervalNumber   OBJECT-TYPE
        SYNTAX          Integer32(1)
        MAX-ACCESS      not-accessible
        STATUS          current
        DESCRIPTION     "Sip call history performance monitor interval number."
        ::= { zxAnSipHisPerfIntervalEntry 1 }  

    zxAnSipHisValidData   OBJECT-TYPE
        SYNTAX          TruthValue
        MAX-ACCESS      read-only
        STATUS          current
        DESCRIPTION     "It indicates whether the peformance result is valid."
        ::= { zxAnSipHisPerfIntervalEntry 2 }           
        
    zxAnSipHisSuccessContactRegs   OBJECT-TYPE
        SYNTAX          Counter32
        MAX-ACCESS      read-only
        STATUS          current
        DESCRIPTION     "The interval count of registers successfully."
        ::= { zxAnSipHisPerfIntervalEntry 3 }

    zxAnSipHisFailedContactRegs   OBJECT-TYPE
        SYNTAX          Counter32
        MAX-ACCESS      read-only
        STATUS          current
        DESCRIPTION     "The interval count of registers unsuccessfully."
        ::= { zxAnSipHisPerfIntervalEntry 4 }

    zxAnSipHisSuccessInCalls   OBJECT-TYPE
        SYNTAX          Counter32
        MAX-ACCESS      read-only
        STATUS          current
        DESCRIPTION     "The interval count of the successful session 
                        incomming calls."
        ::= { zxAnSipHisPerfIntervalEntry 5 }
        
    zxAnSipHisFailedInCalls   OBJECT-TYPE
        SYNTAX          Counter32
        MAX-ACCESS      read-only
        STATUS          current
        DESCRIPTION     "The interval count of the unsuccessful session 
                        incomming calls."
        ::= { zxAnSipHisPerfIntervalEntry 6 }     

    zxAnSipHisSuccessOutCalls   OBJECT-TYPE
        SYNTAX          Counter32
        MAX-ACCESS      read-only
        STATUS          current
        DESCRIPTION     "The interval count of the successful session 
                        outgoing calls."
        ::= { zxAnSipHisPerfIntervalEntry 7 }

    zxAnSipHisFailedOutCalls   OBJECT-TYPE
        SYNTAX          Counter32
        MAX-ACCESS      read-only
        STATUS          current
        DESCRIPTION     "The interval count of the unsuccessful session 
                        outgoing calls."
        ::= { zxAnSipHisPerfIntervalEntry 8 } 
 
    zxAnSipHisOutCallTraffic   OBJECT-TYPE
        SYNTAX          Integer32
        UNITS           "erl"
        MAX-ACCESS      read-only
        STATUS          current
        DESCRIPTION     "The interval traffic of the session outgoing calls."
        ::= { zxAnSipHisPerfIntervalEntry 9 } 

    zxAnSipHisInCallTraffic   OBJECT-TYPE
        SYNTAX          Integer32
        UNITS           "erl"
        MAX-ACCESS      read-only
        STATUS          current
        DESCRIPTION     "The interval traffic of the session incoming calls."
        ::= { zxAnSipHisPerfIntervalEntry 10 } 

    zxAnSipHisTotalCallTraffic   OBJECT-TYPE
        SYNTAX          Integer32
        UNITS           "erl"
        MAX-ACCESS      read-only
        STATUS          current
        DESCRIPTION     "The interval traffic of the total calls."
        ::= { zxAnSipHisPerfIntervalEntry 11 } 

    zxAnSipHisOutCallKeepTime   OBJECT-TYPE
        SYNTAX          Counter32
        UNITS           "seconds"
        MAX-ACCESS      read-only
        STATUS          current
        DESCRIPTION     "The interval outgoing call keeping time."
        ::= { zxAnSipHisPerfIntervalEntry 12 } 

    zxAnSipHisInCallKeepTime   OBJECT-TYPE
        SYNTAX          Counter32
        UNITS           "seconds"
        MAX-ACCESS      read-only
        STATUS          current
        DESCRIPTION     "The interval incoming call keeping time."
        ::= { zxAnSipHisPerfIntervalEntry 13 } 

    zxAnSipHisTotalCallKeepTime   OBJECT-TYPE
        SYNTAX          Counter32
        UNITS           "seconds"
        MAX-ACCESS      read-only
        STATUS          current
        DESCRIPTION     "The interval total call keeping time."
        ::= { zxAnSipHisPerfIntervalEntry 14 } 

    zxAnSipHisOutCallAttempts   OBJECT-TYPE
        SYNTAX          Counter32
        MAX-ACCESS      read-only
        STATUS          current
        DESCRIPTION     "The interval count of outgoing call attempts."
        ::= { zxAnSipHisPerfIntervalEntry 15 } 

    zxAnSipHisOutCallCompletions   OBJECT-TYPE
        SYNTAX          Counter32
        MAX-ACCESS      read-only
        STATUS          current
        DESCRIPTION     "The interval count of outgoing call completions."
        ::= { zxAnSipHisPerfIntervalEntry 16 } 

    zxAnSipHisOutCallLosses   OBJECT-TYPE
        SYNTAX          Counter32
        MAX-ACCESS      read-only
        STATUS          current
        DESCRIPTION     "The interval count of outgoing call losses."
        ::= { zxAnSipHisPerfIntervalEntry 17 }

    zxAnSipHisInCallAttempts   OBJECT-TYPE
        SYNTAX          Counter32
        MAX-ACCESS      read-only
        STATUS          current
        DESCRIPTION     "The interval count of incoming call attempts."
        ::= { zxAnSipHisPerfIntervalEntry 18 } 

    zxAnSipHisInCallCompletions   OBJECT-TYPE
        SYNTAX          Counter32
        MAX-ACCESS      read-only
        STATUS          current
        DESCRIPTION     "The interval count of incoming call completions."
        ::= { zxAnSipHisPerfIntervalEntry 19 } 

    zxAnSipHisInCallLosses   OBJECT-TYPE
        SYNTAX          Counter32
        MAX-ACCESS      read-only
        STATUS          current
        DESCRIPTION     "The interval count of incoming call losses."
        ::= { zxAnSipHisPerfIntervalEntry 20 } 

    zxAnSipHisOutCallCompleteRatio   OBJECT-TYPE
        SYNTAX          Integer32(0..100)
        UNITS           "percent"
        MAX-ACCESS      read-only
        STATUS          current
        DESCRIPTION     "The interval ratio of complete outgoing calls."
        ::= { zxAnSipHisPerfIntervalEntry 21 } 

    zxAnSipHisInCallCompleteRatio   OBJECT-TYPE
        SYNTAX          Integer32(0..100)
        UNITS           "percent"
        MAX-ACCESS      read-only
        STATUS          current
        DESCRIPTION     "The interval ratio of complete incoming calls."
        ::= { zxAnSipHisPerfIntervalEntry 22 } 

    zxAnSipHisTotalCallCompleteRatio   OBJECT-TYPE
        SYNTAX          Integer32(0..100)
        UNITS           "percent"
        MAX-ACCESS      read-only
        STATUS          current
        DESCRIPTION     "The interval ratio of total complete calls."
        ::= { zxAnSipHisPerfIntervalEntry 23 } 
                                
    zxAnSipHisTotalCallLossRatio   OBJECT-TYPE
        SYNTAX          Integer32(0..100)
        UNITS           "percent"
        MAX-ACCESS      read-only
        STATUS          current
        DESCRIPTION     "The interval ratio of call losses."
        ::= { zxAnSipHisPerfIntervalEntry 24 }

        

--------------------------------------------------------------------------------
-- SIP Trap
--------------------------------------------------------------------------------
    
    zxAnSipTrapObjects  OBJECT IDENTIFIER  ::= { zxAnSipTrap 1} 
    zxAnSipLinkDown  NOTIFICATION-TYPE
        OBJECTS {zxAnSipTrapReason,zxAnSipTrapMgcNo }
        STATUS  current
        DESCRIPTION
            "Sip linkdown."
        ::= { zxAnSipTrapObjects 1 }
    
    zxAnSipLinkUp NOTIFICATION-TYPE
        OBJECTS {zxAnSipTrapReason,zxAnSipTrapMgcNo }
        STATUS  current
        DESCRIPTION
            "Sip linkup."
        ::= { zxAnSipTrapObjects 2 } 
        
    zxAnSipUserRegisterFailedAlm  NOTIFICATION-TYPE
        OBJECTS 
        {  
            zxMsagSipUserAuthusername,
            zxMsagSipUserId
        }
        STATUS  current
        DESCRIPTION
            "A zxAnSipUserRegisterFailedAlm trap is sent when SIP user register
             failed."
        ::= { zxAnSipTrapObjects 3 }

    zxAnSipUserRegisterFailedClr  NOTIFICATION-TYPE
        OBJECTS 
        {
            zxMsagSipUserAuthusername,
            zxMsagSipUserId
        }
        STATUS  current
        DESCRIPTION
            "A zxAnSipUserRegisterFailedClr trap is sent when
             SIP user registered successfully."
        ::= { zxAnSipTrapObjects 4 } 
 
    zxAnSipTrapBindVar OBJECT IDENTIFIER  ::= { zxAnSipTrap 2} 
    zxAnSipTrapReason OBJECT-TYPE
        SYNTAX      Integer32
        MAX-ACCESS  read-only
        STATUS      current
        DESCRIPTION
            "reason"
        ::= {zxAnSipTrapBindVar 1}
        
    zxAnSipTrapMgcNo OBJECT-TYPE
        SYNTAX      Integer32
        MAX-ACCESS  read-only
        STATUS      current
        DESCRIPTION
            "MgcNo"
        ::= {zxAnSipTrapBindVar 2}

END

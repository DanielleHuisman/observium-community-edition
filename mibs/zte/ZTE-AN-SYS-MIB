--------------------------------------------------------------------------
-- File Name : ZTE-AN-SYS-MIB.mib
-- Date      : 2006-09-26
-- Author    : ZTE Nms dept.

--
-- Zte System Mgmt Mib for Access Node
-- 
-- 
--------------------------------------------------------------------------


ZTE-AN-SYS-MIB DEFINITIONS ::= BEGIN

    IMPORTS
        MODULE-IDENTITY, OBJECT-TYPE, Integer32, Unsigned32,
        IpAddress, NOTIFICATION-TYPE
                                                    FROM SNMPv2-SMI
        MacAddress,RowStatus,DisplayString,RowStatus,
        TEXTUAL-CONVENTION, TruthValue,MacAddress   FROM SNMPv2-TC        
        InetAddressType, InetAddress ,
        InetAddressPrefixLength                     FROM INET-ADDRESS-MIB  -- [RFC4001] 
        zxAn,ZxAnIfindex                            FROM ZTE-AN-TC-MIB;


    zxAnSysMib MODULE-IDENTITY
        LAST-UPDATED    "200706070840Z"
        ORGANIZATION "ZTE Corporation"
        CONTACT-INFO "ZTE NMS dept. 
                      Su Chunshan   68896292,
                      Zeng Nanxi    68896250 "
        DESCRIPTION  "This MIB defines managed objects of zte system mgmt."
         ::= {zxAn 1}
         

    zxAnSysObjects     OBJECT IDENTIFIER  ::=  { zxAnSysMib 1 }
    zxAnSysTrapObjects OBJECT IDENTIFIER  ::=  { zxAnSysMib 2 }
    
    zxAnSysNmsMgmt     OBJECT IDENTIFIER  ::=  { zxAnSysObjects 100 }
    zxAnSysTimeMgmt    OBJECT IDENTIFIER  ::=  { zxAnSysObjects 101 }
         
    zxAnSysSnmpOperSyslogMgmt    OBJECT IDENTIFIER  ::=  { zxAnSysObjects 102 }
    
    zxAnLog   OBJECT IDENTIFIER   ::= {  zxAnSysObjects  103  }   
    
--------------------------------------------------------------------------------
-- Following objects are defined.
-- 1.System Host Name
-- 2.Error Code for SnmpSet Operation
-- 3.Security Configuration
-- 4.Save Configuration to Flash Media
-- 5.System Running Control
-- 6.NMS Management  
-- 7.Config Time and Zone
-- 8.NTP Configuration
-- 9.PTP Configuration
-- 10.Snmp Operation Syslog Management
-- 11.Sytem Mgmt Trap
-- 12.Log Management
-- 13.Clock Management
-- 14.IPv6 Global Management
-- 15.DNS Management
-- 16.Outband Port Management
-- 17.SNMP Management
-- 18.Profile Operation Management
-- 19.System ARP Management
-- 20.System SSH Management
--------------------------------------------------------------------------------





--------------------------------------------------------------------------------
-- 1.System Host Name
--------------------------------------------------------------------------------
--    zxAnSysHostName   OBJECT-TYPE     
--       SYNTAX      DisplayString  ( SIZE ( 1 .. 64  ) )
--       MAX-ACCESS  read-write
--       STATUS      current
--       DESCRIPTION 
--              "NE host name.It is same as sysName in MIB-II." 
--       ::=  {  zxAnSysObjects  1  }
    


--------------------------------------------------------------------------------
-- 2.Error Code for SnmpSet Operation
--------------------------------------------------------------------------------
    zxAnSnmpSetCmdErrCode   OBJECT-TYPE     
       SYNTAX      Integer32
       MAX-ACCESS  read-only
       STATUS      current
       DESCRIPTION 
              "Error code for SNMP set command.When agent excutes a snmp set,
          this variable should be maintained.Value 0 means success.
          " 
       DEFVAL { 0 }              
       ::=  {  zxAnSysObjects  2  }
    


--------------------------------------------------------------------------------
-- 3.Security Configuration
--------------------------------------------------------------------------------
    zxAnSysSecMgmt    OBJECT IDENTIFIER  ::=  { zxAnSysObjects 3 }

    zxAnCliCrftTerminalEnable OBJECT-TYPE 
       SYNTAX             INTEGER  
          { 
              enable  ( 1 ), 
              disable ( 2 ) 
          } 
       MAX-ACCESS       read-write
       STATUS           current
       DESCRIPTION      "Enable/disable craft terminal interface.

            NOTE: 
                It is ONLY used to RS-232 serial command interface and out-band 
            CLI,DON'T apply it to in-band telnet command interface."

       DEFVAL { enable }
       ::=  {  zxAnSysSecMgmt  1  }
       

    zxAnCliSecurityLevel OBJECT-TYPE 
       SYNTAX             INTEGER  
          { 
              guest  (1), -- read only and ordinary informatin only
              administrator (2) -- read and write advanced informatin
          } 
       MAX-ACCESS       read-write
       STATUS           current
       DESCRIPTION      "Security level of CLI."
       DEFVAL { administrator }
       ::=  {  zxAnSysSecMgmt  2  }
       

    zxAnCliCrftTerminalLoginStatus OBJECT-TYPE 
       SYNTAX             INTEGER  
          { 
              logon  ( 1 ), 
              logout ( 2 ) 
          } 
       MAX-ACCESS       read-only
       STATUS           current
       DESCRIPTION      "The using status of the craft terminal interface."
       ::=  {  zxAnSysSecMgmt  3  }
       

    zxAnCliCrftTerminalLastLoginType OBJECT-TYPE 
       SYNTAX        INTEGER  
          { 
              rs232SerialInterface( 1 ), 
              outbandMgmtInterface( 2 ),
              inbandMgmtInterface( 3 ) 
          } 
       MAX-ACCESS       read-only
       STATUS           current
       DESCRIPTION      "The type of the craft terminal interface lastest logon.
                        "
       ::=  {  zxAnSysSecMgmt  4  }

    zxAnCliPromptName OBJECT-TYPE 
       SYNTAX           DisplayString  (SIZE ( 1 .. 16 ))
       MAX-ACCESS       read-write
       STATUS           current
       DESCRIPTION      "The prompt name of CLI."
       ::=  {  zxAnSysSecMgmt  5  }

    zxAnCliSuperUserName OBJECT-TYPE 
       SYNTAX           DisplayString(SIZE ( 1 .. 16 ))
       MAX-ACCESS       read-only
       STATUS           current
       DESCRIPTION      "The super user name of CLI."
       ::=  {  zxAnSysSecMgmt  6  }

    zxAnCliSuperUserPwd OBJECT-TYPE 
       SYNTAX           DisplayString(SIZE( 1 .. 16 ))
       MAX-ACCESS       read-only
       STATUS           current
       DESCRIPTION      "The super user password of CLI."
       ::=  {  zxAnSysSecMgmt  7  }       
        
    zxAnCliTelnetEnable OBJECT-TYPE
        SYNTAX  INTEGER 
            {
                enable(1),
                disable(2)
            } 
        MAX-ACCESS  read-write
        STATUS      current
        DESCRIPTION     
            "Enable or disable in-band and out-band Telnet."
        DEFVAL   {  enable  }
        ::= { zxAnSysSecMgmt 8 }
        
    zxAnCliUserSuspendMode OBJECT-TYPE
        SYNTAX  INTEGER 
            {
                notSuspend(1),
                byIp(2),
                byUserName(3),
                byIpOrUserName(4)
            } 
        MAX-ACCESS  read-write
        STATUS      current
        DESCRIPTION     
            "CLI user suspending mode.
             
             notSuspend(1)     -- Never suspend user.
             byIp(2)           -- Suspend user by IP address.
             byUserName(3)     -- Suspend user by name.
             byIpOrUserName(4)-- Suspend user by both IP address or name.
            "
        DEFVAL   {  notSuspend  }
        ::= { zxAnSysSecMgmt 9 }
    
    zxAnCliUserSuspendDuration OBJECT-TYPE
        SYNTAX      Integer32(30..1440)
        UNITS       "minutes"
        MAX-ACCESS  read-write
        STATUS      current
        DESCRIPTION     
            "CLI user suspending time."
        DEFVAL   {  30  }
        ::= { zxAnSysSecMgmt 10 }
        
    zxAnCliUserPasswordRetries OBJECT-TYPE
        SYNTAX      Integer32(1..10)
        MAX-ACCESS  read-write
        STATUS      current
        DESCRIPTION     
            "CLI user password retry times."
        DEFVAL   {  3  }
        ::= { zxAnSysSecMgmt 11 }
    
    zxAnCliTryToLoginUserName OBJECT-TYPE 
        SYNTAX      DisplayString  (SIZE ( 0 .. 32 ))
        MAX-ACCESS  accessible-for-notify
        STATUS      current
        DESCRIPTION 
            "The try to login user name."
        ::= { zxAnSysSecMgmt 12 }
        
    zxAnCliTryToLoginUserLocation OBJECT-TYPE 
        SYNTAX      DisplayString  (SIZE ( 0 .. 40 ))
        MAX-ACCESS  accessible-for-notify
        STATUS      current
        DESCRIPTION 
            "If the user's type is console,the object's value is empty string.
             If the user's type is telnet, the object's value is the try to 
             login IP address. "
        ::= { zxAnSysSecMgmt 13 }
        
    zxAnCliMultiSessionsInformEnable OBJECT-TYPE
        SYNTAX           INTEGER 
        {
            enabled(1),
            disabled(2)
        } 
        MAX-ACCESS       read-write
        STATUS           current
        DESCRIPTION     
            "This object indicates whether the information is informed to other
             active sessions when login failed.
            "
        DEFVAL   {  disabled  }
        ::= { zxAnSysSecMgmt 14 }
        
--------------------------------------------------------------------------------
-- 20.System SSH Management
--------------------------------------------------------------------------------
    
    zxAnSysSshObjects        OBJECT IDENTIFIER ::=  { zxAnSysSecMgmt 47 }
        
    zxAnSysSshGlobalObjects  OBJECT IDENTIFIER    
        ::=  {  zxAnSysSshObjects  1  }
    
    zxAnSysSshEnable OBJECT-TYPE
        SYNTAX  INTEGER
        {
            enabled(1), 
            disabled(2)
        } 
        MAX-ACCESS  read-write
        STATUS      current
        DESCRIPTION
            "Enable or disable the SSH service."
        DEFVAL { disabled }
        ::= { zxAnSysSshGlobalObjects 2 }
        
    zxAnSysSshVersion OBJECT-TYPE
        SYNTAX  INTEGER
        {
            v1(1),
            v2(2)
        } 
        MAX-ACCESS  read-write
        STATUS      current
        DESCRIPTION
            "SSH version."
        DEFVAL { v2 }
        ::= { zxAnSysSshGlobalObjects 3 }
        
    zxAnSysSshOnlyEnable OBJECT-TYPE
        SYNTAX  INTEGER
        {
            enabled(1), 
            disabled(2)
        } 
        MAX-ACCESS  read-write
        STATUS      current
        DESCRIPTION
            "Only SSH server activated, more details are given as following:
            The value enabled(1) indicates the device is only accessible 
            via SSH. The value disabled(2) indicates there is no limitation 
            with accessible type, in another word, the device is not only 
            accessible via SSH but also other ways e.g. TELNET etc."
        DEFVAL { disabled }
        ::= { zxAnSysSshGlobalObjects 4 }
        
    zxAnSysSshGenerateKeyEnable OBJECT-TYPE
        SYNTAX  INTEGER
        {
            enabled(1), 
            disabled(2)
        } 
        MAX-ACCESS  read-write
        STATUS      current
        DESCRIPTION
            "Generate SSH key only in case of SSH version 1 selected."
        DEFVAL { disabled }
        ::= { zxAnSysSshGlobalObjects 5 }
        
    zxAnSysSshAuthType OBJECT-TYPE
        SYNTAX  INTEGER
        {
            pap(1), 
            chap(2)
        } 
        MAX-ACCESS  read-write
        STATUS      current
        DESCRIPTION
            "SSH authentication type."
        DEFVAL { chap }
        ::= { zxAnSysSshGlobalObjects 6 }

-- Write Lock Management

    zxAnSysWriteLockObjects   OBJECT IDENTIFIER  ::=  { zxAnSysSecMgmt 48 }

    zxAnSysWriteLockOwner OBJECT-TYPE
        SYNTAX  INTEGER {
            none(1),
            snmp(2),
            console(3),
            telnet(4)
            } 
        MAX-ACCESS  read-only
        STATUS      current
        DESCRIPTION     
            "The write lock owner."
        ::= { zxAnSysWriteLockObjects 1 } 
        
    zxAnSysWriteLockAction OBJECT-TYPE
        SYNTAX  INTEGER {
            lock(1),
            unlock(2)
            }
        MAX-ACCESS  read-write
        STATUS      current
        DESCRIPTION
            "Lock or unlock the write right.
            When it is set to lock(1),only SNMP manager has write lock."
        DEFVAL      { unlock }
        ::= { zxAnSysWriteLockObjects 2 }

 -- Management Cli User Table
    
    zxAnSysCliUserTable  OBJECT-TYPE
        SYNTAX      SEQUENCE OF ZxAnSysCliUserEntry
        MAX-ACCESS  not-accessible
        STATUS      current
        DESCRIPTION
            "A table contain user information for web and console and telnet."
        ::= { zxAnSysSecMgmt 49 }

    zxAnSysCliUserEntry  OBJECT-TYPE
        SYNTAX      ZxAnSysCliUserEntry
        MAX-ACCESS  not-accessible
        STATUS      current
        DESCRIPTION
            "A list of user information."
        INDEX  { zxAnCliUserConfIndex }
        ::= { zxAnSysCliUserTable 1 }

    ZxAnSysCliUserEntry  ::= SEQUENCE {
        zxAnCliUserConfIndex             Integer32,
        zxAnCliUserConfName              DisplayString,
        zxAnCliUserConfPwd               DisplayString,
        zxAnCliUserConfAccessLevel       Integer32,
        zxAnCliUserConfRowStatus         RowStatus,
        zxAnCliUserConfPwdEncryptEnable  INTEGER,
        zxAnCliUserConfMaxSessions       Integer32, 
        zxAnCliUserConfAdminStatus       INTEGER,
        zxAnCliUserConfOperStatus        INTEGER
        }

    zxAnCliUserConfIndex  OBJECT-TYPE 
        SYNTAX      Integer32  
        MAX-ACCESS  not-accessible
        STATUS      current
        DESCRIPTION
            "A simple index ."
        ::= { zxAnSysCliUserEntry 1 }

    zxAnCliUserConfName  OBJECT-TYPE 
        SYNTAX      DisplayString(SIZE(1..16)) 
        MAX-ACCESS  read-create
        STATUS      current
        DESCRIPTION
            "The telnet or console user name."
        ::= { zxAnSysCliUserEntry 2 }

    zxAnCliUserConfPwd  OBJECT-TYPE 
        SYNTAX      DisplayString(SIZE(3..32)) 
        MAX-ACCESS  read-create
        STATUS      current
        DESCRIPTION
            "The telnet or console user password."
        ::= { zxAnSysCliUserEntry 3 }

    zxAnCliUserConfAccessLevel  OBJECT-TYPE 
        SYNTAX      Integer32(0..15) 
        MAX-ACCESS  read-create
        STATUS      current
        DESCRIPTION
            "The user access level.
             0-4: Common user.
             5-9: Operator.
             10-14: Administrator.
             15: Supervisor."
        ::= { zxAnSysCliUserEntry 4 }

    zxAnCliUserConfRowStatus  OBJECT-TYPE 
        SYNTAX      RowStatus
        MAX-ACCESS  read-create
        STATUS      current
        DESCRIPTION
            "The user state in this row."
        ::= { zxAnSysCliUserEntry 5 }

    zxAnCliUserConfPwdEncryptEnable  OBJECT-TYPE 
        SYNTAX      INTEGER
        {
            noEncrypt(1),
            encrypt(2)
        }        
        MAX-ACCESS  read-create
        STATUS      current
        DESCRIPTION
            "This MIB is defined for password mode"
        ::= { zxAnSysCliUserEntry 6 }

    zxAnCliUserConfMaxSessions  OBJECT-TYPE 
        SYNTAX      Integer32(1..4)
        MAX-ACCESS  read-create
        STATUS      current
        DESCRIPTION
            "CLI user maximum login sessions"
        DEFVAL  { 4 }
        ::= { zxAnSysCliUserEntry 7 }

    zxAnCliUserConfAdminStatus  OBJECT-TYPE 
        SYNTAX      INTEGER
        {
            enable(1),
            disable(2)
        }
        MAX-ACCESS  read-create
        STATUS      current
        DESCRIPTION
            "This MIB is set CLI user status"
        ::= { zxAnSysCliUserEntry 8 }

    zxAnCliUserConfOperStatus  OBJECT-TYPE 
        SYNTAX      INTEGER
        {
            normal(1),
            suspended(2),
            disabled(3)
        }        
        MAX-ACCESS  read-only
        STATUS      current
        DESCRIPTION
            "CLI user operational status."
        ::= { zxAnSysCliUserEntry 9 }

    -- Management ACL Table
    zxAnSysMgmtAclTable  OBJECT-TYPE
        SYNTAX      SEQUENCE OF ZxAnSysMgmtAclEntry
        MAX-ACCESS  not-accessible
        STATUS      current
        DESCRIPTION
            ""
        ::= { zxAnSysSecMgmt 50 }

    zxAnSysMgmtAclEntry  OBJECT-TYPE
        SYNTAX      ZxAnSysMgmtAclEntry
        MAX-ACCESS  not-accessible
        STATUS      current
        DESCRIPTION
            ""
        INDEX  { zxAnSysMgmtAclIndex }
        ::= { zxAnSysMgmtAclTable 1 }
        
    ZxAnSysMgmtAclEntry ::= SEQUENCE {
        zxAnSysMgmtAclIndex       INTEGER,
        zxAnSysMgmtAclAlias       DisplayString,        
        zxAnSysMgmtAclRowStatus   RowStatus
    }
    
    zxAnSysMgmtAclIndex  OBJECT-TYPE
        SYNTAX      INTEGER(1..99)
        MAX-ACCESS  not-accessible
        STATUS      current
        DESCRIPTION
            "The index of a management ACL."
        ::= { zxAnSysMgmtAclEntry 1 }
    
    zxAnSysMgmtAclAlias  OBJECT-TYPE
        SYNTAX      DisplayString(SIZE(1..32))
        MAX-ACCESS  read-create
        STATUS      current
        DESCRIPTION
            "The alias of a management ACL."
        ::= { zxAnSysMgmtAclEntry 2 }
        
    zxAnSysMgmtAclRowStatus  OBJECT-TYPE
        SYNTAX      RowStatus 
        MAX-ACCESS  read-create
        STATUS      current
        DESCRIPTION
            "This entry's row status."
        ::= { zxAnSysMgmtAclEntry 30 }

    -- Management ACL Rule Table

    zxAnSysMgmtAclRuleTable  OBJECT-TYPE
        SYNTAX  SEQUENCE OF ZxAnSysMgmtAclRuleEntry
        MAX-ACCESS  not-accessible
        STATUS  current
        DESCRIPTION
            ""
        ::= { zxAnSysSecMgmt 51 }
                 
    zxAnSysMgmtAclRuleEntry  OBJECT-TYPE
        SYNTAX  ZxAnSysMgmtAclRuleEntry
        MAX-ACCESS  not-accessible
        STATUS  current
        DESCRIPTION
            ""
        INDEX  { zxAnSysMgmtAclIndex,
                 zxAnSysMgmtAclRuleID }
        ::= { zxAnSysMgmtAclRuleTable 1 }
        
    ZxAnSysMgmtAclRuleEntry ::= SEQUENCE {
        zxAnSysMgmtAclRuleID                  INTEGER,        
        zxAnSysMgmtAclRuleAccessCtrl          INTEGER,
        zxAnSysMgmtAclRuleSrcAddrType         InetAddressType,
        zxAnSysMgmtAclRuleSrcAddr             InetAddress,
        zxAnSysMngAclRuleSrcAddrWildcard     InetAddress,
        zxAnSysMgmtAclRuleRowStatus           RowStatus
    }
    
    zxAnSysMgmtAclRuleID  OBJECT-TYPE
        SYNTAX      INTEGER(1..127)
        MAX-ACCESS  not-accessible
        STATUS      current
        DESCRIPTION
            ""
        ::= { zxAnSysMgmtAclRuleEntry 1 }    
        
    zxAnSysMgmtAclRuleAccessCtrl  OBJECT-TYPE
        SYNTAX      INTEGER{permit(1),deny(2)}
        MAX-ACCESS  read-create
        STATUS      current
        DESCRIPTION
            ""
        ::= { zxAnSysMgmtAclRuleEntry 2 }  
    
    zxAnSysMgmtAclRuleSrcAddrType  OBJECT-TYPE
        SYNTAX      InetAddressType
        MAX-ACCESS  read-create
        STATUS      current
        DESCRIPTION
            "Source address type."
        DEFVAL { ipv4 }  
        ::= { zxAnSysMgmtAclRuleEntry 3 }  
        
    zxAnSysMgmtAclRuleSrcAddr  OBJECT-TYPE
        SYNTAX      InetAddress
        MAX-ACCESS  read-create
        STATUS      current
        DESCRIPTION
            ""
        ::= { zxAnSysMgmtAclRuleEntry 4 }  
        
    zxAnSysMngAclRuleSrcAddrWildcard  OBJECT-TYPE
        SYNTAX      InetAddress
        MAX-ACCESS  read-create
        STATUS      current
        DESCRIPTION
            ""
        ::= { zxAnSysMgmtAclRuleEntry 5 }  
        
    zxAnSysMgmtAclRuleRowStatus  OBJECT-TYPE
        SYNTAX       RowStatus 
        MAX-ACCESS   read-create
        STATUS       current
        DESCRIPTION
            "This entry's row status."
        ::= { zxAnSysMgmtAclRuleEntry 50 }   
    
    -- Management ACL Bind Table

    zxAnSysMgmtAclBindTable  OBJECT-TYPE
        SYNTAX  SEQUENCE OF ZxAnSysMgmtAclBindEntry
        MAX-ACCESS  not-accessible
        STATUS  current
        DESCRIPTION
            ""
        ::= { zxAnSysSecMgmt 52 }
                 
    zxAnSysMgmtAclBindEntry  OBJECT-TYPE
        SYNTAX  ZxAnSysMgmtAclBindEntry
        MAX-ACCESS  not-accessible
        STATUS  current
        DESCRIPTION
            ""
        INDEX  { zxAnSysMgmtAclProtocol }
        ::= { zxAnSysMgmtAclBindTable 1 }
        
    ZxAnSysMgmtAclBindEntry ::= SEQUENCE {
        zxAnSysMgmtAclProtocol        INTEGER,        
        zxAnSysMgmtAclBindIndex       INTEGER
    }
    
    zxAnSysMgmtAclProtocol  OBJECT-TYPE
        SYNTAX      INTEGER 
          {
           telnet (1),
           snmp (2)
          }
        MAX-ACCESS  not-accessible
        STATUS      current
        DESCRIPTION
            "Protocol type."
        ::= { zxAnSysMgmtAclBindEntry 1 }   
    
    zxAnSysMgmtAclBindIndex  OBJECT-TYPE
        SYNTAX      INTEGER(1..99)
        MAX-ACCESS  read-create
        STATUS      current
        DESCRIPTION
            "Index of management ACL bind to this protocol."
        ::= { zxAnSysMgmtAclBindEntry 2 }   

    zxAnSysCliActiveUsersTable  OBJECT-TYPE
        SYNTAX      SEQUENCE OF ZxAnSysCliActiveUsersEntry
        MAX-ACCESS  not-accessible
        STATUS      current
        DESCRIPTION
            "CLI active user table."
        ::= { zxAnSysSecMgmt 53 }

    zxAnSysCliActiveUsersEntry  OBJECT-TYPE
        SYNTAX      ZxAnSysCliActiveUsersEntry
        MAX-ACCESS  not-accessible
        STATUS      current
        DESCRIPTION
            "An entry of zxAnSysCliActiveUsersTable."
        INDEX  { zxAnCliActiveUserIndex }
        ::= { zxAnSysCliActiveUsersTable 1 }

    ZxAnSysCliActiveUsersEntry  ::=  SEQUENCE {
        zxAnCliActiveUserIndex      Integer32,
        zxAnCliActiveUserType       INTEGER,
        zxAnCliActiveUserName       DisplayString,
        zxAnCliActiveUserPriority   INTEGER,
        zxAnCliActiveUserHost       DisplayString,
        zxAnCliActiveUserIdleTime   DisplayString,
        zxAnCliActiveUserLocation   DisplayString,
        zxAnSysCliActiveUserRowStatus  RowStatus
        }

    zxAnCliActiveUserIndex  OBJECT-TYPE 
        SYNTAX      Integer32  
        MAX-ACCESS  not-accessible
        STATUS      current
        DESCRIPTION
            "A simple index ."
        ::= { zxAnSysCliActiveUsersEntry 1 }

    zxAnCliActiveUserType  OBJECT-TYPE 
        SYNTAX      INTEGER  
        {
            con(1),
            vty(2)
        }
        MAX-ACCESS  read-only
        STATUS      current
        DESCRIPTION
            "Current CLI Active User Type."
        ::= { zxAnSysCliActiveUsersEntry 2 } 

    zxAnCliActiveUserName  OBJECT-TYPE 
        SYNTAX      DisplayString(SIZE(1..16))
        MAX-ACCESS  read-only
        STATUS      current
        DESCRIPTION
            "Current CLI active user name."
        ::= { zxAnSysCliActiveUsersEntry 3 }

    zxAnCliActiveUserPriority  OBJECT-TYPE 
        SYNTAX      INTEGER(0..15)
        MAX-ACCESS  read-only
        STATUS      current
        DESCRIPTION
            "Current CLI active user priority.
             0-4: Common user.
             5-9: Operator.
             10-14: Administrator.
             15: Supervisor."
        ::= { zxAnSysCliActiveUsersEntry 4 } 

    zxAnCliActiveUserHost  OBJECT-TYPE 
        SYNTAX      DisplayString(SIZE(1..40))  
        MAX-ACCESS  read-only
        STATUS      current
        DESCRIPTION
            "Current CLI active user host."
        ::= { zxAnSysCliActiveUsersEntry 5 } 

    zxAnCliActiveUserIdleTime  OBJECT-TYPE 
        SYNTAX      DisplayString(SIZE(1..32))  
        MAX-ACCESS  read-only
        STATUS      current
        DESCRIPTION
            "Current CLI active user idel time, it's format like: HH:MM:SS"
        ::= { zxAnSysCliActiveUsersEntry 6 }

    zxAnCliActiveUserLocation  OBJECT-TYPE 
        SYNTAX      DisplayString(SIZE(1..40))
        MAX-ACCESS  read-only
        STATUS      current
        DESCRIPTION
            "Current CLI active user location."
        ::= { zxAnSysCliActiveUsersEntry 7 }

    zxAnSysCliActiveUserRowStatus  OBJECT-TYPE
        SYNTAX       RowStatus 
        MAX-ACCESS   read-create
        STATUS       current
        DESCRIPTION
            "This entry's row status."
        ::= { zxAnSysCliActiveUsersEntry 31 }                                                     
        
    zxAnSysCommunityConfTable OBJECT-TYPE
        SYNTAX SEQUENCE OF ZxAnSysCommunityConfEntry
        MAX-ACCESS not-accessible
        STATUS current
        DESCRIPTION
            "A table of SNMPv1/v2c community string configuration."
        ::= { zxAnSysSecMgmt 54 }

    zxAnSysCommunityConfEntry OBJECT-TYPE
        SYNTAX ZxAnSysCommunityConfEntry
        MAX-ACCESS not-accessible
        STATUS current
        DESCRIPTION
            "A list of community strings."
        INDEX { zxAnSysCommunityConfCommunity }
        ::= { zxAnSysCommunityConfTable 1 }

    ZxAnSysCommunityConfEntry ::= SEQUENCE {
        zxAnSysCommunityConfCommunity     DisplayString,
        zxAnSysCommunityConfPermission    INTEGER,
        zxAnSysCommunityConfViewName      DisplayString,
        zxAnSysCommunityConfRowStatus     RowStatus
    }

    zxAnSysCommunityConfCommunity  OBJECT-TYPE
        SYNTAX DisplayString (SIZE(1..32))
        MAX-ACCESS not-accessible
        STATUS current
        DESCRIPTION
            "DURABLE: { 'public','':all }
             The SNMPv1/v2c community name string.  
             Name must begin with alphabetic character or '_' and '@' shouldn't
             be used in community string.
             Duplicate community names are not allowed in this table. 
             Note that a null string is not a valid community name 
             (i.e., a null string forces 'zxAnSysCommunityConfRowStatus' 
             to 'notReady(3)')."
        ::= { zxAnSysCommunityConfEntry 1 }

    zxAnSysCommunityConfPermission OBJECT-TYPE
        SYNTAX INTEGER {
               readOnly(1),
               readWrite(2)
        }
        MAX-ACCESS read-create
        STATUS current
        DESCRIPTION
            "DURABLE: { readWrite:all }
             This object specifies the type of access allowed. 'readOnly(1)'
             allows GET operations (i.e., GET, GET-NEXT, GET-BULK) and
             'readWrite(2)' allows both GET and SET operations."
        DEFVAL { readOnly }
        ::= { zxAnSysCommunityConfEntry 2 }

    zxAnSysCommunityConfViewName  OBJECT-TYPE
        SYNTAX DisplayString (SIZE(1..32))
        MAX-ACCESS read-create
        STATUS current
        DESCRIPTION
            "This object is reserved now.
             DURABLE: { 'internet':all }
             At runtime (i.e., not when this object is SET), this view name
             is compared to the 'vacmViewTreeFamilyViewName' in the
             'vacmViewTreeFamilyTable' (see RFC2575).  If a match is
             found and the varbind(s) specify valid object type and instance,
             the 'zxAnSysCommunityConfPermission' privilege is permitted.
             Note that a null string is not a valid view name value.
             Also note that the value of this object does not have to match
             an existing entry in the 'vacmViewTreeFamilyTable' (if no match,
             no access is allowed).
             Note that the factory default value for this object is 'allView' 
             (Equivalent to  'internet'),
             which allows access to the subtree under '1.3.6.1'."
        DEFVAL { "allView" }
        ::= { zxAnSysCommunityConfEntry 3 }
        
    zxAnSysCommunityConfRowStatus OBJECT-TYPE
        SYNTAX  RowStatus
        MAX-ACCESS  read-create
        STATUS  current
        DESCRIPTION
            "DURABLE:
             This object indicates the status of this entry.  A row in this
             table can be created using the 'createAndGo(4)' (i.e., all
             parameters must be valid - supplied in a single SNMP PDU or have
             default values).
             Any object in a conceptual row can be modified independent of the
             value of this object (e.g., can be changed while 'active(1)')."
        ::= { zxAnSysCommunityConfEntry 15 }                                                     
                
--------------------------------------------------------------------------------
-- 4.Save Configuration to Flash Media
--------------------------------------------------------------------------------
    
    zxAnSysDataMgmt    OBJECT IDENTIFIER  ::=  { zxAnSysObjects 4 }

    zxAnSysConfigSavingAction  OBJECT-TYPE     
       SYNTAX      INTEGER
            {
                saveFlash(1)
            }
       MAX-ACCESS  read-write
       STATUS      current
       DESCRIPTION 
              "Save device configuration data to flash media.The file saving
              configuration is startup.dat." 
       ::=  {  zxAnSysDataMgmt  1  }

    zxAnSysConfigSaveStatus OBJECT-TYPE 
       SYNTAX           INTEGER  
          { 
              success ( 1 ), 
              failed  ( 2 ), 
              saving  ( 3 ), 
              noOperation( 4 ) 
          } 
       MAX-ACCESS       read-only
       STATUS           current
       DESCRIPTION      "The status of save flash operation. "
       ::=  {  zxAnSysDataMgmt  2  }
       
    zxAnSysAutoSaveFlashMode   OBJECT-TYPE     
        SYNTAX      INTEGER
        {
            disable ( 1 ) ,
            everyday ( 2 ) , 
            interval ( 3 ) ,
            configChanged ( 4 )
        }      
        MAX-ACCESS  read-write
        STATUS      current
        DESCRIPTION 
            "Automatic save flash mode."
        DEFVAL      { disable }            
        ::=  { zxAnSysDataMgmt 3 } 
  
    zxAnSysDailyAutoSaveFlashTime   OBJECT-TYPE     
        SYNTAX      DisplayString( SIZE(1..9))
        MAX-ACCESS  read-write
        STATUS      current
        DESCRIPTION 
            "The time to auto save flash every day.
            for example:HH:MM:SS.(02:22:33).
            This variable is valid if zxAnSysAutoSaveFlashMode set to everyday(2)." 
        ::=  { zxAnSysDataMgmt 4 }      
               
    zxAnSysAutoSaveFlashStartDate   OBJECT-TYPE     
        SYNTAX      DisplayString( SIZE(1..20))
        MAX-ACCESS  read-write
        STATUS      current
        DESCRIPTION 
            "The start datetime to auto save flash.            
            for example:yyyy-mm-dd HH:MM:SS.(2001-01-01 02:22:33).
            This variable is valid if zxAnSysAutoSaveFlashMode set to interval(3)." 
        ::=  { zxAnSysDataMgmt 5 }          
                         
    zxAnSysAutoSaveFlashInterval   OBJECT-TYPE
        SYNTAX      Integer32( 0..8760 )
        UNITS       "hours"         
        MAX-ACCESS  read-write
        STATUS      current
        DESCRIPTION 
            "The Interval of auto save flash.
            This variable is valid if zxAnSysAutoSaveFlashMode set to interval(3).
            value 0 meas save once only at zxAnSysAutoSaveFlashStartDate."  
        DEFVAL      { 0 }                      
        ::=  { zxAnSysDataMgmt 6 }        

    zxAnSysConfigSaveProgress   OBJECT-TYPE
        SYNTAX          INTEGER(0..100) 
        UNITS             "percents"         
        MAX-ACCESS      read-only
        STATUS          current 
        DESCRIPTION
            "The progress of save flash."            
        ::= {zxAnSysDataMgmt 7 }
        
    zxAnSysDataSaveFlashFailReason    OBJECT-TYPE
        SYNTAX      INTEGER { 
            noError(1),
            flashMediaFull(2),
            createConfigFilesFailed(3),
            openConfigFilesFailed(4),
            standbyCardCopyConfigFilesFailed(5),
            unknown(99)
        } 
        MAX-ACCESS  read-only
        STATUS      current
        DESCRIPTION      
            "The reason of saving flash operation failed. 
             Possible values are:
                 noError(1)               - No error, saving flash successfully
                                            or no saving flash operation.
                 flashMediaFull(2)        - Flash media is full.
                 createConfigFilesFailed(3) - Creating configuration files
                                             failed.
                 openConfigFilesFailed(4)  - Opening configuration files failed.
                 standbyCardCopyConfigFilesFailed(5) - Copying configuration
                                              files failed by the standby card.
                 unknown(99)              - Unknown reason."
        DEFVAL { noError }
        ::= { zxAnSysDataMgmt 8 } 
    zxAnSysCfgChangeSaveFlashEnable   OBJECT-TYPE     
        SYNTAX      INTEGER
        {
            enable ( 1 ) ,
            disable ( 2 ) 
        }      
        MAX-ACCESS  read-write
        STATUS      current
        DESCRIPTION 
            "Enables or disables automatic save flash
            when configuration is changed."
        DEFVAL { enable }           
        ::=  { zxAnSysDataMgmt 9 }
    
    zxAnSysCfgChangeSaveHoldOffTime   OBJECT-TYPE 
        SYNTAX          Integer32( 1..86400 ) 
        UNITS           "seconds"   
        MAX-ACCESS      read-write
        STATUS          current
        DESCRIPTION 
            "The hold off time of automatic save flash when configuration is 
            changed." 
        DEFVAL { 3600 }      
        ::=  {  zxAnSysDataMgmt  10  }
--------------------------------------------------------------------------------
-- 5.System Running Control
--------------------------------------------------------------------------------
    zxAnSysRunningCtrl OBJECT IDENTIFIER  ::=  { zxAnSysObjects 5 }

    zxAnChassisSysReboot    OBJECT-TYPE 
       SYNTAX             INTEGER  
          { 
              rebootSystem (1)
          } 
       MAX-ACCESS       read-write
       STATUS           current
       DESCRIPTION      "Reboot system."
       ::=  {  zxAnSysRunningCtrl  1  }
       
    zxAnSysRevision     OBJECT-TYPE 
       SYNTAX           BITS 
           {
               aclTrafficLimit(0),
               extendedACLTtl(1),
               hybridACLDscp(2),
               xConnectVlan(3),
               qosIIVPortPrfType(4),
               servicePortCosAndMode(5),
               supportIPV6(6),
               supportIgmpHostVersion(7),
               qosII4KTVersion(8),
               supportEtherIfMcastFloodingCtrl(9),
               supportVdslDataRateTrap(10),
               supportBrgUniActualEncapsType(11),
               supportAdslProfileExt(12),
               supportVlanDesc(13),
               supportProtocolVlanMapEnable(14),
               supportMulticastFloodingMode(15),
               supportXdslXtuInitFailTrapEnable(16),
               supportGINP4Vdsl(17),
               supportGINP4Adsl(18),
               supportMvlanCvlanId(19),
               supportSecSvcInterworkVlan(20),
               supportExtendAcceptFrameTypes4DT(21),
               supportSnmpGetbulk(22) 
           } 
       MAX-ACCESS       read-only
       STATUS           current
       DESCRIPTION      "Module revision flag."
       ::=  {  zxAnSysRunningCtrl  2  }
       
    zxAnFileLoadDefaultConfiguration    
       OBJECT-TYPE
       SYNTAX      INTEGER {
                    loadFactoryDefaults(1)
                   }
       MAX-ACCESS  read-write
       STATUS      current
       DESCRIPTION 
           "Use this parameter to load settings. 
           "
       ::=  {  zxAnSysRunningCtrl  3 }


    zxAnSysLastRebootReason    OBJECT-TYPE 
       SYNTAX             INTEGER  
          { 
              byCli(1),
              byNms(2),
              byWatchdog(3),
              byPowerOff(4),
              bySoftwareRestart(5),
              byProcessSuspended(6), 
              unknown (99)
          } 
       MAX-ACCESS       read-only
       STATUS           current
       DESCRIPTION      "It indicates device coldstart  reason"
       ::=  {  zxAnSysRunningCtrl  4  }

    zxAnSysResourceType    OBJECT-TYPE 
       SYNTAX             INTEGER  
          { 
              memory (1)
          } 
       MAX-ACCESS       read-only
       STATUS           current
       DESCRIPTION      "System resource type."
       ::=  {  zxAnSysRunningCtrl  5  }
          
--------------------------------------------------------------------------------
-- 6.NMS Management  
--------------------------------------------------------------------------------
    zxAnSysNmsMgmtPath        OBJECT IDENTIFIER  ::=  {  zxAnSysNmsMgmt  1  }
    zxAnSysServiceMgmtPath    OBJECT IDENTIFIER  ::=  {  zxAnSysNmsMgmt  2  }

--------------------------------------------------------------------------------
-- 6.1 Outband NMS Management  
--------------------------------------------------------------------------------
    zxAnSysNmsMgmtOutbandIpAddr   OBJECT-TYPE     
       SYNTAX      IpAddress
       MAX-ACCESS  read-write
       STATUS      current
       DESCRIPTION 
            "Outband IpAddr for NMS management."
       ::=  {  zxAnSysNmsMgmtPath  1  }


    zxAnSysNmsMgmtOutbandIpMask   OBJECT-TYPE     
       SYNTAX      IpAddress
       MAX-ACCESS  read-write
       STATUS      current
       DESCRIPTION 
            "Outband Ip subnetwork mask for NMS management."
       ::=  {  zxAnSysNmsMgmtPath  2  }


    zxAnSysNmsMgmtOutbandMac   OBJECT-TYPE     
       SYNTAX      MacAddress
       MAX-ACCESS  read-only
       STATUS      current
       DESCRIPTION 
            "Outband MAC for NMS management."
       ::=  {  zxAnSysNmsMgmtPath  3  }
       

--------------------------------------------------------------------------------
-- 6.2 Inband NMS Management  
--------------------------------------------------------------------------------
    zxAnSysNmsMgmtInbandIpAddr   OBJECT-TYPE     
       SYNTAX      IpAddress
       MAX-ACCESS  read-write
       STATUS      current
       DESCRIPTION 
            "Inband IpAddr for NMS management."
       ::=  {  zxAnSysNmsMgmtPath  4  }


    zxAnSysNmsMgmtInbandIpMask   OBJECT-TYPE     
       SYNTAX      IpAddress
       MAX-ACCESS  read-write
       STATUS      current
       DESCRIPTION 
            "Inband Ip subnetwork mask for NMS management."
       ::=  {  zxAnSysNmsMgmtPath  5  }


    zxAnSysNmsMgmtInbandMac   OBJECT-TYPE     
       SYNTAX      MacAddress
       MAX-ACCESS  read-only
       STATUS      current
       DESCRIPTION 
            "Inband MAC for NMS management."
       ::=  {  zxAnSysNmsMgmtPath  6  }



    zxAnSysNmsMgmtInbandVlan   OBJECT-TYPE     
       SYNTAX      Integer32
       MAX-ACCESS  read-write
       STATUS      current
       DESCRIPTION 
            "Inband VLAN for NMS management.
       The VLAN must exist when this Variable is set.   "
       ::=  {  zxAnSysNmsMgmtPath  7  }



    zxAnSysNmsMgmtInbandVpnId   OBJECT-TYPE     
       SYNTAX      Integer32
       MAX-ACCESS  read-write
       STATUS      current
       DESCRIPTION 
            "Inband VPN ID for NMS management."
            
       DEFVAL { 0 }    
       ::=  {  zxAnSysNmsMgmtPath  8  }
       
    zxAnSysNmsMgmtInbandEnable   OBJECT-TYPE     
       SYNTAX      INTEGER
           {
               enable(1),
               disable(2)
           }
       MAX-ACCESS  read-write
       STATUS      current
       DESCRIPTION 
            "Enables or disables inband management."            
       DEFVAL { enable }    
       ::=  {  zxAnSysNmsMgmtPath  11  }
           
--------------------------------------------------------------------------------
-- 6.3 IPv6 Outband NMS Management  
--------------------------------------------------------------------------------

    zxAnSysMgmtOutbandIpv6Addr    OBJECT-TYPE 
        SYNTAX          InetAddress
        MAX-ACCESS      read-write
        STATUS          current
        DESCRIPTION     
            "Outband inet address."
        ::=  {  zxAnSysNmsMgmtPath  9  }
        
    zxAnSysMgmtOutbandIpv6AddrPfxLen    OBJECT-TYPE 
        SYNTAX          InetAddressPrefixLength
        MAX-ACCESS      read-write
        STATUS          current
        DESCRIPTION     
            "Outband inet address prefix length."
        ::=  {  zxAnSysNmsMgmtPath  10  }

--------------------------------------------------------------------------------
-- 6.4 Service Management Ip
--------------------------------------------------------------------------------


    zxAnSysServiceMgmtIpTable   OBJECT-TYPE
        SYNTAX      SEQUENCE  OF  ZxAnSysServiceMgmtIpEntry
        MAX-ACCESS  not-accessible
        STATUS      current
        DESCRIPTION "This table includes the ip group for services management."
        ::=  { zxAnSysServiceMgmtPath  1 }

    zxAnSysServiceMgmtIpEntry   OBJECT-TYPE
        SYNTAX      ZxAnSysServiceMgmtIpEntry
        MAX-ACCESS  not-accessible
        STATUS      current
        DESCRIPTION "An entry in zxAnSysServiceMgmtIpTable.When this entry will 
            be configured, zxAnSysServiceMgmtVpnId,zxAnSysServiceMgmtIpAddr and
            zxAnSysServiceMgmtIpMask must be set to agent together."
        INDEX       { zxAnSysServiceMgmtVlanId  }
        ::=  { zxAnSysServiceMgmtIpTable 1 }

    ZxAnSysServiceMgmtIpEntry  ::=  SEQUENCE {
        zxAnSysServiceMgmtVlanId    Integer32,
        zxAnSysServiceMgmtVpnId     Integer32,
        zxAnSysServiceMgmtIpAddr    IpAddress,
        zxAnSysServiceMgmtIpMask    IpAddress,
        zxAnSysServiceMgmtMac       MacAddress,
        zxAnSysServiceMgmtIpRowStatus RowStatus
        }

        
    zxAnSysServiceMgmtVlanId   OBJECT-TYPE     
       SYNTAX      Integer32 (1..4094)
       MAX-ACCESS  not-accessible
       STATUS      current
       DESCRIPTION 
            " VLAN for services management.
       The VLAN must exist when this Variable is set.   "
       ::=  {  zxAnSysServiceMgmtIpEntry  1  }


    zxAnSysServiceMgmtVpnId   OBJECT-TYPE     
       SYNTAX      Integer32
       MAX-ACCESS  read-create
       STATUS      current
       DESCRIPTION 
            " VPN ID for services management."
            
       DEFVAL { 0 }    
       ::=  {  zxAnSysServiceMgmtIpEntry  2  }
           

    zxAnSysServiceMgmtIpAddr   OBJECT-TYPE     
       SYNTAX      IpAddress
       MAX-ACCESS  read-create
       STATUS      current
       DESCRIPTION 
            " IpAddr for services management."
       ::=  {  zxAnSysServiceMgmtIpEntry  3  }


    zxAnSysServiceMgmtIpMask   OBJECT-TYPE     
       SYNTAX      IpAddress
       MAX-ACCESS  read-create
       STATUS      current
       DESCRIPTION 
            " Ip subnetwork mask for services management."
       ::=  {  zxAnSysServiceMgmtIpEntry  4  }


    zxAnSysServiceMgmtMac   OBJECT-TYPE     
       SYNTAX      MacAddress
       MAX-ACCESS  read-only
       STATUS      current
       DESCRIPTION 
            " MAC for services management."
       ::=  {  zxAnSysServiceMgmtIpEntry  5  }


    zxAnSysServiceMgmtIpRowStatus OBJECT-TYPE
       SYNTAX          RowStatus
       MAX-ACCESS      read-create
       STATUS          current
       DESCRIPTION
            " Rowstatus to create or delete a row of this entry."
     ::= { zxAnSysServiceMgmtIpEntry 6 }
                      

--------------------------------------------------------------------------------
-- 7.Config Time and Zone
--------------------------------------------------------------------------------
  
    zxAnRtcSysDateTime   OBJECT-TYPE     
       SYNTAX      DisplayString  ( SIZE ( 1 .. 20  ) )
       MAX-ACCESS  read-write
       STATUS      current
       DESCRIPTION "This MIB defines ne time.for example:
        yyyy-mm-dd HH:MM:SS.(2001-01-01 02:22:33)."
       ::=  {  zxAnSysTimeMgmt  1  }

    zxAnRtcZoneType OBJECT-TYPE     
       SYNTAX      INTEGER  { east ( 1 ) , west ( 2 ) , zero ( 3 ) } 
       MAX-ACCESS  read-write
       STATUS      current
       DESCRIPTION "zone type."
       ::=  {  zxAnSysTimeMgmt  2  }

    zxAnRtcZoneHours   OBJECT-TYPE     
       SYNTAX      Integer32
       MAX-ACCESS  read-write
       STATUS      current
       DESCRIPTION "zxAnRtcZoneType east /west:  1-12
       no use for zxAnRtcZoneType zero."
       ::=  {  zxAnSysTimeMgmt  3  }    

    zxAnRtcZoneAlias    OBJECT-TYPE     
       SYNTAX      DisplayString  ( SIZE ( 1 .. 32  ) )
       MAX-ACCESS  read-write
       STATUS      current
       DESCRIPTION "Zone alias."
       ::=  {  zxAnSysTimeMgmt  5  }      

    zxAnRtcZoneMinutes   OBJECT-TYPE 
        SYNTAX          Integer32(0..60)
        MAX-ACCESS      read-write
        STATUS          current
        DESCRIPTION     "Minutes offset in a time zone."
        ::=  {  zxAnSysTimeMgmt  6  }


--------------------------------------------------------------------------------
-- 8.NTP Configuration
--------------------------------------------------------------------------------

    zxAnSysNtpMgmt    OBJECT IDENTIFIER  ::=  { zxAnSysTimeMgmt 4 }

    zxAnSysNtpEnable    OBJECT-TYPE 
       SYNTAX             INTEGER  
          { 
              enable ( 1 ) , 
              disable ( 2 ) 
          } 
       MAX-ACCESS       read-write
       STATUS             current
       DESCRIPTION      "Enable/disable NTP in this system."
       DEFVAL { disable }
       ::=  {  zxAnSysNtpMgmt  1  }
       
    zxAnSysNtpServerAddr OBJECT-TYPE 
       SYNTAX       IpAddress
       MAX-ACCESS   read-write
       STATUS       current
       DESCRIPTION  " the NTP server's IP address "
       ::=  {  zxAnSysNtpMgmt  2  }


    zxAnSysNtpClientAddr OBJECT-TYPE 
       SYNTAX       IpAddress
       MAX-ACCESS   read-write
       STATUS       current
       DESCRIPTION  " the NTP client IP address which is a ip of this agent."
       ::=  {  zxAnSysNtpMgmt  3  }
       
    zxAnSysNtpProtoVersion OBJECT-TYPE 
       SYNTAX             INTEGER  
          { 
              version1( 1 ) , 
              version2( 2 ) , 
              version3( 3 ) , 
              version4( 4 ) 
          } 
       MAX-ACCESS   read-write
       STATUS       current
       DESCRIPTION  " the NTP server's protocol version."
       DEFVAL { version3 }
       ::=  {  zxAnSysNtpMgmt  4  }

    
     zxAnSysNtpPollInterval OBJECT-TYPE 
       SYNTAX       Integer32(20..86400)
       UNITS        "seconds"
       MAX-ACCESS   read-write
       STATUS       current
       DESCRIPTION  " the NTP server's fetch time's interval time"
       DEFVAL { 300 }
       ::=  {  zxAnSysNtpMgmt  5  }

    zxAnSysNtpStatusCurrentState OBJECT-TYPE
        SYNTAX      INTEGER 
          {
              unknown(1),
              notRunning(2),
              notSynchronized(3),
              noneConfigured(4),-- no server configured
              syncToLocal(5),   -- NTP is synchronized to own local clock
              syncToRefclock(6),-- NTP is synchronized to a local hardware refclock,(e.g. GPS)
              syncToRemoteServer(7)
          }
      MAX-ACCESS  read-only
      STATUS      current
      DESCRIPTION
        "The current state of the NTP."
      DEFVAL { unknown }
      ::= { zxAnSysNtpMgmt 6 }


      zxAnSysNtpStratum OBJECT-TYPE 
          SYNTAX            Integer32
          MAX-ACCESS    read-only
          STATUS            current
          DESCRIPTION       " the local NTP server 's stratum "
          ::=  {  zxAnSysNtpMgmt  7  }


    zxAnSysNtpCurrentOffset OBJECT-TYPE
      SYNTAX      DisplayString
      UNITS       "seconds"
      MAX-ACCESS  read-only
      STATUS      current
      DESCRIPTION
          "The Time offset to the current selected reference time source.
          "
      ::= { zxAnSysNtpMgmt 8 }


    zxAnSysNtpOffsetAlarmThreshold OBJECT-TYPE
      SYNTAX      Integer32
      UNITS       "ms"
      MAX-ACCESS  read-write
      STATUS      current
      DESCRIPTION
          "The alarm threshold of NTP time offset to the current selected 
          reference time source.When this threshold is across,the trap 
          zxAnSysNtpOffsetOverThreshTrap  should be sent to a manager. 

          NOTE: The ZTE AN agent support second only now.So this value must be 
          the times of 1000ms.   "
      DEFVAL { 7000 }
      ::= { zxAnSysNtpMgmt 9 }  
      
    zxAnSysNtpMode    OBJECT-TYPE
        SYNTAX  INTEGER {
            symmetricActive(1),
            symmetricPassive(2),
            client(3),
            server(4),
            broadcast(5),
            unspecified(255)
        }
        MAX-ACCESS  read-only
        STATUS      current
        DESCRIPTION 
            "The NTP mode."
        ::= { zxAnSysNtpMgmt 10 }
        
    zxAnSysNtpCurrServerIpAddrType    OBJECT-TYPE
        SYNTAX      InetAddressType
        MAX-ACCESS  read-only
        STATUS      current
        DESCRIPTION      
            "IP address type of the current synchronizing NTP server."
        DEFVAL  { ipv4 }
        ::= { zxAnSysNtpMgmt 11 }
        
    zxAnSysNtpCurrServerIpAddress    OBJECT-TYPE
        SYNTAX      InetAddress
        MAX-ACCESS  read-only
        STATUS      current
        DESCRIPTION
            "IP address of the current synchronizing NTP server."
        ::= { zxAnSysNtpMgmt 12 }
        
    zxAnSysNtpCurrServerVrf    OBJECT-TYPE
        SYNTAX      DisplayString(SIZE(0..32))  
        MAX-ACCESS  read-only
        STATUS      current
        DESCRIPTION
            "The VRF name of the current synchronizing NTP server."
        ::= { zxAnSysNtpMgmt 13 }
        
     zxAnSysNtpClientAddrType    OBJECT-TYPE
        SYNTAX      InetAddressType
        MAX-ACCESS  read-write
        STATUS      current
        DESCRIPTION      
            "NTP client IP address type."
        DEFVAL  { ipv4 }
        ::= { zxAnSysNtpMgmt 14 }
        
    zxAnSysNtpClientAddrIpv6    OBJECT-TYPE
        SYNTAX      InetAddress
        MAX-ACCESS  read-write
        STATUS      current
        DESCRIPTION
            "NTP client IP address for IPv6."
        ::= { zxAnSysNtpMgmt 15 }
    
    zxAnSysNtpAuthenticationEnable    OBJECT-TYPE
        SYNTAX      INTEGER{
            enable(1),
            disable(2)  
        }
        MAX-ACCESS  read-write
        STATUS      current
        DESCRIPTION
            "Enables or disables NTP authentication."
        DEFVAL  { disable }
        ::= { zxAnSysNtpMgmt 16 }
        
    zxAnSysNtpServerTable    OBJECT-TYPE
        SYNTAX      SEQUENCE  OF  ZxAnSysNtpServerEntry
        MAX-ACCESS  not-accessible
        STATUS      current
        DESCRIPTION     
            "NTP server configuration table."
        ::= { zxAnSysNtpMgmt 51 }    

    zxAnSysNtpServerEntry    OBJECT-TYPE
        SYNTAX      ZxAnSysNtpServerEntry
        MAX-ACCESS  not-accessible
        STATUS      current
        DESCRIPTION     
            "NTP server configuration entry."
        INDEX   { zxAnSysNtpServerPriority }
        ::= { zxAnSysNtpServerTable 1 } 
    
    ZxAnSysNtpServerEntry  ::=  SEQUENCE {
        zxAnSysNtpServerPriority        Integer32,
        zxAnSysNtpServerVrf             DisplayString,
        zxAnSysNtpServerIpAddressType   InetAddressType,  
        zxAnSysNtpServerIpAddress       InetAddress,
        zxAnSysNtpServerVersion         Integer32,
        zxAnSysNtpServerAuthKeyId       Integer32,
        zxAnSysNtpServerLock            INTEGER,
        zxAnSysNtpServerRowStatus       RowStatus
        }
    
    zxAnSysNtpServerPriority    OBJECT-TYPE 
        SYNTAX      Integer32( 1..5 )       
        MAX-ACCESS  not-accessible
        STATUS      current
        DESCRIPTION     
            "Priority of the NTP server.The min number with high priority"
        ::= { zxAnSysNtpServerEntry 1 } 
        
    zxAnSysNtpServerVrf    OBJECT-TYPE
        SYNTAX      DisplayString(SIZE(0..32)) 
        MAX-ACCESS  read-create
        STATUS      current
        DESCRIPTION
            "VRF name of the NTP server.
            NE returns empty string when it's unconfigured."
        ::= { zxAnSysNtpServerEntry 2 }    
        
    zxAnSysNtpServerIpAddressType    OBJECT-TYPE
        SYNTAX      InetAddressType
        MAX-ACCESS  read-create
        STATUS      current
        DESCRIPTION      
            "IP address type of the NTP server."
        DEFVAL  { ipv4 }
        ::= { zxAnSysNtpServerEntry 3 } 
        
    zxAnSysNtpServerIpAddress    OBJECT-TYPE
        SYNTAX      InetAddress
        MAX-ACCESS  read-create
        STATUS      current
        DESCRIPTION
            "IP address of the NTP server."
        ::= { zxAnSysNtpServerEntry 4 }  

    zxAnSysNtpServerVersion    OBJECT-TYPE
        SYNTAX      Integer32 (1..4)
        MAX-ACCESS  read-create
        STATUS      current
        DESCRIPTION
            "Version number of the NTP."
        ::= { zxAnSysNtpServerEntry 5 } 
        
    zxAnSysNtpServerAuthKeyId    OBJECT-TYPE
        SYNTAX      Integer32(0..255)
        MAX-ACCESS  read-create
        STATUS      current
        DESCRIPTION
            "Authentication key ID of the NTP server. 
            Value 0 means unconfigured."
        ::= { zxAnSysNtpServerEntry 6 }  
        
    zxAnSysNtpServerLock    OBJECT-TYPE
        SYNTAX      INTEGER {
            lock(1),
            unlock(2)
        }
        MAX-ACCESS  read-create
        STATUS      current
        DESCRIPTION
            "Lock or unlock the NTP server. Only one server can be locked.
            If one server is locked,the locked server can be used to 
            synchronize time.
            If no server is locked,the server which has the highest 
            priority can be used to synchronize time."
        ::= { zxAnSysNtpServerEntry 7 } 
        
    zxAnSysNtpServerRowStatus    OBJECT-TYPE
        SYNTAX      RowStatus
        MAX-ACCESS  read-create
        STATUS      current
        DESCRIPTION
            "The row status of this entry."
        ::= { zxAnSysNtpServerEntry 30 }    
        
    zxAnSysNtpAuthenticationTable    OBJECT-TYPE
        SYNTAX      SEQUENCE  OF  ZxAnSysNtpAuthenticationEntry
        MAX-ACCESS  not-accessible
        STATUS      current
        DESCRIPTION     
            "NTP authentication configuration table."
        ::= { zxAnSysNtpMgmt 52 }     

    zxAnSysNtpAuthenticationEntry    OBJECT-TYPE
        SYNTAX      ZxAnSysNtpAuthenticationEntry
        MAX-ACCESS  not-accessible
        STATUS      current
        DESCRIPTION     
            "NTP authentication configuration entry."
        INDEX   { zxAnSysNtpAuthenticationKeyId }
        ::= { zxAnSysNtpAuthenticationTable 1 } 
    
    ZxAnSysNtpAuthenticationEntry  ::=  SEQUENCE {
        zxAnSysNtpAuthenticationKeyId       Integer32,
        zxAnSysNtpAuthenticationKey         DisplayString,
        zxAnSysNtpAuthenticationTrust       TruthValue,
        zxAnSysNtpAuthRowStatus             RowStatus
        }
    
    zxAnSysNtpAuthenticationKeyId    OBJECT-TYPE 
        SYNTAX      Integer32( 1..255 )       
        MAX-ACCESS  not-accessible
        STATUS      current
        DESCRIPTION     
            "NTP authentication key ID."
        ::= { zxAnSysNtpAuthenticationEntry 1 } 

    zxAnSysNtpAuthenticationKey    OBJECT-TYPE 
        SYNTAX      DisplayString(SIZE(1..32))       
        MAX-ACCESS  read-create
        STATUS      current
        DESCRIPTION     
            "NTP authentication key."
        ::= { zxAnSysNtpAuthenticationEntry 2 }  

    zxAnSysNtpAuthenticationTrust    OBJECT-TYPE 
        SYNTAX      TruthValue       
        MAX-ACCESS  read-create
        STATUS      current
        DESCRIPTION     
            "NTP authentication trust status."
        ::= { zxAnSysNtpAuthenticationEntry 3 } 
        
    zxAnSysNtpAuthRowStatus    OBJECT-TYPE
        SYNTAX      RowStatus
        MAX-ACCESS  read-create
        STATUS      current
        DESCRIPTION
            "The row status of this entry."
        ::= { zxAnSysNtpAuthenticationEntry 30 }    

    zxAnSysNtpIfConfigTable    OBJECT-TYPE
        SYNTAX      SEQUENCE  OF  ZxAnSysNtpIfConfigEntry
        MAX-ACCESS  not-accessible
        STATUS      current
        DESCRIPTION     
            "NTP layer 3 interface configuration table."
        ::= { zxAnSysNtpMgmt 53 }     

    zxAnSysNtpIfConfigEntry    OBJECT-TYPE
        SYNTAX      ZxAnSysNtpIfConfigEntry
        MAX-ACCESS  not-accessible
        STATUS      current
        DESCRIPTION     
            "NTP layer 3 interface configuration entry."
        INDEX   { zxAnSysNtpIfIndex }
        ::= { zxAnSysNtpIfConfigTable 1 } 
    
    ZxAnSysNtpIfConfigEntry  ::=  SEQUENCE {
        zxAnSysNtpIfIndex                  ZxAnIfindex,
        zxAnSysNtpIfBroadcastClientEn      INTEGER,
        zxAnSysNtpIfMulticastClientEn      INTEGER,
        zxAnSysNtpIfMulticastIpAddrType    InetAddressType,
        zxAnSysNtpIfMulticastIpAddr        InetAddress,
        zxAnSysNtpIfConfigRowStatus     RowStatus
        }
        
    zxAnSysNtpIfIndex    OBJECT-TYPE 
        SYNTAX      ZxAnIfindex      
        MAX-ACCESS  not-accessible
        STATUS      current
        DESCRIPTION     
            "The ifindex of the NTP layer 3 interface."
        ::= { zxAnSysNtpIfConfigEntry 1 } 
        
    zxAnSysNtpIfBroadcastClientEn    OBJECT-TYPE
        SYNTAX      INTEGER{
            enable(1),
            disable(2)  
        }
        MAX-ACCESS  read-create
        STATUS      current
        DESCRIPTION
            "Enables or disables NTP broadcast client mode."
        ::= { zxAnSysNtpIfConfigEntry 2 } 
        
    zxAnSysNtpIfMulticastClientEn    OBJECT-TYPE
        SYNTAX      INTEGER{
            enable(1),
            disable(2)  
        }
        MAX-ACCESS  read-create
        STATUS      current
        DESCRIPTION
            "Enables or disables NTP multicast client mode."
        ::= { zxAnSysNtpIfConfigEntry 3 } 
    
    zxAnSysNtpIfMulticastIpAddrType    OBJECT-TYPE
        SYNTAX      InetAddressType
        MAX-ACCESS  read-create
        STATUS      current
        DESCRIPTION
            "Multicast IP address type. 
            This variable is valid if zxAnSysNtpMulticastClientEnable is 
            enable."
        DEFVAL  { ipv4 }
        ::= { zxAnSysNtpIfConfigEntry 4 }    
        
    zxAnSysNtpIfMulticastIpAddr    OBJECT-TYPE
        SYNTAX      InetAddress
        MAX-ACCESS  read-create
        STATUS      current
        DESCRIPTION
            "Multicast IP address. 
            This variable is valid if zxAnSysNtpMulticastClientEnable is 
            enable."         
        ::= { zxAnSysNtpIfConfigEntry 5 }   

    zxAnSysNtpIfConfigRowStatus    OBJECT-TYPE
        SYNTAX      RowStatus
        MAX-ACCESS  read-create
        STATUS      current
        DESCRIPTION
            "The row status of this entry."
        ::= { zxAnSysNtpIfConfigEntry 30 }          


        
--------------------------------------------------------------------------------
-- 9.PTP Configuration
--------------------------------------------------------------------------------

    zxAnSysPtpMgmt    OBJECT IDENTIFIER  ::=  { zxAnSysTimeMgmt 8 }
    
    zxAnSysPtpGlobalObjects OBJECT  IDENTIFIER  ::=  {  zxAnSysPtpMgmt  1  }

    zxAnSysPtpConfigClockMode  OBJECT-TYPE 
       SYNTAX  INTEGER 
       {
            ordinary(1),
            boundary(2)
       }
       MAX-ACCESS  read-write
       STATUS      current
       DESCRIPTION  
           "The PTP clock mode."
       REFERENCE           
           "IEEE 1588 Section 15.5.3.3.1.1"
       DEFVAL      { ordinary }           
       ::=  {  zxAnSysPtpGlobalObjects  1  }

    zxAnSysPtpConfigTsc  OBJECT-TYPE 
       SYNTAX      TruthValue  
       MAX-ACCESS  read-write
       STATUS      current
       DESCRIPTION  
           "The two_steps attribution is true or not.            
            
            true - A clock that provides time information using the 
                      combination of an event message and a subsequent 
                      general message. 
                                
            false - A clock that provides time information using a 
                      single event message."
       REFERENCE           
           "IEEE 1588 Section 15.5.3.3.1.1"
       DEFVAL      { true }           
       ::=  {  zxAnSysPtpGlobalObjects  2  }
       
    zxAnSysPtpServiceVlan OBJECT-TYPE 
       SYNTAX       Integer32
       MAX-ACCESS   read-write
       STATUS       current
       DESCRIPTION  
           "The vlan ID of the precision clock synchronization service."
       DEFVAL       { 1 }           
       ::=  {  zxAnSysPtpGlobalObjects  3  }
       
    zxAnSysPtpTodTransMode OBJECT-TYPE 
       SYNTAX         INTEGER
        {
            transparent(1),
            untransmit(2),
            local(3)
        }
       MAX-ACCESS   read-write
       STATUS       current
       DESCRIPTION  
           "The transmit type of TOD."
       DEFVAL       { untransmit }           
       ::=  {  zxAnSysPtpGlobalObjects  4  }
       
    zxAnSysPtpTodSignalType OBJECT-TYPE 
       SYNTAX         INTEGER
        {
            chinaMobile(1),
            chinaTelecom(2)
        }
       MAX-ACCESS   read-write
       STATUS       current
       DESCRIPTION  
           "The signal type of TOD, it's only used in the case where 
            zxAnSysPtpTodMode is 'local'."
       DEFVAL       { chinaMobile }           
       ::=  {  zxAnSysPtpGlobalObjects  5  }
   
    zxAnSysPtpPortTable OBJECT-TYPE
        SYNTAX       SEQUENCE OF ZxAnSysPtpPortEntry
        MAX-ACCESS   not-accessible
        STATUS       current
        DESCRIPTION  "The PTP Port Table."
        ::= { zxAnSysPtpMgmt 2 }

    zxAnSysPtpPortEntry OBJECT-TYPE
        SYNTAX       ZxAnSysPtpPortEntry
        MAX-ACCESS   not-accessible
        STATUS       current
        DESCRIPTION  "The PTP Port Entry"
        INDEX { zxAnSysPtpPortIndex }
        ::= { zxAnSysPtpPortTable 1 }

    ZxAnSysPtpPortEntry ::= SEQUENCE {
        zxAnSysPtpPortIndex               INTEGER,
        zxAnSysPtpPortConfState           INTEGER,
        zxAnSysPtpPortSyncInterval        INTEGER,
        zxAnSysPtpPortClockDestIpAddress  InetAddress,
        zxAnSysPtpPortRowStatus           RowStatus
    }
    
    zxAnSysPtpPortIndex OBJECT-TYPE
        SYNTAX       INTEGER (1..128)
        MAX-ACCESS   not-accessible
        STATUS       current
        DESCRIPTION  "The id of the ptp port."
        ::= { zxAnSysPtpPortEntry 1 }   
    
    zxAnSysPtpPortConfState OBJECT-TYPE
        SYNTAX       INTEGER
        {
            master (1),
            slave (2)
        }
        MAX-ACCESS   read-create
        STATUS       current
        DESCRIPTION  "The config state of the ptp port."
        ::= { zxAnSysPtpPortEntry 2 }   
    
    zxAnSysPtpPortSyncInterval OBJECT-TYPE
        SYNTAX       INTEGER(1..128) 
        UNITS        "pps"
        MAX-ACCESS   read-create
        STATUS       current
        DESCRIPTION  "The frequency of clock synchronization packets of 
                      this slave, in packets per second. 
                      The value should be 2^n, such as 1, 2, 4, 8, 16 
                      and so on."
        ::= { zxAnSysPtpPortEntry 3 } 
        
    zxAnSysPtpPortClockDestIpAddress OBJECT-TYPE
        SYNTAX       InetAddress
        MAX-ACCESS   read-create
        STATUS       current
        DESCRIPTION  "The IP address of the clock destination."
        ::= { zxAnSysPtpPortEntry 4 }   
   
    zxAnSysPtpPortRowStatus OBJECT-TYPE
        SYNTAX       RowStatus
        MAX-ACCESS   read-create
        STATUS       current
        DESCRIPTION  "Rowstatus to create or delete a row of this entry."
     ::= { zxAnSysPtpPortEntry 20 }
          
       
--------------------------------------------------------------------------------
-- 10.SummerTime Configuration
--------------------------------------------------------------------------------

    zxAnSysSummerTimeMgmt    OBJECT IDENTIFIER  ::=  { zxAnSysTimeMgmt 7 }

    zxAnRtcSummerTimeAdminStatus    OBJECT-TYPE 
       SYNTAX             INTEGER  
          { 
              enable ( 1 ) , 
              disable ( 2 ) 
          } 
       MAX-ACCESS       read-write
       STATUS           current
       DESCRIPTION      "An indication of whether the summer time feature
                      is enabled on this device. When this object
                      is set to enable, then zxAnRtcSummerTimeOffset,
                      zxAnRtcSummerTimeStart and zxAnRtcSummerTimeEnd  objects 
                      are set to default values. When this object is set
                      to disable, then zxAnRtcSummerTimeOffset, zxAnRtcSummerTimeStart,
                      zxAnRtcSummerTimeEnd objects are not instantiated and the summer 
                      time feature is disabled"
       DEFVAL { disable }
       ::=  {  zxAnSysSummerTimeMgmt  1  }
       
    zxAnRtcSummerTimeName   OBJECT-TYPE     
       SYNTAX      DisplayString  ( SIZE ( 1 .. 32  ) )
       MAX-ACCESS  read-write
       STATUS      current
       DESCRIPTION "Summer Time name."
       ::=  {  zxAnSysSummerTimeMgmt  2  }    
       
    zxAnRtcSummerTimeType    OBJECT-TYPE 
       SYNTAX             INTEGER  
          { 
              once ( 1 ) , 
              recurring ( 2 ) 
          } 
       MAX-ACCESS       read-write
       STATUS           current
       DESCRIPTION      "If type is once,the summer time feature will work only once on this device.If type is  recurring,
       the summer time feature will work every year on this device."
       DEFVAL { once }
       ::=  {  zxAnSysSummerTimeMgmt  3  }          
       
    zxAnRtcSummerTimeStart   OBJECT-TYPE     
       SYNTAX      DisplayString  ( SIZE ( 1 .. 20  ) )
       MAX-ACCESS  read-write
       STATUS      current
       DESCRIPTION "Indicates summer time starts at this time every year.
                    It's format is: ww-dd-mm HH:MM:SS
                      tokens    contents     range
                      ww         week        1..5,ff last = ff
                      dd         day         1..7
                                            where sunday = 1, saturday = 7
                      mm         month       1..12
                                            where january = 1 december = 12
                      HH         hour        0..23
                      MM         minute      0..59
                      SS         second      0..59
                      For example, the first Monday in Feb at 13:30pm
                      should be given as
                          01-02-02 13:30:00
                      For the last Tuesday in dec at 1:20am should be
                      given as
                         ff-03-12 01:20:00
                      This object is not instantiated when zxAnRtcSummerTimeAdminStatus object is set to false."
       DEFVAL { "ff-01-03 02:00:00" }
       ::=  {  zxAnSysSummerTimeMgmt  4  }
       
    zxAnRtcSummerTimeEnd   OBJECT-TYPE     
       SYNTAX      DisplayString  ( SIZE ( 1 .. 20  ) )
       MAX-ACCESS  read-write
       STATUS      current
       DESCRIPTION "Indicates summer time ends at this time every year.
                    It's format is: ww-dd-mm HH:MM:SS
                      tokens    contents     range
                      ww         week        1..5,ff last = ff
                      dd         day         1..7
                                            where sunday = 1, saturday = 7
                      mm         month       1..12
                                            where january = 1 december = 12
                      HH         hour        0..23
                      MM         minute      0..59
                      SS         second      0..59
                      For example, the first Monday in Feb at 13:30pm
                      should be given as
                          01-02-02 13:30:00
                      For the last Tuesday in dec at 1:20am should be
                      given as
                         ff-03-12 01:20:00
                      This object is not instantiated when zxAnRtcSummerTimeAdminStatus object is set to false."
       DEFVAL { "ff-01-10 02:00:00" }                      
       ::=  {  zxAnSysSummerTimeMgmt  5  }              

    zxAnRtcSummerTimeOffset   OBJECT-TYPE 
        SYNTAX          Integer32(1 .. 300)
        UNITS           "minute"
        MAX-ACCESS      read-write
        STATUS          current
        DESCRIPTION     "The value of this object indicates number of
                      minutes to add  or to subtract during summer time.
                      This object is not instantiated when
                      zxAnRtcSummerTimeAdminStatus object is set to false."
        DEFVAL { 60 }
        ::=  {  zxAnSysSummerTimeMgmt  6  }
        
    zxAnRtcSummerTimeOperStatus    OBJECT-TYPE 
       SYNTAX             INTEGER  
          { 
              summertime ( 1 ) , 
              standard ( 2 ) 
          } 
       MAX-ACCESS       read-only
       STATUS           current
       DESCRIPTION      "An indication of whether the summer time feature
                      is worked on this device. "
       ::=  {  zxAnSysSummerTimeMgmt  7  }        



--------------------------------------------------------------------------------
-- 9.Snmp Operation Syslog Management
--------------------------------------------------------------------------------
    zxAnSysSnmpOperSyslogStatus   OBJECT-TYPE     
       SYNTAX      INTEGER
            {
                logRead(1), logWrite(2), logReadAndWrite(3), logNone(4)
            }
       MAX-ACCESS  read-write
       STATUS      current
       DESCRIPTION 
              "The status of forwarding SNMP operations through syslog protocol." 
       DEFVAL { logNone }
       ::=  {  zxAnSysSnmpOperSyslogMgmt  1  }

    zxAnSysSnmpOperOidExceptTable   OBJECT-TYPE
        SYNTAX      SEQUENCE  OF  ZxAnSysSnmpOperOidExceptEntry
        MAX-ACCESS  not-accessible
        STATUS      current
        DESCRIPTION "This table includes the oid group of SNMP operation 
                     which is excluded from forwarding."
        ::=  { zxAnSysSnmpOperSyslogMgmt  10 }

    zxAnSysSnmpOperOidExceptEntry   OBJECT-TYPE
        SYNTAX      ZxAnSysSnmpOperOidExceptEntry
        MAX-ACCESS  not-accessible
        STATUS      current
        DESCRIPTION "An entry in zxAnSysSnmpOperOidExceptTable."
        INDEX       { zxAnSysSnmpOidId  }
        ::=  { zxAnSysSnmpOperOidExceptTable 1 }

    ZxAnSysSnmpOperOidExceptEntry  ::=  SEQUENCE {
        zxAnSysSnmpOidId        Integer32,
        zxAnSysSnmpOidItem      DisplayString,
        zxAnSysSnmpOidRowStatus RowStatus
        }

        
    zxAnSysSnmpOidId   OBJECT-TYPE     
       SYNTAX      Integer32 (1..10)
       MAX-ACCESS  not-accessible
       STATUS      current
       DESCRIPTION 
            " Id of this SNMP OID entry. "
       ::=  {  zxAnSysSnmpOperOidExceptEntry  1  }


    zxAnSysSnmpOidItem   OBJECT-TYPE     
       SYNTAX      DisplayString
       MAX-ACCESS  read-create
       STATUS      current
       DESCRIPTION 
            " SNMP OID which is excluded from forwarding through syslog."
            
       ::=  {  zxAnSysSnmpOperOidExceptEntry  2  }

    zxAnSysSnmpOidRowStatus OBJECT-TYPE
       SYNTAX          RowStatus
       MAX-ACCESS      read-create
       STATUS          current
       DESCRIPTION
            " Rowstatus to create or delete a row of this entry."
     ::= { zxAnSysSnmpOperOidExceptEntry 10 }


--------------------------------------------------------------------------------
-- 12.Log Management
--------------------------------------------------------------------------------
   
    zxAnLogTypeTable  OBJECT-TYPE
        SYNTAX      SEQUENCE  OF  ZxAnLogTypeEntry
        MAX-ACCESS  not-accessible
        STATUS      current
        DESCRIPTION "log type definition table, it store all the types and levels supported."
        ::=  { zxAnLog  1 }

    zxAnLogTypeEntry  OBJECT-TYPE
        SYNTAX      ZxAnLogTypeEntry
        MAX-ACCESS  not-accessible
        STATUS      current
        DESCRIPTION "An entry in zxAnLogTypeTable."
        INDEX       { zxAnLogType, zxAnLogLevel   }
        ::=  { zxAnLogTypeTable 1 }

    ZxAnLogTypeEntry  ::=  SEQUENCE {
        zxAnLogType         Integer32,
        zxAnLogLevel        Integer32,
        zxAnLogTypeDesc     DisplayString
        }     
         
    zxAnLogType       OBJECT-TYPE 
        SYNTAX          Integer32 
        MAX-ACCESS      not-accessible
        STATUS          current
        DESCRIPTION     "the log type"
        ::=  {  zxAnLogTypeEntry  1  }           
           
    zxAnLogLevel       OBJECT-TYPE 
        SYNTAX          Integer32 
        MAX-ACCESS      not-accessible
        STATUS          current
        DESCRIPTION     "The log level, value 0 means there is no level 
                         definition of current type."
        ::=  {  zxAnLogTypeEntry  2  }            
    
    zxAnLogTypeDesc    OBJECT-TYPE 
       SYNTAX           DisplayString  ( SIZE ( 1 .. 128 ) )
       MAX-ACCESS       read-only
       STATUS           current
       DESCRIPTION      "The description of current log type and level.
                         The format is TYPE|LEVEL|DESCRIPTION, divided by |."
       ::=  {  zxAnLogTypeEntry  3  }    
               
   
   zxAnLogConfTable  OBJECT-TYPE
        SYNTAX      SEQUENCE  OF  ZxAnLogConfEntry
        MAX-ACCESS  not-accessible
        STATUS      current
        DESCRIPTION "log configuration table,
                     it used to configure the log of type and level."
        ::=  { zxAnLog  2 }

    zxAnLogConfEntry  OBJECT-TYPE
        SYNTAX      ZxAnLogConfEntry
        MAX-ACCESS  not-accessible
        STATUS      current
        DESCRIPTION "An entry in zxAnLogConfTable."
        INDEX       { zxAnLogConfType, zxAnLogConfLevel   }
        ::=  { zxAnLogConfTable 1 }

    ZxAnLogConfEntry  ::=  SEQUENCE {
        zxAnLogConfType     Integer32,
        zxAnLogConfLevel    Integer32,
        zxAnLogCapability   BITS,
        zxAnLogConfig       BITS
        }      
   
    zxAnLogConfType     OBJECT-TYPE 
        SYNTAX          Integer32 
        MAX-ACCESS      not-accessible
        STATUS          current
        DESCRIPTION     "the log type"
        ::=  {  zxAnLogConfEntry  1  }           
           
    zxAnLogConfLevel        OBJECT-TYPE 
        SYNTAX          Integer32 
        MAX-ACCESS      not-accessible
        STATUS          current
        DESCRIPTION     "The log level, value 0 means there is no level 
                         definition of current type."
        ::=  {  zxAnLogConfEntry  2  }    
   
    zxAnLogCapability OBJECT-TYPE 
        SYNTAX BITS {
           syslog(0),
           memory(1),
           highMemory(2),
           flash(3),
           reserved1(4),
           reserved2(5),
           reserved3(6),
           reserved4(7)
        }
        MAX-ACCESS      read-only
        STATUS          current
        DESCRIPTION     
            " the log capability for given level of given type.
              syslog(0): tranfer to syslog, this bit is only used by MAP.          
              memory(1): save to memory, it will lost after NE reboot.
              highMemory(2): save to high memory, it will lost while NE power off.             
              flash(3): save to flash.        
            "
        ::=  {  zxAnLogConfEntry  3  }   
        
    zxAnLogConfig OBJECT-TYPE 
        SYNTAX BITS {
           syslog(0),
           memory(1),
           highMemory(2),
           flash(3),
           reserved1(4),
           reserved2(5),
           reserved3(6),
           reserved4(7)
        }
        MAX-ACCESS      read-write
        STATUS          current
        DESCRIPTION     
            " the log configuration for given level of given type.
              syslog(0): tranfer to syslog, this bit is only used by MAP.             
              memory(1): save to memory, it will lost after NE reboot.
              highMemory(2): save to high memory, it will lost while NE power off.             
              flash(3): save to flash.        
            "
        ::=  {  zxAnLogConfEntry  4  }     
               
   zxAnLogGlobalObjects  OBJECT IDENTIFIER  ::= {zxAnLog 10}            
    zxAnLogClear       OBJECT-TYPE 
        SYNTAX          Integer32
        MAX-ACCESS      read-write
        STATUS          current
        DESCRIPTION     
        "  zxAnLogClear uses a complex coding to support different 
           types and different levels log clear.
                              
           |    Byte 3    |    Byte 2    |    Byte 1    |    Byte 0    |
           |--------------|--------------|--------------|--------------|
           |           Reserved          |  log type    |  log  level  |
           |           16 bits           |   8 bits     |    8 bits    |
           |-----------------------------|--------------|--------------|
           
           ** type  :       refer to zxAnLogType for definition.    
                            0x00 indicates all types. 
                            
           ** level :       refer to zxAnLogLevel for definition.   
                            0x00 indicates all levels or no level definition for current type.   
                                    
           value 0 means clear all logs."
           
        ::=  {  zxAnLogGlobalObjects  1  } 

--------------------------------------------------------------------------------
-- 13.Clock Management
--------------------------------------------------------------------------------
    
    zxAnSysClockMgmt    OBJECT IDENTIFIER  ::=  { zxAnSysObjects 104 }

    zxAnSysConfigClockSource OBJECT-TYPE 
        SYNTAX  INTEGER  
            { 
              bitse1(1), 
              bits2m(2),
              est2m(3),  
              ttl2m(4),    
              e12ml(5),    
              e12mr(6),    
              default(7)     
            } 
        MAX-ACCESS       read-write
        STATUS           current
        DESCRIPTION      
            "Configured clock source. 
            bitse1(1):E1 clock.
            bits2m(2):backplane X56 clock.
            est2m(3):DTI card E1 clock.
            ttl2m(4):backplane X92 clock.            
            e12ml(5):right control card No.0 E1 clock.
            e12mr(6):left control card No.4 E1 clock.
            default(7):control card clock.
            "        
        DEFVAL { default }
        ::=  {  zxAnSysClockMgmt  1  }

    zxAnSysActualClockSource OBJECT-TYPE 
        SYNTAX  INTEGER  
            { 
              bitse1(1), 
              bits2m(2),
              est2m(3),  
              ttl2m(4),    
              e12ml(5),    
              e12mr(6),    
              default(7)      
            } 
        MAX-ACCESS       read-only
        STATUS           current
        DESCRIPTION      "Actual clock source. "        
        DEFVAL { default }
        ::=  {  zxAnSysClockMgmt  2  }

    zxAnSysSupportClockSource OBJECT-TYPE 
        SYNTAX  BITS  
            { 
              bitse1(0), 
              bits2m(1),
              est2m(2),  
              ttl2m(3),    
              e12ml(4),    
              e12mr(5),    
              default(6)     
            } 
        MAX-ACCESS       read-only
        STATUS           current
        DESCRIPTION      "The clock source list supported by this equipment. No recomanded to display it in NMS"
        ::=  {  zxAnSysClockMgmt  3  }

    zxAnSysAvailableClockSource OBJECT-TYPE 
        SYNTAX  BITS  
            { 
              bitse1(0), 
              bits2m(1),
              est2m(2),  
              ttl2m(3),    
              e12ml(4),    
              e12mr(5),    
              default(6)     
            } 
        MAX-ACCESS       read-only
        STATUS           current
        DESCRIPTION      "Current available clock source list. " 
        ::=  {  zxAnSysClockMgmt  4  }

    zxAnSysClockSourcePriority OBJECT-TYPE 
        SYNTAX  DisplayString          
        MAX-ACCESS       read-write
        STATUS           current
        DESCRIPTION      
            "Clock source priority. For example, the string '3,4,2,5,6,1' means there are 6 priorities. 
            And priority 1 is clock source 3(est2m),priority 2 is clock source 4(ttl2m),etc.
            The clock source values refer to zxAnSysConfigClockSource."
        ::=  {  zxAnSysClockMgmt  5  }

    zxAnSysActualClockSourceE1 OBJECT-TYPE 
        SYNTAX  DisplayString
        MAX-ACCESS       read-only
        STATUS           current
        DESCRIPTION      "Actual clock source E1 position. For example,'1-1-8-1' means rack 1 shelf 1 slot 8 E1 1." 
        ::=  {  zxAnSysClockMgmt  6  }   

    zxAnSysLastClockSource OBJECT-TYPE 
        SYNTAX  INTEGER  
            { 
              bitse1(1), 
              bits2m(2),
              est2m(3),  
              ttl2m(4),    
              e12ml(5),    
              e12mr(6),    
              default(7)      
            } 
        MAX-ACCESS       read-only
        STATUS           current
        DESCRIPTION      "Last clock source. " 
        ::=  {  zxAnSysClockMgmt  7  } 

    zxAnSysLastClockSourceE1 OBJECT-TYPE 
        SYNTAX      DisplayString
        MAX-ACCESS  read-only
        STATUS      current
        DESCRIPTION      
            "Last clock source E1 position. For example,'1-1-8-1' means
             rack 1 shelf 1 slot 8 E1 1." 
        ::=  {  zxAnSysClockMgmt  8  } 

    zxAnSysClockSourceTrapEnable OBJECT-TYPE 
        SYNTAX  BITS  
            { 
              bitse1(0), 
              bits2m(1),
              est2m(2),  
              ttl2m(3),    
              e12ml(4),    
              e12mr(5),    
              default(6)     
            } 
        MAX-ACCESS       read-write
        STATUS           current
        DESCRIPTION      
            "Enables and disables the trap of clock source unavailable. 
            Value 0 means disable the trap of this clock source. 
            Value 1 means enable the trap of this clock source." 
        ::=  {  zxAnSysClockMgmt  9  }  

    zxAnSysClockSourceIfType OBJECT-TYPE 
        SYNTAX  INTEGER  
            { 
              e1(1), 
              t1(2)    
            } 
        MAX-ACCESS       read-write
        STATUS           current
        DESCRIPTION      "Clock source interface type. "        
        DEFVAL { e1 }
        ::=  {  zxAnSysClockMgmt  10  }

    zxAnSysDsx1ClockSourceTable OBJECT-TYPE
        SYNTAX     SEQUENCE OF ZxAnSysDsx1ClockSourceEntry
        MAX-ACCESS not-accessible
        STATUS     current
        DESCRIPTION
            "A table of E1 clock source list."
        ::= { zxAnSysClockMgmt 100 }

    zxAnSysDsx1ClockSourceEntry OBJECT-TYPE
        SYNTAX     ZxAnSysDsx1ClockSourceEntry
        MAX-ACCESS not-accessible
        STATUS     current
        DESCRIPTION
            "Entry of E1 clock source table."
        INDEX { zxAnSysDsx1ClkSrcRack, zxAnSysDsx1ClkSrcShelf,
                zxAnSysDsx1ClkSrcSlot, zxAnSysDsx1ClkSrcLinkNo }
        ::= { zxAnSysDsx1ClockSourceTable 1 }

    ZxAnSysDsx1ClockSourceEntry ::= SEQUENCE {
        zxAnSysDsx1ClkSrcRack              Integer32,
        zxAnSysDsx1ClkSrcShelf             Integer32,
        zxAnSysDsx1ClkSrcSlot              Integer32,
        zxAnSysDsx1ClkSrcLinkNo            Integer32,
        zxAnSysDsx1ClkSrcAvailableStatus   INTEGER,        
        zxAnSysDsx1ClkSrcCurrUsingStatus   INTEGER,    
        zxAnSysDsx1ClkSrcPriority          Integer32   
    }
    
    zxAnSysDsx1ClkSrcRack  OBJECT-TYPE
        SYNTAX       Integer32
        MAX-ACCESS   not-accessible
        STATUS       current
        DESCRIPTION  "Rack of E1 clock source."
        ::={zxAnSysDsx1ClockSourceEntry 1}

    zxAnSysDsx1ClkSrcShelf  OBJECT-TYPE
        SYNTAX       Integer32
        MAX-ACCESS   not-accessible
        STATUS       current
        DESCRIPTION  "Shelf of E1 clock source."
        ::={zxAnSysDsx1ClockSourceEntry 2}

    zxAnSysDsx1ClkSrcSlot  OBJECT-TYPE
        SYNTAX       Integer32
        MAX-ACCESS   not-accessible
        STATUS       current
        DESCRIPTION  "Slot of E1 clock source."
        ::={zxAnSysDsx1ClockSourceEntry 3}
  
    zxAnSysDsx1ClkSrcLinkNo  OBJECT-TYPE
        SYNTAX       Integer32
        MAX-ACCESS   not-accessible
        STATUS       current
        DESCRIPTION  "Link number of E1 clock source."
        ::={zxAnSysDsx1ClockSourceEntry 4} 

    zxAnSysDsx1ClkSrcAvailableStatus  OBJECT-TYPE
        SYNTAX       INTEGER  
            { 
              available(1), 
              unavailable(2)  
            } 
        MAX-ACCESS   read-only
        STATUS       current
        DESCRIPTION  "The available status of E1 clock source."
        ::={zxAnSysDsx1ClockSourceEntry 5} 

    zxAnSysDsx1ClkSrcCurrUsingStatus  OBJECT-TYPE
        SYNTAX       INTEGER  
            { 
              inUse(1), 
              unused(2)  
            } 
        MAX-ACCESS   read-only
        STATUS       current
        DESCRIPTION  "The current using status of E1 clock source. 
                     'inUse' indicates that this E1 is used as clock source 
                     currently. And only one E1 will be used as clock source
                     currently."
        ::={zxAnSysDsx1ClockSourceEntry 6} 

    zxAnSysDsx1ClkSrcPriority  OBJECT-TYPE
        SYNTAX       Integer32
        MAX-ACCESS   read-write
        STATUS       current
        DESCRIPTION  "The priority of E1 clock source. The value range is from
                     1 to the maximum number of E1 clock source. For example,
                     if NE supports 32 E1, the valid value will be from 1 to 
                     32. The highest priority value is 1.   
                     The default value is 255 which means unconfigured 
                     priority."
        DEFVAL       {255}
        ::={zxAnSysDsx1ClockSourceEntry 7} 

--------------------------------------------------------------------------------
-- 14.IPv6 Global Management
--------------------------------------------------------------------------------
   
    zxAnSysIpv6GlobalMgmt    OBJECT IDENTIFIER  ::=  { zxAnSysObjects 105 }
    
    zxAnSysIpv6GlobalEnable  OBJECT-TYPE 
        SYNTAX      INTEGER 
            {
              enable(1), 
              disable(2)
            }
        MAX-ACCESS  read-write
        STATUS      current
        DESCRIPTION
            "Enable/Disable IPv6."
        DEFVAL { disable }
        ::= { zxAnSysIpv6GlobalMgmt 1}

            
--------------------------------------------------------------------------------
-- 15.DNS Management
--------------------------------------------------------------------------------

    zxAnSysDns    OBJECT IDENTIFIER  ::=  { zxAnSysObjects 106 }
    
    zxAnSysDnsServerTable OBJECT-TYPE
        SYNTAX     SEQUENCE OF ZxAnSysDnsServerEntry
        MAX-ACCESS not-accessible
        STATUS     current
        DESCRIPTION
            "A table of DNS server configuration."
        ::= { zxAnSysDns 1 }

    zxAnSysDnsServerEntry OBJECT-TYPE
        SYNTAX     ZxAnSysDnsServerEntry
        MAX-ACCESS not-accessible
        STATUS     current
        DESCRIPTION
            "A list of DNS servers."
        INDEX { zxAnSysDnsServerIpAddressType, zxAnSysDnsServerIpAddress }
        ::= { zxAnSysDnsServerTable 1 }

    ZxAnSysDnsServerEntry ::= SEQUENCE {
        zxAnSysDnsServerIpAddressType        InetAddressType,
        zxAnSysDnsServerIpAddress            InetAddress,
        zxAnSysDnsServerType                 INTEGER,
        zxAnSysDnsServerRowStatus            RowStatus
    }
    
    zxAnSysDnsServerIpAddressType  OBJECT-TYPE 
        SYNTAX           InetAddressType
        MAX-ACCESS       not-accessible
        STATUS           current
        DESCRIPTION      
            "This object indicates the type of DNS server IP address."
        ::=  {  zxAnSysDnsServerEntry  1  } 
        
    zxAnSysDnsServerIpAddress  OBJECT-TYPE 
        SYNTAX           InetAddress
        MAX-ACCESS       not-accessible
        STATUS           current
        DESCRIPTION      
            "This Objects allows an NMS to configure a DNS server IP address."
        ::=  {  zxAnSysDnsServerEntry  2  }                   

    zxAnSysDnsServerType  OBJECT-TYPE 
        SYNTAX           INTEGER
            {
                primary(1),
                secondary(2)
            }
        MAX-ACCESS       read-create
        STATUS           current
        DESCRIPTION      
            "This Objects allows an NMS to specify whether the Server IP address
             is the primary DNS server or the secondary DNS server. Only One
             Primary DNS server is allowed to be configured."
        ::=  {  zxAnSysDnsServerEntry  3  }        
    
    zxAnSysDnsServerRowStatus  OBJECT-TYPE 
        SYNTAX           RowStatus
        MAX-ACCESS       read-create
        STATUS           current
        DESCRIPTION      ""
        ::=  {  zxAnSysDnsServerEntry  10  }
        
    zxAnSysDnsGlobalObjects           OBJECT IDENTIFIER  ::=  { zxAnSysDns 50 }
    
    zxAnSysDnsRequestMode OBJECT-TYPE
        SYNTAX      INTEGER
        {
            ttl(1),
            requestOnceWhenPowerOn(2)
        }
        MAX-ACCESS  read-write
        STATUS      current
        DESCRIPTION
            "DNS request mode.
             ttl(1) - Request the DNS server with the interval of TTL.
             requestOnceWhenPowerOn(2) - Request the DNS server once when system
                                         power on."
        DEFVAL  { ttl }
        ::= { zxAnSysDnsGlobalObjects 1 }

--------------------------------------------------------------------------------
-- 16.Outband Port Management
--------------------------------------------------------------------------------
  
    zxAnSysOutbandPortMgmt    OBJECT IDENTIFIER  ::=  { zxAnSysObjects 107 }

    zxAnSysOutbandPortAdminStatus OBJECT-TYPE
        SYNTAX  INTEGER {
                up(1),
                down(2)
            }
        MAX-ACCESS  read-write
        STATUS      current
        DESCRIPTION
            "The desired state of the interface."
        ::= { zxAnSysOutbandPortMgmt 1 }

    zxAnSysOutbandPortOperStatus OBJECT-TYPE
        SYNTAX  INTEGER 
        {
             up(1),
             down(2)
        }
        MAX-ACCESS  read-only
        STATUS      current
        DESCRIPTION
            "The current operational state of the interface. "
        ::= { zxAnSysOutbandPortMgmt 2 }

    zxAnSysOutbandPortDuplexSpeed OBJECT-TYPE
        SYNTAX          INTEGER 
        {
             autoNegotiate(1),
             half10(2), -- 10M-half
             full10(3), -- 10M-full
             half100(4),-- 100M-half
             full100(5),-- 100M-full
             full1000(6),-- 1000M-full
             full10000(7),-- 10000M-full
             illegal(99) 
        }
        MAX-ACCESS      read-write
        STATUS          current
        DESCRIPTION
            "DURABLE: { auto_negotiate:all }
            The desired speed and duplex for this interface. If the selected
            control is not possible on the interface, a value of illegal(99)
            is returned.  If the port type does NOT support the default
            of auto_negotiate(1), then the application initializes the
            port to a valid value (e.g., 1000full(6)).  Note that not all
            controls are possible for all interfaces.  For example, only
            full-1000(6) is available for Gigabit Ethernet interfaces."
        ::= { zxAnSysOutbandPortMgmt 3 }


    zxAnSysOutbandPortActualDuplex OBJECT-TYPE
        SYNTAX          INTEGER 
        {
             autoNegotiate(1),
             half(2),
             full(3)
        }
        MAX-ACCESS      read-only
        STATUS          current
        DESCRIPTION
            "The actual duplex for this interface. "
        ::= { zxAnSysOutbandPortMgmt 4 }

    zxAnSysOutbandPortActualSpeed OBJECT-TYPE
        SYNTAX          INTEGER 
        {
             speed10(1),
             speed100(2),
             speed1000(3),
             speed10000(4),
             autoSpeed(5)
        }
        MAX-ACCESS      read-only
        STATUS          current
        DESCRIPTION
            "The actual speed for this interface. "
        ::= { zxAnSysOutbandPortMgmt 5 }
        
    zxAnSysOutbandPortTagMode OBJECT-TYPE
        SYNTAX          INTEGER 
        {
             untagged(1),
             tagged(2)
        }
        MAX-ACCESS      read-write
        STATUS          current
        DESCRIPTION
            "The tag mode for this interface.
            untagged(1):zxAnSysOutbandPortVlanId and zxAnSysOutbandPortCos 
            are invalid.
            tagged(2): zxAnSysOutbandPortVlanId is required.
            zxAnSysOutbandPortCos is optional.
            If VLAN ID and CoS are configured, the packet which has the same 
            VLAN ID and CoS can be received. 
            If only VLAN ID is configured,the packet which has the same VLAN ID 
            can be received."
        ::= { zxAnSysOutbandPortMgmt 6 } 

    zxAnSysOutbandPortVlanId OBJECT-TYPE
        SYNTAX          Integer32 (0..4094)
        MAX-ACCESS      read-write
        STATUS          current
        DESCRIPTION
            "VLAN ID for this interface. Value 0 means unconfigured." 
        ::= { zxAnSysOutbandPortMgmt 7 }     
    
    zxAnSysOutbandPortCos OBJECT-TYPE
        SYNTAX          Integer32 (0..7 | 255)
        MAX-ACCESS      read-write
        STATUS          current
        DESCRIPTION
            "CoS value for this interface. Value 255 means unconfigured." 
        ::= { zxAnSysOutbandPortMgmt 8 }     

--------------------------------------------------------------------------------
-- 17.SNMP Management    
--------------------------------------------------------------------------------
        
    zxAnSysSnmpMgmt    OBJECT IDENTIFIER  ::=  { zxAnSysObjects 108 }
    
    zxAnSnmpEngineIdGenerateMode   OBJECT-TYPE     
       SYNTAX      INTEGER
       {
            mac(1),
            sysName(2)
       }
       MAX-ACCESS  read-write
       STATUS      current
       DESCRIPTION 
          "It determines how to generate the SnmpEngineID."
       DEFVAL { mac }              
       ::=  {  zxAnSysSnmpMgmt  1  }
    zxAnSnmpSupportedVersion   OBJECT-TYPE     
       SYNTAX      INTEGER
       {
            all(1),
            onlySnmpV3(2)
       }
       MAX-ACCESS  read-write
       STATUS      current
       DESCRIPTION 
          "This value configs the SNMP version.
          all(1)          --support SNMPv1,SNMPv2,SNMPv3.
          onlySnmpV3(2)   --only support SNMPv3."
       DEFVAL { all }              
       ::=  {  zxAnSysSnmpMgmt  2  }
--------------------------------------------------------------------------------
-- 18.Profile Operation Management
--------------------------------------------------------------------------------

    zxAnSysProfileOperMgmt   OBJECT IDENTIFIER ::= { zxAnSysObjects 109 }
    
    zxAnSysProfileOperGlobalObjects  
        OBJECT IDENTIFIER ::= { zxAnSysProfileOperMgmt 1 }
    
    zxAnSysProfileCategory OBJECT-TYPE
        SYNTAX      DisplayString(SIZE(0..32))
        MAX-ACCESS  accessible-for-notify
        STATUS      current
        DESCRIPTION
            "This object indicates the category of profile."
        ::= { zxAnSysProfileOperGlobalObjects 1 }
    
    zxAnSysProfileName OBJECT-TYPE
        SYNTAX      DisplayString(SIZE(0..32))
        MAX-ACCESS  accessible-for-notify
        STATUS      current
        DESCRIPTION
            "This object is used to indicate the profile name.
             Empty string means that the profile does not support profile name.
            "
        ::= { zxAnSysProfileOperGlobalObjects 2 }
        
    zxAnSysProfileId OBJECT-TYPE
        SYNTAX      Integer32
        MAX-ACCESS  accessible-for-notify
        STATUS      current
        DESCRIPTION
            "This object is used to indicate the profile ID.
             Value 0 means that the profile does not support ID.
            "
        ::= { zxAnSysProfileOperGlobalObjects 3 }
        
    zxAnSysProfileInfo OBJECT-TYPE
        SYNTAX      DisplayString(SIZE(0..256))
        MAX-ACCESS  accessible-for-notify
        STATUS      current
        DESCRIPTION
            "This object is used to indicate the profile information, such as
             showing the port list that the profile has been applied.
            "
        ::= { zxAnSysProfileOperGlobalObjects 4 }

--------------------------------------------------------------------------------
-- 19.System ARP Management
--------------------------------------------------------------------------------

    zxAnSysMgmtArp   OBJECT IDENTIFIER ::= { zxAnSysObjects 110 }
    
    zxAnSysMgmtArpGlobalObjects  OBJECT IDENTIFIER ::= { zxAnSysMgmtArp 1 }
    
    zxAnSysMgmtArpAgingTime OBJECT-TYPE
        SYNTAX      Integer32(1..60)
        UNITS       "minutes"
        MAX-ACCESS  read-write
        STATUS      current
        DESCRIPTION "The management aging time for the ARP table of current 
            device."            
        DEFVAL { 20 }                   
        ::= { zxAnSysMgmtArpGlobalObjects 1 }
    
--------------------------------------------------------------------------------
-- 11.Sytem Mgmt Trap
--------------------------------------------------------------------------------

--------------------------------------------------------------------------------
-- 11.1 Ntp Trap
--------------------------------------------------------------------------------
    zxAnSysNtpTrapGroup  OBJECT IDENTIFIER  ::= { zxAnSysTrapObjects 5 }

    zxAnSysNtpOffsetOverThreshTrap      NOTIFICATION-TYPE
            OBJECTS { zxAnSysNtpCurrentOffset,
                      zxAnSysNtpOffsetAlarmThreshold  }
            STATUS  current
            DESCRIPTION
                "zxAnSysNtpOffsetAlarmThreshold is reached."
            ::= { zxAnSysNtpTrapGroup 1 }

    zxAnSysNtpOffsetUnderThreshTrap      NOTIFICATION-TYPE
            OBJECTS { zxAnSysNtpCurrentOffset,
                      zxAnSysNtpOffsetAlarmThreshold  }
            STATUS  current
            DESCRIPTION
                "zxAnSysNtpCurrentOffset is below
                 zxAnSysNtpOffsetAlarmThreshold.
                "
            ::= { zxAnSysNtpTrapGroup 2 }

--------------------------------------------------------------------------------
-- 11.2 Security Trap
--------------------------------------------------------------------------------
    zxAnSysSecurityTrapGroup  OBJECT IDENTIFIER  ::= { zxAnSysTrapObjects 6 }

    zxAnSysSecCrftTerminLogonTrap      NOTIFICATION-TYPE
       OBJECTS {   zxAnCliCrftTerminalLastLoginType,zxAnCliActiveUserName,
                   zxAnCliActiveUserLocation }
    
            STATUS  current
            DESCRIPTION
                " User has logon equipment through the craft terminal interface.
                "
            ::= { zxAnSysSecurityTrapGroup 1 }



    zxAnSysSecCrftTerminLogoutTrap      NOTIFICATION-TYPE
       OBJECTS {   zxAnCliCrftTerminalLastLoginType,zxAnCliActiveUserName,
                   zxAnCliActiveUserLocation }
            STATUS  current
            DESCRIPTION
                " User has logout equipment from the craft terminal interface."
            ::= { zxAnSysSecurityTrapGroup 2 }
            
    zxAnSysSecCrftTerminLoginFailed     NOTIFICATION-TYPE
        OBJECTS { 
                    zxAnCliCrftTerminalLastLoginType,
                    zxAnCliTryToLoginUserName,
                    zxAnCliTryToLoginUserLocation
                }
        STATUS  current
        DESCRIPTION
            "Notification when a user login failed.
             When a user login failed from console,
             the zxAnCliTryToLoginUserName and zxAnCliTryToLoginUserLocation is
             empty string.
             when a user login failed from telnet, 
             the zxAnCliTryToLoginUserLocation is user's IP address."
        ::= { zxAnSysSecurityTrapGroup 3 }
            
--------------------------------------------------------------------------------
-- 11.3 Summer time Trap
--------------------------------------------------------------------------------
    zxAnSysSummerTimeTrapGroup  OBJECT IDENTIFIER  ::= { zxAnSysTrapObjects 7 }

    zxAnSysSummerTimeStartTrap      NOTIFICATION-TYPE
            OBJECTS { zxAnRtcSummerTimeName,zxAnRtcSummerTimeOffset, zxAnRtcSummerTimeStart, zxAnRtcSummerTimeEnd  }
            STATUS  current
            DESCRIPTION
                "It indication the summer time feature is start on this device."
            ::= { zxAnSysSummerTimeTrapGroup 1 }

    zxAnSysSummerTimeEndTrap      NOTIFICATION-TYPE
            OBJECTS { zxAnRtcSummerTimeName,zxAnRtcSummerTimeOffset, zxAnRtcSummerTimeStart, zxAnRtcSummerTimeEnd  }
            STATUS  current
            DESCRIPTION
                " It indication the summer time feature is end on this device."
            ::= { zxAnSysSummerTimeTrapGroup 2 }            

--------------------------------------------------------------------------------
-- 11.4 Clock Trap
--------------------------------------------------------------------------------
    zxAnSysClockTrapGroup  OBJECT IDENTIFIER  ::= { zxAnSysTrapObjects 8 }

    zxAnSysClockSourceSwitchTrap      NOTIFICATION-TYPE
        OBJECTS { zxAnSysActualClockSource,zxAnSysLastClockSource, 
            zxAnSysActualClockSourceE1, zxAnSysLastClockSourceE1  }
        STATUS  current
        DESCRIPTION
            "The clock source of NE has been switched."
        ::= { zxAnSysClockTrapGroup 1 }

    zxAnSysClkSrcUnavailableTrap      NOTIFICATION-TYPE
        OBJECTS { zxAnSysLastClockSource }
        STATUS  current
        DESCRIPTION
            "The clock source is unavailable."
        ::= { zxAnSysClockTrapGroup 2 }

    zxAnSysClkSrcAvailableTrap      NOTIFICATION-TYPE
        OBJECTS { zxAnSysLastClockSource }
        STATUS  current
        DESCRIPTION
            "The clock source is available."
        ::= { zxAnSysClockTrapGroup 3 }

--------------------------------------------------------------------------------
-- 11.5 Operate Profile Trap
--------------------------------------------------------------------------------

    zxAnSysProfileOperTrapGroup  OBJECT IDENTIFIER  ::= { zxAnSysTrapObjects 9 }
    
    zxAnSysDelAppliedPrfFailedNotify      NOTIFICATION-TYPE
        OBJECTS 
            { 
                zxAnSysProfileCategory,
                zxAnSysProfileName, 
                zxAnSysProfileId, 
                zxAnSysProfileInfo
            }
        STATUS  current
        DESCRIPTION
            "This notification will be sent to managemet system when a profile
             that has been applied is deleted.
             
             If profile supports name, zxAnSysProfileName must be filled first.
             
             If profile supports ID, zxAnSysProfileId should be filled 
             with profile ID.
            "
        ::= { zxAnSysProfileOperTrapGroup 1 }

--------------------------------------------------------------------------------
-- 11.6 System Resource Trap
--------------------------------------------------------------------------------

    zxAnSysResourceTrapGroup  OBJECT IDENTIFIER  ::= { zxAnSysTrapObjects 10 }
    
    zxAnSysResourceInsufficientTrap       NOTIFICATION-TYPE
        OBJECTS 
            { 
                zxAnSysResourceType
            }
        STATUS  current
        DESCRIPTION
            "This message will be sent to managemet system when system resource 
            is insufficient."
        ::= { zxAnSysResourceTrapGroup 1 }
END

ZTE-AN-V5-MIB DEFINITIONS ::= BEGIN

  IMPORTS
      MODULE-IDENTITY         FROM SNMPv2-SMI
      NOTIFICATION-TYPE       FROM SNMPv2-SMI
      OBJECT-TYPE             FROM SNMPv2-SMI 
      enterprises             FROM SNMPv2-SMI
      Counter32               FROM SNMPv2-SMI
      Integer32               FROM SNMPv2-SMI 
      Counter64               FROM SNMPv2-SMI 
      Unsigned32              FROM SNMPv2-SMI  
      Gauge32                 FROM SNMPv2-SMI
      TEXTUAL-CONVENTION      FROM SNMPv2-TC
      RowStatus               FROM SNMPv2-TC 
      DisplayString           FROM SNMPv2-TC
      TruthValue              FROM SNMPv2-TC;

    zxAnV5Mib MODULE-IDENTITY
        LAST-UPDATED    "0608140000Z"  -- july. 23, 2005
        ORGANIZATION    "zte Telcom Co. Ltd."
        CONTACT-INFO    "E-mail: shen.yuyang@zte.com.cn,
                         E-mail: suchunshan@zte.com.cn"
        DESCRIPTION     "This MIB defines PortLocating managed objects for Access Node."

    ::= { zxAn 5200 }
    
    zte OBJECT IDENTIFIER ::= { enterprises 3902 }
    zxAn OBJECT IDENTIFIER ::= { zte 1015 }
    msagmajorVersion OBJECT IDENTIFIER ::= { zxAnV5Mib 3 }

-- MODULE DESCRIPTION END 

msagV5Service OBJECT IDENTIFIER ::= { msagmajorVersion 5 }

   v5InterfaceTable OBJECT-TYPE
      SYNTAX    SEQUENCE OF V5InterfaceEntry
      MAX-ACCESS not-accessible
      STATUS     current
      DESCRIPTION ""
      ::={msagV5Service 1}

  v5InterfaceEntry OBJECT-TYPE
      SYNTAX    V5InterfaceEntry
      MAX-ACCESS not-accessible
      STATUS     current
      DESCRIPTION ""
      INDEX {v5IFID}
      ::={v5InterfaceTable 1}

  V5InterfaceEntry ::=
        SEQUENCE{
          v5IFID                 Unsigned32,
          v5IFType               INTEGER,
          v5IFVar                INTEGER,
          v5IFLeType             INTEGER,
          v5IFStatus             INTEGER,
          v5IFCommCtrlStatus     INTEGER,
          v5IFPstnDLStatus       INTEGER,
          v5IFBccDLStatus        INTEGER,
          v5IFLinkDLStatus       INTEGER,
          v5IFCtrlDLStatus       INTEGER,
          v5IFProtMDLStatus      INTEGER,
          v5IFProtBDLStatus      INTEGER,
          v5IFNewV5IID           Unsigned32,
          v5IFRowStatus          RowStatus
      }

    v5IFID    OBJECT-TYPE
        SYNTAX      Unsigned32
        MAX-ACCESS  not-accessible
        STATUS      current
        DESCRIPTION ""
        ::= { v5InterfaceEntry 1 }

    v5IFType    OBJECT-TYPE
        SYNTAX      INTEGER{v51Type(1),v52Type(2)}
        MAX-ACCESS  read-create
        STATUS      current
        DESCRIPTION ""
        ::= { v5InterfaceEntry 2 }

    v5IFVar    OBJECT-TYPE
        SYNTAX      INTEGER(0..254)
        MAX-ACCESS  read-create
        STATUS      current
        DESCRIPTION ""
        ::= { v5InterfaceEntry 3 }

    v5IFLeType    OBJECT-TYPE
        SYNTAX      INTEGER{
            leNormal(0),
            leF_150(1),
            leS11240(2),
            leL_5ESS(3),
            leC_C08(4),
            leEWSD(5),
            leDMS(6),
            leSP30(7),
            leNec(8),
            leHJD04(9),
            leSTND(10),
            leCompliance(11)
        }
        MAX-ACCESS  read-create
        STATUS      current
        DESCRIPTION ""
        ::= { v5InterfaceEntry 4 }

    v5IFStatus    OBJECT-TYPE
        SYNTAX      INTEGER{inDeactive(0),inActive(1),inCtrlDeactive(2),inInvalid(255)}
        MAX-ACCESS  read-create
        STATUS      current
        DESCRIPTION ""
        ::= { v5InterfaceEntry 5 }

    v5IFCommCtrlStatus    OBJECT-TYPE
        SYNTAX      INTEGER{commNormal(0),commStop(1)}
        MAX-ACCESS  read-only
        STATUS      current
        DESCRIPTION ""
        ::= { v5InterfaceEntry 6 }

    v5IFPstnDLStatus     OBJECT-TYPE
        SYNTAX      INTEGER{dlNormal(0),dlAbNormal(1)}
        MAX-ACCESS  read-only
        STATUS      current
        DESCRIPTION ""
        ::= { v5InterfaceEntry 7 }

   v5IFBccDLStatus     OBJECT-TYPE
        SYNTAX      INTEGER{dlNormal(0),dlAbNormal(1)}
        MAX-ACCESS  read-only
        STATUS      current
        DESCRIPTION ""
        ::= { v5InterfaceEntry 8 }

   v5IFLinkDLStatus     OBJECT-TYPE
        SYNTAX      INTEGER{dlNormal(0),dlAbNormal(1)}
        MAX-ACCESS  read-only
        STATUS      current
        DESCRIPTION ""
        ::= { v5InterfaceEntry 9 }

   v5IFCtrlDLStatus     OBJECT-TYPE
        SYNTAX      INTEGER{dlNormal(0),dlAbNormal(1)}
        MAX-ACCESS  read-only
        STATUS      current
        DESCRIPTION ""
        ::= { v5InterfaceEntry 10 }

   v5IFProtMDLStatus     OBJECT-TYPE
        SYNTAX      INTEGER{dlNormal(0),dlAbNormal(1)}
        MAX-ACCESS  read-only
        STATUS      current
        DESCRIPTION ""
        ::= { v5InterfaceEntry 11 }

   v5IFProtBDLStatus     OBJECT-TYPE
        SYNTAX      INTEGER{dlNormal(0),dlAbNormal(1)}
        MAX-ACCESS  read-only
        STATUS      current
        DESCRIPTION ""
        ::= { v5InterfaceEntry 12 }

   v5IFNewV5IID     OBJECT-TYPE
        SYNTAX      Unsigned32
        MAX-ACCESS  read-create
        STATUS      current
        DESCRIPTION ""
        ::= { v5InterfaceEntry 13 }

    v5IFRowStatus    OBJECT-TYPE
        SYNTAX      RowStatus
        MAX-ACCESS  read-create
        STATUS      current
        DESCRIPTION ""
        ::= { v5InterfaceEntry 14 }

    v5LinkTable OBJECT-TYPE
      SYNTAX    SEQUENCE OF V5LinkEntry
      MAX-ACCESS not-accessible
      STATUS     current
      DESCRIPTION ""
      ::={msagV5Service 3}

   v5LinkEntry OBJECT-TYPE
      SYNTAX    V5LinkEntry
      MAX-ACCESS not-accessible
      STATUS     current
      DESCRIPTION ""
      INDEX {v5LinkV5IID, v5LinkID}
      ::={v5LinkTable 1}

   V5LinkEntry ::=
        SEQUENCE{
          v5LinkV5IID           Unsigned32,
          v5LinkID              INTEGER,
          v5LinkRack            INTEGER,
          v5LinkShelf           INTEGER,
          v5LinkSlot            INTEGER,
          v5LinkE1No            INTEGER,
          v5LinkType            INTEGER,
          v5LinkStatus          INTEGER,
          v5LinkTs15PchFlag     INTEGER,
          v5LinkTs16PchFlag     INTEGER,
          v5LinkTs31PchFlag     INTEGER,
          v5LinkNewID           INTEGER,
          v5LinkRowStatus       RowStatus,
          v5linkBlockFlag       INTEGER,
          v5linkVerify          INTEGER,
          v5linkTs              INTEGER,
          v5linkAnfaultSet      INTEGER
      }

    v5LinkV5IID    OBJECT-TYPE
        SYNTAX      Unsigned32
        MAX-ACCESS  not-accessible
        STATUS      current
        DESCRIPTION ""
        ::= { v5LinkEntry 1 }

    v5LinkID    OBJECT-TYPE
        SYNTAX      INTEGER(1..255)
        MAX-ACCESS  not-accessible
        STATUS      current
        DESCRIPTION ""
        ::= { v5LinkEntry 2 }

    v5LinkRack    OBJECT-TYPE
        SYNTAX      INTEGER(1..3)
        MAX-ACCESS  read-create
        STATUS      current
        DESCRIPTION ""
        ::= { v5LinkEntry 3 }

    v5LinkShelf    OBJECT-TYPE
        SYNTAX      INTEGER(1..5)
        MAX-ACCESS  read-create
        STATUS      current
        DESCRIPTION ""
        ::= { v5LinkEntry 4 }

    v5LinkSlot    OBJECT-TYPE
        SYNTAX      INTEGER(1..23)
        MAX-ACCESS  read-create
        STATUS      current
        DESCRIPTION ""
        ::= { v5LinkEntry 5 }

    v5LinkE1No    OBJECT-TYPE
        SYNTAX      INTEGER(1..8)
        MAX-ACCESS  read-create
        STATUS      current
        DESCRIPTION ""
        ::= { v5LinkEntry 6 }

    v5LinkType    OBJECT-TYPE
        SYNTAX      INTEGER{mainLink(0),standbyLink(1),normalLink(2)}
        MAX-ACCESS  read-only
        STATUS      current
        DESCRIPTION ""
        ::= { v5LinkEntry 7 }

    v5LinkStatus    OBJECT-TYPE
        SYNTAX      INTEGER{
            linkNormal(0),
            linkFault(1),
            linkFaultBlock(2),
            linkRemoteBlock(3),
            linkLocalBlock(4),
            linkCicBlock(5),
            linkBlock(6)
        }
        MAX-ACCESS  read-only
        STATUS      current
        DESCRIPTION ""
        ::= { v5LinkEntry 8 }

    v5LinkTs15PchFlag    OBJECT-TYPE
        SYNTAX      INTEGER{tsUnUsed(0),tsUnsed(1)}
        MAX-ACCESS  read-only
        STATUS      current
        DESCRIPTION ""
        ::= { v5LinkEntry 9 }

    v5LinkTs16PchFlag    OBJECT-TYPE
        SYNTAX      INTEGER{tsUnUsed(0),tsUsed(1)}
        MAX-ACCESS  read-only
        STATUS      current
        DESCRIPTION ""
        ::= { v5LinkEntry 10 }

    v5LinkTs31PchFlag    OBJECT-TYPE
        SYNTAX      INTEGER{tsUnUsed(0),tsUsed(1)}
        MAX-ACCESS  read-only
        STATUS      current
        DESCRIPTION ""
        ::= { v5LinkEntry 11 }

    v5LinkNewID    OBJECT-TYPE
        SYNTAX      INTEGER(1..255)
        MAX-ACCESS  read-create
        STATUS      current
        DESCRIPTION ""
        ::= { v5LinkEntry 12 }

    v5LinkRowStatus    OBJECT-TYPE
        SYNTAX      RowStatus
        MAX-ACCESS  read-create
        STATUS      current
        DESCRIPTION ""
        ::= { v5LinkEntry 13 }

  v5linkBlockFlag    OBJECT-TYPE
        SYNTAX      INTEGER(1..3)
        MAX-ACCESS  read-create
        STATUS      current
        DESCRIPTION "1-block with delay;2-block with not delay;3-unblock"
        ::= { v5LinkEntry 14 }
        
  v5linkVerify    OBJECT-TYPE
        SYNTAX      INTEGER(1)
        MAX-ACCESS  read-create
        STATUS      current
        DESCRIPTION ""
        ::= { v5LinkEntry 15 }
        
  v5linkTs        OBJECT-TYPE
        SYNTAX      INTEGER(15..31)
        MAX-ACCESS  read-create
        STATUS      current
        DESCRIPTION ""
        ::= { v5LinkEntry 16 }
        
  v5linkAnfaultSet  OBJECT-TYPE
        SYNTAX      INTEGER(1)
        MAX-ACCESS  read-create
        STATUS      current
        DESCRIPTION ""
        ::= { v5LinkEntry 17 }
        
  v5PchTable OBJECT-TYPE
      SYNTAX    SEQUENCE OF V5PchEntry
      MAX-ACCESS not-accessible
      STATUS     current
      DESCRIPTION ""
      ::={msagV5Service 5}

  v5PchEntry OBJECT-TYPE
      SYNTAX    V5PchEntry
      MAX-ACCESS not-accessible
      STATUS     current
      DESCRIPTION ""
      INDEX {v5PchV5IID,v5PchLinkId,v5PchLinkTs}
      ::={v5PchTable 1}

  V5PchEntry ::=
        SEQUENCE{
          v5PchV5IID       Unsigned32,
          v5PchLinkId      INTEGER,
          v5PchLinkTs      INTEGER,
          v5PchProtGrp     INTEGER,
          v5PchStatus      INTEGER,
          v5PchCtsTln      Integer32,
          v5PchRowStatus   RowStatus
      }

    v5PchV5IID    OBJECT-TYPE
        SYNTAX      Unsigned32
        MAX-ACCESS  not-accessible
        STATUS      current
        DESCRIPTION ""
        ::= { v5PchEntry 1 }

    v5PchLinkId    OBJECT-TYPE
        SYNTAX      INTEGER(1..255)
        MAX-ACCESS  not-accessible
        STATUS      current
        DESCRIPTION ""
        ::= { v5PchEntry 2 }

   v5PchLinkTs     OBJECT-TYPE
        SYNTAX      INTEGER(0..31)
        MAX-ACCESS  not-accessible
        STATUS      current
        DESCRIPTION ""
        ::= { v5PchEntry 3 }

   v5PchProtGrp     OBJECT-TYPE
        SYNTAX      INTEGER(1..2)
        MAX-ACCESS  read-create
        STATUS      current
        DESCRIPTION ""
        ::= { v5PchEntry 4 }

   v5PchStatus     OBJECT-TYPE
        SYNTAX      INTEGER{pchNormal(0),pchAbNormal(1)}
        MAX-ACCESS  read-only
        STATUS      current
        DESCRIPTION ""
        ::= { v5PchEntry 5 }

   v5PchCtsTln     OBJECT-TYPE
        SYNTAX      Integer32
        MAX-ACCESS  read-only
        STATUS      current
        DESCRIPTION ""
        ::= { v5PchEntry 6 }

   v5PchRowStatus     OBJECT-TYPE
        SYNTAX      RowStatus
        MAX-ACCESS  read-create
        STATUS      current
        DESCRIPTION ""
        ::= { v5PchEntry 7 }

    v5LchTable OBJECT-TYPE
      SYNTAX    SEQUENCE OF V5LchEntry
      MAX-ACCESS not-accessible
      STATUS     current
      DESCRIPTION ""
      ::={msagV5Service 6}

  v5LchEntry OBJECT-TYPE
      SYNTAX    V5LchEntry
      MAX-ACCESS not-accessible
      STATUS     current
      DESCRIPTION ""
      INDEX {v5LchV5IID,v5LchLcci}
      ::={v5LchTable 1}

  V5LchEntry ::=
        SEQUENCE{
          v5LchV5IID             Unsigned32,
          v5LchLcci              INTEGER,
          v5LchLinkID            INTEGER,
          v5LchLinkTs            INTEGER,
          v5LchIsdnCreatedFlag   INTEGER,
          v5LchPstnCrreatedFlag  INTEGER,
          v5LchCtrlCreatedFlag   INTEGER,
          v5LchBccCreatedFlag    INTEGER,
          v5LchLinkCreatedFlag   INTEGER,
          v5LchProtCreatedFlag   INTEGER,
          v5LchCurrLinkId        INTEGER,
          v5LchCurrLinkTs        INTEGER,
          v5LchSwitch            INTEGER,
          v5LchRowStatus         RowStatus
      }

    v5LchV5IID    OBJECT-TYPE
        SYNTAX      Unsigned32(0..4294967294)
        MAX-ACCESS  not-accessible
        STATUS      current
        DESCRIPTION ""
        ::= { v5LchEntry 1 }

   v5LchLcci     OBJECT-TYPE
        SYNTAX      INTEGER(1..65535)
        MAX-ACCESS  not-accessible
        STATUS      current
        DESCRIPTION ""
        ::= { v5LchEntry 2 }

   v5LchLinkID     OBJECT-TYPE
        SYNTAX      INTEGER(1..255)
        MAX-ACCESS  read-create
        STATUS      current
        DESCRIPTION ""
        ::= { v5LchEntry 3 }

   v5LchLinkTs     OBJECT-TYPE
        SYNTAX      INTEGER(0..31)
        MAX-ACCESS  read-create
        STATUS      current
        DESCRIPTION ""
        ::= { v5LchEntry 4 }

   v5LchIsdnCreatedFlag     OBJECT-TYPE
        SYNTAX      INTEGER{flagNotCreated(0),flagCreated(1)}
        MAX-ACCESS  read-create
        STATUS      current
        DESCRIPTION ""
        ::= { v5LchEntry 5 }

   v5LchPstnCrreatedFlag     OBJECT-TYPE
        SYNTAX      INTEGER{flagNotCreated(0),flagCreated(1)}
        MAX-ACCESS  read-create
        STATUS      current
        DESCRIPTION ""
        ::= { v5LchEntry 6 }

   v5LchCtrlCreatedFlag     OBJECT-TYPE
        SYNTAX      INTEGER{flagNotCreated(0),flagCreated(1)}
        MAX-ACCESS  read-create
        STATUS      current
        DESCRIPTION ""
        ::= { v5LchEntry 7 }

    v5LchBccCreatedFlag    OBJECT-TYPE
        SYNTAX      INTEGER{flagNotCreated(0),flagCreated(1)}
        MAX-ACCESS  read-create
        STATUS      current
        DESCRIPTION ""
        ::= { v5LchEntry 8 }

    v5LchLinkCreatedFlag    OBJECT-TYPE
        SYNTAX      INTEGER{flagNotCreated(0),flagCreated(1)}
        MAX-ACCESS  read-create
        STATUS      current
        DESCRIPTION ""
        ::= { v5LchEntry 9 }

    v5LchProtCreatedFlag    OBJECT-TYPE
        SYNTAX      INTEGER{flagNotCreated(0),flagCreated(1)}
        MAX-ACCESS  read-create
        STATUS      current
        DESCRIPTION ""
        ::= { v5LchEntry 10 }

    v5LchCurrLinkId OBJECT-TYPE
        SYNTAX      INTEGER(1..255)
        MAX-ACCESS  read-only
        STATUS      current
        DESCRIPTION ""
        ::= { v5LchEntry 11 }

   v5LchCurrLinkTs  OBJECT-TYPE
        SYNTAX      INTEGER(0..31)
        MAX-ACCESS  read-only
        STATUS      current
        DESCRIPTION ""
        ::= { v5LchEntry 12 }

    v5LchSwitch    OBJECT-TYPE
        SYNTAX      INTEGER{noop(0),switch(1)}
        MAX-ACCESS  read-create
        STATUS      current
        DESCRIPTION ""
        ::= { v5LchEntry 13 }

   v5LchRowStatus   OBJECT-TYPE
        SYNTAX      RowStatus
        MAX-ACCESS  read-create
        STATUS      current
        DESCRIPTION ""
        ::= { v5LchEntry 14 }

    v5PstnUserTable OBJECT-TYPE
        SYNTAX      SEQUENCE OF V5PstnUserEntry
        MAX-ACCESS  not-accessible
        STATUS      current
        DESCRIPTION "A table of V5 User configuration."
        ::= { msagV5Service 8 }

    v5PstnUserEntry OBJECT-TYPE
        SYNTAX      V5PstnUserEntry
        MAX-ACCESS  not-accessible
        STATUS      current
        DESCRIPTION "A list of V5 User configuration."
        INDEX     { pstnV5IID, pstnL3Addr}
        ::= { v5PstnUserTable 1 }

    V5PstnUserEntry  ::= SEQUENCE {
        pstnV5IID               Unsigned32,
        pstnL3Addr              INTEGER,
        pstnRack                INTEGER,
        pstnShelf               INTEGER,
        pstnSlot                INTEGER,
        pstnPort                INTEGER,
        trunkRack               INTEGER,
        trunkShelf              INTEGER,
        trunkSlot               INTEGER,
        trunkE1No               INTEGER,
        trunkCircuit            INTEGER,
        pstnConnType            INTEGER,
        pstnTelType             Integer32,
        pstnPortStatus          INTEGER,
        pstnProtocolStatus      INTEGER,
        pstnSum                 INTEGER,
        pstnRowStatus           RowStatus,
        pstnportBlock           INTEGER,
        pstnportUnBlock         INTEGER
    }

    pstnV5IID       OBJECT-TYPE
        SYNTAX      Unsigned32
        MAX-ACCESS  not-accessible
        STATUS      current
        DESCRIPTION "the Id of V5 interface"
        ::= { v5PstnUserEntry 1 }

    pstnL3Addr      OBJECT-TYPE
        SYNTAX      INTEGER (0..32767)
        MAX-ACCESS  not-accessible
        STATUS      current
        DESCRIPTION "the L3 address of PSTN"
        ::= { v5PstnUserEntry 2 }

    pstnRack        OBJECT-TYPE
        SYNTAX      INTEGER (1..3)
        MAX-ACCESS  read-create
        STATUS      current
        DESCRIPTION "the rack sequence used by PSTN"
        ::= { v5PstnUserEntry 3 }

    pstnShelf       OBJECT-TYPE
        SYNTAX      INTEGER (1..5)
        MAX-ACCESS  read-create
        STATUS      current
        DESCRIPTION "the shelf sequence used by PSTN"
        ::= { v5PstnUserEntry 4 }

    pstnSlot        OBJECT-TYPE
        SYNTAX      INTEGER (1..23)
        MAX-ACCESS  read-create
        STATUS      current
        DESCRIPTION "the slot sequence used by PSTN"
        ::= { v5PstnUserEntry 5 }

    pstnPort        OBJECT-TYPE
        SYNTAX      INTEGER (0..31)
        MAX-ACCESS  read-create
        STATUS      current
        DESCRIPTION "the time slot used by PSTN"
        ::= { v5PstnUserEntry 6 }

    trunkRack       OBJECT-TYPE
        SYNTAX      INTEGER (1..3)
        MAX-ACCESS  read-create
        STATUS      current
        DESCRIPTION "the rack sequence used by trunk"
        ::= { v5PstnUserEntry 7 }

    trunkShelf      OBJECT-TYPE
        SYNTAX      INTEGER (1..5)
        MAX-ACCESS  read-create
        STATUS      current
        DESCRIPTION "the shelf sequence used by trunk"
        ::= { v5PstnUserEntry 8 }

    trunkSlot       OBJECT-TYPE
        SYNTAX      INTEGER(8|11..12)
        MAX-ACCESS  read-create
        STATUS      current
        DESCRIPTION "the slot sequence used by trunk"
        ::= { v5PstnUserEntry 9 }

    trunkE1No       OBJECT-TYPE
        SYNTAX      INTEGER (0..8)
        MAX-ACCESS  read-create
        STATUS      current
        DESCRIPTION "the E1 sequence used by trunk"
        ::= { v5PstnUserEntry 10 }

    trunkCircuit    OBJECT-TYPE
        SYNTAX      INTEGER (0..31)
        MAX-ACCESS  read-create
        STATUS      current
        DESCRIPTION "the time slot used by trunk"
        ::= { v5PstnUserEntry 11 }

    pstnConnType    OBJECT-TYPE
        SYNTAX      INTEGER {fix(0),active(1)}
        MAX-ACCESS  read-create
        STATUS      current
        DESCRIPTION "the connection type of PSTN"
        ::= { v5PstnUserEntry 12 }

    pstnTelType     OBJECT-TYPE
        SYNTAX      Integer32
        MAX-ACCESS  read-only
        STATUS      current
        DESCRIPTION "the telphone type of PSTN, unused"
        ::= { v5PstnUserEntry 13 }

    pstnPortStatus  OBJECT-TYPE
        SYNTAX      INTEGER {v5UpStop(0), vtUpIdle(1), v5UpBusy(2)}
        MAX-ACCESS  read-only
        STATUS      current
        DESCRIPTION "the status of PSTN port"
        ::= { v5PstnUserEntry 17 }

    pstnProtocolStatus  OBJECT-TYPE
        SYNTAX          INTEGER {ctrlIdle(0), ctrlBusy(1)}
        MAX-ACCESS      read-only
        STATUS          current
        DESCRIPTION     "the status of PSTN protocol"
        ::= { v5PstnUserEntry 18 }

    pstnSum             OBJECT-TYPE
        SYNTAX          INTEGER (1..192)
        MAX-ACCESS      read-create
        STATUS          current
        DESCRIPTION     "the customer number added once, write only"
        ::= { v5PstnUserEntry 25 }

    pstnRowStatus OBJECT-TYPE
         SYNTAX          RowStatus
         MAX-ACCESS      read-create
         STATUS          current
         DESCRIPTION     ""
         ::= { v5PstnUserEntry 26 }
         
    pstnportBlock       OBJECT-TYPE
         SYNTAX          INTEGER(0..1)
         MAX-ACCESS      read-create
         STATUS          current
         DESCRIPTION     "0-block with not delay;1-block with delay"
         ::= { v5PstnUserEntry 27 }
         
    pstnportUnBlock     OBJECT-TYPE
         SYNTAX          INTEGER(1)
         MAX-ACCESS      read-create
         STATUS          current
         DESCRIPTION     ""
         ::= { v5PstnUserEntry 28 }

    v5IsdnUserTable OBJECT-TYPE
        SYNTAX      SEQUENCE OF V5IsdnUserEntry
        MAX-ACCESS  not-accessible
        STATUS      current
        DESCRIPTION "A table of V5 Isdn User configuration."
        ::= { msagV5Service 9 }

    v5IsdnUserEntry OBJECT-TYPE
        SYNTAX      V5IsdnUserEntry
        MAX-ACCESS  not-accessible
        STATUS      current
        DESCRIPTION "A list of V5 User configuration."
        INDEX     { isdnV5IID, isdnEfAddr}
        ::= { v5IsdnUserTable 1 }

    V5IsdnUserEntry  ::= SEQUENCE {
        isdnV5IID               Unsigned32,
        isdnEfAddr              INTEGER,
        isdnRack                INTEGER,
        isdnShelf               INTEGER,
        isdnSlot                INTEGER,
        isdnPort                INTEGER,
        isdnTrunkRack           INTEGER,
        isdnTrunkShelf          INTEGER,
        isdnTrunkSlot           INTEGER,
        isdnTrunkE1No           INTEGER,
        isdnTrunkCircuit        INTEGER,
        isdnConnType            INTEGER,
        isdnTelType             Integer32,
        isdnDsLcci              INTEGER,
        isdnGroupLcci           INTEGER,
        isdnFrameLcci           INTEGER,
        isdnPortStatus          INTEGER,
        isdnProtocolStatus      INTEGER,
        isdnSemiPermFlag        INTEGER,
        isdnPolarityFlag        INTEGER,
        isdnDistance            Integer32,
        isdnV51UpPir            Integer32,
        isdnV52UpPir            Integer32,
        isdnV5IsAnfault         Integer32,
        isdnSum                 INTEGER,
        isdnRowStatus           RowStatus,
        isdnActive              INTEGER,
        isdnBlock               INTEGER,
        isdnUnBlock             INTEGER
    }

    isdnV5IID       OBJECT-TYPE
        SYNTAX      Unsigned32
        MAX-ACCESS  not-accessible
        STATUS      current
        DESCRIPTION "the ID of V5 interface"
        ::= { v5IsdnUserEntry 1 }

    isdnEfAddr      OBJECT-TYPE
        SYNTAX      INTEGER (0..8191)
        MAX-ACCESS  not-accessible
        STATUS      current
        DESCRIPTION ""
        ::= { v5IsdnUserEntry 2 }

    isdnRack        OBJECT-TYPE
        SYNTAX      INTEGER (1..3)
        MAX-ACCESS  read-create
        STATUS      current
        DESCRIPTION "the rack sequence used by ISDN"
        ::= { v5IsdnUserEntry 3 }

    isdnShelf       OBJECT-TYPE
        SYNTAX      INTEGER (1..5)
        MAX-ACCESS  read-create
        STATUS      current
        DESCRIPTION "the shelf sequence used by ISDN"
        ::= { v5IsdnUserEntry 4 }

    isdnSlot        OBJECT-TYPE
        SYNTAX      INTEGER (1..23)
        MAX-ACCESS  read-create
        STATUS      current
        DESCRIPTION "the slot sequence used by ISDN"
        ::= { v5IsdnUserEntry 5 }

    isdnPort        OBJECT-TYPE
        SYNTAX      INTEGER (0..31)
        MAX-ACCESS  read-create
        STATUS      current
        DESCRIPTION "the time slot used by ISDN"
        ::= { v5IsdnUserEntry 6 }

    isdnTrunkRack       OBJECT-TYPE
        SYNTAX      INTEGER (1..3)
        MAX-ACCESS  read-create
        STATUS      current
        DESCRIPTION "the rack sequence used by trunk"
        ::= { v5IsdnUserEntry 7 }

    isdnTrunkShelf      OBJECT-TYPE
        SYNTAX      INTEGER (1..5)
        MAX-ACCESS  read-create
        STATUS      current
        DESCRIPTION "the shelf sequence used by trunk"
        ::= { v5IsdnUserEntry 8 }

    isdnTrunkSlot       OBJECT-TYPE
        SYNTAX      INTEGER(8|11..12)
        MAX-ACCESS  read-create
        STATUS      current
        DESCRIPTION "the slot sequence used by trunk"
        ::= { v5IsdnUserEntry 9 }

    isdnTrunkE1No       OBJECT-TYPE
        SYNTAX      INTEGER (0..8)
        MAX-ACCESS  read-create
        STATUS      current
        DESCRIPTION "the E1 sequence used by trunk"
        ::= { v5IsdnUserEntry 10 }

    isdnTrunkCircuit    OBJECT-TYPE
        SYNTAX      INTEGER (0..31)
        MAX-ACCESS  read-create
        STATUS      current
        DESCRIPTION "the time slot used by trunk"
        ::= { v5IsdnUserEntry 11 }

    isdnConnType    OBJECT-TYPE
        SYNTAX      INTEGER {fix(0),active(1)}
        MAX-ACCESS  read-create
        STATUS      current
        DESCRIPTION "the connect type of ISDN"
        ::= { v5IsdnUserEntry 12 }

    isdnTelType     OBJECT-TYPE
        SYNTAX      Integer32
        MAX-ACCESS  read-create
        STATUS      current
        DESCRIPTION "the telphone type of ISDN, unused"
        ::= { v5IsdnUserEntry 13 }

    isdnDsLcci      OBJECT-TYPE
        SYNTAX      INTEGER (0..65534)
        MAX-ACCESS  read-create
        STATUS      current
        DESCRIPTION "the ID of logical C channel used by ISDN ds"
        ::= { v5IsdnUserEntry 14 }

    isdnGroupLcci   OBJECT-TYPE
        SYNTAX      INTEGER (0..65534)
        MAX-ACCESS  read-create
        STATUS      current
        DESCRIPTION "the ID of logical C channel used by ISDN group"
        ::= { v5IsdnUserEntry 15 }

    isdnFrameLcci   OBJECT-TYPE
        SYNTAX      INTEGER (0..65534)
        MAX-ACCESS  read-create
        STATUS      current
        DESCRIPTION "the ID of logical C channel used by ISDN frame"
        ::= { v5IsdnUserEntry 16 }

    isdnPortStatus  OBJECT-TYPE
        SYNTAX      INTEGER {v5UpStop(0), vtUpIdle(1), v5UpBusy(2)}
        MAX-ACCESS  read-only
        STATUS      current
        DESCRIPTION "the status of ISDN port"
        ::= { v5IsdnUserEntry 17 }

    isdnProtocolStatus  OBJECT-TYPE
        SYNTAX          INTEGER {ctrlIdle(0), ctrlBusy(1)}
        MAX-ACCESS      read-only
        STATUS          current
        DESCRIPTION     "the status of the control protocol "
        ::= { v5IsdnUserEntry 18 }

    isdnSemiPermFlag    OBJECT-TYPE
        SYNTAX          INTEGER{flagUsed(0), flagUnused(1)}
        MAX-ACCESS      read-create
        STATUS          current
        DESCRIPTION     "unused"
        ::= { v5IsdnUserEntry 19 }

    isdnPolarityFlag    OBJECT-TYPE
        SYNTAX          INTEGER{positive(0),negative(1)}
        MAX-ACCESS      read-create
        STATUS          current
        DESCRIPTION     "unused"
        ::= { v5IsdnUserEntry 20 }

    isdnDistance        OBJECT-TYPE
        SYNTAX          Integer32
        MAX-ACCESS      read-create
        STATUS          current
        DESCRIPTION     "unused"
        ::= { v5IsdnUserEntry 21 }

    isdnV51UpPir        OBJECT-TYPE
        SYNTAX          Integer32
        MAX-ACCESS      read-only
        STATUS          current
        DESCRIPTION     "the priority of V51, unused"
        ::= { v5IsdnUserEntry 22 }

    isdnV52UpPir        OBJECT-TYPE
        SYNTAX          Integer32
        MAX-ACCESS      read-only
        STATUS          current
        DESCRIPTION     "thr priority of V52, unused"
        ::= { v5IsdnUserEntry 23 }

    isdnV5IsAnfault     OBJECT-TYPE
        SYNTAX          Integer32
        MAX-ACCESS      read-only
        STATUS          current
        DESCRIPTION     "unused"
        ::= { v5IsdnUserEntry 24 }

    isdnSum             OBJECT-TYPE
        SYNTAX          INTEGER (1..192)
        MAX-ACCESS      read-create
        STATUS          current
        DESCRIPTION     "the customer number added once, write only"
        ::= { v5IsdnUserEntry 25 }

    isdnRowStatus OBJECT-TYPE
         SYNTAX          RowStatus
         MAX-ACCESS      read-create
         STATUS          current
         DESCRIPTION     ""
         ::= { v5IsdnUserEntry 26 }
         
    isdnActive  OBJECT-TYPE
         SYNTAX          INTEGER(1)
         MAX-ACCESS      read-create
         STATUS          current
         DESCRIPTION     ""
         ::= { v5IsdnUserEntry 27 }
         
    isdnBlock  OBJECT-TYPE
         SYNTAX          INTEGER(0..1)
         MAX-ACCESS      read-create
         STATUS          current
         DESCRIPTION     "0-block with not delay;1-block with delay"
         ::= { v5IsdnUserEntry 28 }
         
    isdnUnBlock  OBJECT-TYPE
         SYNTAX          INTEGER(1)
         MAX-ACCESS      read-create
         STATUS          current
         DESCRIPTION     ""
         ::= { v5IsdnUserEntry 29 }
         
   msagServiceV5  OBJECT-TYPE
        SYNTAX    INTEGER{notSupport(0),support(1)} 
        MAX-ACCESS  read-only
        STATUS    current
        DESCRIPTION  ""
        ::={msagV5Service 10}

    v5LinkTsTable   OBJECT-TYPE
        SYNTAX      SEQUENCE OF V5LinkTsEntry
        MAX-ACCESS  not-accessible
        STATUS      current
        DESCRIPTION
            ""
        ::= { msagV5Service 11 }

    v5LinkTsEntry   OBJECT-TYPE
        SYNTAX      V5LinkTsEntry
        MAX-ACCESS  not-accessible
        STATUS      current
        DESCRIPTION
            ""
        INDEX     { v5LinkTsV5IID, v5LinkTsLinkID , v5LinkTsNo}
        ::= { v5LinkTsTable 1 }

    V5LinkTsEntry ::= SEQUENCE {
        v5LinkTsV5IID           Unsigned32,
        v5LinkTsLinkID          INTEGER,
        v5LinkTsNo              INTEGER,
        v5LinkTsState           INTEGER,
        v5LinkTsL3Addr          INTEGER,
        v5LinkTsFlag            INTEGER,
        v5LinkTsBlock           INTEGER,
        v5LinkTsUnBlock         INTEGER
    }

    v5LinkTsV5IID       OBJECT-TYPE
        SYNTAX      Unsigned32
        MAX-ACCESS  not-accessible
        STATUS      current
        DESCRIPTION
                    "the ID of V5 interface"
        ::= { v5LinkTsEntry 1 }

    v5LinkTsLinkID          OBJECT-TYPE
        SYNTAX      INTEGER (0..255)
        MAX-ACCESS  not-accessible
        STATUS      current
        DESCRIPTION
                    "the ID of V5 link"
        ::= { v5LinkTsEntry 2 }
       
    v5LinkTsNo          OBJECT-TYPE
        SYNTAX      INTEGER(0..255)
        MAX-ACCESS  not-accessible
        STATUS      current
        DESCRIPTION
                    "the TS NO of V5 link"
        ::= { v5LinkTsEntry 3 }
        
    v5LinkTsState    OBJECT-TYPE
        SYNTAX          INTEGER{tlnidle(0),tlnbusy(1),tlnblock(2),tlninvalid(255)}
        MAX-ACCESS      read-only
        STATUS          current
        DESCRIPTION     "the state of link ts"
        ::= { v5LinkTsEntry 4 }

    v5LinkTsL3Addr    OBJECT-TYPE
        SYNTAX          INTEGER(0..32767)
        MAX-ACCESS      read-only
        STATUS          current
        DESCRIPTION     "the L3 address"
        ::= { v5LinkTsEntry 5 }
        
    v5LinkTsFlag    OBJECT-TYPE
        SYNTAX          INTEGER(1)
        MAX-ACCESS      read-write
        STATUS          current
        DESCRIPTION     "The flag of get operate"
        ::= { v5LinkTsEntry 6 }
        
    v5LinkTsBlock    OBJECT-TYPE
        SYNTAX          INTEGER(1)
        MAX-ACCESS      read-write
        STATUS          current
        DESCRIPTION     "block link ts : only 16 ts"
        ::= { v5LinkTsEntry 7 }
        
    v5LinkTsUnBlock    OBJECT-TYPE
        SYNTAX          INTEGER(1)
        MAX-ACCESS      read-write
        STATUS          current
        DESCRIPTION     "unblock link ts : only 16 ts"
        ::= { v5LinkTsEntry 8 }   
        
        
------------------------

    zxAnV5UaLinkTable   OBJECT-TYPE
        SYNTAX      SEQUENCE OF ZxAnV5UaLinkEntry
        MAX-ACCESS  not-accessible
        STATUS      current
        DESCRIPTION
            "The V5UA link config table."
        ::= { msagV5Service 12 }

    zxAnV5UaLinkEntry   OBJECT-TYPE
        SYNTAX      ZxAnV5UaLinkEntry
        MAX-ACCESS  not-accessible
        STATUS      current
        DESCRIPTION
            "The V5UA link config entry."
        INDEX     { zxAnV5UaLinkRack, zxAnV5UaLinkShelf , zxAnV5UaLinkSlot, 
                    zxAnV5UaLinkDsx1LinkNo, zxAnV5UaLinkDsx1TsNo}
        ::= { zxAnV5UaLinkTable 1 }

    ZxAnV5UaLinkEntry ::= SEQUENCE {
        zxAnV5UaLinkRack                Integer32,
        zxAnV5UaLinkShelf               Integer32,
        zxAnV5UaLinkSlot                Integer32,
        zxAnV5UaLinkDsx1LinkNo          Integer32,          
        zxAnV5UaLinkDsx1TsNo            Integer32,         
        zxAnV5UaLinkV5LinkId            Integer32,       
        zxAnV5UaLinkAsId                Integer32,   
        zxAnV5UaLinkIfId                Integer32,
        zxAnV5UaLinkRowStatus           RowStatus
    }

    zxAnV5UaLinkRack  OBJECT-TYPE
        SYNTAX      Integer32
        MAX-ACCESS  not-accessible
        STATUS      current
        DESCRIPTION
            " This object indicates the rack number."
        ::= { zxAnV5UaLinkEntry 1 }  
        
    zxAnV5UaLinkShelf  OBJECT-TYPE
        SYNTAX      Integer32
        MAX-ACCESS  not-accessible
        STATUS      current
        DESCRIPTION
            " This object indicates the shelf number."
        ::= { zxAnV5UaLinkEntry 2 }

    zxAnV5UaLinkSlot  OBJECT-TYPE
        SYNTAX      Integer32
        MAX-ACCESS  not-accessible
        STATUS      current
        DESCRIPTION
            " This object indicates the slot number. "
        ::= { zxAnV5UaLinkEntry 3 }          
        
    zxAnV5UaLinkDsx1LinkNo  OBJECT-TYPE
        SYNTAX      Integer32(1..16)
        MAX-ACCESS  not-accessible
        STATUS      current
        DESCRIPTION
            " This object indicates the E1/T1 number."
        ::= { zxAnV5UaLinkEntry 4 }

    zxAnV5UaLinkDsx1TsNo  OBJECT-TYPE
        SYNTAX      Integer32
        MAX-ACCESS  not-accessible
        STATUS      current
        DESCRIPTION
            " This object indicates the TS number. "
        ::= { zxAnV5UaLinkEntry 5 }            
        

     zxAnV5UaLinkV5LinkId      OBJECT-TYPE
        SYNTAX      Integer32(0..255)
        MAX-ACCESS  read-create
        STATUS      current
        DESCRIPTION    "V5 Link ID."
        ::={zxAnV5UaLinkEntry 6}    

        
    zxAnV5UaLinkAsId      OBJECT-TYPE
        SYNTAX      Integer32(1..127)
        MAX-ACCESS  read-create
        STATUS      current
        DESCRIPTION    "Application server ID."
        ::={zxAnV5UaLinkEntry 7}    
    
    zxAnV5UaLinkIfId      OBJECT-TYPE
        SYNTAX      Integer32(1..128)
        MAX-ACCESS  read-create
        STATUS      current
        DESCRIPTION    "Interface identifier, same to MGC."
        ::={zxAnV5UaLinkEntry 8}    
        
    zxAnV5UaLinkRowStatus      OBJECT-TYPE
        SYNTAX      RowStatus
        MAX-ACCESS  read-create
        STATUS      current
        DESCRIPTION    "The row status of this entry."
        ::={zxAnV5UaLinkEntry 50}  
        

 
END

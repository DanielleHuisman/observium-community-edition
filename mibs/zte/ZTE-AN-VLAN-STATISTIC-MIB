--------------------------------------------------------------------------
-- File Name : ZTE-AN-VLAN-STATISTIC-MIB.mib
-- Date      : 2009-10-21
-- Author    : ZTE Nms dept.

--
-- Zte Vlan Statistic Mgmt Mib for Access Node
-- 
-- 
--------------------------------------------------------------------------


ZTE-AN-VLAN-STATISTIC-MIB DEFINITIONS ::= BEGIN

    IMPORTS
        MODULE-IDENTITY, OBJECT-TYPE, Integer32, Unsigned32,Counter64,Gauge32
                                                    FROM SNMPv2-SMI
        RowStatus,DisplayString,TEXTUAL-CONVENTION,TruthValue
                                                    FROM SNMPv2-TC
        zxAn ,VlanId ,ZxAnIfindex                   FROM ZTE-AN-TC-MIB;


    zxAnVlanStatisticMib MODULE-IDENTITY
        LAST-UPDATED    "200910271030Z"
        ORGANIZATION "ZTE Corporation"
        CONTACT-INFO "ZTE NMS dept. "
                      
        DESCRIPTION  "This MIB defines managed objects of zte vlan statistic mgmt."
         ::= { zxAn 191 }
--------------------------------------------------------------------------
-- Vlan Statistic 
-- 1. zxAnVlanPerfEnableTable
-- 2. zxAnSwVlanPerfTable
-- 3. zxAnUserVlanPerfTable
-- 4. zxAnVlanStatTable
-------------------------------------------------------------------------- 

--------------------------------------------------------------------------
-- 1. zxAnVlanPerfEnableTable
--------------------------------------------------------------------------    
    zxAnVlanPerfEnableTable OBJECT-TYPE
        SYNTAX      SEQUENCE OF ZxAnVlanPerfEnableEntry
        MAX-ACCESS  not-accessible
        STATUS      current
        DESCRIPTION
            "1:1 Vlan Mib table."
        ::= { zxAnVlanStatisticMib 1 }

    zxAnVlanPerfEnableEntry OBJECT-TYPE
        SYNTAX      ZxAnVlanPerfEnableEntry
        MAX-ACCESS  not-accessible
        STATUS      current
        DESCRIPTION
            ""
        INDEX   { zxAnEnVlanId }
        ::= { zxAnVlanPerfEnableTable 1 }


    ZxAnVlanPerfEnableEntry  ::= SEQUENCE {
        zxAnEnVlanId              VlanId,
        zxVlanPerfEnable          INTEGER,
        zxVlanIDAllEnable         DisplayString
        }

    zxAnEnVlanId OBJECT-TYPE
        SYNTAX      VlanId
        MAX-ACCESS  not-accessible
        STATUS      current
        DESCRIPTION
            "An index for vlan."
        ::= { zxAnVlanPerfEnableEntry 1 }

    zxVlanPerfEnable  OBJECT-TYPE
        SYNTAX      INTEGER {
                      enable(1),
                      disable(2)
                    }
        MAX-ACCESS  read-write
        STATUS      current
        DESCRIPTION
           " "
        ::= {zxAnVlanPerfEnableEntry 2}

    zxVlanIDAllEnable OBJECT-TYPE
        SYNTAX      DisplayString (SIZE (0..128))
        MAX-ACCESS  read-write
        STATUS      current
        DESCRIPTION
          "Enable valan id,return like this '1,3,20' "
        ::= {zxAnVlanPerfEnableEntry 3}
        
--------------------------------------------------------------------------
-- 2. zxAnSwVlanPerfTable
--------------------------------------------------------------------------

    zxAnSwVlanPerfTable OBJECT-TYPE
        SYNTAX      SEQUENCE OF ZxAnSwVlanPerfEntry
        MAX-ACCESS  not-accessible
        STATUS      current
        DESCRIPTION
            "1:1 Vlan Mib table. C220 and C300 will not use this table.
             It only used by AG. 
           "
        ::= { zxAnVlanStatisticMib 2 }

    zxAnSwVlanPerfEntry OBJECT-TYPE
        SYNTAX      ZxAnSwVlanPerfEntry
        MAX-ACCESS  not-accessible
        STATUS      current
        DESCRIPTION
            ""
        INDEX   { zxAnSwVlanId }
        ::= { zxAnSwVlanPerfTable 1 }

    ZxAnSwVlanPerfEntry  ::= SEQUENCE {
        zxAnSwVlanId                                VlanId,
        zxAnSwVlanInOctets                          Counter64,
        zxAnSwVlanOutOctets                         Counter64,
        zxAnSwVlanInPkts                            Counter64,
        zxAnSwVlanOutPkts                           Counter64,
        zxAnSwVlanInBandwidth                       Integer32,
        zxAnSwVlanOutBandwidth                      Integer32,
        zxAnSwVlanInBandwidthUtility                Integer32,
        zxAnSwVlanOutBandwidthUtility               Integer32,
        zxAnSwVlanInCurrOctetRate                   Gauge32,
        zxAnSwVlanOutCurrOctetRate                  Gauge32,
        zxAnSwVlanInCurrPktRate                     Gauge32,
        zxAnSwVlanOutCurrPktRate                    Gauge32,
        zxAnSwVlanInUcastPkts                       Counter64,
        zxAnSwVlanOutUcastPkts                      Counter64,
        zxAnSwVlanInMulticastPkts                   Counter64,
        zxAnSwVlanOutMulticastPkts                  Counter64,
        zxAnSwVlanInNUcastPkts                      Counter64,
        zxAnSwVlanOutNUcastPkts                     Counter64,
        zxAnSwVlanInBroadcastPkts                   Counter64,
        zxAnSwVlanOutBroadcastPkts                  Counter64,
        zxAnSwVlanInDiscards                        Counter64,
        zxAnSwVlanOutDiscards                       Counter64,
        zxAnSwVlanInUndersizePkts                   Counter64,
        zxAnSwVlanOutUndersizePkts                  Counter64,
        zxAnSwVlanInOversizePkts                    Counter64,
        zxAnSwVlanOutOversizePkts                   Counter64,  
        zxAnSwVlanInCRCAlignErrors                  Counter64,
        zxAnSwVlanOutCRCAlignErrors                 Counter64,  
        zxAnSwVlanInFragments                       Counter64,
        zxAnSwVlanOutFragments                      Counter64, 
        zxAnSwVlanInJabbers                         Counter64,
        zxAnSwVlanOutJabbers                        Counter64, 
        zxAnSwVlanInCollisions                      Counter64,
        zxAnSwVlanOutCollisions                     Counter64,        
        zxAnSwVlanInUnknownProtos                   Counter64,
        zxAnSwVlanOutUnknownProtos                  Counter64      
        }

    zxAnSwVlanId OBJECT-TYPE
        SYNTAX      VlanId
        MAX-ACCESS  not-accessible
        STATUS      current
        DESCRIPTION
            "The VLAN id."
        ::= { zxAnSwVlanPerfEntry 1 }

    zxAnSwVlanInOctets  OBJECT-TYPE 
          SYNTAX         Counter64
          MAX-ACCESS     read-only
          STATUS         current
          DESCRIPTION
           "The total number of octets received,including framing characters. "
          ::= {zxAnSwVlanPerfEntry 2}

    zxAnSwVlanOutOctets  OBJECT-TYPE
          SYNTAX         Counter64
          MAX-ACCESS     read-only
          STATUS         current
          DESCRIPTION
           "The total number of octets transmitted, including framing characters. "
          ::= {zxAnSwVlanPerfEntry 3}

    zxAnSwVlanInPkts  OBJECT-TYPE
          SYNTAX          Counter64
          MAX-ACCESS      read-only
          STATUS          current
          DESCRIPTION
           "The total number of packets received "
          ::= {zxAnSwVlanPerfEntry 4}

    zxAnSwVlanOutPkts  OBJECT-TYPE
          SYNTAX         Counter64
          MAX-ACCESS     read-only
          STATUS         current
          DESCRIPTION
           "The total number of packets transmitted "
          ::= {zxAnSwVlanPerfEntry 5}

    zxAnSwVlanInBandwidth  OBJECT-TYPE
          SYNTAX         Integer32
          UNITS          "kbps"
          MAX-ACCESS     read-only
          STATUS         current
          DESCRIPTION
           "The bandwidth of receiving direction. "
          ::= {zxAnSwVlanPerfEntry 6}

    zxAnSwVlanOutBandwidth  OBJECT-TYPE
          SYNTAX         Integer32
          UNITS          "kbps"
          MAX-ACCESS     read-only
          STATUS         current
          DESCRIPTION
           "The bandwidth of transmitting direction. "
          ::= {zxAnSwVlanPerfEntry 7}


    zxAnSwVlanInBandwidthUtility  OBJECT-TYPE
          SYNTAX         Integer32
          UNITS          "%"
          MAX-ACCESS     read-only
          STATUS         current
          DESCRIPTION
           "The bandwidth utility of receiving direction. "
          ::= {zxAnSwVlanPerfEntry 8}

    zxAnSwVlanOutBandwidthUtility  OBJECT-TYPE
          SYNTAX         Integer32
          UNITS          "%"
          MAX-ACCESS     read-only
          STATUS         current
          DESCRIPTION
           "The bandwidth utility of transmitting direction. "
          ::= {zxAnSwVlanPerfEntry 9}

    zxAnSwVlanInCurrOctetRate  OBJECT-TYPE
          SYNTAX         Gauge32
          MAX-ACCESS     read-only
          STATUS         current
          DESCRIPTION
           "The number of received bytes per second."
          ::= {zxAnSwVlanPerfEntry 10}

    zxAnSwVlanOutCurrOctetRate  OBJECT-TYPE
          SYNTAX         Gauge32
          MAX-ACCESS     read-only
          STATUS         current
          DESCRIPTION
           "The number of transmitted bytes per second."
          ::= {zxAnSwVlanPerfEntry 11}
          
    zxAnSwVlanInCurrPktRate  OBJECT-TYPE
          SYNTAX         Gauge32
          MAX-ACCESS     read-only
          STATUS         current
          DESCRIPTION
           "The number of received packets per second. "
          ::= {zxAnSwVlanPerfEntry 12}

    zxAnSwVlanOutCurrPktRate  OBJECT-TYPE
          SYNTAX         Gauge32
          MAX-ACCESS     read-only
          STATUS         current
          DESCRIPTION
           "The number of transmitted packets per second. "
          ::= {zxAnSwVlanPerfEntry 13}          
          
    zxAnSwVlanInUcastPkts  OBJECT-TYPE
          SYNTAX         Counter64
          MAX-ACCESS     read-only
          STATUS         current
          DESCRIPTION
           "The number of subnetwork unicast packets delivered 
                      to a higher-layer protocol. "
          ::= {zxAnSwVlanPerfEntry 14}  
                  
    zxAnSwVlanOutUcastPkts  OBJECT-TYPE
          SYNTAX         Counter64
          MAX-ACCESS     read-only
          STATUS         current
          DESCRIPTION
           "The total number of packets that higher-level
                      protocols requested be transmitted to a
                      subnetwork unicast address, including those that
                      were discarded or not sent. "
          ::= {zxAnSwVlanPerfEntry 15}  
          
    zxAnSwVlanInMulticastPkts  OBJECT-TYPE
          SYNTAX         Counter64
          MAX-ACCESS     read-only
          STATUS         current
          DESCRIPTION
           "The number of subnetwork multicast packets delivered 
                      to a higher-layer protocol."
          ::= {zxAnSwVlanPerfEntry 16}  
                  
    zxAnSwVlanOutMulticastPkts  OBJECT-TYPE
          SYNTAX         Counter64
          MAX-ACCESS     read-only
          STATUS         current
          DESCRIPTION
           "The total number of packets that higher-level
                      protocols requested be transmitted to a
                      subnetwork multicast address, including those that
                      were discarded or not sent. "
          ::= {zxAnSwVlanPerfEntry 17}
          
    zxAnSwVlanInNUcastPkts  OBJECT-TYPE
          SYNTAX         Counter64
          MAX-ACCESS     read-only
          STATUS         current
          DESCRIPTION
           "The number of non-unicast (i.e., subnetwork-
                      broadcast or subnetwork-multicast) packets
                      delivered to a higher-layer protocol. "
          ::= {zxAnSwVlanPerfEntry 18}  
                  
    zxAnSwVlanOutNUcastPkts  OBJECT-TYPE
          SYNTAX         Counter64
          MAX-ACCESS     read-only
          STATUS         current
          DESCRIPTION
           "The total number of packets that higher-level
                      protocols requested be transmitted to a non-
                      unicast (i.e., a subnetwork-broadcast or
                      subnetwork-multicast) address, including those
                      that were discarded or not sent. "
          ::= {zxAnSwVlanPerfEntry 19} 
          
    zxAnSwVlanInBroadcastPkts  OBJECT-TYPE
          SYNTAX         Counter64
          MAX-ACCESS     read-only
          STATUS         current
          DESCRIPTION
           "The number of subnetwork broadcast packets delivered 
                      to a higher-layer protocol. "
          ::= {zxAnSwVlanPerfEntry 20}  
                  
    zxAnSwVlanOutBroadcastPkts  OBJECT-TYPE
          SYNTAX         Counter64
          MAX-ACCESS     read-only
          STATUS         current
          DESCRIPTION
           "The total number of packets that higher-level
                      protocols requested be transmitted to a
                      subnetwork broadcast address, including those that
                      were discarded or not sent. "
          ::= {zxAnSwVlanPerfEntry 21}          
          
    zxAnSwVlanInDiscards  OBJECT-TYPE
          SYNTAX         Counter64
          MAX-ACCESS     read-only
          STATUS         current
          DESCRIPTION
           "The number of inbound packets which were chosen
                      to be discarded even though no errors had been
                      detected to prevent their being deliverable to a
                      higher-layer protocol.  One possible reason for
                      discarding such a packet could be to free up
                      buffer space.  "
          ::= {zxAnSwVlanPerfEntry 22}  
                  
    zxAnSwVlanOutDiscards  OBJECT-TYPE
          SYNTAX         Counter64
          MAX-ACCESS     read-only
          STATUS         current
          DESCRIPTION
           "The number of outbound packets which were chosen
                      to be discarded even though no errors had been
                      detected to prevent their being transmitted.  One
                      possible reason for discarding such a packet could
                      be to free up buffer space."
          ::= {zxAnSwVlanPerfEntry 23} 
          
    zxAnSwVlanInUndersizePkts  OBJECT-TYPE
          SYNTAX         Counter64
          MAX-ACCESS     read-only
          STATUS         current
          DESCRIPTION
           "The total number of packets received that were
                  less than 64 octets long (excluding framing bits,
                  but including FCS octets) and were otherwise well
                  formed."
          ::= {zxAnSwVlanPerfEntry 24} 
          
    zxAnSwVlanOutUndersizePkts  OBJECT-TYPE
          SYNTAX         Counter64
          MAX-ACCESS     read-only
          STATUS         current
          DESCRIPTION
           "The total number of packets transmit that were
                  less than 64 octets long (excluding framing bits,
                  but including FCS octets) and were otherwise well
                  formed."
          ::= {zxAnSwVlanPerfEntry 25}   
          
    zxAnSwVlanInOversizePkts  OBJECT-TYPE
          SYNTAX         Counter64
          MAX-ACCESS     read-only
          STATUS         current
          DESCRIPTION
           "The total number of packets received that were
                  longer than 1518 octets (excluding framing bits,
                  but including FCS octets) and were otherwise
                  well formed."
          ::= {zxAnSwVlanPerfEntry 26} 
          
    zxAnSwVlanOutOversizePkts  OBJECT-TYPE
          SYNTAX         Counter64
          MAX-ACCESS     read-only
          STATUS         current
          DESCRIPTION
           "The total number of packets transmit that were
                  longer than 1518 octets (excluding framing bits,
                  but including FCS octets) and were otherwise
                  well formed."
          ::= {zxAnSwVlanPerfEntry 27} 
          
    zxAnSwVlanInCRCAlignErrors  OBJECT-TYPE
          SYNTAX         Counter64
          MAX-ACCESS     read-only
          STATUS         current
          DESCRIPTION
           "The total number of packets received that
                  had a length (excluding framing bits, but
                  including FCS octets) of between 64 and 1518
                  octets, inclusive, but but had either a bad
                  Frame Check Sequence (FCS) with an integral
                  number of octets (FCS Error) or a bad FCS with
                  a non-integral number of octets (Alignment Error)."
          ::= {zxAnSwVlanPerfEntry 28} 
          
    zxAnSwVlanOutCRCAlignErrors  OBJECT-TYPE
          SYNTAX         Counter64
          MAX-ACCESS     read-only
          STATUS         current
          DESCRIPTION
           "The total number of packets transmit that
                  had a length (excluding framing bits, but
                  including FCS octets) of between 64 and 1518
                  octets, inclusive, but but had either a bad
                  Frame Check Sequence (FCS) with an integral
                  number of octets (FCS Error) or a bad FCS with
                  a non-integral number of octets (Alignment Error)."
          ::= {zxAnSwVlanPerfEntry 29}           
          
    zxAnSwVlanInFragments  OBJECT-TYPE
          SYNTAX         Counter64
          MAX-ACCESS     read-only
          STATUS         current
          DESCRIPTION
           "The total number of packets received that were less
                  than 64 octets in length (excluding framing bits but
                  including FCS octets) and had either a bad Frame
                  Check Sequence (FCS) with an integral number of
                  octets (FCS Error) or a bad FCS with a non-integral
                  number of octets (Alignment Error).

                  Note that it is entirely normal for
                  etherStatsFragments to increment.  This is because
                  it counts both runts (which are normal occurrences
                  due to collisions) and noise hits."
          ::= {zxAnSwVlanPerfEntry 30} 
          
    zxAnSwVlanOutFragments  OBJECT-TYPE
          SYNTAX         Counter64
          MAX-ACCESS     read-only
          STATUS         current
          DESCRIPTION
           "The total number of packets transmit that were less
                  than 64 octets in length (excluding framing bits but
                  including FCS octets) and had either a bad Frame
                  Check Sequence (FCS) with an integral number of
                  octets (FCS Error) or a bad FCS with a non-integral
                  number of octets (Alignment Error).

                  Note that it is entirely normal for
                  etherStatsFragments to increment.  This is because
                  it counts both runts (which are normal occurrences
                  due to collisions) and noise hits."
          ::= {zxAnSwVlanPerfEntry 31}                                           
          
    zxAnSwVlanInJabbers  OBJECT-TYPE
          SYNTAX         Counter64
          MAX-ACCESS     read-only
          STATUS         current
          DESCRIPTION
           "The total number of packets received that were
                  longer than 1518 octets (excluding framing bits,
                  but including FCS octets), and had either a bad
                  Frame Check Sequence (FCS) with an integral number
                  of octets (FCS Error) or a bad FCS with a
                  non-integral number of octets (Alignment Error).

                  Note that this definition of jabber is different
                  than the definition in IEEE-802.3 section 8.2.1.5
                  (10BASE5) and section 10.3.1.4 (10BASE2).  These
                  documents define jabber as the condition where any
                  packet exceeds 20 ms.  The allowed range to detect
                  jabber is between 20 ms and 150 ms."
          ::= {zxAnSwVlanPerfEntry 32} 
          
    zxAnSwVlanOutJabbers  OBJECT-TYPE
          SYNTAX         Counter64
          MAX-ACCESS     read-only
          STATUS         current
          DESCRIPTION
           "The total number of packets transmit that were
                  longer than 1518 octets (excluding framing bits,
                  but including FCS octets), and had either a bad
                  Frame Check Sequence (FCS) with an integral number
                  of octets (FCS Error) or a bad FCS with a
                  non-integral number of octets (Alignment Error).

                  Note that this definition of jabber is different
                  than the definition in IEEE-802.3 section 8.2.1.5
                  (10BASE5) and section 10.3.1.4 (10BASE2).  These
                  documents define jabber as the condition where any
                  packet exceeds 20 ms.  The allowed range to detect
                  jabber is between 20 ms and 150 ms.."
          ::= {zxAnSwVlanPerfEntry 33} 
          
    zxAnSwVlanInCollisions  OBJECT-TYPE
          SYNTAX         Counter64
          MAX-ACCESS     read-only
          STATUS         current
          DESCRIPTION
           "The best estimate of the total number of collisions
                  on this Ethernet segment.

                  The value returned will depend on the location of
                  the RMON probe. Section 8.2.1.3 (10BASE-5) and
                  section 10.3.1.3 (10BASE-2) of IEEE standard 802.3
                  states that a station must detect a collision, in
                  the receive mode, if three or more stations are
                  transmitting simultaneously.  A repeater port must
                  detect a collision when two or more stations are
                  transmitting simultaneously.  Thus a probe placed on
                  a repeater port could record more collisions than a
                  probe connected to a station on the same segment
                  would.

                  Probe location plays a much smaller role when
                  considering 10BASE-T.  14.2.1.4 (10BASE-T) of IEEE
                  standard 802.3 defines a collision as the
                  simultaneous presence of signals on the DO and RD
                  circuits (transmitting and receiving at the same
                  time).  A 10BASE-T station can only detect
                  collisions when it is transmitting.  Thus probes
                  placed on a station and a repeater, should report
                  the same number of collisions.

                  Note also that an RMON probe inside a repeater
                  should ideally report collisions between the
                  repeater and one or more other hosts (transmit
                  collisions as defined by IEEE 802.3k) plus receiver
                  collisions observed on any coax segments to which
                  the repeater is connected."
          ::= {zxAnSwVlanPerfEntry 34} 
          
    zxAnSwVlanOutCollisions  OBJECT-TYPE
          SYNTAX         Counter64
          MAX-ACCESS     read-only
          STATUS         current
          DESCRIPTION
           "The best estimate of the total number of collisions
                  on this Ethernet segment.

                  The value returned will depend on the location of
                  the RMON probe. Section 8.2.1.3 (10BASE-5) and
                  section 10.3.1.3 (10BASE-2) of IEEE standard 802.3
                  states that a station must detect a collision, in
                  the receive mode, if three or more stations are
                  transmitting simultaneously.  A repeater port must
                  detect a collision when two or more stations are
                  transmitting simultaneously.  Thus a probe placed on
                  a repeater port could record more collisions than a
                  probe connected to a station on the same segment
                  would.

                  Probe location plays a much smaller role when
                  considering 10BASE-T.  14.2.1.4 (10BASE-T) of IEEE
                  standard 802.3 defines a collision as the
                  simultaneous presence of signals on the DO and RD
                  circuits (transmitting and receiving at the same
                  time).  A 10BASE-T station can only detect
                  collisions when it is transmitting.  Thus probes
                  placed on a station and a repeater, should report
                  the same number of collisions.

                  Note also that an RMON probe inside a repeater
                  should ideally report collisions between the
                  repeater and one or more other hosts (transmit
                  collisions as defined by IEEE 802.3k) plus receiver
                  collisions observed on any coax segments to which
                  the repeater is connected."
          ::= {zxAnSwVlanPerfEntry 35}  
          
    zxAnSwVlanInUnknownProtos  OBJECT-TYPE
          SYNTAX         Counter64
          MAX-ACCESS     read-only
          STATUS         current
          DESCRIPTION
           "The other such variable, InternalMacReceiveErrors, is a general
                  catchall for all other errors. If no other errors are detected 
                  by the hardware or software then returning 0 for the counter is 
                  perfectly  acceptable."
          ::= {zxAnSwVlanPerfEntry 36} 
          
    zxAnSwVlanOutUnknownProtos  OBJECT-TYPE
          SYNTAX         Counter64
          MAX-ACCESS     read-only
          STATUS         current
          DESCRIPTION
           "The other such variable, InternalMacReceiveErrors, is a general
                  catchall for all other errors. If no other errors are detected 
                  by the hardware or software then returning 0 for the counter is 
                  perfectly  acceptable."
          ::= {zxAnSwVlanPerfEntry 37}                                
                           
--------------------------------------------------------------------------
-- 3. zxAnUserVlanPerfTable
--------------------------------------------------------------------------

    zxAnUserVlanPerfTable OBJECT-TYPE
        SYNTAX      SEQUENCE OF ZxAnUserVlanPerfEntry
        MAX-ACCESS  not-accessible
        STATUS      current
        DESCRIPTION
            "Interface VLAN performance table."
        ::= { zxAnVlanStatisticMib 3 }

    zxAnUserVlanPerfEntry OBJECT-TYPE
        SYNTAX      ZxAnUserVlanPerfEntry
        MAX-ACCESS  not-accessible
        STATUS      current
        DESCRIPTION
            "Interface VLAN performance entry."
        INDEX   { zxAnUserVlanPortIfIndex, zxAnUserVlanId}
        ::= { zxAnUserVlanPerfTable 1 }

    ZxAnUserVlanPerfEntry  ::= SEQUENCE {
        zxAnUserVlanPortIfIndex                     ZxAnIfindex,
        zxAnUserVlanId                              VlanId,        
        zxAnUserVlanPerfReset                       INTEGER,
        zxAnUserVlanRxPkts                          Counter64,
        zxAnUserVlanTxPkts                          Counter64,
        zxAnUserVlanRxOctetRate                     Gauge32,
        zxAnUserVlanTxOctetRate                     Gauge32,
        zxAnUserVlanRxOctetPeakRate                 Gauge32,
        zxAnUserVlanTxOctetPeakRate                 Gauge32,        
        zxAnUserVlanRxUcastPkts                     Counter64,
        zxAnUserVlanTxUcastPkts                     Counter64,
        zxAnUserVlanRxMulticastPkts                 Counter64,
        zxAnUserVlanTxMulticastPkts                 Counter64,
        zxAnUserVlanRxBroadcastPkts                 Counter64,
        zxAnUserVlanTxBroadcastPkts                 Counter64,
        zxAnUserVlanRxDiscards                      Counter64,
        zxAnUserVlanTxDiscards                      Counter64,      
        zxAnUserVlanRxErrors                        Counter64,
        zxAnUserVlanTxErrors                        Counter64,
        zxAnUserVlanRxUcastOctetRate                Gauge32,
        zxAnUserVlanTxUcastOctetRate                Gauge32,
        zxAnUserVlanRxUcastOctetPeakRate            Gauge32,
        zxAnUserVlanTxUcastOctetPeakRate            Gauge32,
        zxAnUserVlanRxMcastOctetRate                Gauge32,
        zxAnUserVlanTxMcastOctetRate                Gauge32,
        zxAnUserVlanRxMcastOctetPeakRate            Gauge32,
        zxAnUserVlanTxMcastOctetPeakRate            Gauge32,
        zxAnUserVlanPerfRowStatus                   RowStatus
        }

    zxAnUserVlanPortIfIndex  OBJECT-TYPE
        SYNTAX      ZxAnIfindex
        MAX-ACCESS  not-accessible
        STATUS      current
        DESCRIPTION
            "The user port index."
        ::= { zxAnUserVlanPerfEntry 1 }

    zxAnUserVlanId OBJECT-TYPE
        SYNTAX      VlanId
        MAX-ACCESS  not-accessible
        STATUS      current
        DESCRIPTION
            "VLAN ID."
        ::= { zxAnUserVlanPerfEntry 2 }
        
    zxAnUserVlanPerfReset   OBJECT-TYPE
        SYNTAX      INTEGER
        {
            perfReset(1)
        }
        MAX-ACCESS  read-create
        STATUS      current
        DESCRIPTION 
            "Reset interface VLAN statistics counter manually when it is set to 
             '1'."
        REFERENCE
            "Used by MAP"
        ::= { zxAnUserVlanPerfEntry 3 }
        
    zxAnUserVlanRxPkts  OBJECT-TYPE
        SYNTAX      Counter64
        MAX-ACCESS  read-only
        STATUS      current
        DESCRIPTION
            "Received packets."
        ::= { zxAnUserVlanPerfEntry 4 }

    zxAnUserVlanTxPkts  OBJECT-TYPE
        SYNTAX      Counter64
        MAX-ACCESS  read-only
        STATUS      current
        DESCRIPTION
            "Transmitted packets."
        ::= { zxAnUserVlanPerfEntry 5 }

    zxAnUserVlanRxOctetRate  OBJECT-TYPE
        SYNTAX      Gauge32
        UNITS       "kbps"
        MAX-ACCESS  read-only
        STATUS      current
        DESCRIPTION
            "Received octet rate."
        ::= { zxAnUserVlanPerfEntry 6 }

    zxAnUserVlanTxOctetRate  OBJECT-TYPE
        SYNTAX      Gauge32
        UNITS       "kbps"
        MAX-ACCESS  read-only
        STATUS      current
        DESCRIPTION
            "Transmitted octet rate."
        ::= { zxAnUserVlanPerfEntry 7 }
          
    zxAnUserVlanRxOctetPeakRate  OBJECT-TYPE
        SYNTAX      Gauge32
        UNITS       "kbps"
        MAX-ACCESS  read-only
        STATUS      current
        DESCRIPTION
            "Received octet  Peak rate."
        ::= { zxAnUserVlanPerfEntry 8 }

    zxAnUserVlanTxOctetPeakRate  OBJECT-TYPE
        SYNTAX      Gauge32
        UNITS       "kbps"
        MAX-ACCESS  read-only
        STATUS      current
        DESCRIPTION
            "Transmitted octet Peak rate."
        ::= { zxAnUserVlanPerfEntry 9 }
                                  
    zxAnUserVlanRxUcastPkts  OBJECT-TYPE
        SYNTAX      Counter64
        MAX-ACCESS  read-only
        STATUS      current
        DESCRIPTION
            "Received unicast packets."
        ::= { zxAnUserVlanPerfEntry 10 }  
                  
    zxAnUserVlanTxUcastPkts  OBJECT-TYPE
        SYNTAX      Counter64
        MAX-ACCESS  read-only
        STATUS      current
        DESCRIPTION
            "Transmitted unicast packets."
        ::= { zxAnUserVlanPerfEntry 11 }  
          
    zxAnUserVlanRxMulticastPkts  OBJECT-TYPE
        SYNTAX      Counter64
        MAX-ACCESS  read-only
        STATUS      current
        DESCRIPTION
            "Received multicast packets."
        ::= { zxAnUserVlanPerfEntry 12 }  
                  
    zxAnUserVlanTxMulticastPkts  OBJECT-TYPE
        SYNTAX      Counter64
        MAX-ACCESS  read-only
        STATUS      current
        DESCRIPTION
            "Transmitted multicast packets."
        ::= { zxAnUserVlanPerfEntry 13 }
                    
    zxAnUserVlanRxBroadcastPkts  OBJECT-TYPE
        SYNTAX      Counter64
        MAX-ACCESS  read-only
        STATUS      current
        DESCRIPTION
            "Received broadcast packets."
        ::= { zxAnUserVlanPerfEntry 14 }  
                  
    zxAnUserVlanTxBroadcastPkts  OBJECT-TYPE
        SYNTAX      Counter64
        MAX-ACCESS  read-only
        STATUS      current
        DESCRIPTION
            "Transmitted broadcast packets."
        ::= { zxAnUserVlanPerfEntry 15 }     

    zxAnUserVlanRxDiscards  OBJECT-TYPE
        SYNTAX      Counter64
        MAX-ACCESS  read-only
        STATUS      current
        DESCRIPTION
            "Received discarded packets."
        ::= { zxAnUserVlanPerfEntry 16 }  
                  
    zxAnUserVlanTxDiscards  OBJECT-TYPE
        SYNTAX      Counter64
        MAX-ACCESS  read-only
        STATUS      current
        DESCRIPTION
            "Transmitted discarded packets."
        ::= { zxAnUserVlanPerfEntry 17 }     
                        
    zxAnUserVlanRxErrors OBJECT-TYPE
        SYNTAX      Counter64
        MAX-ACCESS  read-only
        STATUS      current
        DESCRIPTION
            "For packet-oriented interfaces, the number of inbound packets that
             contained errors preventing them from being deliverable to a 
             higher-layer protocol. For character-oriented or fixed-length 
             interfaces, the number of inbound transmission units that 
             contained errors preventing them from being deliverable to a 
             higher-layer protocol."
        ::= { zxAnUserVlanPerfEntry 18 }
    
    zxAnUserVlanTxErrors OBJECT-TYPE
        SYNTAX      Counter64
        MAX-ACCESS  read-only
        STATUS      current
        DESCRIPTION
            "For packet-oriented interfaces, the number of outbound packets that 
             contained errors preventing them from being deliverable to a 
             higher-layer protocol. For character-oriented or fixed-length 
             interfaces, the number of outbound transmission units that 
             contained errors preventing them from being deliverable to a 
             higher-layer protocol."
        ::= { zxAnUserVlanPerfEntry 19 }
    
    zxAnUserVlanRxUcastOctetRate OBJECT-TYPE
        SYNTAX      Gauge32
        UNITS       "kbps"
        MAX-ACCESS  read-only
        STATUS      current
        DESCRIPTION
            "Received unicast octet rate."
        ::= { zxAnUserVlanPerfEntry 20 }
        
    zxAnUserVlanTxUcastOctetRate OBJECT-TYPE
        SYNTAX      Gauge32
        UNITS       "kbps"
        MAX-ACCESS  read-only
        STATUS      current
        DESCRIPTION
            "Transmitted unicast octet rate."
        ::= { zxAnUserVlanPerfEntry 21 }
        
    zxAnUserVlanRxUcastOctetPeakRate OBJECT-TYPE
        SYNTAX      Gauge32
        UNITS       "kbps"
        MAX-ACCESS  read-only
        STATUS      current
        DESCRIPTION
            "Received unicast octet peak rate."
        ::= { zxAnUserVlanPerfEntry 22 }
        
    zxAnUserVlanTxUcastOctetPeakRate OBJECT-TYPE
        SYNTAX      Gauge32
        UNITS       "kbps"
        MAX-ACCESS  read-only
        STATUS      current
        DESCRIPTION
            "Transmitted unicast octet peak rate."
        ::= { zxAnUserVlanPerfEntry 23 }
        
    zxAnUserVlanRxMcastOctetRate OBJECT-TYPE
        SYNTAX      Gauge32
        UNITS       "kbps"
        MAX-ACCESS  read-only
        STATUS      current
        DESCRIPTION
            "Received multicast octet rate."
        ::= { zxAnUserVlanPerfEntry 24 }
        
    zxAnUserVlanTxMcastOctetRate OBJECT-TYPE
        SYNTAX      Gauge32
        UNITS       "kbps"
        MAX-ACCESS  read-only
        STATUS      current
        DESCRIPTION
            "Transmitted multicast octet rate."
        ::= { zxAnUserVlanPerfEntry 25 }
        
    zxAnUserVlanRxMcastOctetPeakRate OBJECT-TYPE
        SYNTAX      Gauge32
        UNITS       "kbps"
        MAX-ACCESS  read-only
        STATUS      current
        DESCRIPTION
            "Received multicast octet peak rate."
        ::= { zxAnUserVlanPerfEntry 26 }
        
    zxAnUserVlanTxMcastOctetPeakRate OBJECT-TYPE
        SYNTAX      Gauge32
        UNITS       "kbps"
        MAX-ACCESS  read-only
        STATUS      current
        DESCRIPTION
            "Transmitted multicast octet peak rate."
        ::= { zxAnUserVlanPerfEntry 27 }

    zxAnUserVlanPerfRowStatus  OBJECT-TYPE
        SYNTAX      RowStatus
        MAX-ACCESS  read-create
        STATUS      current
        DESCRIPTION
            "This object indicates the status of this entry."
        ::= { zxAnUserVlanPerfEntry 100 }
        
--------------------------------------------------------------------------
-- 4. zxAnVlanStatTable
--------------------------------------------------------------------------
    zxAnVlanStatTable OBJECT-TYPE
        SYNTAX      SEQUENCE OF ZxAnVlanStatEntry
        MAX-ACCESS  not-accessible
        STATUS      current
        DESCRIPTION
            "The statistic table based on SVLAN and CVLAN."
        ::= { zxAnVlanStatisticMib 4 }

    zxAnVlanStatEntry OBJECT-TYPE
        SYNTAX      ZxAnVlanStatEntry
        MAX-ACCESS  not-accessible
        STATUS      current
        DESCRIPTION
            "SVLAN and CVLAN statistics entry."
        INDEX   { zxAnSVlanId, zxAnCVlanId }
        ::= { zxAnVlanStatTable 1 }

    ZxAnVlanStatEntry  ::= SEQUENCE {
        zxAnSVlanId                    VlanId,
        zxAnCVlanId                    INTEGER,
        zxAnVlanRxOctets               Counter64,
        zxAnVlanTxOctets               Counter64,
        zxAnVlanRxPkts                 Counter64,
        zxAnVlanTxPkts                 Counter64,
        zxAnVlanRxPktRate              Gauge32,
        zxAnVlanTxPktRate              Gauge32,
        zxAnVlanRxDiscardPkts          Counter64,
        zxAnVlanTxDiscardPkts          Counter64,
        zxAnVlanLackOfBufferDiscards   Counter64,
        zxAnVlanDelayExceededDiscards  Counter64,
        zxAnVlanErrorDiscards          Counter64,
        zxAnVlanIngressFilterDiscards  Counter64,
        zxAnVlanRxOctetRate            Gauge32,
        zxAnVlanTxOctetRate            Gauge32,
        zxAnVlanRxOctetPeakRate        Gauge32,
        zxAnVlanTxOctetPeakRate        Gauge32,
        zxAnVlanRxUcastPkts            Counter64,
        zxAnVlanTxUcastPkts            Counter64,        
        zxAnVlanRxUcastOctets          Counter64,
        zxAnVlanTxUcastOctets          Counter64,
        zxAnVlanRxUcastOctetRate       Gauge32,
        zxAnVlanTxUcastOctetRate       Gauge32,
        zxAnVlanRxUcastOctetPeakRate   Gauge32,
        zxAnVlanTxUcastOctetPeakRate   Gauge32,
        zxAnVlanRxMcastPkts            Counter64,
        zxAnVlanTxMcastPkts            Counter64,
        zxAnVlanRxMcastOctets          Counter64,
        zxAnVlanTxMcastOctets          Counter64,
        zxAnVlanRxMcastOctetRate       Gauge32,
        zxAnVlanTxMcastOctetRate       Gauge32,
        zxAnVlanRxMcastOctetPeakRate   Gauge32,
        zxAnVlanTxMcastOctetPeakRate   Gauge32,
        zxAnVlanRxBcastPkts            Counter64,
        zxAnVlanTxBcastPkts            Counter64,
        zxAnVlanRxBcastOctets          Counter64,
        zxAnVlanTxBcastOctets          Counter64,
        zxAnVlanRxFloodPkts            Counter64,
        zxAnVlanTxFloodPkts            Counter64,
        zxAnVlanRxFloodOctets          Counter64,
        zxAnVlanTxFloodOctets          Counter64,
        zxAnVlanStatRowStatus          RowStatus
        }

    zxAnSVlanId OBJECT-TYPE
        SYNTAX      VlanId
        MAX-ACCESS  not-accessible
        STATUS      current
        DESCRIPTION
            "The SVLAN ID."
        ::= { zxAnVlanStatEntry 1 }

    zxAnCVlanId OBJECT-TYPE
        SYNTAX      INTEGER(0..4094)
        MAX-ACCESS  not-accessible
        STATUS      current
        DESCRIPTION
            "The CVLAN ID. 0 indicated statistics only based on SVLAN."
        ::= { zxAnVlanStatEntry 2 }
        
    zxAnVlanRxOctets  OBJECT-TYPE 
          SYNTAX         Counter64
          MAX-ACCESS     read-only
          STATUS         current
          DESCRIPTION
           "The total number of received octets."
          ::= {zxAnVlanStatEntry 3}

    zxAnVlanTxOctets  OBJECT-TYPE
          SYNTAX         Counter64
          MAX-ACCESS     read-only
          STATUS         current
          DESCRIPTION
           "The total number of transmitted octets."
          ::= {zxAnVlanStatEntry 4}

    zxAnVlanRxPkts  OBJECT-TYPE
          SYNTAX          Counter64
          MAX-ACCESS      read-only
          STATUS          current
          DESCRIPTION
           "The total number of received packets."
          ::= {zxAnVlanStatEntry 5}

    zxAnVlanTxPkts  OBJECT-TYPE
          SYNTAX         Counter64
          MAX-ACCESS     read-only
          STATUS         current
          DESCRIPTION
           "The total number of ptransmitted packets."
          ::= {zxAnVlanStatEntry 6}

    zxAnVlanRxPktRate  OBJECT-TYPE
          SYNTAX         Gauge32
          UNITS          "pps"
          MAX-ACCESS     read-only
          STATUS         current
          DESCRIPTION
           "The number of received packets per second."
          ::= {zxAnVlanStatEntry 7}

    zxAnVlanTxPktRate  OBJECT-TYPE
          SYNTAX         Gauge32
          UNITS          "pps"
          MAX-ACCESS     read-only
          STATUS         current
          DESCRIPTION
           "The number of transmitted packets per second."
          ::= {zxAnVlanStatEntry 8}          
          
    zxAnVlanRxDiscardPkts  OBJECT-TYPE
          SYNTAX         Counter64
          MAX-ACCESS     read-only
          STATUS         current
          DESCRIPTION
           "The number of received discarded packets."
          ::= {zxAnVlanStatEntry 9}  
                  
    zxAnVlanTxDiscardPkts  OBJECT-TYPE
          SYNTAX         Counter64
          MAX-ACCESS     read-only
          STATUS         current
          DESCRIPTION
           "The number of transmitted discarded packets."
          ::= {zxAnVlanStatEntry 10} 
    
    zxAnVlanLackOfBufferDiscards  OBJECT-TYPE
        SYNTAX         Counter64
        MAX-ACCESS     read-only
        STATUS         current
        DESCRIPTION    "The number of packets discarded by this port due
        to the lack of the buffer space."          
        ::= {zxAnVlanStatEntry 11} 
        
    zxAnVlanDelayExceededDiscards  OBJECT-TYPE
        SYNTAX         Counter64
        MAX-ACCESS     read-only
        STATUS         current
        DESCRIPTION    "The number of packets discarded by this port due
        to excessive transit delay."
        ::= {zxAnVlanStatEntry 12}

    zxAnVlanErrorDiscards  OBJECT-TYPE
        SYNTAX         Counter64
        MAX-ACCESS     read-only
        STATUS         current
        DESCRIPTION    "The number of error packets discarded by this port."
        ::= {zxAnVlanStatEntry 13}
    
    zxAnVlanIngressFilterDiscards  OBJECT-TYPE
        SYNTAX         Counter64
        MAX-ACCESS     read-only
        STATUS         current
        DESCRIPTION    "The number of packets discarded by this port due
        to the ingress filtering."
        ::= {zxAnVlanStatEntry 14}
    
    zxAnVlanRxOctetRate  OBJECT-TYPE
        SYNTAX         Gauge32
        UNITS          "kbps"
        MAX-ACCESS     read-only
        STATUS         current
        DESCRIPTION
            "Received octet rate."
        ::= { zxAnVlanStatEntry 15 }
        
    zxAnVlanTxOctetRate  OBJECT-TYPE
        SYNTAX         Gauge32
        UNITS          "kbps"
        MAX-ACCESS     read-only
        STATUS         current
        DESCRIPTION
            "Transmitted octet rate."
        ::= { zxAnVlanStatEntry 16 }
        
    zxAnVlanRxOctetPeakRate  OBJECT-TYPE
        SYNTAX         Gauge32
        UNITS          "kbps"
        MAX-ACCESS     read-only
        STATUS         current
        DESCRIPTION
            "Received octet peak rate."
        ::= { zxAnVlanStatEntry 17 }
        
    zxAnVlanTxOctetPeakRate  OBJECT-TYPE
        SYNTAX         Gauge32
        UNITS          "kbps"
        MAX-ACCESS     read-only
        STATUS         current
        DESCRIPTION
            "Transmitted octet peak rate."
        ::= { zxAnVlanStatEntry 18 }    

    zxAnVlanRxUcastPkts  OBJECT-TYPE
        SYNTAX         Counter64
        MAX-ACCESS     read-only
        STATUS         current
        DESCRIPTION
            "Transmitted unicast packets."
        ::= { zxAnVlanStatEntry 19 }

    zxAnVlanTxUcastPkts  OBJECT-TYPE
        SYNTAX         Counter64
        MAX-ACCESS     read-only
        STATUS         current
        DESCRIPTION
            "Received unicast packets."
        ::= { zxAnVlanStatEntry 20 }

    zxAnVlanRxUcastOctets  OBJECT-TYPE
        SYNTAX         Counter64
        UNITS          "bytes"
        MAX-ACCESS     read-only
        STATUS         current
        DESCRIPTION
            "Transmitted unicast octets."
        ::= { zxAnVlanStatEntry 21 }

    zxAnVlanTxUcastOctets  OBJECT-TYPE
        SYNTAX         Counter64
        UNITS          "bytes"
        MAX-ACCESS     read-only
        STATUS         current
        DESCRIPTION
            "Received unicast octets."
        ::= { zxAnVlanStatEntry 22 }

    zxAnVlanRxUcastOctetRate  OBJECT-TYPE
        SYNTAX         Gauge32
        UNITS          "kbps"
        MAX-ACCESS     read-only
        STATUS         current
        DESCRIPTION
            "Received unicast octet rate."
        ::= { zxAnVlanStatEntry 23 }

    zxAnVlanTxUcastOctetRate   OBJECT-TYPE
        SYNTAX         Gauge32
        UNITS          "kbps"
        MAX-ACCESS     read-only
        STATUS         current
        DESCRIPTION
            "Transmitted unicast octet rate."
        ::= { zxAnVlanStatEntry 24 }
        
    zxAnVlanRxUcastOctetPeakRate  OBJECT-TYPE
        SYNTAX         Gauge32
        UNITS          "kbps"
        MAX-ACCESS     read-only
        STATUS         current
        DESCRIPTION
            "Received unicast octet peak rate."
        ::= { zxAnVlanStatEntry 25 }

    zxAnVlanTxUcastOctetPeakRate   OBJECT-TYPE
        SYNTAX         Gauge32
        UNITS          "kbps"
        MAX-ACCESS     read-only
        STATUS         current
        DESCRIPTION
            "Transmitted unicast octet peak rate."
        ::= { zxAnVlanStatEntry 26 }

    zxAnVlanRxMcastPkts  OBJECT-TYPE
        SYNTAX         Counter64
        MAX-ACCESS     read-only
        STATUS         current
        DESCRIPTION
            "Received multicast packets."
        ::= { zxAnVlanStatEntry 27 }

    zxAnVlanTxMcastPkts  OBJECT-TYPE
        SYNTAX         Counter64
        MAX-ACCESS     read-only
        STATUS         current
        DESCRIPTION
            "Transmitted multicast packets."
        ::= { zxAnVlanStatEntry 28 }

    zxAnVlanRxMcastOctets  OBJECT-TYPE
        SYNTAX         Counter64
        UNITS          "bytes"
        MAX-ACCESS     read-only
        STATUS         current
        DESCRIPTION
            "Received multicast octets."
        ::= { zxAnVlanStatEntry 29 }

    zxAnVlanTxMcastOctets  OBJECT-TYPE
        SYNTAX         Counter64
        UNITS          "bytes"
        MAX-ACCESS     read-only
        STATUS         current
        DESCRIPTION
            "Transmitted multicast octets."
        ::= { zxAnVlanStatEntry 30 }

    zxAnVlanRxMcastOctetRate   OBJECT-TYPE
        SYNTAX         Gauge32
        UNITS          "kbps"
        MAX-ACCESS     read-only
        STATUS         current
        DESCRIPTION
            "Received multicast octet rate."
        ::= { zxAnVlanStatEntry 31 }

    zxAnVlanTxMcastOctetRate   OBJECT-TYPE
        SYNTAX         Gauge32
        UNITS          "kbps"
        MAX-ACCESS     read-only
        STATUS         current
        DESCRIPTION
            "Transmitted multicast octet rate."
        ::= { zxAnVlanStatEntry 32 }
        
    zxAnVlanRxMcastOctetPeakRate   OBJECT-TYPE
        SYNTAX         Gauge32
        UNITS          "kbps"
        MAX-ACCESS     read-only
        STATUS         current
        DESCRIPTION
            "Received multicast octet peak rate."
        ::= { zxAnVlanStatEntry 33 }

    zxAnVlanTxMcastOctetPeakRate   OBJECT-TYPE
        SYNTAX         Gauge32
        UNITS          "kbps"
        MAX-ACCESS     read-only
        STATUS         current
        DESCRIPTION
            "Transmitted multicast octet peak rate."
        ::= { zxAnVlanStatEntry 34 }

    zxAnVlanRxBcastPkts  OBJECT-TYPE
        SYNTAX         Counter64
        MAX-ACCESS     read-only
        STATUS         current
        DESCRIPTION
            "Received broadcast packets."
        ::= { zxAnVlanStatEntry 35 }

    zxAnVlanTxBcastPkts  OBJECT-TYPE
        SYNTAX         Counter64
        MAX-ACCESS     read-only
        STATUS         current
        DESCRIPTION
            "Transmitted broadcast packets."
        ::= { zxAnVlanStatEntry 36 }

    zxAnVlanRxBcastOctets  OBJECT-TYPE
        SYNTAX         Counter64
        UNITS          "bytes"
        MAX-ACCESS     read-only
        STATUS         current
        DESCRIPTION
            "Received broadcast octets."
        ::= { zxAnVlanStatEntry 37 }

    zxAnVlanTxBcastOctets  OBJECT-TYPE
        SYNTAX         Counter64
        UNITS          "bytes"
        MAX-ACCESS     read-only
        STATUS         current
        DESCRIPTION
            "Transmitted broadcast octets."
        ::= { zxAnVlanStatEntry 38 }

    zxAnVlanRxFloodPkts  OBJECT-TYPE
        SYNTAX         Counter64
        MAX-ACCESS     read-only
        STATUS         current
        DESCRIPTION
            "Received flood packets."
        ::= { zxAnVlanStatEntry 39 }

    zxAnVlanTxFloodPkts  OBJECT-TYPE
        SYNTAX         Counter64
        MAX-ACCESS     read-only
        STATUS         current
        DESCRIPTION
            "Transmitted flood packets."
        ::= { zxAnVlanStatEntry 40 }

    zxAnVlanRxFloodOctets  OBJECT-TYPE
        SYNTAX         Counter64
        UNITS          "bytes"
        MAX-ACCESS     read-only
        STATUS         current
        DESCRIPTION
            "Received flood octets."
        ::= { zxAnVlanStatEntry 41 }

    zxAnVlanTxFloodOctets  OBJECT-TYPE
        SYNTAX         Counter64
        UNITS          "bytes"
        MAX-ACCESS     read-only
        STATUS         current
        DESCRIPTION
            "Transmitted flood octets."
        ::= { zxAnVlanStatEntry 42 }

    zxAnVlanStatRowStatus  OBJECT-TYPE
        SYNTAX      RowStatus
        MAX-ACCESS  read-create
        STATUS      current
        DESCRIPTION
            "This object indicates the status of this entry."
        ::= { zxAnVlanStatEntry 101 }
                                       
END

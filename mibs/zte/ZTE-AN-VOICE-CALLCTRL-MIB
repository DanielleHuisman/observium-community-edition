-------------------------------------------------------------------------------
-- File Name : ZTE-AN-VOICE-CALLCTRL-MIB.mib
-- Date      : 2010-08-24
-- Author    : ZTE Nms dept.

--
-- Zte Voip Base Mib for Access Node
--
--
-------------------------------------------------------------------------------


ZTE-AN-VOICE-CALLCTRL-MIB DEFINITIONS ::= BEGIN

    IMPORTS
        MODULE-IDENTITY, NOTIFICATION-TYPE, OBJECT-TYPE, enterprises,
        IpAddress, Counter32, Integer32, Counter64, Unsigned32, Gauge32
                            FROM SNMPv2-SMI
        TEXTUAL-CONVENTION, MacAddress, DateAndTime, RowStatus, DisplayString,
        TruthValue          FROM SNMPv2-TC
        InetAddressType, InetAddress         FROM INET-ADDRESS-MIB;

    zxAnVoiceCallCtrlMib MODULE-IDENTITY
        LAST-UPDATED    "0608140000Z"  -- july. 23, 2005
        ORGANIZATION    "zte Telcom Co. Ltd."
        CONTACT-INFO    "E-mail: shen.yuyang@zte.com.cn,
                         E-mail: suchunshan@zte.com.cn"
        DESCRIPTION     "This MIB defines PortLocating managed objects for Access Node."
    
    ::= { zxAn 5200 }

    zte OBJECT IDENTIFIER ::= { enterprises 3902 }
    zxAn OBJECT IDENTIFIER ::= { zte 1015 }
    zxAnVoiceMgmt OBJECT IDENTIFIER ::= { zxAnVoiceCallCtrlMib 3 }
    zxAnVoipCallCtrl OBJECT IDENTIFIER ::= { zxAnVoiceMgmt 6 }   
    
-------------------------------------------------------------------------------
-- Following objects are defined.
-- 1. zxAnCallOptimizationTable
-- 3. msagCallResStatistic
-- 4. zxAnVoipCallCtrlGlobalObjects
-- 5. zxAnCallEscapeFxoTable
-- 6. zxAnCallEscapePriTable
-- 7. zxAnCallEscapePriDLinkTable
-------------------------------------------------------------------------------

-------------------------------------------------------------------------------
--  1.zxAnCallOptimizationTable
-------------------------------------------------------------------------------
    --msagChangeOidFromGlobalConfig OBJECT IDENTIFIER ::= { zxAnVoiceMgmt 1 }

    zxAnCallOptimizationTable OBJECT-TYPE
        SYNTAX      SEQUENCE OF ZxAnCallOptimizationEntry
        MAX-ACCESS  not-accessible
        STATUS      current
        DESCRIPTION ""
        --::={msagChangeOidFromGlobalConfig 13}
        ::= { zxAnVoipCallCtrl 1301 }

    zxAnCallOptimizationEntry OBJECT-TYPE
        SYNTAX      ZxAnCallOptimizationEntry
        MAX-ACCESS  not-accessible
        STATUS      current
        DESCRIPTION ""
        INDEX {zxAnCallOptIndex}
        ::= { zxAnCallOptimizationTable 1 }

    ZxAnCallOptimizationEntry ::= SEQUENCE {
        zxAnCallOptIndex                     INTEGER,
        zxAnCallOptOpenMsgAck                INTEGER,
        zxAnCallOptPlayToneAck               INTEGER,
        zxAnCallOptSubPriority               INTEGER,
        --zxAnCallOptNumMax                  INTEGER,
        --zxAnCallOptH248MsgAck              INTEGER,
        --zxAnCallOptH248MsgPn               INTEGER,
        zxAnCallOptH248Statistic             INTEGER,
        --zxAnCallOptH248HookOffEvent        INTEGER,
        --zxAnCallOptH248HookOnEvent         INTEGER,
        zxAnCallOptServiceAbnormal           INTEGER,
        zxAnCallOptMgProtocolErr             INTEGER,
        zxAnCallOptMgcProtocolErr            INTEGER,
        zxAnCallOptMgInsideErr               INTEGER,
        --zxAnCallOptHookOffLimiteCycle        INTEGER,
        --zxAnCallOptHookOffLimiteBlock        INTEGER,
        --zxAnCallOptHookOffLimiteUnblock      INTEGER,
        --zxAnCallOptMgcCallWaitTone           INTEGER,
        --zxAnCallOptToneArea                  INTEGER,

        --zxAnCallOptIpsThreshold              INTEGER,
        --zxAnCallOptCongestionTime            INTEGER,
        --zxAnCallOptPhoneNumberMatchType      Integer32,
  
        zxAnCallOptCallLimit                INTEGER,
        zxAnCallOptCallLimitMaxUserNum      Integer32
        }

    zxAnCallOptIndex OBJECT-TYPE
        SYNTAX      INTEGER(1)
        MAX-ACCESS  not-accessible
        STATUS      current
        DESCRIPTION ""
        ::= { zxAnCallOptimizationEntry 1 }

    zxAnCallOptOpenMsgAck OBJECT-TYPE
        SYNTAX      INTEGER {
            send(1),
            notsend(2)
            }
        MAX-ACCESS  read-write
        STATUS      current
        DESCRIPTION ""
        ::= { zxAnCallOptimizationEntry 2 }

    zxAnCallOptPlayToneAck OBJECT-TYPE
        SYNTAX      INTEGER {
            send(1),
            notsend(2)
            }
        MAX-ACCESS  read-write
        STATUS      current
        DESCRIPTION ""
        ::= { zxAnCallOptimizationEntry 3 }

    zxAnCallOptSubPriority OBJECT-TYPE
        SYNTAX      INTEGER {
            higher(1),
            nothigher(2)
            }
        MAX-ACCESS  read-write
        STATUS      current
        DESCRIPTION ""
        ::= { zxAnCallOptimizationEntry 4 }

    zxAnCallOptH248Statistic OBJECT-TYPE
        SYNTAX      INTEGER {
            send(1),
            notsend(2)
            }
        MAX-ACCESS  read-write
        STATUS      current
        DESCRIPTION ""
        ::= { zxAnCallOptimizationEntry 8 }

    zxAnCallOptServiceAbnormal OBJECT-TYPE
        SYNTAX      INTEGER {
            alwayssend(1),
            notalways(2)
            }
        MAX-ACCESS  read-write
        STATUS      current
        DESCRIPTION ""
        ::= { zxAnCallOptimizationEntry 11 }

    zxAnCallOptMgProtocolErr OBJECT-TYPE
        SYNTAX      INTEGER {
            alwayssend(1),
            notalways(2)
            }
        MAX-ACCESS  read-write
        STATUS      current
        DESCRIPTION ""
        ::= { zxAnCallOptimizationEntry 12 }

    zxAnCallOptMgcProtocolErr OBJECT-TYPE
        SYNTAX      INTEGER {
            alwayssend(1),
            notalways(2)
            }
        MAX-ACCESS  read-write
        STATUS      current
        DESCRIPTION ""
        ::= { zxAnCallOptimizationEntry 13 }

    zxAnCallOptMgInsideErr OBJECT-TYPE
        SYNTAX      INTEGER {
            alwayssend(1),
            notalways(2)
            }
        MAX-ACCESS  read-write
        STATUS      current
        DESCRIPTION ""
        ::= { zxAnCallOptimizationEntry 14 }     
  
    zxAnCallOptCallLimit  OBJECT-TYPE
        SYNTAX      INTEGER {
            limitByMg(1),
            limitByMgc(2),
            noLimit(3)
            }
        MAX-ACCESS  read-write
        STATUS      current
        DESCRIPTION 
            "The call limit type."
        DEFVAL { noLimit }
        ::= { zxAnCallOptimizationEntry 15 } 
        
    zxAnCallOptCallLimitMaxUserNum  OBJECT-TYPE
        SYNTAX       Integer32(0..128)
        MAX-ACCESS   read-write
        STATUS       current
        DESCRIPTION  
            "The maximum number of current users.
             Only valid when zxAnCallOptCallLimit is limitByMg(1)."
        DEFVAL { 128 }
        ::= { zxAnCallOptimizationEntry 16 }       
   
-------------------------------------------------------------------------------
--  3.msagCallResStatistic
------------------------------------------------------------------------------- 

    msagCallResStatistic OBJECT IDENTIFIER ::= { zxAnVoipCallCtrl 5 }
   
    msagCRAccessRatio    OBJECT-TYPE
        SYNTAX      DisplayString(SIZE(0..10))
        MAX-ACCESS  read-only
        STATUS      current
        DESCRIPTION ""
        ::= { msagCallResStatistic 1 }

    msagCRIPSUsingRatio    OBJECT-TYPE
        SYNTAX      DisplayString(SIZE(0..10))
        MAX-ACCESS  read-only
        STATUS      current
        DESCRIPTION ""
        ::= { msagCallResStatistic 2 }

    msagCROpenChannelReq    OBJECT-TYPE
        SYNTAX      Integer32
        MAX-ACCESS  read-only
        STATUS      current
        DESCRIPTION ""
        ::= { msagCallResStatistic 3 }

    msagCRRecOpenSucces    OBJECT-TYPE
        SYNTAX      Integer32
        MAX-ACCESS  read-only
        STATUS      current
        DESCRIPTION ""
        ::= { msagCallResStatistic 4 }

    msagCRRecOpenFail    OBJECT-TYPE
        SYNTAX      Integer32
        MAX-ACCESS  read-only
        STATUS      current
        DESCRIPTION ""
        ::= { msagCallResStatistic 5 }

    msagCROpenChannTimerOut    OBJECT-TYPE
        SYNTAX      Integer32
        MAX-ACCESS  read-only
        STATUS      current
        DESCRIPTION ""
        ::= { msagCallResStatistic 6 }

    msagCRModifyChannel    OBJECT-TYPE
        SYNTAX      Integer32
        MAX-ACCESS  read-only
        STATUS      current
        DESCRIPTION ""
        ::= { msagCallResStatistic 7 }

    msagCRRecModifySucces    OBJECT-TYPE
        SYNTAX      Integer32
        MAX-ACCESS  read-only
        STATUS      current
        DESCRIPTION ""
        ::= { msagCallResStatistic 8 }

    msagCRModifyChFail    OBJECT-TYPE
        SYNTAX      Integer32
        MAX-ACCESS  read-only
        STATUS      current
        DESCRIPTION ""
        ::= { msagCallResStatistic 9 }

    msagCRWtModifyChannTimerOut    OBJECT-TYPE
        SYNTAX      Integer32
        MAX-ACCESS  read-only
        STATUS      current
        DESCRIPTION ""
        ::= { msagCallResStatistic 10 }

    msagCRSendCloseChannel    OBJECT-TYPE
        SYNTAX      Integer32
        MAX-ACCESS  read-only
        STATUS      current
        DESCRIPTION ""
        ::= { msagCallResStatistic 11 }

    msagCRRecCloseChanSucc    OBJECT-TYPE
        SYNTAX      Integer32
        MAX-ACCESS  read-only
        STATUS      current
        DESCRIPTION ""
        ::= { msagCallResStatistic 12 }

    msagCRRecCloseChanFail    OBJECT-TYPE
        SYNTAX      Integer32
        MAX-ACCESS  read-only
        STATUS      current
        DESCRIPTION ""
        ::= { msagCallResStatistic 13 }

    msagCRRecCloseChanTimerOut    OBJECT-TYPE
        SYNTAX      Integer32
        MAX-ACCESS  read-only
        STATUS      current
        DESCRIPTION ""
        ::= { msagCallResStatistic 14 }

    msagCRRecMprReload    OBJECT-TYPE
        SYNTAX      Integer32
        MAX-ACCESS  read-only
        STATUS      current
        DESCRIPTION ""
        ::= { msagCallResStatistic 15 }

    msagCRClearRTPRecord    OBJECT-TYPE
        SYNTAX      INTEGER(1)
        MAX-ACCESS  read-write
        STATUS      current
        DESCRIPTION ""
        ::= { msagCallResStatistic 16 }  
        
--------------------------------------------------------------------------------
-- 4. zxAnVoipCallCtrlGlobalObjects
--------------------------------------------------------------------------------

    zxAnVoipCallCtrlGlobalObjects OBJECT IDENTIFIER ::= { zxAnVoipCallCtrl 1300 }

    zxAnVoipCallCtrlMgmtCapabilities OBJECT-TYPE
        SYNTAX      BITS {
            nbPlatform(0)
            }
        MAX-ACCESS  read-only
        STATUS      current
        DESCRIPTION
            "The VOIP callctrl management capabilities of this equipment.
            The bit value 1 means the function represented by this bit is
            supported by this equipment.            
            bit 1: value 1 means support narrowband platform.
            NOTE: No recommended to display it in NMS."
        ::= { zxAnVoipCallCtrlGlobalObjects 1 }

--------------------------------------------------------------------------------
-- 5. zxAnCallEscapeFxoTable
--------------------------------------------------------------------------------
    zxAnCallEscapeObjects OBJECT IDENTIFIER ::= { zxAnVoipCallCtrl 1302 }

    zxAnCallEscapeFxoTable OBJECT-TYPE
        SYNTAX      SEQUENCE OF ZxAnCallEscapeFxoEntry
        MAX-ACCESS  not-accessible
        STATUS      current
        DESCRIPTION 
            "FXO call escape configuration table."
        ::= { zxAnCallEscapeObjects 2 }

    zxAnCallEscapeFxoEntry OBJECT-TYPE
        SYNTAX      ZxAnCallEscapeFxoEntry
        MAX-ACCESS  not-accessible
        STATUS      current
        DESCRIPTION 
            "Entry of FXO call escape table."
        INDEX { zxAnCallEscapeRack,zxAnCallEscapeShelf,
                zxAnCallEscapeSlot,zxAnCallEscapePort}
        ::= { zxAnCallEscapeFxoTable 1 }

    ZxAnCallEscapeFxoEntry ::= SEQUENCE {
        zxAnCallEscapeRack              Integer32,
        zxAnCallEscapeShelf             Integer32,
        zxAnCallEscapeSlot              Integer32,
        zxAnCallEscapePort              Integer32,
        zxAnCallEscapeFxoOperNum        Integer32,        
        zxAnCallEscapeFxoRowStatus      RowStatus
    }
   
    zxAnCallEscapeRack  OBJECT-TYPE
        SYNTAX      Integer32
        MAX-ACCESS  not-accessible
        STATUS      current
        DESCRIPTION 
            "Rack of FXO call escape."
        ::={zxAnCallEscapeFxoEntry 1}
  
    zxAnCallEscapeShelf  OBJECT-TYPE
        SYNTAX      Integer32
        MAX-ACCESS  not-accessible
        STATUS      current
        DESCRIPTION 
            "Shelf of FXO call escape."
        ::={zxAnCallEscapeFxoEntry 2}
  
    zxAnCallEscapeSlot  OBJECT-TYPE
        SYNTAX      Integer32
        MAX-ACCESS  not-accessible
        STATUS      current
        DESCRIPTION 
            "Slot of FXO call escape."
        ::={zxAnCallEscapeFxoEntry 3}
  
    zxAnCallEscapePort  OBJECT-TYPE
        SYNTAX      Integer32
        MAX-ACCESS  not-accessible
        STATUS      current
        DESCRIPTION 
            "Port of FXO call escape."
        ::={zxAnCallEscapeFxoEntry 4}

    zxAnCallEscapeFxoOperNum  OBJECT-TYPE
        SYNTAX      Integer32
        MAX-ACCESS  read-create
        STATUS      current
        DESCRIPTION 
            "Batch operation number of FXO call escape."
        ::={zxAnCallEscapeFxoEntry 5}

    zxAnCallEscapeFxoRowStatus  OBJECT-TYPE
        SYNTAX      RowStatus
        MAX-ACCESS  read-create
        STATUS      current
        DESCRIPTION 
            "The status of this conceptual row.
            The state of this conceptual row only support 'not exist' and  
            'active'.
            The action of this conceptual row only support 'createAndGo' and 
            'destroy'.
            
            To create a row in this table, a manager must set this object to 
            createAndGo(4).
    
            To delete a row in this table, a manager must set this object to 
            destroy(6). 
             
            To query this object, always return active(1)."
        ::= { zxAnCallEscapeFxoEntry 50 }

--------------------------------------------------------------------------------
-- 6. zxAnCallEscapePriTable
--------------------------------------------------------------------------------
         
    zxAnCallEscapePriTable OBJECT-TYPE
        SYNTAX      SEQUENCE OF ZxAnCallEscapePriEntry
        MAX-ACCESS  not-accessible
        STATUS      current
        DESCRIPTION 
            "PRI call escape configuration table."
        ::= { zxAnCallEscapeObjects 3 }

    zxAnCallEscapePriEntry OBJECT-TYPE
        SYNTAX      ZxAnCallEscapePriEntry
        MAX-ACCESS  not-accessible
        STATUS      current
        DESCRIPTION 
            "Entry of PRI call escape table."
        INDEX { zxAnCallEscapeRack,zxAnCallEscapeShelf,
                zxAnCallEscapeSlot,zxAnCallEscapeDsx1LinkNo}
        ::= { zxAnCallEscapePriTable 1 }

    ZxAnCallEscapePriEntry ::= SEQUENCE {        
        zxAnCallEscapeDsx1LinkNo        Integer32,   
        zxAnCallEscapePriOperNum        Integer32,
        zxAnCallEscapePriRowStatus      RowStatus
    }
  
    zxAnCallEscapeDsx1LinkNo  OBJECT-TYPE
        SYNTAX      Integer32
        MAX-ACCESS  not-accessible
        STATUS      current
        DESCRIPTION 
            "E1/T1 link No. of PRI call escape."
        ::={zxAnCallEscapePriEntry 1}

    zxAnCallEscapePriOperNum  OBJECT-TYPE
        SYNTAX      Integer32
        MAX-ACCESS  read-create
        STATUS      current
        DESCRIPTION 
            "Batch operation number of PRI call escape."
        ::={zxAnCallEscapePriEntry 2}

    zxAnCallEscapePriRowStatus  OBJECT-TYPE
        SYNTAX      RowStatus
        MAX-ACCESS  read-create
        STATUS      current
        DESCRIPTION 
            "The status of this conceptual row.
            The state of this conceptual row only support 'not exist' and  
            'active'.
            The action of this conceptual row only support 'createAndGo' and 
            'destroy'.
            
            To create a row in this table, a manager must set this object to 
            createAndGo(4).
    
            To delete a row in this table, a manager must set this object to 
            destroy(6). 
             
            To query this object, always return active(1)."
        ::= { zxAnCallEscapePriEntry 50 }    

--------------------------------------------------------------------------------
-- 7. zxAnCallEscapePriDLinkTable
--------------------------------------------------------------------------------
    zxAnCallEscapePriDLinkTable OBJECT-TYPE
        SYNTAX      SEQUENCE OF ZxAnCallEscapePriDLinkEntry
        MAX-ACCESS  not-accessible
        STATUS      current
        DESCRIPTION 
            "PRI call escape link configuration table."
        ::={zxAnCallEscapeObjects 4}

    zxAnCallEscapePriDLinkEntry OBJECT-TYPE
        SYNTAX      ZxAnCallEscapePriDLinkEntry
        MAX-ACCESS  not-accessible
        STATUS      current
        DESCRIPTION 
            "Entry of PRI call escape link configuration table."
        INDEX { zxAnCallEscapeRack,zxAnCallEscapeShelf,zxAnCallEscapeSlot,
                zxAnCallEscapeDsx1LinkNo,zxAnCallEscapePriDLinkTimeslot}
        ::={zxAnCallEscapePriDLinkTable 1}

    ZxAnCallEscapePriDLinkEntry ::=
        SEQUENCE{          
            zxAnCallEscapePriDLinkTimeslot    Integer32,
            zxAnCallEscapePriDLinkLinkId      Integer32,            
            zxAnCallEscapePriDLinkOperNum     Integer32,
            zxAnCallEscapePriDLinkLinkType    INTEGER, 
            zxAnCallEscapePriDLinkRowStatus   RowStatus
        }

    zxAnCallEscapePriDLinkTimeslot OBJECT-TYPE
        SYNTAX      Integer32(1..31)
        MAX-ACCESS  not-accessible
        STATUS      current
        DESCRIPTION 
            "D-channel timeslot of PRI link."        
        ::= { zxAnCallEscapePriDLinkEntry 1 }

    zxAnCallEscapePriDLinkLinkId  OBJECT-TYPE
        SYNTAX      Integer32(1..512)
        MAX-ACCESS  read-create
        STATUS      current
        DESCRIPTION 
            "Link ID of PRI link."
        ::= { zxAnCallEscapePriDLinkEntry 2 }

    zxAnCallEscapePriDLinkOperNum  OBJECT-TYPE
        SYNTAX      Integer32
        MAX-ACCESS  read-create
        STATUS      current
        DESCRIPTION 
            "Batch operation number of PRI link."
        ::={zxAnCallEscapePriDLinkEntry 3}

    zxAnCallEscapePriDLinkLinkType  OBJECT-TYPE
        SYNTAX      INTEGER {
            networkSide(1),
            subscriberSide(2)
        }
        MAX-ACCESS  read-create
        STATUS      current
        DESCRIPTION 
            "Link type of PRI link."
        DEFVAL { networkSide }
        ::={zxAnCallEscapePriDLinkEntry 4}

    zxAnCallEscapePriDLinkRowStatus     OBJECT-TYPE
        SYNTAX      RowStatus
        MAX-ACCESS  read-create
        STATUS      current
        DESCRIPTION 
            "The status of this conceptual row.
            The state of this conceptual row only support 'not exist' and  
            'active'.
            The action of this conceptual row only support 'createAndGo' and 
            'destroy'.
            
            To create a row in this table, a manager must set this object to 
            createAndGo(4).
    
            To delete a row in this table, a manager must set this object to 
            destroy(6). 
             
            To query this object, always return active(1)."
        ::= { zxAnCallEscapePriDLinkEntry 50 }
     
END

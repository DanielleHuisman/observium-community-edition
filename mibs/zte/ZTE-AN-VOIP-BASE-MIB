ZTE-AN-VOIP-BASE-MIB DEFINITIONS ::= BEGIN

  IMPORTS
   MODULE-IDENTITY,NOTIFICATION-TYPE,OBJECT-TYPE, enterprises,IpAddress,Counter32,
         Integer32, Counter64, Unsigned32, Gauge32          FROM SNMPv2-SMI
         
     -- DisplayString                          FROM SNMPv2-TC
     -- ZxAnIfindex,zxAn                       FROM ZTE-AN-TC-MIB;
      TEXTUAL-CONVENTION,MacAddress,DateAndTime,RowStatus,DisplayString,TruthValue
      FROM SNMPv2-TC
    InetAddressType, InetAddress     FROM INET-ADDRESS-MIB;

    zxAnVoipBaseMib MODULE-IDENTITY
        LAST-UPDATED    "0608140000Z"  -- july. 23, 2005
        ORGANIZATION    "zte Telcom Co. Ltd."
        CONTACT-INFO    "E-mail: shen.yuyang@zte.com.cn,
                         E-mail: suchunshan@zte.com.cn"
        DESCRIPTION     "This MIB defines PortLocating managed objects for Access Node."

    ::= { msag 5200 }
    -- ::= { zxAn 5200 }

    zte OBJECT IDENTIFIER ::= { enterprises 3902 }
    msag OBJECT IDENTIFIER ::= { zte 1015 }
    msagmajorVersion OBJECT IDENTIFIER ::= { zxAnVoipBaseMib 3 }
 
-- MODULE DESCRIPTION END 
--------------------------------------------------------

--NEXT TEXT CONVENTION DEFINITION    
   A200ShelfTypes::= TEXTUAL-CONVENTION
        STATUS      current
        DESCRIPTION
                    "\u5b9a\u4e49ZXSS10-A200\u4e2d\u4f7f\u7528\u7684\u673a\u6846\u7c7b\u578b\uff1a
        DBCONBSTBASE :  \u63a7\u5236\u6846
        DBCONBSTBASE1:  \u63a7\u5236\u6269\u5c55\u6846
        DBCONBSTSLC  :  \u7528\u6237\u63a5\u5165\u6846
        DBCONBSTSLC1 :  \u7528\u6237\u63a5\u5165\u6269\u5c55\u6846"
        SYNTAX      INTEGER
      {
        dBCONBSTBASE(1),
        dBCONBSTBASE1(2),
        dBCONBSTSLC(3),
        dBCONBSTSLC1(4),
        dBCONBSTMSAGEX(5),
        dBCONBSTMSAGCTL(6),
        dBONU100(8),
        dBOUT50C(9),
        dBOUT50D(10),
        dBMBSLCTL(11),
        dBMBSLEX(12),
        dBTPUEX(13),
        dBPPEX(14),
        dBDOUBLEPPEX(15)
      }

   A200BoardTypes::= TEXTUAL-CONVENTION
        STATUS      current
        DESCRIPTION
                    " \u5b9a\u4e49ZXSS10-A200\u4e2d\u4f7f\u7528\u7684\u7535\u8def\u677f\u7c7b\u578b
        DBCONWBTASCL :  \u6a21\u62df\u7528\u6237\u677f
        DBCONWBTAMTT :  \u591a\u529f\u80fd\u6d4b\u8bd5\u677f
        DBCONWBTMFP  :  \u591a\u529f\u80fd\u4e3b\u5904\u7406\u6a21\u5757
        DBCONWBTAPR  :  \u5305\u5904\u7406\u53ca\u8d44\u6e90\u677f
        DBCONWBTANIC :  \u7f51\u7edc\u63a5\u53e3\u677f
        DBCONWBTASP  :  \u7528\u6237\u5355\u5143\u9a71\u52a8\u677f
        DBCONWBTASPI :  \u7528\u6237\u5355\u5143\u9a71\u52a8\u63a5\u53e3\u677f
        DBCONWBTAPOW :  \u63a5\u5165\u7f51\u5173\u7684\u7535\u6e90\u677f
        DBCONWBTAPOWP:  \u63a5\u5165\u7f51\u5173\u7684\u7535\u6e90\u677f
        DBCONWBTAFAN :  \u63a5\u5165\u7f51\u5173\u7684\u98ce\u6247"
        SYNTAX      INTEGER
      {
         dBCONWBTASCL(1),
         dBCONWBTAMTT(2),
         dBCONWBTMFP(3),
         dBCONWBTAPR(4),
         dBCONWBTAMSNIC(5),
         dBCONWBTASP(6),
         dBCONWBTASPI(7),
         dBCONWBTAPOW(8),
         dBCONWBTAPOWP(9),
         dBCONWBTAFAN(10)
      }
                
--TEXT CONVENTION END
------------------------------------------------------------------

--NEXT DEFINE TABLES IN THIS MIB

    msagGlobalConfig OBJECT IDENTIFIER ::= { msagmajorVersion 1 }

--mgcfg table definition begin
   a200MgCfgTable OBJECT-TYPE
   SYNTAX    SEQUENCE OF A200MgCfgEntry
   MAX-ACCESS  not-accessible
   STATUS    current
   DESCRIPTION  "ZXSS10-A200\u63a5\u5165\u7f51\u5173\u914d\u7f6e\u6570\u636e\uff0c\u63cf\u8ff0\u7f51\u5173\u5c5e\u6027"
  ::={msagGlobalConfig 1}

   a200MgCfgEntry OBJECT-TYPE
   SYNTAX    A200MgCfgEntry
   MAX-ACCESS  not-accessible
   STATUS    current
   DESCRIPTION  "colunms and index of mgccfg table"
   INDEX {a200mgid}
  ::={a200MgCfgTable 1}
 
  A200MgCfgEntry::=
   SEQUENCE{
      a200mgid         Integer32,
      a200protype      Integer32,
      a200version      Integer32,
      a200encodetp     Integer32,
      a200mgport       Integer32,
      a200translay     Integer32,
      a200transpro     Integer32,
      a200mgDomainName DisplayString,
      a200mgInfo       INTEGER,
      a200mgcid1       INTEGER,
      a200mgcid2       INTEGER,
      a200mgcid3       INTEGER,
      a200mgcid4       INTEGER,
      a200selfexchange INTEGER,
      a200protectcall  INTEGER,
      a200disasterprot INTEGER,
      a200mgRowStatus  RowStatus,

      a200tractnum     Integer32,
      a200sdpcho       Integer32,
      a200retrannum    Integer32,
      a200resdelay     Integer32,
      a200retranmin    Integer32,
      a200lkpttime     Integer32,
      a200pendtime     Integer32,
      a200pendcount    Integer32,
      a200kprestime    Integer32,
      a200tranidmax    Unsigned32,
      a200tranidmin    Unsigned32,
      a200rtpFaxPri1          INTEGER,
      a200rtpFaxPri2          INTEGER,
      a200subsuspendrtp       INTEGER,
      a200hotlinewithspace    INTEGER,
      a200rtp2833Type         INTEGER,
      a200ipsThreshold        INTEGER,
      a200congesttime         INTEGER,
      a200congesttone         INTEGER,
      a200callmatchtype       Integer32,
      a200currentmgcid        Integer32,

      a200mgSigTos            INTEGER,
      a200mgPSTNMediaVoiceTos INTEGER,
      a200mgPSTNMediaFaxTos   INTEGER,
      a200mgPSTNMediaModemTos INTEGER,
      a200mgPSTNMediaDataTos  INTEGER,
      a200mgISDNMediaVoiceTos INTEGER,
      a200mgISDNMediaFaxTos   INTEGER,
      a200mgISDNMediaModemTos INTEGER,
      a200mgISDNMediaDataTos  INTEGER,

      a200ringprofile         INTEGER,
      a200toneprofile         INTEGER,
      a200flashprofile        INTEGER,

      a200chg16kcwidth        Unsigned32,
      a200chg16kcinterval     Unsigned32,
      a200charge16kcvol       INTEGER,
      a200kcflag              INTEGER,
      a200ExternalSelfswitchEnable  INTEGER,
      zxAnIpsUsage            Integer32,
      a200MgCallEscapeMode    INTEGER
    }

    a200mgid  OBJECT-TYPE
      SYNTAX      Integer32
      MAX-ACCESS  not-accessible
      STATUS      current
      DESCRIPTION "\u903b\u8f91MG\u7f16\u53f7"
      ::={a200MgCfgEntry 1}

    a200protype  OBJECT-TYPE
      SYNTAX      Integer32
      MAX-ACCESS  read-create
      STATUS      current
      DESCRIPTION "\u63a7\u5236\u534f\u8bae\u7c7b\u578b:
        =1\uff1ah248\uff0c  =2\uff1amgcp"
      ::={a200MgCfgEntry 2}

    a200version  OBJECT-TYPE
      SYNTAX      Integer32
      MAX-ACCESS  read-create
      STATUS      current
      DESCRIPTION "\u63a7\u5236\u534f\u8bae\u7248\u672c\u53f7"
      ::={a200MgCfgEntry 3}

    a200encodetp  OBJECT-TYPE
      SYNTAX       Integer32
      MAX-ACCESS    read-create
      STATUS       current
      DESCRIPTION  "\u534f\u8bae\u5c01\u88c5\u683c\u5f0f:
        =1\uff1a\u6587\u672c\u683c\u5f0f\uff0c  =2\uff1a\u4e8c\u8fdb\u5236\u683c\u5f0f"
      ::={a200MgCfgEntry 4}

    a200mgport  OBJECT-TYPE
      SYNTAX      Integer32
      MAX-ACCESS  read-create
      STATUS      current
      DESCRIPTION "MG\u63a7\u5236\u534f\u8bae\u7684UDP\u7aef\u53e3\u53f7"
      ::={a200MgCfgEntry 5}

    a200translay  OBJECT-TYPE
      SYNTAX      Integer32
      MAX-ACCESS  read-create
      STATUS      current
      DESCRIPTION "\u5e95\u5c42\u4f20\u8f93\u7c7b\u578b:
         =1: ip,  =2: atm"
      ::={a200MgCfgEntry 6}

    a200transpro  OBJECT-TYPE
      SYNTAX      Integer32
      MAX-ACCESS  read-create
      STATUS      current
      DESCRIPTION "\u4f20\u8f93\u534f\u8bae\u7c7b\u578b:
         =1: udp,  =2: tcp"
      ::={a200MgCfgEntry 7}

   a200mgDomainName  OBJECT-TYPE
      SYNTAX      DisplayString(SIZE(0..32))
      MAX-ACCESS  read-create
      STATUS      current
      DESCRIPTION ""
      ::={a200MgCfgEntry 8}

    a200mgInfo  OBJECT-TYPE
      SYNTAX      INTEGER{useIp(0),useDomain(1),ipsIdle(4),englishTone(128)}
      MAX-ACCESS  read-create
      STATUS      current
      DESCRIPTION ""
      ::={a200MgCfgEntry 9}

    a200mgcid1  OBJECT-TYPE
      SYNTAX      INTEGER(1..255)
      MAX-ACCESS  read-create
      STATUS      current
      DESCRIPTION "\u63a7\u5236\u672cMG\u7684MGC\u7f16\u53f7"
      ::={a200MgCfgEntry 10}

    a200mgcid2      OBJECT-TYPE
      SYNTAX      INTEGER(1..255)
      MAX-ACCESS  read-create
      STATUS      current
      DESCRIPTION ""
      ::={a200MgCfgEntry 11}

    a200mgcid3      OBJECT-TYPE
      SYNTAX      INTEGER(1..255)
      MAX-ACCESS  read-create
      STATUS      current
      DESCRIPTION ""
      ::={a200MgCfgEntry 12}

    a200mgcid4      OBJECT-TYPE
      SYNTAX      INTEGER(1..255)
      MAX-ACCESS  read-create
      STATUS      current
      DESCRIPTION ""
      ::={a200MgCfgEntry 13}

    a200selfexchange  OBJECT-TYPE
      SYNTAX      INTEGER{disable(0),enable(1)}
      MAX-ACCESS  read-create
      STATUS      current
      DESCRIPTION ""
      ::={a200MgCfgEntry 14}

    a200protectcall  OBJECT-TYPE
      SYNTAX      INTEGER{disable(0),enable(1)}
      MAX-ACCESS  read-create
      STATUS      current
      DESCRIPTION ""
      ::={a200MgCfgEntry 15}

    a200disasterprot  OBJECT-TYPE
      SYNTAX      INTEGER{disble(0),enable(1)}
      MAX-ACCESS  read-create
      STATUS      current
      DESCRIPTION ""
      ::={a200MgCfgEntry 16}

    a200mgRowStatus  OBJECT-TYPE
      SYNTAX      RowStatus
      MAX-ACCESS  read-create
      STATUS      current
      DESCRIPTION "insert,delete,update"
      ::={a200MgCfgEntry 17}

    a200tractnum  OBJECT-TYPE
      SYNTAX      Integer32
      MAX-ACCESS  read-create
      STATUS      current
      DESCRIPTION "MG\u6700\u591a\u63a5\u6536\u4e8b\u52a1\u6570, >=5000, <=7000"
      ::={a200MgCfgEntry 18}

    a200sdpcho  OBJECT-TYPE
      SYNTAX      Integer32
      MAX-ACCESS  read-create
      STATUS      current
      DESCRIPTION "SDP\u652f\u6301\u547d\u4ee4\u7c7b\u522b"
      ::={a200MgCfgEntry 19}

    a200retrannum  OBJECT-TYPE
      SYNTAX      Integer32
      MAX-ACCESS  read-create
      STATUS      current
      DESCRIPTION "\u5305\u6700\u5927\u91cd\u4f20\u6b21\u6570 ; >=3 <=7"
      ::={a200MgCfgEntry 20}

    a200resdelay  OBJECT-TYPE
      SYNTAX      Integer32
      MAX-ACCESS  read-create
      STATUS      current
      DESCRIPTION "MG\u91cd\u8d77\u5ef6\u8fdf\u65f6\u95f4\uff0c\u4ee5\u79d2\u4e3a\u5355\u4f4d >=20s <=255s"
      ::={a200MgCfgEntry 21}

    a200retranmin OBJECT-TYPE
      SYNTAX      Integer32
      MAX-ACCESS  read-create
      STATUS      current
      DESCRIPTION "\u6700\u77ed\u91cd\u4f20\u5b9a\u65f6\uff0c\u4ee5100ms\u5355\u4f4d\u8ba1; >300ms <1.5s"
      ::={a200MgCfgEntry 22}

      a200lkpttime  OBJECT-TYPE
      SYNTAX      Integer32
      MAX-ACCESS  read-create
      STATUS      current
      DESCRIPTION "\u94fe\u8def\u68c0\u6d4b\u6d88\u606f\u7684\u53d1\u9001\u95f4\u9694\u7ea6,\u5728\u6b64\u65f6\u95f4\u5185\u8981\u53d1\u9001\u4e24\u6b21\u68c0\u6d4b\u6d88\u606f"
      ::={a200MgCfgEntry 23}

    a200pendtime  OBJECT-TYPE
      SYNTAX      Integer32
      MAX-ACCESS  read-create
      STATUS      current
      DESCRIPTION "\u4e8b\u52a1\u4e2d\u63d2\u5165\u7684\u4e00\u6b21\u6302\u8d77\u65f6\u95f4\uff0c\u4ee5100ms\u8ba1
        >=300ms <=1s"
      ::={a200MgCfgEntry 24}

    a200pendcount  OBJECT-TYPE
      SYNTAX      Integer32
      MAX-ACCESS  read-create
      STATUS      current
      DESCRIPTION "\u4e00\u4e2a\u4e8b\u52a1\u4e2d\u6700\u5927\u5141\u8bb8\u63d2\u5165\u7684\u6302\u8d77\u6b21\u6570\uff0c
        >=20  <=50"
      ::={a200MgCfgEntry 25}

    a200kprestime  OBJECT-TYPE
      SYNTAX      Integer32
      MAX-ACCESS  read-create
      STATUS      current
      DESCRIPTION "\u5bf9MGC\u5e94\u7b54\u7684\u4fdd\u7559\u65f6\u95f4 ,>20s <50s recommand 30s"
      ::={a200MgCfgEntry 26}

    a200tranidmax  OBJECT-TYPE
      SYNTAX      Unsigned32
      MAX-ACCESS  read-create
      STATUS      current
      DESCRIPTION "transactionId\u7684\u6700\u5927\u5141\u8bb8\u503c <0xffffffff"
      ::={a200MgCfgEntry 27}

    a200tranidmin  OBJECT-TYPE
      SYNTAX      Unsigned32
      MAX-ACCESS  read-create
      STATUS      current
      DESCRIPTION "transactionId\u7684\u6700\u5c0f\u5141\u8bb8\u503c >=0"
      ::={a200MgCfgEntry 28}

    a200rtpFaxPri1  OBJECT-TYPE
      SYNTAX    INTEGER{faxVBD(1),faxT38(2)}
      MAX-ACCESS      read-create
      STATUS    current
      DESCRIPTION  ""
      ::={a200MgCfgEntry 29}

    a200rtpFaxPri2  OBJECT-TYPE
      SYNTAX    INTEGER{faxVBD(1),faxT38(2)}
      MAX-ACCESS      read-create
      STATUS    current
      DESCRIPTION  ""
      ::={a200MgCfgEntry 30}

    a200subsuspendrtp  OBJECT-TYPE
      SYNTAX    INTEGER{sub(1),notsub(2)}
      MAX-ACCESS      read-create
      STATUS    current
      DESCRIPTION  ""
      ::={a200MgCfgEntry 31}

    a200hotlinewithspace  OBJECT-TYPE
      SYNTAX        INTEGER{withoutSpace(0),withSpace(1),withT(2)}
      MAX-ACCESS    read-create
      STATUS        current
      DESCRIPTION  
            "Hotline report format.
            withoutSpace(0): Report empty string to SS
            withSpace(1):    Report space to SS
            withT(2):        Report T to SS"
      ::={a200MgCfgEntry 32}

    a200rtp2833Type  OBJECT-TYPE
      SYNTAX    INTEGER{ type2833Redun(1),typeRTP(2),type2833NoRedun(3) }
      MAX-ACCESS      read-create
      STATUS    current
      DESCRIPTION  ""
      ::={a200MgCfgEntry 33}

    a200ipsThreshold  OBJECT-TYPE
      SYNTAX    INTEGER(1..100)
      MAX-ACCESS      read-create
      STATUS    current
      DESCRIPTION  ""
      ::={a200MgCfgEntry 34}

    a200congesttime  OBJECT-TYPE
      SYNTAX    INTEGER(10..20)
      MAX-ACCESS  read-create
      STATUS    current
      DESCRIPTION  "\u52a0\u5bc6\u65b9\u6cd5\u9009\u62e9, \u6682\u65f6\u672a\u7528"
      ::={a200MgCfgEntry 35}

    a200congesttone  OBJECT-TYPE
      SYNTAX    INTEGER{congtone(0)}
      MAX-ACCESS  read-create
      STATUS    current
      DESCRIPTION  "\u52a0\u5bc6\u65b9\u6cd5\u9009\u62e9, \u6682\u65f6\u672a\u7528"
      ::={a200MgCfgEntry 36}

    a200callmatchtype  OBJECT-TYPE
      SYNTAX    Integer32
      MAX-ACCESS  read-create
      STATUS    current
      DESCRIPTION  "\u52a0\u5bc6\u65b9\u6cd5\u9009\u62e9, \u6682\u65f6\u672a\u7528"
      ::={a200MgCfgEntry 37}

    a200currentmgcid  OBJECT-TYPE
      SYNTAX    Integer32
      MAX-ACCESS  read-create
      STATUS    current
      DESCRIPTION  "\u52a0\u5bc6\u65b9\u6cd5\u9009\u62e9, \u6682\u65f6\u672a\u7528"
      ::={a200MgCfgEntry 38}

    a200mgSigTos  OBJECT-TYPE
      SYNTAX    INTEGER{typeCommon(0),typeMinFee(1),typeMaxSecurity(2),typeMaxThruput(4),typeMinDelay(8)}
      MAX-ACCESS  read-create
      STATUS    current
      DESCRIPTION  ""
      ::={a200MgCfgEntry 39}

    a200mgPSTNMediaVoiceTos  OBJECT-TYPE
      SYNTAX    INTEGER{typeCommon(0),typeMinFee(1),typeMaxSecurity(2),typeMaxThruput(4),typeMinDelay(8)}
      MAX-ACCESS  read-create
      STATUS    current
      DESCRIPTION  ""
      ::={a200MgCfgEntry 40}

    a200mgPSTNMediaFaxTos  OBJECT-TYPE
      SYNTAX    INTEGER{typeCommon(0),typeMinFee(1),typeMaxSecurity(2),typeMaxThruput(4),typeMinDelay(8)}
      MAX-ACCESS  read-create
      STATUS    current
      DESCRIPTION  ""
      ::={a200MgCfgEntry 41}

    a200mgPSTNMediaModemTos  OBJECT-TYPE
      SYNTAX    INTEGER{typeCommon(0),typeMinFee(1),typeMaxSecurity(2),typeMaxThruput(4),typeMinDelay(8)}
      MAX-ACCESS  read-create
      STATUS    current
      DESCRIPTION  ""
      ::={a200MgCfgEntry 42}

    a200mgPSTNMediaDataTos  OBJECT-TYPE
      SYNTAX    INTEGER{typeCommon(0),typeMinFee(1),typeMaxSecurity(2),typeMaxThruput(4),typeMinDelay(8)}
      MAX-ACCESS  read-create
      STATUS    current
      DESCRIPTION  ""
      ::={a200MgCfgEntry 43}

    a200mgISDNMediaVoiceTos  OBJECT-TYPE
      SYNTAX    INTEGER{typeCommon(0),typeMinFee(1),typeMaxSecurity(2),typeMaxThruput(4),typeMinDelay(8)}
      MAX-ACCESS  read-create
      STATUS    current
      DESCRIPTION  ""
      ::={a200MgCfgEntry 44}

    a200mgISDNMediaFaxTos  OBJECT-TYPE
      SYNTAX    INTEGER{typeCommon(0),typeMinFee(1),typeMaxSecurity(2),typeMaxThruput(4),typeMinDelay(8)}
      MAX-ACCESS  read-create
      STATUS    current
      DESCRIPTION  ""
      ::={a200MgCfgEntry 45}

    a200mgISDNMediaModemTos  OBJECT-TYPE
      SYNTAX    INTEGER{typeCommon(0),typeMinFee(1),typeMaxSecurity(2),typeMaxThruput(4),typeMinDelay(8)}
      MAX-ACCESS  read-create
      STATUS    current
      DESCRIPTION  ""
      ::={a200MgCfgEntry 46}

    a200mgISDNMediaDataTos  OBJECT-TYPE
      SYNTAX    INTEGER{typeCommon(0),typeMinFee(1),typeMaxSecurity(2),typeMaxThruput(4),typeMinDelay(8)}
      MAX-ACCESS  read-create
      STATUS    current
      DESCRIPTION  ""
      ::={a200MgCfgEntry 47}

    a200ringprofile  OBJECT-TYPE
      SYNTAX    INTEGER(0..255)
      MAX-ACCESS   read-create
      STATUS    current
      DESCRIPTION  ""
      ::={a200MgCfgEntry 48}

    a200toneprofile  OBJECT-TYPE
      SYNTAX    INTEGER(0..255)
      MAX-ACCESS   read-create
      STATUS    current
      DESCRIPTION  ""
      ::={a200MgCfgEntry 49}

    a200flashprofile OBJECT-TYPE
      SYNTAX    INTEGER(0..255)
      MAX-ACCESS  read-create
      STATUS    current
      DESCRIPTION  ""
      ::={a200MgCfgEntry 50}

    a200chg16kcwidth OBJECT-TYPE
      SYNTAX    Unsigned32(0..4294967295)
      MAX-ACCESS  read-create
      STATUS    current
      DESCRIPTION  ""
      ::={a200MgCfgEntry 51}
     
    a200chg16kcinterval OBJECT-TYPE
      SYNTAX    Unsigned32(0..4294967295)
      MAX-ACCESS  read-create
      STATUS    current
      DESCRIPTION  ""
      ::={a200MgCfgEntry 52}
      
    a200charge16kcvol OBJECT-TYPE
      SYNTAX    INTEGER(0..2)
      MAX-ACCESS  read-create
      STATUS    current
      DESCRIPTION  ""
      ::={a200MgCfgEntry 53}
      
    a200kcflag OBJECT-TYPE
      SYNTAX    INTEGER{power16KC(0),power12KC(1),nopower16KC(2),nopower12KC(3)}
      MAX-ACCESS  read-create
      STATUS    current
      DESCRIPTION  ""
      ::={a200MgCfgEntry 54}

    a200ExternalSelfswitchEnable  OBJECT-TYPE
      SYNTAX      INTEGER{enable(1),disable(2)}
      MAX-ACCESS  read-create
      STATUS      current
      DESCRIPTION "External selfswitch enable status. If NE supports it, bit(0)
         of zxAnVoipBaseCapabilities must be set to 1."
      DEFVAL      {disable}
      ::={a200MgCfgEntry 55}

    zxAnIpsUsage  OBJECT-TYPE
      SYNTAX        Integer32(0..100)
      UNITS         "percent"
      MAX-ACCESS    read-only
      STATUS        current
      DESCRIPTION  
          "The usage of IPS resource."
      ::={a200MgCfgEntry 56}

    a200MgCallEscapeMode  OBJECT-TYPE
        SYNTAX      INTEGER {
            none(1),
            pri(2),
            fxo(3)            
        }        
        MAX-ACCESS  read-create
        STATUS      current
        DESCRIPTION 
            "The call escape mode used by this MG when the H248 or SIP link 
            is broken."
        DEFVAL      { none }
        ::= { a200MgCfgEntry 57 }

--end of mgcfg table

--mgccfg table definition begin

    a200mgccfgTable OBJECT-TYPE
      SYNTAX    SEQUENCE OF A200mgccfgEntry
      MAX-ACCESS  not-accessible
      STATUS    current
      DESCRIPTION  "\u5a92\u4f53\u7f51\u5173\u63a7\u5236\u5668\uff08MGC\uff09\u914d\u7f6e\u4fe1\u606f"
      ::={msagGlobalConfig 2}

    a200mgccfgEntry OBJECT-TYPE
      SYNTAX    A200mgccfgEntry
      MAX-ACCESS  not-accessible
      STATUS    current
      DESCRIPTION  "colunms and index of mgcfg table"
      INDEX {a200mgcmgcid}
      ::={a200mgccfgTable 1}

  A200mgccfgEntry::=
   SEQUENCE{
      a200mgcmgcid      Integer32,
      a200mgctypeid     INTEGER,
      a200mgcip         IpAddress,
      a200mgcport       Integer32,
      a200mgcdomain     DisplayString,
      a200mgcinfo       INTEGER,
      a200mgcMD5Info    INTEGER,
      a200mgcRowStatus  RowStatus
   }


    a200mgcmgcid  OBJECT-TYPE
      SYNTAX    Integer32
      MAX-ACCESS  not-accessible
      STATUS    current
      DESCRIPTION  "MGC\u7f16\u53f7"
      ::={a200mgccfgEntry 1}

    a200mgctypeid   OBJECT-TYPE
      SYNTAX    INTEGER(1..255)
      MAX-ACCESS  read-create
      STATUS    current
      DESCRIPTION  ""
      ::={a200mgccfgEntry 2}

    a200mgcip   OBJECT-TYPE
      SYNTAX    IpAddress
      MAX-ACCESS  read-create
      STATUS    current
      DESCRIPTION  "MGC\u7684IP\u5730\u57401"
      ::={a200mgccfgEntry 3}

    a200mgcport  OBJECT-TYPE
      SYNTAX    Integer32
      MAX-ACCESS  read-create
      STATUS    current
      DESCRIPTION  "MGC\u7684IP\u5730\u57401\u7684\u63a7\u5236\u534f\u8bae\u7aef\u53e3\u53f7"
      ::={a200mgccfgEntry 4}

   a200mgcdomain   OBJECT-TYPE
      SYNTAX    DisplayString (SIZE (0..32))
      MAX-ACCESS  read-create
      STATUS    current
      DESCRIPTION  ""
      ::={a200mgccfgEntry 5}

    a200mgcinfo   OBJECT-TYPE
      SYNTAX    INTEGER(0..1)
      MAX-ACCESS  read-create
      STATUS    current
      DESCRIPTION  ""
      ::={a200mgccfgEntry 6}

    a200mgcMD5Info   OBJECT-TYPE
      SYNTAX    INTEGER(0..10)
      MAX-ACCESS  read-create
      STATUS    current
      DESCRIPTION  ""
      ::={a200mgccfgEntry 7}

    a200mgcRowStatus   OBJECT-TYPE
      SYNTAX    RowStatus
      MAX-ACCESS  read-create
      STATUS    current
      DESCRIPTION  "insert,delete,update"
      ::={a200mgccfgEntry 8}


--end of mgccfg table

--Mgc type table begin

   a200MgcTypeTable OBJECT-TYPE
   SYNTAX    SEQUENCE OF A200MgcTypeEntry
   MAX-ACCESS  not-accessible
   STATUS    current
   DESCRIPTION  ""
  ::={msagGlobalConfig 3}

   a200MgcTypeEntry OBJECT-TYPE
   SYNTAX    A200MgcTypeEntry
   MAX-ACCESS  not-accessible
   STATUS    current
   DESCRIPTION  ""
   INDEX { a200MgcTypeId }
  ::={a200MgcTypeTable 1}

   A200MgcTypeEntry ::=
      SEQUENCE{
         a200MgcTypeId                INTEGER,
         a200MgcTypeDesc              DisplayString,
         a200MgcTypeMaxTransPkg       INTEGER,
         a200MgcTypeReasonQuote       INTEGER,
         a200MgcTypeQueryStatus       INTEGER,
         a200MgcTypeHeartBeat         INTEGER,
         a200MgcTypeDmLong            INTEGER,
         a200MgcTypeDmShort           INTEGER,
         a200MgcTypeDmStart           INTEGER,
         a200MgcTypeWithTime          INTEGER,
         a200MgcTypeWithDelay         INTEGER,
         a200MgcTypeProfileName       DisplayString,
         a200MgcTypeUserOut           INTEGER,
         a200MgcTypeAgOut             INTEGER,
         a200MgcTypeHeartId           Unsigned32,
         a200MgcTypeAgRegOldMT        INTEGER,
         a200MgcTypeCanclerror        INTEGER,
         a200MgcTypeRowStatus         RowStatus
       }

      a200MgcTypeId OBJECT-TYPE
        SYNTAX        INTEGER(1..255)
        MAX-ACCESS  not-accessible
        STATUS      current
        DESCRIPTION    ""
        ::={a200MgcTypeEntry 1}

      a200MgcTypeDesc OBJECT-TYPE
        SYNTAX    DisplayString(SIZE(1..17))
        MAX-ACCESS  read-create
        STATUS      current
        DESCRIPTION    ""
        ::={a200MgcTypeEntry 2}

      a200MgcTypeMaxTransPkg OBJECT-TYPE
        SYNTAX        INTEGER(1..3)
        MAX-ACCESS  read-create
        STATUS      current
        DESCRIPTION    ""
        ::={a200MgcTypeEntry 3}

      a200MgcTypeReasonQuote OBJECT-TYPE
        SYNTAX        INTEGER{typeEnable(1),typeDisable(2)}
        MAX-ACCESS  read-create
        STATUS      current
        DESCRIPTION    ""
        ::={a200MgcTypeEntry 4}

      a200MgcTypeQueryStatus OBJECT-TYPE
        SYNTAX        INTEGER{typeDisable(0),typeEnable(1)}
        MAX-ACCESS  read-create
        STATUS      current
        DESCRIPTION    ""
        ::={a200MgcTypeEntry 5}

      a200MgcTypeHeartBeat OBJECT-TYPE
        SYNTAX        INTEGER(0..65535)
        MAX-ACCESS  read-create
        STATUS      current
        DESCRIPTION    ""
        ::={a200MgcTypeEntry 6}

      a200MgcTypeDmLong      OBJECT-TYPE
        SYNTAX        INTEGER(0..50)
        MAX-ACCESS  read-create
        STATUS      current
        DESCRIPTION    ""
        ::={a200MgcTypeEntry 7}

      a200MgcTypeDmShort      OBJECT-TYPE
        SYNTAX        INTEGER(0..50)
        MAX-ACCESS  read-create
        STATUS      current
        DESCRIPTION    ""
        ::={a200MgcTypeEntry 8}

      a200MgcTypeDmStart      OBJECT-TYPE
        SYNTAX        INTEGER(0..50)
        MAX-ACCESS  read-create
        STATUS      current
        DESCRIPTION    ""
        ::={a200MgcTypeEntry 9}

     a200MgcTypeWithTime      OBJECT-TYPE
       SYNTAX    INTEGER{include(1),notinclude(2)}
       MAX-ACCESS  read-create
       STATUS    current
       DESCRIPTION  ""
       ::={a200MgcTypeEntry 10}

     a200MgcTypeWithDelay      OBJECT-TYPE
       SYNTAX    INTEGER(0..65535)
       MAX-ACCESS  read-create
       STATUS    current
       DESCRIPTION  ""
       ::={a200MgcTypeEntry 11}

     a200MgcTypeProfileName      OBJECT-TYPE
       SYNTAX    DisplayString(SIZE(0..10))
       MAX-ACCESS  read-create
       STATUS    current
       DESCRIPTION  ""
       ::={a200MgcTypeEntry 12}

     a200MgcTypeUserOut      OBJECT-TYPE
       SYNTAX    INTEGER(900..915)
       MAX-ACCESS  read-create
       STATUS    current
       DESCRIPTION  ""
       ::={a200MgcTypeEntry 13}

     a200MgcTypeAgOut      OBJECT-TYPE
       SYNTAX    INTEGER(900..915)
       MAX-ACCESS  read-create
       STATUS    current
       DESCRIPTION  ""
       ::={a200MgcTypeEntry 14}

     a200MgcTypeHeartId      OBJECT-TYPE
       SYNTAX    Unsigned32
       MAX-ACCESS  read-create
       STATUS    current
       DESCRIPTION  ""
       ::={a200MgcTypeEntry 15}

     a200MgcTypeAgRegOldMT      OBJECT-TYPE
       SYNTAX    INTEGER(1..2)
       MAX-ACCESS  read-create
       STATUS    current
       DESCRIPTION  ""
       ::={a200MgcTypeEntry 16}

     a200MgcTypeCanclerror      OBJECT-TYPE
       SYNTAX    INTEGER(1..2)
       MAX-ACCESS  read-create
       STATUS    current
       DESCRIPTION  ""
       ::={a200MgcTypeEntry 17}

      a200MgcTypeRowStatus OBJECT-TYPE
        SYNTAX        RowStatus
        MAX-ACCESS  read-create
        STATUS      current
        DESCRIPTION    ""
        ::={a200MgcTypeEntry 18}

--end of MGC type table

--MEDIA NAT table begin
   a200MedNatTable OBJECT-TYPE
   SYNTAX    SEQUENCE OF A200MedNatEntry
   MAX-ACCESS  not-accessible
   STATUS    current
   DESCRIPTION  ""
  ::={msagGlobalConfig 4}

   a200MedNatEntry OBJECT-TYPE
   SYNTAX    A200MedNatEntry
   MAX-ACCESS  not-accessible
   STATUS    current
   DESCRIPTION  "describe colunms and index in NAT table"
   INDEX { a200mednatIpsRack, a200mednatIpsShelf, a200mednatIpsSlot,
    a200mednatSubCard }
  ::={a200MedNatTable 1}

   A200MedNatEntry::=
      SEQUENCE{
       a200mednatIpsRack       Integer32,
       a200mednatIpsShelf      Integer32,
       a200mednatIpsSlot       Integer32,
       a200mednatSubCard       Integer32,
       a200mednatNicRack       Integer32,
       a200mednatNicShelf      Integer32,
       a200mednatNicSlot       Integer32,
       a200mednatInPhyPort     Integer32,
       a200mednatExPhyPort     Integer32,
       a200mednatExIp          IpAddress,
       a200mednatUdpPort       Integer32,
       a200mednatRowStatus     RowStatus,
       a200natCtrlId           Integer32
   }

  a200mednatIpsRack  OBJECT-TYPE
   SYNTAX    Integer32
   MAX-ACCESS not-accessible
   STATUS    current
   DESCRIPTION  ""
  ::={a200MedNatEntry 1}

  a200mednatIpsShelf    OBJECT-TYPE
   SYNTAX    Integer32
   MAX-ACCESS  not-accessible
   STATUS    current
   DESCRIPTION  ""
  ::={a200MedNatEntry 2}

  a200mednatIpsSlot   OBJECT-TYPE
   SYNTAX    Integer32
   MAX-ACCESS  not-accessible
   STATUS    current
   DESCRIPTION  ""
  ::={a200MedNatEntry 3}

  a200mednatSubCard   OBJECT-TYPE
   SYNTAX    Integer32
   MAX-ACCESS  not-accessible
   STATUS    current
   DESCRIPTION  ""
  ::={a200MedNatEntry 4}

  a200mednatNicRack  OBJECT-TYPE
   SYNTAX    Integer32
   MAX-ACCESS  read-create
   STATUS    current
   DESCRIPTION  ""
  ::={a200MedNatEntry 5}

  a200mednatNicShelf  OBJECT-TYPE
   SYNTAX    Integer32
   MAX-ACCESS  read-create
   STATUS    current
   DESCRIPTION  ""
  ::={a200MedNatEntry 6}

  a200mednatNicSlot  OBJECT-TYPE
   SYNTAX    Integer32
   MAX-ACCESS  read-create
   STATUS    current
   DESCRIPTION  ""
  ::={a200MedNatEntry 7}

  a200mednatInPhyPort  OBJECT-TYPE
   SYNTAX    Integer32
   MAX-ACCESS  read-create
   STATUS    current
   DESCRIPTION  ""
  ::={a200MedNatEntry 8}

  a200mednatExPhyPort  OBJECT-TYPE
   SYNTAX    Integer32
   MAX-ACCESS  read-create
   STATUS    current
   DESCRIPTION  ""
  ::={a200MedNatEntry 9}

  a200mednatExIp  OBJECT-TYPE
   SYNTAX    IpAddress
   MAX-ACCESS  read-create
   STATUS    current
   DESCRIPTION  ""
  ::={a200MedNatEntry 10}

  a200mednatUdpPort   OBJECT-TYPE
   SYNTAX    Integer32
   MAX-ACCESS  read-create
   STATUS    current
   DESCRIPTION  ""
  ::={a200MedNatEntry 11}

  a200mednatRowStatus   OBJECT-TYPE
   SYNTAX    RowStatus
   MAX-ACCESS  read-create
   STATUS    current
   DESCRIPTION  "insert,delete,update"
  ::={a200MedNatEntry 12}

  a200natCtrlId   OBJECT-TYPE
   SYNTAX    Integer32
   MAX-ACCESS  read-only
   STATUS    current
   DESCRIPTION  ""
  ::={a200MedNatEntry 13}

--end of nat table

--QOVS table begin

   a200QovsTable OBJECT-TYPE
   SYNTAX    SEQUENCE OF A200QovsEntry
   MAX-ACCESS  not-accessible
   STATUS    current
   DESCRIPTION  ""
  ::={msagGlobalConfig 5}

   a200QovsEntry OBJECT-TYPE
   SYNTAX    A200QovsEntry
   MAX-ACCESS  not-accessible
   STATUS    current
   DESCRIPTION  ""
   INDEX { a200QovsId }
  ::={a200QovsTable 1}

   A200QovsEntry ::=
      SEQUENCE{
      a200QovsId        INTEGER,
      a200QovsLoss      INTEGER,
      a200QovsDelay     INTEGER,
      a200QovsJitter    INTEGER,
      a200QovsRowStatus RowStatus
       }

   a200QovsId OBJECT-TYPE
   SYNTAX    INTEGER(1..5)
   MAX-ACCESS  not-accessible
   STATUS    current
   DESCRIPTION  ""
  ::={a200QovsEntry 1}

   a200QovsLoss OBJECT-TYPE
   SYNTAX    INTEGER(1..100)
   MAX-ACCESS  read-create
   STATUS    current
   DESCRIPTION  ""
  ::={a200QovsEntry 2}

   a200QovsDelay OBJECT-TYPE
   SYNTAX    INTEGER(1..1000)
   MAX-ACCESS  read-create
   STATUS    current
   DESCRIPTION  ""
  ::={a200QovsEntry 3}

   a200QovsJitter OBJECT-TYPE
   SYNTAX    INTEGER(1..1000)
   MAX-ACCESS  read-create
   STATUS    current
   DESCRIPTION  ""
  ::={a200QovsEntry 4}

   a200QovsRowStatus OBJECT-TYPE
   SYNTAX    RowStatus
   MAX-ACCESS  read-create
   STATUS    current
   DESCRIPTION  ""
  ::={a200QovsEntry 5}

--end of Qovs table

--miscellaneous table begin
    a200MiscTable OBJECT-TYPE
    SYNTAX        SEQUENCE OF A200MiscEntry
    MAX-ACCESS    not-accessible
    STATUS        current
    DESCRIPTION   ""
    ::={msagGlobalConfig 7}

    a200MiscEntry OBJECT-TYPE
    SYNTAX       A200MiscEntry
    MAX-ACCESS   not-accessible
    STATUS       current
    DESCRIPTION  ""
    INDEX {a200MiscIndex}
    ::={a200MiscTable 1}

    A200MiscEntry ::=
       SEQUENCE{
          a200MiscIndex              INTEGER,
          a200MiscFlashDelay         INTEGER,
          a200MiscCalledPartyReanwer INTEGER,
          a200MiscH248BusyStatus     INTEGER,
          a200MiscHowlTone           INTEGER,
          a200MiscH248Short          INTEGER,
          a200MiscH248Long           INTEGER,
          a200MiscRTPtimer           INTEGER,
          a200MiscH248RingPattern    INTEGER,
          a200MiscCallAlarm          INTEGER,
          a200MiscInterCallAlarm     INTEGER,
          a200MiscFreshTnet          INTEGER,
          a200MiscCheckContext       INTEGER,
          a200MiscUpPort             INTEGER,
          a200MiscResReportPeriod    INTEGER,
          a200MiscAgMustDetOvrLd     INTEGER,
          a200MiscErrReplyInformSSEn INTEGER,
          a200MiscCookieEchoFormat   INTEGER,
          a200MiscCheckSumFormat     INTEGER,
          a200MiscIuaIsdnHwFormat    INTEGER
      }

    a200MiscIndex  OBJECT-TYPE
    SYNTAX    INTEGER(1)
    MAX-ACCESS  not-accessible
    STATUS    current
    DESCRIPTION  ""
    ::={a200MiscEntry 1}

    a200MiscFlashDelay  OBJECT-TYPE
    SYNTAX    INTEGER(10..50)
    MAX-ACCESS  read-write
    STATUS    current
    DESCRIPTION  ""
    ::={a200MiscEntry 2}

    a200MiscCalledPartyReanwer  OBJECT-TYPE
    SYNTAX    INTEGER(10..600)
    MAX-ACCESS  read-write
    STATUS    current
    DESCRIPTION  ""
    ::={a200MiscEntry 3}

    a200MiscH248BusyStatus  OBJECT-TYPE
    SYNTAX    INTEGER(10..1000)
    MAX-ACCESS  read-write
    STATUS    current
    DESCRIPTION  ""
    ::={a200MiscEntry 4}

    a200MiscHowlTone  OBJECT-TYPE
    SYNTAX    INTEGER(10..1000)
    MAX-ACCESS  read-write
    STATUS    current
    DESCRIPTION  ""
    ::={a200MiscEntry 5}

    a200MiscH248Short  OBJECT-TYPE
    SYNTAX    INTEGER(10..50)
    MAX-ACCESS  read-write
    STATUS    current
    DESCRIPTION  ""
    ::={a200MiscEntry 6}

    a200MiscH248Long  OBJECT-TYPE
    SYNTAX    INTEGER(10..100)
    MAX-ACCESS  read-write
    STATUS    current
    DESCRIPTION  ""
    ::={a200MiscEntry 7}

    a200MiscRTPtimer  OBJECT-TYPE
    SYNTAX    INTEGER(10..50)
    MAX-ACCESS  read-write
    STATUS    current
    DESCRIPTION  ""
    ::={a200MiscEntry 8}

    a200MiscH248RingPattern  OBJECT-TYPE
    SYNTAX       INTEGER{ms(1),tenms(2),hundredms(3)}
    MAX-ACCESS   read-write
    STATUS       current
    DESCRIPTION  ""
    ::={a200MiscEntry 9}

    a200MiscCallAlarm  OBJECT-TYPE
    SYNTAX       INTEGER(10..500)
    MAX-ACCESS   read-write
    STATUS       current
    DESCRIPTION  ""
    ::={a200MiscEntry 10}

    a200MiscInterCallAlarm  OBJECT-TYPE
    SYNTAX       INTEGER(10..300)
    MAX-ACCESS   read-write
    STATUS       current
    DESCRIPTION  ""
    ::={a200MiscEntry 11}

    a200MiscFreshTnet  OBJECT-TYPE
    SYNTAX       INTEGER(10..600)
    MAX-ACCESS   read-write
    STATUS       current
    DESCRIPTION  ""
    ::={a200MiscEntry 12}

    a200MiscCheckContext  OBJECT-TYPE
    SYNTAX       INTEGER{disable(0),enable(1)}
    MAX-ACCESS   read-write
    STATUS       current
    DESCRIPTION  ""
    ::={a200MiscEntry 13}

    a200MiscUpPort  OBJECT-TYPE
    SYNTAX       INTEGER{withTimeStamp(0),noTimeStamp(1)}
    MAX-ACCESS   read-write
    STATUS       current
    DESCRIPTION  ""
    ::={a200MiscEntry 14}

    a200MiscResReportPeriod  OBJECT-TYPE
    SYNTAX       INTEGER(0..65535)
    MAX-ACCESS   read-write
    STATUS       current
    DESCRIPTION  ""
    ::={a200MiscEntry 15}

    a200MiscAgMustDetOvrLd  OBJECT-TYPE
    SYNTAX       INTEGER{disable(0),enable(1)}
    MAX-ACCESS   read-write
    STATUS       current
    DESCRIPTION  ""
    ::={a200MiscEntry 16}

    a200MiscErrReplyInformSSEn  OBJECT-TYPE
    SYNTAX       INTEGER{disable(0),enable(1)}
    MAX-ACCESS   read-write
    STATUS       current
    DESCRIPTION  ""
    ::={a200MiscEntry 17}

    a200MiscCookieEchoFormat  OBJECT-TYPE
    SYNTAX       INTEGER{formZTE(0),formStandard(1)}
    MAX-ACCESS   read-write
    STATUS       current
    DESCRIPTION  ""
    ::={a200MiscEntry 18}

    a200MiscCheckSumFormat  OBJECT-TYPE
    SYNTAX       INTEGER{formADLER32(0),formCRC32(1)}
    MAX-ACCESS   read-write
    STATUS       current
    DESCRIPTION  ""
    ::={a200MiscEntry 19}

    a200MiscIuaIsdnHwFormat  OBJECT-TYPE
    SYNTAX    INTEGER{formDisable(0),formEnable(1)}
    MAX-ACCESS  read-write
    STATUS    current
    DESCRIPTION  ""
    ::={a200MiscEntry 20}
-- end of miscellaneous Table

-------------------------------------------------------------------------------
-- a200DigitMapTable
-------------------------------------------------------------------------------   
      
    a200DigitMapTable OBJECT-TYPE
        SYNTAX    SEQUENCE OF A200DigitMapEntry
        MAX-ACCESS  not-accessible
        STATUS    current
        DESCRIPTION  ""
        ::={msagGlobalConfig 8}

    a200DigitMapEntry OBJECT-TYPE
        SYNTAX      A200DigitMapEntry
        MAX-ACCESS  not-accessible
        STATUS      current
        DESCRIPTION ""
        INDEX { a200DigitMapDas }
        ::= { a200DigitMapTable 1 }

    A200DigitMapEntry ::= SEQUENCE {
        a200DigitMapDas                 INTEGER,
        a200DigitMapMgid                INTEGER,
        a200DigitMapSrvType             INTEGER,
        a200DigitMapDgtName             DisplayString,
        a200DigitMapDgtMap              DisplayString,
        a200DigitMapRowStatus           RowStatus
    }

    a200DigitMapDas  OBJECT-TYPE
        SYNTAX      INTEGER(1..255)
        MAX-ACCESS  not-accessible
        STATUS      current
        DESCRIPTION ""
        ::= { a200DigitMapEntry 1 }

    a200DigitMapMgid  OBJECT-TYPE
        SYNTAX      INTEGER(1)
        MAX-ACCESS  read-create
        STATUS      current
        DESCRIPTION ""
        ::= { a200DigitMapEntry 2 }

    a200DigitMapSrvType  OBJECT-TYPE
        SYNTAX      INTEGER {
            h248(0),
            selfchange(1),
            sip(2),
            urgencymap(3),
            callEscape(4)
            }
        MAX-ACCESS  read-create
        STATUS      current
        DESCRIPTION ""
        ::= { a200DigitMapEntry 3 }

    a200DigitMapDgtName  OBJECT-TYPE
        SYNTAX      DisplayString(SIZE(1..20))
        MAX-ACCESS  read-create
        STATUS      current
        DESCRIPTION ""
        ::= { a200DigitMapEntry 4 }

    a200DigitMapDgtMap  OBJECT-TYPE
        SYNTAX      DisplayString(SIZE(1..250))
        MAX-ACCESS  read-create
        STATUS      current
        DESCRIPTION ""
        ::= { a200DigitMapEntry 5 }

    a200DigitMapRowStatus  OBJECT-TYPE
        SYNTAX      RowStatus
        MAX-ACCESS  read-create
        STATUS      current
        DESCRIPTION ""
        ::= { a200DigitMapEntry 6 }


--voip interface table begin
--  a200VoipInterfaceTable OBJECT-TYPE
--    SYNTAX    SEQUENCE OF A200VoipInterfaceEntry
--    MAX-ACCESS  not-accessible
--    STATUS    current
--    DESCRIPTION  ""
--    ::={msagGlobalConfig 9}
--end of voip interface table

--voip route table begin
  a200VoipRouteTable OBJECT-TYPE
    SYNTAX    SEQUENCE OF A200VoipRouteEntry
    MAX-ACCESS  not-accessible
    STATUS    current
    DESCRIPTION  ""
    ::={msagGlobalConfig 10}

  a200VoipRouteEntry OBJECT-TYPE
    SYNTAX     A200VoipRouteEntry
    MAX-ACCESS  not-accessible
    STATUS     current
    DESCRIPTION  ""
    INDEX{
      a200VoipRouteMgId,
      a200VoipRouteType,
      a200VoipRouteDestIp
    }
    ::={a200VoipRouteTable 1}

  A200VoipRouteEntry ::=
    SEQUENCE{
        a200VoipRouteMgId        INTEGER,
        a200VoipRouteType        INTEGER,
        a200VoipRouteDestIp      IpAddress,
        a200VoipRouteDestMask    IpAddress,
        a200VoipRouteNexthop     IpAddress,
        a200VoipRouteNexthopMac  MacAddress,
        a200VoipRouteArpTime     INTEGER,
        a200VoipRouteRowStatus   RowStatus
    }
    
  a200VoipRouteMgId OBJECT-TYPE
    SYNTAX     INTEGER(1)
    MAX-ACCESS  not-accessible
    STATUS      current
    DESCRIPTION  ""
    ::={a200VoipRouteEntry 1}

  a200VoipRouteType OBJECT-TYPE
    SYNTAX     INTEGER{media(1),ctrl(2)}
    MAX-ACCESS  not-accessible
    STATUS      current
    DESCRIPTION  ""
    ::={a200VoipRouteEntry 2}

  a200VoipRouteDestIp OBJECT-TYPE
    SYNTAX     IpAddress
    MAX-ACCESS  not-accessible
    STATUS     current
    DESCRIPTION  ""
    ::={a200VoipRouteEntry 3}

  a200VoipRouteDestMask OBJECT-TYPE
    SYNTAX     IpAddress
    MAX-ACCESS  read-create
    STATUS     current
    DESCRIPTION  ""
    ::={a200VoipRouteEntry 4}  

  a200VoipRouteNexthop OBJECT-TYPE
    SYNTAX     IpAddress
    MAX-ACCESS  read-create
    STATUS      current
    DESCRIPTION  ""
    ::={a200VoipRouteEntry 5}

  a200VoipRouteNexthopMac OBJECT-TYPE
    SYNTAX     MacAddress
    MAX-ACCESS  read-create
    STATUS     current
    DESCRIPTION  ""
    ::={a200VoipRouteEntry 6}

  a200VoipRouteArpTime OBJECT-TYPE
    SYNTAX    INTEGER(5..720)
    MAX-ACCESS  read-create
    STATUS    current
    DESCRIPTION  ""
    ::={a200VoipRouteEntry 7}

  a200VoipRouteRowStatus OBJECT-TYPE
    SYNTAX     RowStatus
    MAX-ACCESS  read-create
    STATUS     current
    DESCRIPTION  ""
    ::={a200VoipRouteEntry 20}

--end of voip route table

--begin of ctrlport table
    a200CtlPortTable OBJECT-TYPE
        SYNTAX      SEQUENCE OF A200CtlPortEntry
        MAX-ACCESS  not-accessible
        STATUS      current
        DESCRIPTION
            ""
        ::= {msagGlobalConfig 11}

    a200CtlPortEntry OBJECT-TYPE
        SYNTAX      A200CtlPortEntry
        MAX-ACCESS  not-accessible
        STATUS      current
        DESCRIPTION  
            "describe colunms and index in CtlPort table"
        INDEX       { a200CtlPortCtlId }
        ::= {a200CtlPortTable 1}

    A200CtlPortEntry::= SEQUENCE {
        a200CtlPortCtlId     Integer32,
        a200CtlPortInfo      INTEGER,
        a200CtlPortUdpPort   Integer32,
        a200CtlPortRowStatus RowStatus
        }

    a200CtlPortCtlId  OBJECT-TYPE
        SYNTAX       Integer32(2..40)
        MAX-ACCESS   not-accessible
        STATUS       current
        DESCRIPTION  ""
        ::= {a200CtlPortEntry 1}

    a200CtlPortInfo  OBJECT-TYPE
        SYNTAX       INTEGER
            {
                udp(0),
                tcp(1)
            }
        MAX-ACCESS   read-create
        STATUS       current
        DESCRIPTION  ""
        DEFVAL      {udp}
        ::= {a200CtlPortEntry 2}

    a200CtlPortUdpPort  OBJECT-TYPE
        SYNTAX       Integer32(0..65535)
        MAX-ACCESS   read-create
        STATUS       current
        DESCRIPTION  ""
        ::= {a200CtlPortEntry 3}

    a200CtlPortRowStatus  OBJECT-TYPE
        SYNTAX       RowStatus
        MAX-ACCESS   read-create
        STATUS       current
        DESCRIPTION  ""
        ::= {a200CtlPortEntry 4} 
--end of ctrlport table

--call optimize table begin

   callOptimizeTable OBJECT-TYPE
   SYNTAX       SEQUENCE OF CallOptimizeEntry
   MAX-ACCESS   not-accessible
   STATUS       current
   DESCRIPTION  ""
  ::={msagGlobalConfig 13}

   callOptimizeEntry OBJECT-TYPE
   SYNTAX       CallOptimizeEntry
   MAX-ACCESS   not-accessible
   STATUS       current
   DESCRIPTION  ""
   INDEX {calloptIndex}
   ::={callOptimizeTable 1}

   CallOptimizeEntry ::=
      SEQUENCE{
      calloptIndex                     INTEGER,
      calloptOpenMsgAck                INTEGER,
      calloptPlayToneAck               INTEGER,
      calloptSubPriority               INTEGER,
      calloptNumMax                    INTEGER,
      calloptH248MsgAck                INTEGER,
      calloptH248MsgPn                 INTEGER,
      calloptH248Statistic             INTEGER,
      calloptH248HookOffEvent          INTEGER,
      calloptH248HookOnEvent           INTEGER,
      calloptServiceAbnormal           INTEGER,
      calloptMgProtocolErr             INTEGER,
      calloptMgcProtocolErr            INTEGER,
      calloptMgInsideErr               INTEGER,
      calloptHookOffLimiteCycle        INTEGER,
      calloptHookOffLimiteBlock        INTEGER,
      calloptHookOffLimiteUnblock      INTEGER,
      calloptMgcCallWaitTone           INTEGER,
      calloptToneArea                  INTEGER,
      calloptH248LinkBreakTone         INTEGER
   }

    calloptIndex OBJECT-TYPE
        SYNTAX                  INTEGER(1)
        MAX-ACCESS              not-accessible
        STATUS                  current
        DESCRIPTION             ""
        ::={callOptimizeEntry 1}

   calloptOpenMsgAck OBJECT-TYPE
        SYNTAX                  INTEGER{send(1),notsend(2)}
        MAX-ACCESS              read-write
        STATUS                  current
        DESCRIPTION             ""
        ::={callOptimizeEntry 2}

  calloptPlayToneAck OBJECT-TYPE
        SYNTAX                  INTEGER{send(1),notsend(2)}
        MAX-ACCESS              read-write
        STATUS                  current
        DESCRIPTION             ""
        ::={callOptimizeEntry 3}

  calloptSubPriority OBJECT-TYPE
        SYNTAX                  INTEGER{higher(1),nothigher(2)}
        MAX-ACCESS              read-write
        STATUS                  current
        DESCRIPTION             ""
        ::={callOptimizeEntry 4}

  calloptNumMax OBJECT-TYPE
        SYNTAX                  INTEGER(0..16)
        MAX-ACCESS              read-write
        STATUS                  current
        DESCRIPTION             ""
        ::={callOptimizeEntry 5}

  calloptH248MsgAck OBJECT-TYPE
        SYNTAX                  INTEGER{send(1),notsend(2)}
        MAX-ACCESS              read-write
        STATUS                  current
        DESCRIPTION             ""
        ::={callOptimizeEntry 6}

  calloptH248MsgPn OBJECT-TYPE
        SYNTAX                  INTEGER{send(1),notsend(2)}
        MAX-ACCESS              read-write
        STATUS                  current
        DESCRIPTION             ""
        ::={callOptimizeEntry 7}

  calloptH248Statistic OBJECT-TYPE
        SYNTAX                  INTEGER{send(1),notsend(2)}
        MAX-ACCESS              read-write
        STATUS                  current
        DESCRIPTION             ""
        ::={callOptimizeEntry 8}

  calloptH248HookOffEvent OBJECT-TYPE
        SYNTAX                  INTEGER{alwayssend(1),notalways(2)}
        MAX-ACCESS              read-write
        STATUS                  current
        DESCRIPTION             ""
        ::={callOptimizeEntry 9}

  calloptH248HookOnEvent OBJECT-TYPE
        SYNTAX                  INTEGER{alwayssend(1),notalways(2)}
        MAX-ACCESS              read-write
        STATUS                  current
        DESCRIPTION             ""
        ::={callOptimizeEntry 10}

  calloptServiceAbnormal OBJECT-TYPE
        SYNTAX                  INTEGER{alwayssend(1),notalways(2)}
        MAX-ACCESS              read-write
        STATUS                  current
        DESCRIPTION             ""
        ::={callOptimizeEntry 11}

  calloptMgProtocolErr OBJECT-TYPE
        SYNTAX                  INTEGER{alwayssend(1),notalways(2)}
        MAX-ACCESS              read-write
        STATUS                  current
        DESCRIPTION             ""
        ::={callOptimizeEntry 12}

  calloptMgcProtocolErr OBJECT-TYPE
        SYNTAX                  INTEGER{alwayssend(1),notalways(2)}
        MAX-ACCESS              read-write
        STATUS                  current
        DESCRIPTION             ""
        ::={callOptimizeEntry 13}

  calloptMgInsideErr OBJECT-TYPE
        SYNTAX                  INTEGER{alwayssend(1),notalways(2)}
        MAX-ACCESS              read-write
        STATUS                  current
        DESCRIPTION             ""
        ::={callOptimizeEntry 14}

  calloptHookOffLimiteCycle OBJECT-TYPE
        SYNTAX                  INTEGER(30..600)
        MAX-ACCESS              read-write
        STATUS                  current
        DESCRIPTION             ""
        ::={callOptimizeEntry 15}

  calloptHookOffLimiteBlock OBJECT-TYPE
        SYNTAX                  INTEGER(15..600)
        MAX-ACCESS              read-write
        STATUS                  current
        DESCRIPTION             ""
        ::={callOptimizeEntry 16}

   calloptHookOffLimiteUnblock OBJECT-TYPE
        SYNTAX                  INTEGER(12..600)
        MAX-ACCESS              read-write
        STATUS                  current
        DESCRIPTION             ""
        ::={callOptimizeEntry 17}

   calloptMgcCallWaitTone OBJECT-TYPE
        SYNTAX                  INTEGER{breakdown(1),notbreakdown(2)}
        MAX-ACCESS              read-write
        STATUS                  current
        DESCRIPTION             ""
        ::={callOptimizeEntry 18}
        
   calloptToneArea OBJECT-TYPE
        SYNTAX                  INTEGER
        {
            mainland(1), 
            hongkong(2), 
            singapore(3),
            russia(4),
            chile(5),
            dominican(6),
            argentina(7),
            croatia(8),
            turkey(9),
            singapore2(10),
            malaysia(11),
            belgium(12),
            india(13),
            taiwan(14),
            srilanka(15),
            austria(16),
            greece(17),
            nepal(18),
            colombia(19),
            peru(20),
            morocco(21),
            hungary(22)
        }
        MAX-ACCESS              read-write
        STATUS                  current
        DESCRIPTION             "Tone area."
        ::={callOptimizeEntry 19} 

    calloptH248LinkBreakTone OBJECT-TYPE
        SYNTAX      INTEGER {
            busyTone(1),
            informationTone(2)
            }
        MAX-ACCESS  read-write
        STATUS      current
        DESCRIPTION             
           "It defines which tone will be played when H.248 link is broken."
        DEFVAL      { busyTone }
        ::={callOptimizeEntry 20}

--end of call optimize table

-------------------------------------------------------------------------------
---  msagLoadDefaultRingProfile
-------------------------------------------------------------------------------
    msagLoadDefaultRingProfile OBJECT-TYPE
        SYNTAX      INTEGER(1)
        MAX-ACCESS  read-write
        STATUS      current
        DESCRIPTION ""
        ::= { msagGlobalConfig 14 }        
--------------------------------------------------------------------------------

--voip interface table begin
   zxAnVoipInterfaceTable OBJECT-TYPE
    SYNTAX    SEQUENCE OF ZxAnVoipInterfaceEntry
    MAX-ACCESS  not-accessible
    STATUS    current
    DESCRIPTION  ""
    ::={msagGlobalConfig 15}

  zxAnVoipInterfaceEntry OBJECT-TYPE
    SYNTAX     ZxAnVoipInterfaceEntry
    MAX-ACCESS  not-accessible
    STATUS     current
    DESCRIPTION  ""
    INDEX{zxAnMgId}
    ::={zxAnVoipInterfaceTable 1}
    
  ZxAnVoipInterfaceEntry ::=
    SEQUENCE{
       zxAnMgId                    INTEGER,
       zxAnVoipCtrlIpAddr          IpAddress,
       zxAnVoipCtrlIpMask          IpAddress,
       zxAnVoipMediaIpaddr         IpAddress,
       zxAnVoipMediaIpMask         IpAddress,
       zxAnVoipInterfaceRowStatus  RowStatus
    }
    
  zxAnMgId  OBJECT-TYPE
   SYNTAX    INTEGER(1)
   MAX-ACCESS  not-accessible
   STATUS    current
   DESCRIPTION  ""
  ::={zxAnVoipInterfaceEntry 1}
    
  zxAnVoipCtrlIpAddr OBJECT-TYPE
    SYNTAX    IpAddress
    MAX-ACCESS  read-create
    STATUS    current
    DESCRIPTION  ""
    ::={zxAnVoipInterfaceEntry 2}
    
  zxAnVoipCtrlIpMask OBJECT-TYPE
    SYNTAX    IpAddress
    MAX-ACCESS  read-create
    STATUS    current
    DESCRIPTION  ""
    ::={zxAnVoipInterfaceEntry 3}
  
  zxAnVoipMediaIpaddr OBJECT-TYPE
    SYNTAX    IpAddress
    MAX-ACCESS  read-create
    STATUS    current
    DESCRIPTION  ""
    ::={zxAnVoipInterfaceEntry 4}
  
  zxAnVoipMediaIpMask OBJECT-TYPE
    SYNTAX    IpAddress
    MAX-ACCESS  read-create
    STATUS    current
    DESCRIPTION  ""
    ::={zxAnVoipInterfaceEntry 5}
  
  zxAnVoipInterfaceRowStatus  OBJECT-TYPE
   SYNTAX    RowStatus
   MAX-ACCESS  read-create
   STATUS    current
   DESCRIPTION  ""
  ::={zxAnVoipInterfaceEntry 20}

--end of voip interface table

    zxAnVoipBaseGlobalObjects OBJECT IDENTIFIER ::= { msagGlobalConfig 17 }

    zxAnVoipBaseCapabilities OBJECT-TYPE
        SYNTAX     BITS {
            externalSelfswitch(0),
            slcFeedCurrent(1),
            slcHighImpedance(2),
            callerTestMode(3),
            callEscapeMode(4)            
        }
        MAX-ACCESS  read-only
        STATUS      current
        DESCRIPTION
            "The VOIP base management capabilities of this equipment.
            The bit value 1 means the function represented by this bit is 
            supported by this equipment.  

            externalSelfswitch(0): support a200ExternalSelfswitch.
            slcFeedCurrent(1): support a200slcFeedCurrent.
            slcHighImpedance(2): support a200slcHighImpedanceOper and 
                a200slcNoneHighImpedanceOper.
            callerTestMode(3): support call test mode for voip caller test.
            callEscapeMode(4): support a200MgCallEscapeMode.

            NOTE: No recomanded to display it in NMS."
        ::= { zxAnVoipBaseGlobalObjects 1 } 

    zxAnSelfswitchTktObjects OBJECT IDENTIFIER ::= {zxAnVoipBaseGlobalObjects 2} 

    zxAnSelfswitchTktEnable   OBJECT-TYPE 
        SYNTAX          INTEGER{enable(1),disable(2)}
        MAX-ACCESS      read-write
        STATUS          current
        DESCRIPTION     "The Selfswitch ticket enable status."
        DEFVAL          {disable}
        ::= { zxAnSelfswitchTktObjects 1 }

    zxAnSelfswitchTktUploadInterval   OBJECT-TYPE 
        SYNTAX          Integer32(1..44640)
        UNITS           "minute"
        MAX-ACCESS      read-write
        STATUS          current
        DESCRIPTION     "Interval of uploading selfswitch ticket files to FTP
            server. "
        DEFVAL          {1440}
        ::= { zxAnSelfswitchTktObjects 2 }

    zxAnSelfswitchTktSizeThreshold   OBJECT-TYPE 
        SYNTAX          Integer32(1..100) 
        UNITS           "percent"
        MAX-ACCESS      read-write
        STATUS          current
        DESCRIPTION     "Flash size threshold of selfswitch ticket. If the 
             threshold is reached, NE will upload ticket files to FTP server."
        DEFVAL          {80}
        ::= { zxAnSelfswitchTktObjects 3 }
    

-- zxAnSelfswitchTktFtpTable begin

    zxAnSelfswitchTktFtpTable OBJECT-TYPE
        SYNTAX  SEQUENCE OF ZxAnSelfswitchTktFtpEntry
        MAX-ACCESS  not-accessible
        STATUS  current
        DESCRIPTION  "The selfswitch ticket FTP configuration table."
    ::={msagGlobalConfig 18}

    zxAnSelfswitchTktFtpEntry OBJECT-TYPE
        SYNTAX  ZxAnSelfswitchTktFtpEntry
        MAX-ACCESS  not-accessible
        STATUS  current
        DESCRIPTION  
            "An entry in the selfswitch ticket FTP configuration table."
        INDEX { zxAnSelfswitchTktFtpServerId }
    ::={zxAnSelfswitchTktFtpTable 1}

    ZxAnSelfswitchTktFtpEntry::=
        SEQUENCE{
            zxAnSelfswitchTktFtpServerId      Integer32,
            zxAnSelfswitchTktFtpServerIpType  InetAddressType,
            zxAnSelfswitchTktFtpServerIp      InetAddress,
            zxAnSelfswitchTktFtpUserName      DisplayString,
            zxAnSelfswitchTktFtpUserPwd       DisplayString,
            zxAnSelfswitchTktFtpServerPath    DisplayString,
            zxAnSelfswitchTktFtpRowStatus     RowStatus
        }

    zxAnSelfswitchTktFtpServerId  OBJECT-TYPE
        SYNTAX  Integer32(1)
        MAX-ACCESS  not-accessible
        STATUS  current
        DESCRIPTION  "FTP server id."
        ::={zxAnSelfswitchTktFtpEntry 1}

    zxAnSelfswitchTktFtpServerIpType  OBJECT-TYPE 
        SYNTAX          InetAddressType
        MAX-ACCESS      read-create
        STATUS          current
        DESCRIPTION     "The IP address type of the FTP server used for 
            uploading selfswitch ticket files."
        ::= { zxAnSelfswitchTktFtpEntry 2 }

    zxAnSelfswitchTktFtpServerIp  OBJECT-TYPE 
        SYNTAX          InetAddress
        MAX-ACCESS      read-create
        STATUS          current
        DESCRIPTION     "The IP address of the FTP server used for uploading
            selfswtich ticket files."
        ::= { zxAnSelfswitchTktFtpEntry 3 }

    zxAnSelfswitchTktFtpUserName   OBJECT-TYPE 
        SYNTAX          DisplayString(SIZE(1 .. 32)) 
        MAX-ACCESS      read-create
        STATUS          current
        DESCRIPTION     "The FTP username."
        ::= { zxAnSelfswitchTktFtpEntry 4 }

    zxAnSelfswitchTktFtpUserPwd    OBJECT-TYPE 
        SYNTAX          DisplayString(SIZE(1 .. 32)) 
        MAX-ACCESS      read-create
        STATUS          current
        DESCRIPTION     "The FTP user password."
        ::= { zxAnSelfswitchTktFtpEntry 5 }

    zxAnSelfswitchTktFtpServerPath   OBJECT-TYPE 
        SYNTAX          DisplayString(SIZE(0 .. 64)) 
        MAX-ACCESS      read-create
        STATUS          current
        DESCRIPTION     "The FTP server path, start from the root directory."
        ::= { zxAnSelfswitchTktFtpEntry 6 }

    zxAnSelfswitchTktFtpRowStatus  OBJECT-TYPE
        SYNTAX          RowStatus
        MAX-ACCESS      read-create
        STATUS          current
        DESCRIPTION     "This object indicates the status of this entry."
        ::={ zxAnSelfswitchTktFtpEntry 20}

-- end of zxAnSelfswitchTktFtpTable

-- zxAnDsx1ProtectionGroupTable begin

    zxAnDsx1ProtectionGroupTable OBJECT-TYPE
        SYNTAX  SEQUENCE OF ZxAnDsx1ProtectionGroupEntry
        MAX-ACCESS  not-accessible
        STATUS  current
        DESCRIPTION  "The E1/T1 protection group table."
    ::={msagGlobalConfig 19}

    zxAnDsx1ProtectionGroupEntry OBJECT-TYPE
        SYNTAX  ZxAnDsx1ProtectionGroupEntry
        MAX-ACCESS  not-accessible
        STATUS  current
        DESCRIPTION  "An entry of the E1/T1 protection group table."
        INDEX { zxAnDsx1ProtectionGroupId }
    ::={zxAnDsx1ProtectionGroupTable 1}

    ZxAnDsx1ProtectionGroupEntry::=
        SEQUENCE{
            zxAnDsx1ProtectionGroupId            Integer32, 
            zxAnDsx1ProtectionGroupName          DisplayString,
            zxAnDsx1MasterDsx1Rack               Integer32,
            zxAnDsx1MasterDsx1Shelf              Integer32,
            zxAnDsx1MasterDsx1Slot               Integer32,
            zxAnDsx1MasterDsx1LinkNo             Integer32,
            zxAnDsx1StandbyDsx1Rack              Integer32,
            zxAnDsx1StandbyDsx1Shelf             Integer32,
            zxAnDsx1StandbyDsx1Slot              Integer32,
            zxAnDsx1StandbyDsx1LinkNo            Integer32,
            zxAnDsx1CurrWorkingDsx1              INTEGER,
            zxAnDsx1ProtectionGroupRowStatus     RowStatus 
        }
    
    zxAnDsx1ProtectionGroupId  OBJECT-TYPE
        SYNTAX       Integer32(1..48)
        MAX-ACCESS   not-accessible
        STATUS       current
        DESCRIPTION  "E1/T1 protection group ID."
        ::={zxAnDsx1ProtectionGroupEntry 1}

    zxAnDsx1ProtectionGroupName  OBJECT-TYPE
        SYNTAX       DisplayString(SIZE(0..32))
        MAX-ACCESS   read-create
        STATUS       current
        DESCRIPTION  "E1/T1 protection group name."
        ::={zxAnDsx1ProtectionGroupEntry 2}

    zxAnDsx1MasterDsx1Rack  OBJECT-TYPE
        SYNTAX       Integer32
        MAX-ACCESS   read-create
        STATUS       current
        DESCRIPTION  "Rack of the master E1/T1 in the group."
        ::={zxAnDsx1ProtectionGroupEntry 3}

    zxAnDsx1MasterDsx1Shelf  OBJECT-TYPE
        SYNTAX       Integer32
        MAX-ACCESS   read-create
        STATUS       current
        DESCRIPTION  "Shelf of the master E1/T1 in the group."
        ::={zxAnDsx1ProtectionGroupEntry 4}

    zxAnDsx1MasterDsx1Slot  OBJECT-TYPE
        SYNTAX       Integer32
        MAX-ACCESS   read-create
        STATUS       current
        DESCRIPTION  "Slot of the master E1/T1 in the group."
        ::={zxAnDsx1ProtectionGroupEntry 5}

    zxAnDsx1MasterDsx1LinkNo  OBJECT-TYPE
        SYNTAX       Integer32
        MAX-ACCESS   read-create
        STATUS       current
        DESCRIPTION  "Link number of the master E1/T1 in the group."
        ::={zxAnDsx1ProtectionGroupEntry 6}

    zxAnDsx1StandbyDsx1Rack  OBJECT-TYPE
        SYNTAX       Integer32
        MAX-ACCESS   read-create
        STATUS       current
        DESCRIPTION  "Rack of the standby E1/T1 in the group."
        ::={zxAnDsx1ProtectionGroupEntry 7}

    zxAnDsx1StandbyDsx1Shelf  OBJECT-TYPE
        SYNTAX       Integer32
        MAX-ACCESS   read-create
        STATUS       current
        DESCRIPTION  "Shelf of the standby E1/T1 in the group."
        ::={zxAnDsx1ProtectionGroupEntry 8}

    zxAnDsx1StandbyDsx1Slot  OBJECT-TYPE
        SYNTAX       Integer32
        MAX-ACCESS   read-create
        STATUS       current
        DESCRIPTION  "Slot of the standby E1/T1 in the group."
        ::={zxAnDsx1ProtectionGroupEntry 9}

    zxAnDsx1StandbyDsx1LinkNo  OBJECT-TYPE
        SYNTAX       Integer32
        MAX-ACCESS   read-create
        STATUS       current
        DESCRIPTION  "Link number of the standby E1/T1 in the group."
        ::={zxAnDsx1ProtectionGroupEntry 10}

    zxAnDsx1CurrWorkingDsx1  OBJECT-TYPE
        SYNTAX       INTEGER
            {
                 none(1),
                 master(2),
                 standby(3)
            }
        MAX-ACCESS   read-only
        STATUS       current
        DESCRIPTION  "Current working E1/T1 in the group."
        ::={zxAnDsx1ProtectionGroupEntry 11}

    zxAnDsx1ProtectionGroupRowStatus OBJECT-TYPE
        SYNTAX       RowStatus
        MAX-ACCESS   read-create
        STATUS       current
        DESCRIPTION
            "This object indicates the status of this entry."
        ::={zxAnDsx1ProtectionGroupEntry 20}

-- end of zxAnDsx1ProtectionGroupTable

-- zxAnHwTimeSlotUsageTable begin

    zxAnHwTimeSlotUsageObjects OBJECT IDENTIFIER 
        ::= {msagGlobalConfig 20}
        
    zxAnHwTimeSlotUsageGlobalObjects OBJECT IDENTIFIER 
        ::= {zxAnHwTimeSlotUsageObjects 1}
    
    zxAnHwTimeSlotUsageThreshold  OBJECT-TYPE
        SYNTAX      Integer32(0..100)
        UNITS       "percent"        
        MAX-ACCESS  read-write
        STATUS      current
        DESCRIPTION
            "The threshold of HW time slot usage 
            between master shelf and slave shelf."
        ::= { zxAnHwTimeSlotUsageGlobalObjects 1 }     

    zxAnHwTimeSlotUsageTable OBJECT-TYPE
        SYNTAX      SEQUENCE OF ZxAnHwTimeSlotUsageEntry
        MAX-ACCESS  not-accessible
        STATUS      current
        DESCRIPTION
            "HW time slot usage table."
        ::= { zxAnHwTimeSlotUsageObjects 2 }

    zxAnHwTimeSlotUsageEntry OBJECT-TYPE
        SYNTAX      ZxAnHwTimeSlotUsageEntry
        MAX-ACCESS  not-accessible
        STATUS      current
        DESCRIPTION
            "HW time slot usage entry."
        INDEX { zxAnHwTimeSlotUsageRack, 
                zxAnHwTimeSlotUsageShelf }
        ::= { zxAnHwTimeSlotUsageTable 1 } 

    ZxAnHwTimeSlotUsageEntry ::= SEQUENCE {
        zxAnHwTimeSlotUsageRack         Integer32,
        zxAnHwTimeSlotUsageShelf        Integer32,
        zxAnHwTimeSlotUsage             Integer32
        }

    zxAnHwTimeSlotUsageRack  OBJECT-TYPE
        SYNTAX      Integer32
        MAX-ACCESS  not-accessible
        STATUS      current
        DESCRIPTION
            "Rack of slave shelf."
        ::= { zxAnHwTimeSlotUsageEntry 1 } 
        
    zxAnHwTimeSlotUsageShelf  OBJECT-TYPE
        SYNTAX      Integer32
        MAX-ACCESS  not-accessible
        STATUS      current
        DESCRIPTION
            "Shelf of slave shelf."
        ::= { zxAnHwTimeSlotUsageEntry 2 } 
        
    zxAnHwTimeSlotUsage  OBJECT-TYPE
        SYNTAX      Integer32(0..100)
        UNITS       "percent" 
        MAX-ACCESS  read-only
        STATUS      current
        DESCRIPTION
            "The usage of HW time slot 
            between master shelf and slave shelf."
        ::= { zxAnHwTimeSlotUsageEntry 3 }
        
-- end of zxAnHwTimeSlotUsageTable                 

------------------------------------------------------------------------------
-- Self Switch Telephone Number Load Management
------------------------------------------------------------------------------
    zxAnSelfswitchTelLoadObjects    OBJECT IDENTIFIER   
        ::=  {  zxAnVoipBaseGlobalObjects  3  }
      
    zxAnSelfswitchTelLoadFileName       OBJECT-TYPE 
        SYNTAX          DisplayString(SIZE(1..32))
        MAX-ACCESS      read-write
        STATUS          current
        DESCRIPTION     
            "The file name of telephone number file.
             Start to load telephone number file from local 
             when zxAnSelfswitchTelLoadFileName is set."
        ::=  {  zxAnSelfswitchTelLoadObjects  1  }            
   
    zxAnSelfswitchTelLoadStatus       OBJECT-TYPE 
        SYNTAX          INTEGER  {
            notStarted(1),
            inProgress(2),
            success(3),
            failed(4)               
        }       
        MAX-ACCESS      read-only
        STATUS          current
        DESCRIPTION     
            "The status of Loading telephone number."
        ::=  {  zxAnSelfswitchTelLoadObjects  2  }           
 
    zxAnSelfswitchTelLoadFailReason       OBJECT-TYPE     
        SYNTAX          INTEGER  {
            noError(1),
            badFile(2),
            noTelOfSelfNe(3),                
            otherErrors(255)            
        }         
        MAX-ACCESS      read-only
        STATUS          current
        DESCRIPTION     
            "The failed reason of Loading telephone number."
        ::=  {  zxAnSelfswitchTelLoadObjects  3  }         
    
    zxAnVoicePortLockoutTrapEnable       OBJECT-TYPE     
        SYNTAX          INTEGER  {
            enabled(1),
            disabled(2)           
        }         
        MAX-ACCESS      read-write
        STATUS          current
        DESCRIPTION     
            "Enables or disables voice port lockout trap."
        DEFVAL { disabled }   
        ::=  {  zxAnVoipBaseGlobalObjects  4  }        
------------------------------------------------------------
   msagResource OBJECT IDENTIFIER ::= { msagmajorVersion 3 }

--SlcTerminationID table begin
   a200SlcTermIDTable OBJECT-TYPE
   SYNTAX    SEQUENCE OF A200SlcTermIDEntry
   MAX-ACCESS  not-accessible
   STATUS    current
   DESCRIPTION  ""
  ::={msagResource 6}

   a200SlcTermIDEntry OBJECT-TYPE
   SYNTAX    A200SlcTermIDEntry
   MAX-ACCESS  not-accessible
   STATUS    current
   DESCRIPTION  "describe colunms and index in TerminationIDOperation table"
   INDEX { a200slcTermIDrackno,a200slcTermIDshelfno,
          a200slcTermIDslotno,a200slcTermIDBeginIndex}
  ::={a200SlcTermIDTable 1}

   A200SlcTermIDEntry::=
     SEQUENCE{
        a200slcTermIDrackno       Integer32,
        a200slcTermIDshelfno      Integer32,
        a200slcTermIDslotno       Integer32,
        a200slcTermIDBeginIndex   INTEGER,
        a200slcTermIDOperSum      INTEGER,
        a200slcTermIDTMID         OCTET STRING,
        a200slcTermIDType         INTEGER,
        a200slcTermIDBeginNo      Integer32,
        a200slcTermIDDigitLen     INTEGER,
        a200slcTermIDMgId         INTEGER,
        a200slcTerminationID      INTEGER,
        a200slcTermIDRowStatus    RowStatus
  }

   a200slcTermIDrackno  OBJECT-TYPE
   SYNTAX    Integer32
   MAX-ACCESS  not-accessible
   STATUS    current
   DESCRIPTION  ""
  ::={a200SlcTermIDEntry 1}

   a200slcTermIDshelfno OBJECT-TYPE
   SYNTAX    Integer32
   MAX-ACCESS  not-accessible
   STATUS    current
   DESCRIPTION  ""
  ::={a200SlcTermIDEntry 2}

   a200slcTermIDslotno   OBJECT-TYPE
   SYNTAX    Integer32
   MAX-ACCESS  not-accessible
   STATUS    current
   DESCRIPTION  ""
  ::={a200SlcTermIDEntry 3}

   a200slcTermIDBeginIndex   OBJECT-TYPE
   SYNTAX    INTEGER(0..31)
   MAX-ACCESS  not-accessible
   STATUS    current
   DESCRIPTION  ""
  ::={a200SlcTermIDEntry 4}

   a200slcTermIDOperSum       OBJECT-TYPE
   SYNTAX    INTEGER(1..192)
   MAX-ACCESS  read-create
   STATUS    current
   DESCRIPTION  ""
  ::={a200SlcTermIDEntry 5}

   a200slcTermIDTMID  OBJECT-TYPE
   SYNTAX    OCTET STRING (SIZE(0 .. 63))
   MAX-ACCESS  read-create
   STATUS    current
   DESCRIPTION  ""
  ::={a200SlcTermIDEntry 6}

   a200slcTermIDType  OBJECT-TYPE
   SYNTAX       INTEGER{type1(1),type2(2),type3(3)}
   MAX-ACCESS   read-create
   STATUS       current
   DESCRIPTION  "   Type 1:USER00100100000-USER00100100031,
   type 2:USER0-USER31
   type 3:User000-USER031"
  ::={a200SlcTermIDEntry 7}

   a200slcTermIDBeginNo  OBJECT-TYPE
   SYNTAX    Integer32
   MAX-ACCESS  read-create
   STATUS    current
   DESCRIPTION  "Use for type 2 and 3"
  ::={a200SlcTermIDEntry 8}

   a200slcTermIDDigitLen    OBJECT-TYPE
   SYNTAX    INTEGER(2..64)
   MAX-ACCESS  read-create
   STATUS    current
   DESCRIPTION  ""
  ::={a200SlcTermIDEntry 9}

   a200slcTermIDMgId       OBJECT-TYPE
   SYNTAX    INTEGER(1..255)
   MAX-ACCESS  read-create
   STATUS    current
   DESCRIPTION  ""
  ::={a200SlcTermIDEntry 11}

   a200slcTerminationID    OBJECT-TYPE
   SYNTAX        INTEGER(2..64)
   MAX-ACCESS    read-only
   STATUS        current
   DESCRIPTION   ""
  ::={a200SlcTermIDEntry 12}

   a200slcTermIDRowStatus  OBJECT-TYPE
   SYNTAX       RowStatus
   MAX-ACCESS   read-create
   STATUS       current
   DESCRIPTION  "insert,delete"
  ::={a200SlcTermIDEntry 13}

--end of slcTerminationIDOperation table

-------------------------------------------------------------------------------
--a200IpsTermIDTable
-------------------------------------------------------------------------------  
    a200IpsTermIDTable OBJECT-TYPE
        SYNTAX      SEQUENCE OF A200IpsTermIDEntry
        MAX-ACCESS  not-accessible
        STATUS      current
        DESCRIPTION ""
        ::= { msagResource 7 }

    a200IpsTermIDEntry OBJECT-TYPE
        SYNTAX      A200IpsTermIDEntry
        MAX-ACCESS  not-accessible
        STATUS      current
        DESCRIPTION "describe colunms and index in TerminationIDOperation table"
        INDEX { a200IpsTermIDSeqNo }
        ::= {a200IpsTermIDTable 1 }

    A200IpsTermIDEntry ::= SEQUENCE {
        a200IpsTermIDSeqNo        Integer32,
        a200IpsTermIDDeltag       INTEGER,
        a200IpsTermIDBeginSeqNo   INTEGER,
        a200IpsTermIDOperNum      INTEGER,
        a200IpsTermIDTMIDFix      DisplayString,
        a200IpsTermIDType         INTEGER,
        a200IpsTermIDDigitLen     INTEGER,
        a200IpsTermIDBeginNo      Integer32,
        a200IpsTermIDMgId         INTEGER,
        a200IpsTerminationID      DisplayString,
        a200IpsTermIDRowStatus    RowStatus
        }

    a200IpsTermIDSeqNo  OBJECT-TYPE
        SYNTAX      Integer32
        MAX-ACCESS  not-accessible
        STATUS      current
        DESCRIPTION ""
        ::= { a200IpsTermIDEntry 1 }

    a200IpsTermIDDeltag    OBJECT-TYPE
        SYNTAX      INTEGER(1..2)
        MAX-ACCESS  read-create
        STATUS      current
        DESCRIPTION ""
        ::= { a200IpsTermIDEntry 2 }

    a200IpsTermIDBeginSeqNo    OBJECT-TYPE
        SYNTAX      INTEGER(1..720)
        MAX-ACCESS  read-create
        STATUS      current
        DESCRIPTION ""
        ::= { a200IpsTermIDEntry 3 }

    a200IpsTermIDOperNum    OBJECT-TYPE
        SYNTAX      INTEGER(1..720)
        MAX-ACCESS  read-create
        STATUS      current
        DESCRIPTION ""
        ::= { a200IpsTermIDEntry 4 }

    a200IpsTermIDTMIDFix  OBJECT-TYPE
        SYNTAX      DisplayString(SIZE(0 .. 63))
        MAX-ACCESS  read-create
        STATUS      current
        DESCRIPTION ""
        ::= { a200IpsTermIDEntry 5 }

    a200IpsTermIDType  OBJECT-TYPE
        SYNTAX      INTEGER {
            type2(2),
            type3(3)
            }
        MAX-ACCESS  read-create
        STATUS      current
        DESCRIPTION
            "type 2:RTP0-RTP31 type 3:RTP000-RTP031"
        ::= { a200IpsTermIDEntry 6 }

    a200IpsTermIDDigitLen    OBJECT-TYPE
        SYNTAX      INTEGER(2..64)
        MAX-ACCESS  read-create
        STATUS      current
        DESCRIPTION ""
        ::= { a200IpsTermIDEntry 7 }

    a200IpsTermIDBeginNo  OBJECT-TYPE
        SYNTAX      Integer32
        MAX-ACCESS  read-create
        STATUS      current
        DESCRIPTION 
            "Use for type 2 and 3"
        ::= { a200IpsTermIDEntry 8 }

    a200IpsTermIDMgId       OBJECT-TYPE
        SYNTAX      INTEGER(1..255)
        MAX-ACCESS  read-create
        STATUS      current
        DESCRIPTION ""
        ::= { a200IpsTermIDEntry 9 }

    a200IpsTerminationID  OBJECT-TYPE
        SYNTAX      DisplayString(SIZE(0..64))
        MAX-ACCESS  read-only
        STATUS      current
        DESCRIPTION 
            "insert,delete"
        ::= { a200IpsTermIDEntry 10 }

    a200IpsTermIDRowStatus  OBJECT-TYPE
        SYNTAX      RowStatus
        MAX-ACCESS  read-create
        STATUS      current
        DESCRIPTION 
           "insert,delete"
        ::= { a200IpsTermIDEntry 11 }


--rtppar table begin
   a200RtpParTable OBJECT-TYPE
   SYNTAX    SEQUENCE OF A200RtpParEntry
   MAX-ACCESS  not-accessible
   STATUS    current
   DESCRIPTION  ""
  ::={msagResource 8}

   a200RtpParEntry OBJECT-TYPE
   SYNTAX    A200RtpParEntry
   MAX-ACCESS  not-accessible
   STATUS    current
   DESCRIPTION  "describe colunms and index in rtppar table"
   INDEX { a200rtpparparid }
  ::={a200RtpParTable 1}

   A200RtpParEntry::=
     SEQUENCE{
        a200rtpparparid          INTEGER,
        a200rtpparvadval         INTEGER,
        a200rtppardtmfrlmod      INTEGER,
        a200rtpparpcmlaw         INTEGER,
        a200rtpparsiltopcm       INTEGER,
        a200rtppardcfilter       INTEGER,
        a200rtpparpcmtopkggain   INTEGER,
        a200rtpparpkgtopcmgain   INTEGER,
        a200rtpparconceal        INTEGER,
        a200rtpparecmdisabl      INTEGER,
        a200rtpparspeedlim       INTEGER,
        a200rtpparerrrecov       INTEGER,
        a200rtppartcfproc        INTEGER,
        a200rtppart38enable      INTEGER,
        a200rtppardtmfduplex     INTEGER,
        a200rtpparNumBeforeOff   INTEGER,
        a200rtpparIgnoreA        INTEGER,
        a200rtpparToneDuplex     INTEGER,
        a200rtppardecodadapt     INTEGER,
        a200rtpparg723rate       INTEGER,
        a200rtpparpckgendis      INTEGER,
        a200rtppardtmfpyld       INTEGER,
        a200rtppardtmfredpyld    INTEGER,
        a200rtpparfaxdatared     INTEGER,
        a200rtppart30msgred      INTEGER,
        a200rtpparmasecenal      INTEGER,
        a200rtpparhdwecdis       INTEGER,
        a200rtpparhecfrz         INTEGER,
        a200rtpparectxf          INTEGER,
        a200rtpparectxm          INTEGER,
        a200rtpparecrxm          INTEGER,
        a200rtpparheclen         INTEGER,
        a200rtpparlpwmin         INTEGER,
        a200rtpparlpwmax         INTEGER,
        a200rtpparlpwinit        INTEGER,
        a200rtpparlpr            INTEGER,
        a200rtpparfsklevel       INTEGER,
        a200rtpparg711redund     INTEGER,
        a200rtpparmodemmode      INTEGER,
        a200rtpparap             INTEGER,
        a200rtppardeletmode      INTEGER,
        a200rtpparnortptime      INTEGER,
        a200rtpparfaxswtime      INTEGER,
        a200rtppardtmfcidelec    INTEGER  
  }

   a200rtpparparid  OBJECT-TYPE
   SYNTAX    INTEGER(1..254)
   MAX-ACCESS  not-accessible
   STATUS    current
   DESCRIPTION  ""
  ::={a200RtpParEntry 1}
  
   a200rtpparvadval  OBJECT-TYPE
   SYNTAX    INTEGER{disable(0),defaultscheme(1),pt13scheme(2),nosilence(3)}
   MAX-ACCESS  read-write
   STATUS    current
   DESCRIPTION  ""
  ::={a200RtpParEntry 2}
  
   a200rtppardtmfrlmod  OBJECT-TYPE
   SYNTAX    INTEGER{voiceCoding(1),redRfc2833(2),aal2Ietf(4),nredRfc2833(6),notRelay(0)}
   MAX-ACCESS  read-write
   STATUS    current
   DESCRIPTION  ""
  ::={a200RtpParEntry 3}
  
   a200rtpparpcmlaw  OBJECT-TYPE
   SYNTAX    INTEGER{aLaw(0),uLaw(1)}
   MAX-ACCESS  read-write
   STATUS    current
   DESCRIPTION  ""
  ::={a200RtpParEntry 4}
  
   a200rtpparsiltopcm  OBJECT-TYPE
   SYNTAX    INTEGER{comfortNoise(0),silence(1)}
   MAX-ACCESS  read-write
   STATUS    current
   DESCRIPTION  ""
  ::={a200RtpParEntry 5}
  
   a200rtppardcfilter  OBJECT-TYPE
   SYNTAX    INTEGER{enable(0),disable(1)}
   MAX-ACCESS  read-write
   STATUS    current
   DESCRIPTION  ""
  ::={a200RtpParEntry 6}
  
   a200rtpparpcmtopkggain  OBJECT-TYPE
   SYNTAX    INTEGER(0..200)
   MAX-ACCESS  read-write
   STATUS    current
   DESCRIPTION  ""
  ::={a200RtpParEntry 7}
  
   a200rtpparpkgtopcmgain  OBJECT-TYPE
   SYNTAX    INTEGER(0..200)
   MAX-ACCESS  read-write
   STATUS    current
   DESCRIPTION  ""
  ::={a200RtpParEntry 8}
  
   a200rtpparconceal  OBJECT-TYPE
   SYNTAX    INTEGER{notReplace(0),whiteLine(1),lastLine(2)}
   MAX-ACCESS  read-write
   STATUS    current
   DESCRIPTION  ""
  ::={a200RtpParEntry 9}
  
   a200rtpparecmdisabl  OBJECT-TYPE
   SYNTAX    INTEGER{enable(0),disable(1)}
   MAX-ACCESS  read-write
   STATUS    current
   DESCRIPTION  ""
  ::={a200RtpParEntry 10}
  
   a200rtpparspeedlim  OBJECT-TYPE
   SYNTAX    INTEGER{noLimit(0),is2400bps(1),is4800bps(2),is7200bps(3),is9600bps(4),is12000bps(5),is14400bps(6)}
   MAX-ACCESS  read-write
   STATUS    current
   DESCRIPTION  ""
  ::={a200RtpParEntry 11}
  
   a200rtpparerrrecov  OBJECT-TYPE
   SYNTAX    INTEGER{redundancy(0),fec(1)}
   MAX-ACCESS  read-write
   STATUS    current
   DESCRIPTION  ""
  ::={a200RtpParEntry 12}
  
   a200rtppartcfproc  OBJECT-TYPE
   SYNTAX    INTEGER{procedure2(0),procedure1(1)}
   MAX-ACCESS  read-write
   STATUS    current
   DESCRIPTION  ""
  ::={a200RtpParEntry 13}
  
   a200rtppart38enable  OBJECT-TYPE
   SYNTAX    INTEGER{t30(0),t38(1),rtp(2),halfControl(10),fullControl(11)}
   MAX-ACCESS  read-write
   STATUS    current
   DESCRIPTION  ""
  ::={a200RtpParEntry 14}
  
   a200rtppardtmfduplex  OBJECT-TYPE
   SYNTAX    INTEGER(0..1)
   MAX-ACCESS  read-write
   STATUS    current
   DESCRIPTION  ""
  ::={a200RtpParEntry 15}
  
   a200rtpparNumBeforeOff  OBJECT-TYPE
   SYNTAX    INTEGER(0..7)
   MAX-ACCESS  read-write
   STATUS    current
   DESCRIPTION  ""
  ::={a200RtpParEntry 16}
  
   a200rtpparIgnoreA  OBJECT-TYPE
   SYNTAX    INTEGER(0..1)
   MAX-ACCESS  read-write
   STATUS    current
   DESCRIPTION  ""
  ::={a200RtpParEntry 17}
  
   a200rtpparToneDuplex  OBJECT-TYPE
   SYNTAX    INTEGER(0..1)
   MAX-ACCESS  read-write
   STATUS    current
   DESCRIPTION  ""
  ::={a200RtpParEntry 18}
  
   a200rtppardecodadapt  OBJECT-TYPE
   SYNTAX    INTEGER(0..1)
   MAX-ACCESS  read-write
   STATUS    current
   DESCRIPTION  ""
  ::={a200RtpParEntry 19}
  
   a200rtpparg723rate  OBJECT-TYPE
   SYNTAX    INTEGER{lowRate(0),highRate(1)}
   MAX-ACCESS  read-write
   STATUS    current
   DESCRIPTION  ""
  ::={a200RtpParEntry 20}
  
   a200rtpparpckgendis  OBJECT-TYPE
   SYNTAX    INTEGER{enable(0),disable(1)}
   MAX-ACCESS  read-write
   STATUS    current
   DESCRIPTION  ""
  ::={a200RtpParEntry 21}
  
   a200rtppardtmfpyld  OBJECT-TYPE
   SYNTAX    INTEGER(0..255)
   MAX-ACCESS  read-write
   STATUS    current
   DESCRIPTION  ""
  ::={a200RtpParEntry 22}
  
   a200rtppardtmfredpyld  OBJECT-TYPE
   SYNTAX    INTEGER(0..255)
   MAX-ACCESS  read-write
   STATUS    current
   DESCRIPTION  ""
  ::={a200RtpParEntry 23}
  
   a200rtpparfaxdatared  OBJECT-TYPE
   SYNTAX    INTEGER(0..200)
   MAX-ACCESS  read-write
   STATUS    current
   DESCRIPTION  ""
  ::={a200RtpParEntry 24}
  
   a200rtppart30msgred  OBJECT-TYPE
   SYNTAX    INTEGER(0..7)
   MAX-ACCESS  read-write
   STATUS    current
   DESCRIPTION  ""
  ::={a200RtpParEntry 25}
  
   a200rtpparmasecenal  OBJECT-TYPE
   SYNTAX    INTEGER{disable(0),enable(1)}
   MAX-ACCESS  read-write
   STATUS    current
   DESCRIPTION  ""
  ::={a200RtpParEntry 26}
  
   a200rtpparhdwecdis  OBJECT-TYPE
   SYNTAX    INTEGER{enable(0),disable(1)}
   MAX-ACCESS  read-write
   STATUS    current
   DESCRIPTION  ""
  ::={a200RtpParEntry 27}
  
   a200rtpparhecfrz  OBJECT-TYPE
   SYNTAX    INTEGER{allowUpdate(0),disableUpdate(1)}
   MAX-ACCESS  read-write
   STATUS    current
   DESCRIPTION  ""
  ::={a200RtpParEntry 28}
  
   a200rtpparectxf  OBJECT-TYPE
   SYNTAX    INTEGER{nonLinear(0),fixedGain(1)}
   MAX-ACCESS  read-write
   STATUS    current
   DESCRIPTION  ""
  ::={a200RtpParEntry 29}
  
   a200rtpparectxm  OBJECT-TYPE
   SYNTAX    INTEGER{normal(0),mute(1)}
   MAX-ACCESS  read-write
   STATUS    current
   DESCRIPTION  ""
  ::={a200RtpParEntry 30}
  
   a200rtpparecrxm  OBJECT-TYPE
   SYNTAX    INTEGER{normal(0),mute(1)}
   MAX-ACCESS  read-write
   STATUS    current
   DESCRIPTION  ""
  ::={a200RtpParEntry 31}
  
   a200rtpparheclen  OBJECT-TYPE
   SYNTAX    INTEGER(0..15)
   MAX-ACCESS  read-write
   STATUS    current
   DESCRIPTION  ""
  ::={a200RtpParEntry 32}
  
   a200rtpparlpwmin  OBJECT-TYPE
   SYNTAX    INTEGER(0..255)
   MAX-ACCESS  read-write
   STATUS    current
   DESCRIPTION  ""
  ::={a200RtpParEntry 33}
  
   a200rtpparlpwmax  OBJECT-TYPE
   SYNTAX    INTEGER(0..255)
   MAX-ACCESS  read-write
   STATUS    current
   DESCRIPTION  ""
  ::={a200RtpParEntry 34}
  
   a200rtpparlpwinit  OBJECT-TYPE
   SYNTAX    INTEGER(0..255)
   MAX-ACCESS  read-write
   STATUS    current
   DESCRIPTION  ""
  ::={a200RtpParEntry 35}
  
   a200rtpparlpr  OBJECT-TYPE
   SYNTAX    INTEGER(0..100)
   MAX-ACCESS  read-write
   STATUS    current
   DESCRIPTION  ""
  ::={a200RtpParEntry 36}
  
   a200rtpparfsklevel  OBJECT-TYPE
   SYNTAX    INTEGER(62..382)
   MAX-ACCESS  read-write
   STATUS    current
   DESCRIPTION  ""
  ::={a200RtpParEntry 37}
  
   a200rtpparg711redund  OBJECT-TYPE
   SYNTAX    INTEGER{noRedundancy(0),is1Package(1),is2Package(2),is3Package(3)}
   MAX-ACCESS  read-write
   STATUS    current
   DESCRIPTION  ""
  ::={a200RtpParEntry 38}
  
   a200rtpparmodemmode  OBJECT-TYPE
   SYNTAX    INTEGER{modemDelay5s(0),transparent(2),modemImmediate(3),faxImmediate(4),cidImmediate(5),ipModem(6),fullCtrl(11)}
   MAX-ACCESS  read-write
   STATUS    current
   DESCRIPTION  ""
  ::={a200RtpParEntry 39}
  
   a200rtpparap  OBJECT-TYPE
   SYNTAX    INTEGER(0..65535)
   MAX-ACCESS  read-write
   STATUS    current
   DESCRIPTION  ""
  ::={a200RtpParEntry 40}
  
   a200rtppardeletmode  OBJECT-TYPE
   SYNTAX    INTEGER(0..1)
   MAX-ACCESS  read-write
   STATUS    current
   DESCRIPTION  ""
  ::={a200RtpParEntry 41}
  
   a200rtpparnortptime  OBJECT-TYPE
   SYNTAX    INTEGER(0..65535)
   MAX-ACCESS  read-write
   STATUS    current
   DESCRIPTION  ""
  ::={a200RtpParEntry 42}
  
   a200rtpparfaxswtime  OBJECT-TYPE
   SYNTAX    INTEGER(0..65535)
   MAX-ACCESS  read-write
   STATUS    current
   DESCRIPTION  ""
  ::={a200RtpParEntry 43}
  
   a200rtppardtmfcidelec  OBJECT-TYPE
   SYNTAX    INTEGER(100..630)
   MAX-ACCESS  read-write
   STATUS    current
   DESCRIPTION  ""
  ::={a200RtpParEntry 44}
  
--end of rtppar table

-----------------------------------------------------------
    msagCallCtrl OBJECT IDENTIFIER ::= { msagmajorVersion 6 }
       
    msagH248Perform  OBJECT IDENTIFIER  ::= { msagCallCtrl 6 }   

    msagH248PSRecMsg    OBJECT-TYPE
        SYNTAX          Integer32
        MAX-ACCESS      read-only
        STATUS          current
        DESCRIPTION     ""
        ::= { msagH248Perform 1 }

    msagH248PSSendMsg    OBJECT-TYPE
        SYNTAX          Integer32
        MAX-ACCESS      read-only
        STATUS          current
        DESCRIPTION     ""
        ::= { msagH248Perform 2 }

    msagH248PSRecMsgByte    OBJECT-TYPE
        SYNTAX          Integer32
        MAX-ACCESS      read-only
        STATUS          current
        DESCRIPTION     ""
        ::= { msagH248Perform 3 }

    msagH248PSSendMsgByte    OBJECT-TYPE
        SYNTAX          Integer32
        MAX-ACCESS      read-only
        STATUS          current
        DESCRIPTION     ""
        ::= { msagH248Perform 4 }

    msagH248PSProtocolError    OBJECT-TYPE
        SYNTAX          Integer32
        MAX-ACCESS      read-only
        STATUS          current
        DESCRIPTION     ""
        ::= { msagH248Perform 5 }

    msagH248PSTimerOut    OBJECT-TYPE
        SYNTAX          Integer32
        MAX-ACCESS      read-only
        STATUS          current
        DESCRIPTION     ""
        ::= { msagH248Perform 6 }

    msagH248PSDisconnect    OBJECT-TYPE
        SYNTAX          Integer32
        MAX-ACCESS      read-only
        STATUS          current
        DESCRIPTION     ""
        ::= { msagH248Perform 7 }

    msagH248PSMGCChange    OBJECT-TYPE
        SYNTAX          Integer32
        MAX-ACCESS      read-only
        STATUS          current
        DESCRIPTION     ""
        ::= { msagH248Perform 8 }

    msagH248PSTransmitError    OBJECT-TYPE
        SYNTAX          Integer32
        MAX-ACCESS      read-only
        STATUS          current
        DESCRIPTION     ""
        ::= { msagH248Perform 9 }

   calllimitipsthruput  OBJECT-TYPE
   SYNTAX    Unsigned32(0..4294967295)
   MAX-ACCESS  read-write
   STATUS    current
   DESCRIPTION  ""
  ::={msagCallCtrl 19}

   calllimitnicthruput  OBJECT-TYPE
   SYNTAX    Unsigned32(0..4294967295)
   MAX-ACCESS  read-write
   STATUS    current
   DESCRIPTION  ""
  ::={msagCallCtrl 20}

   calllimitcalllimit  OBJECT-TYPE
   SYNTAX    INTEGER{limitByMg(1),limitByMgc(2),notLimit(3)}
   MAX-ACCESS  read-write
   STATUS    current
   DESCRIPTION  ""
   ::={msagCallCtrl 21}

   calllimitcpubusylimit  OBJECT-TYPE
   SYNTAX   INTEGER{allwaysLimit(1),notLimit(2)}
   MAX-ACCESS  read-write
   STATUS      current
   DESCRIPTION    ""
   ::={msagCallCtrl 22}

   calllimitupportlimit  OBJECT-TYPE
   SYNTAX    INTEGER{allwaysLimit(1),notLimit(2)}
   MAX-ACCESS  read-write
   STATUS    current
   DESCRIPTION  ""
  ::={msagCallCtrl 23}

   calllimitipslimit  OBJECT-TYPE
   SYNTAX    INTEGER{allwaysLimit(1),notLimit(2)}
   MAX-ACCESS  read-write
   STATUS    current
   DESCRIPTION  ""
  ::={msagCallCtrl 24}

   calllimitniclimit  OBJECT-TYPE
   SYNTAX    INTEGER{allwaysLimit(1),notLimit(2)}
   MAX-ACCESS  read-write
   STATUS    current
   DESCRIPTION  ""
  ::={msagCallCtrl 25}
  

--upport table begin
   upPortTable OBJECT-TYPE
   SYNTAX    SEQUENCE OF UpPortEntry
   MAX-ACCESS  not-accessible
   STATUS    current
   DESCRIPTION  ""
   ::={msagCallCtrl 1}

   upPortEntry OBJECT-TYPE
   SYNTAX    UpPortEntry
   MAX-ACCESS  not-accessible
   STATUS    current
   DESCRIPTION  ""
   INDEX {upportid}
   ::={upPortTable 1}

   UpPortEntry ::=
      SEQUENCE{
      upportid               INTEGER,
      upportrack             INTEGER,
      upportshelf            INTEGER,
      upportslot             INTEGER,
      upportport             INTEGER,
      upportsendrateth       Unsigned32,
      upportreceiverateth    Unsigned32,
      upportRowStatus        RowStatus
   }

   upportid  OBJECT-TYPE
   SYNTAX    INTEGER(1..2)
   MAX-ACCESS  not-accessible
   STATUS    current
   DESCRIPTION  ""
  ::={upPortEntry 1}
  
   upportrack  OBJECT-TYPE
   SYNTAX    INTEGER(1..3)
   MAX-ACCESS  read-create
   STATUS    current
   DESCRIPTION  ""
  ::={upPortEntry 2}
  
   upportshelf  OBJECT-TYPE
   SYNTAX    INTEGER(1..5)
   MAX-ACCESS  read-create
   STATUS    current
   DESCRIPTION  ""
  ::={upPortEntry 3}
  
   upportslot  OBJECT-TYPE
   SYNTAX    INTEGER(1..23)
   MAX-ACCESS  read-create
   STATUS    current
   DESCRIPTION  ""
  ::={upPortEntry 29}
  
   upportport  OBJECT-TYPE
   SYNTAX    INTEGER(1..4)
   MAX-ACCESS  read-create
   STATUS    current
   DESCRIPTION  ""
  ::={upPortEntry 31}
  
   upportsendrateth  OBJECT-TYPE
   SYNTAX    Unsigned32(1..104857600)
   MAX-ACCESS  read-create
   STATUS    current
   DESCRIPTION  ""
  ::={upPortEntry 33}
  
   upportreceiverateth  OBJECT-TYPE
   SYNTAX    Unsigned32(1..104857600)
   MAX-ACCESS  read-create
   STATUS    current
   DESCRIPTION  ""
  ::={upPortEntry 35}
  
   upportRowStatus  OBJECT-TYPE
   SYNTAX    RowStatus
   MAX-ACCESS  read-create
   STATUS    current
   DESCRIPTION  ""
  ::={upPortEntry 37}
  
--end of upport table

--tone table begin
   toneTable OBJECT-TYPE
   SYNTAX    SEQUENCE OF ToneEntry
   MAX-ACCESS  not-accessible
   STATUS    current
   DESCRIPTION  ""
   ::={msagCallCtrl 2}

   toneEntry OBJECT-TYPE
   SYNTAX    ToneEntry
   MAX-ACCESS  not-accessible
   STATUS    current
   DESCRIPTION  ""
   INDEX {tonemgid}
   ::={toneTable 1}

   ToneEntry ::=
      SEQUENCE{
      tonemgid                  INTEGER,
      tonefaxcngtone            INTEGER,
      tonev21flagstone          INTEGER,
      tonet38faxend             INTEGER,
      toneansamwitone           INTEGER,
      toneansamwotone           INTEGER,
      toneanswitone             INTEGER,
      toneanswotone             INTEGER
   }

   tonemgid  OBJECT-TYPE
   SYNTAX    INTEGER(1..255)
   MAX-ACCESS  not-accessible
   STATUS    current
   DESCRIPTION  ""
  ::={toneEntry 1}

   tonefaxcngtone  OBJECT-TYPE
   SYNTAX    INTEGER{notReport(0),report(1)}
   MAX-ACCESS  read-write
   STATUS    current
   DESCRIPTION  ""
  ::={toneEntry 2}

   tonev21flagstone  OBJECT-TYPE
   SYNTAX    INTEGER{notReport(0),report(1)}
   MAX-ACCESS  read-write
   STATUS    current
   DESCRIPTION  ""
  ::={toneEntry 3}

   tonet38faxend  OBJECT-TYPE
   SYNTAX    INTEGER{notReport(0),report(1)}
   MAX-ACCESS  read-write
   STATUS    current
   DESCRIPTION  ""
   ::={toneEntry 4}

   toneansamwitone  OBJECT-TYPE
   SYNTAX   INTEGER{notReport(0),report(1)}
   MAX-ACCESS  read-write
   STATUS      current
   DESCRIPTION    ""
   ::={toneEntry 5}

   toneansamwotone  OBJECT-TYPE
   SYNTAX    INTEGER{notReport(0),report(1)}
   MAX-ACCESS  read-write
   STATUS    current
   DESCRIPTION  ""
  ::={toneEntry 6}

   toneanswitone  OBJECT-TYPE
   SYNTAX    INTEGER{notReport(0),report(1)}
   MAX-ACCESS  read-write
   STATUS    current
   DESCRIPTION  ""
  ::={toneEntry 7}

   toneanswotone  OBJECT-TYPE
   SYNTAX    INTEGER{notReport(0),report(1)}
   MAX-ACCESS  read-write
   STATUS    current
   DESCRIPTION  ""
  ::={toneEntry 8}
  
--end of tone table

   tonefixtonechip  OBJECT-TYPE
   SYNTAX    INTEGER{dsp(1),ips(2)}
   MAX-ACCESS  read-write
   STATUS    current
   DESCRIPTION  ""
  ::={msagCallCtrl 3}

  ------------------------------------------------------------

--------------------------------------------------------------------------------
--  VoIP Call Test
--------------------------------------------------------------------------------
    zxAnVoipCallTest OBJECT IDENTIFIER  ::=  { msagmajorVersion 12 }

--------------------------------------------------------------------------------
--  VoIP Callee Test
--------------------------------------------------------------------------------

    zxAnVoipCalleeTestTable OBJECT-TYPE
        SYNTAX      SEQUENCE OF ZxAnVoipCalleeTestEntry
        MAX-ACCESS  not-accessible
        STATUS      current
        DESCRIPTION
            "The table listing callee test entries. An entry indicates a test."
        REFERENCE
            "Used by MAP"
        ::= { zxAnVoipCallTest 1 }

    zxAnVoipCalleeTestEntry OBJECT-TYPE
        SYNTAX      ZxAnVoipCalleeTestEntry
        MAX-ACCESS  not-accessible
        STATUS      current
        DESCRIPTION
            "An entry in the zxAnVoipCalleeTestTable."
        INDEX       { zxAnVoipCalleeTestRack,
                      zxAnVoipCalleeTestShelf,
                      zxAnVoipCalleeTestSlot,
                      zxAnVoipCalleeTestPort,
                      zxAnVoipCalleeTestOnu,
                      zxAnVoipCalleeTestCircuitType,
                      zxAnVoipCalleeTestLogicalId }
        ::= { zxAnVoipCalleeTestTable 1 }

    ZxAnVoipCalleeTestEntry ::= SEQUENCE {
        zxAnVoipCalleeTestRack         Integer32,
        zxAnVoipCalleeTestShelf        Integer32,
        zxAnVoipCalleeTestSlot         Integer32,
        zxAnVoipCalleeTestPort         Integer32,
        zxAnVoipCalleeTestOnu          Integer32,
        zxAnVoipCalleeTestCircuitType  INTEGER,
        zxAnVoipCalleeTestLogicalId    OBJECT IDENTIFIER,
        zxAnVoipCalleeTestAction       INTEGER,
        zxAnVoipCalleeTestTimeout      INTEGER,
        zxAnVoipCalleeTestStatus       INTEGER,
        zxAnVoipCalleeTestPortStatus   INTEGER,
        zxAnVoipCalleeTestFailReason   INTEGER,
        zxAnVoipCalleeTestFailDetail   DisplayString,
        zxAnVoipCalleeTestRowStatus    RowStatus
    }

    zxAnVoipCalleeTestRack OBJECT-TYPE
        SYNTAX      Integer32
        MAX-ACCESS  not-accessible
        STATUS      current
        DESCRIPTION
            "This object indicates the rack number."
        ::= { zxAnVoipCalleeTestEntry 1 }

    zxAnVoipCalleeTestShelf OBJECT-TYPE
        SYNTAX      Integer32
        MAX-ACCESS  not-accessible
        STATUS      current
        DESCRIPTION
            "This object indicates the shelf number."
        ::= { zxAnVoipCalleeTestEntry 2 }

    zxAnVoipCalleeTestSlot OBJECT-TYPE
        SYNTAX      Integer32
        MAX-ACCESS  not-accessible
        STATUS      current
        DESCRIPTION
            "This object indicates the slot number."
        ::= { zxAnVoipCalleeTestEntry 3 }

    zxAnVoipCalleeTestPort OBJECT-TYPE
        SYNTAX      Integer32
        MAX-ACCESS  not-accessible
        STATUS      current
        DESCRIPTION
            "This object indicates the physical port number."
        ::= { zxAnVoipCalleeTestEntry 4 }

    zxAnVoipCalleeTestOnu OBJECT-TYPE
        SYNTAX      Integer32
        MAX-ACCESS  not-accessible
        STATUS      current
        DESCRIPTION
            "When zxAnVoipCalleeTestCircuitType are 'onu' or 'gemportOrLlid' or
            'servicePort', this object indicates 'onu ID'.
            When zxAnVoipCalleeTestCircuitType are 'physicalPort' or
            'bridgePort', its value is '0'."
        ::= { zxAnVoipCalleeTestEntry 5 }

    zxAnVoipCalleeTestCircuitType OBJECT-TYPE
        SYNTAX      INTEGER {    
                        physicalPort(1),
                        bridgePort(2),
                        onu(3),
                        gemportOrLlid(4),
                        onuUni(5),
                        servicePort(11)
                    }
        MAX-ACCESS  not-accessible
        STATUS      current
        DESCRIPTION
            "This object indicates the type of port."
        ::= { zxAnVoipCalleeTestEntry 6 }

    zxAnVoipCalleeTestLogicalId OBJECT-TYPE
        SYNTAX      OBJECT IDENTIFIER
        MAX-ACCESS  not-accessible
        STATUS      current
        DESCRIPTION
            "This value is an oid which indicats the logical index.

            When zxAnVoipCalleeTestCircuitType is 'physicalPort', its value is
            '0'.
            When zxAnVoipCalleeTestCircuitType is 'bridgePort', this object
            includes {pvc}, such as oid {1} indicates pvc1.
            When zxAnVoipCalleeTestCircuitType is 'onu', its value is '0'.
            When zxAnVoipCalleeTestCircuitType is 'gemportOrLlid', this object
            includes {gemport/llid}, such as oid {1} indicates gemport1/llid1.
            When zxAnVoipCalleeTestCircuitType is 'onuUni', this object
            includes {ONU slot and UNIID}, this type is used for SFU only.
            When the slotNo is not cared about, the slotNo should be 0, 
            such as oid{0.1}, which indicates slotNo0 and UNIID1.
            When zxAnVoipCalleeTestCircuitType is 'servicePort', this object
            includes {serviceportID}, such as oid {1} indicates serviceportID1."
        ::= { zxAnVoipCalleeTestEntry 7 }

    zxAnVoipCalleeTestAction OBJECT-TYPE
        SYNTAX      INTEGER {
                        start(1),
                        stop(2)
                    }
        MAX-ACCESS  read-create
        STATUS      current
        DESCRIPTION
            "The object is used to start or stop test. The object could be
            specified when creating an entry, also could be specified alone in a
            SET operation.

            start(1) - Start the test.
            stop(2) - Stop the test. Agent should stop test following regular
            on-hook procedure.
            "
        DEFVAL { stop }
        ::= { zxAnVoipCalleeTestEntry 8 }

    zxAnVoipCalleeTestTimeout OBJECT-TYPE
        SYNTAX      INTEGER(60..300)
        UNITS       "seconds"
        MAX-ACCESS  read-create
        STATUS      current
        DESCRIPTION
            "The time-out of test. Agent should stop test following regular
            on-hook procedure, if the test hasn't completed after time-out yet."
        DEFVAL{90}
        ::= { zxAnVoipCalleeTestEntry 9 }

    zxAnVoipCalleeTestStatus OBJECT-TYPE
        SYNTAX      INTEGER {
                        notStarted(1),
                        inProgress(2),
                        success(3),
                        failed(4)
                    }
        MAX-ACCESS  read-only
        STATUS      current
        DESCRIPTION
            "The status of test. Agent need keep this parameter updated so that
            manager can get the latest status of test by polling.

            notStarted(1) - Test is not started.
            inProgress(2) - Test is in progress.
            success(3) - Test is successful. It means that the voice path of
            call is well, while the on-hook operation is successful.
            failed(4) - Test failed.
            "
        ::= { zxAnVoipCalleeTestEntry 10 }

    zxAnVoipCalleeTestPortStatus OBJECT-TYPE
        SYNTAX      INTEGER {    
                        idle(1),
                        ringing(2),
                        offHook(3),
                        connected(4),
                        busyTone(5),
                        onHook(6),
                        testEnd(7)
                    }
        MAX-ACCESS  read-only
        STATUS      current
        DESCRIPTION
            "This object indicates the current status of port.

            idle(1) - The state of port is idle.
            ringing(2) - The state of port is ringing.
            offHook(3) - The state of port is off-hook.
            connected(4) - Voice data path is established. The port can receive
            and send voice data.
            busyTone(5) - The port is playing busy tone.
            onHook(6) - The state of port is on-hook.
            testEnd(7) - Test ended. The port is available for user.
            "
        ::= { zxAnVoipCalleeTestEntry 11 }

    zxAnVoipCalleeTestFailReason OBJECT-TYPE
        SYNTAX      INTEGER {
                        other(1),
                        noRing(2),
                        noUpstreamVoice(3),
                        noDownstreamVoice(4),
                        noBidirectionVoice(5),
                        ringReleasedEarly(6),
                        noDigit(7),
                        wrongDigit(8)
                    }
        MAX-ACCESS  read-only
        STATUS      current
        DESCRIPTION
            "The failed reason of test.

            other(1) - Other reason.
            noRing(2) - No ringing.
            noUpstreamVoice(3) - No upstream voice.
            noDownstreamVoice(4) - No downstream voice.
            noBidirectionVoice(5) - No upstream and downstream voice.
            ringReleasedEarly(6) - Ring released early.
            noDigit(7) - No digit.
            wrongDigit(8) - Wrong digit.
            "
        ::= { zxAnVoipCalleeTestEntry 12 }

    zxAnVoipCalleeTestFailDetail OBJECT-TYPE
        SYNTAX      DisplayString (SIZE (0..255))
        MAX-ACCESS  read-only
        STATUS      current
        DESCRIPTION
            "The failed detail. This field should be filled when the value of
            zxAnVoipCalleeTestFailReason is 'other'."
        ::= { zxAnVoipCalleeTestEntry 13 }

    zxAnVoipCalleeTestRowStatus  OBJECT-TYPE
        SYNTAX      RowStatus
        MAX-ACCESS  read-create
        STATUS      current
        DESCRIPTION
            "This object is used to create a new row or delete an existing row
            in this table. Only 'createAndGo' and 'destroy' need to be
            supported. If test is in progress, agent should reject the 'destroy'
            request from manager.

            'createAndGo' means creating an entry.
            'destroy' means deleting an entry."
        ::= { zxAnVoipCalleeTestEntry 50 }

--------------------------------------------------------------------------------
--  VoIP Caller Test
--------------------------------------------------------------------------------

    zxAnVoipCallerTestTable OBJECT-TYPE
        SYNTAX      SEQUENCE OF ZxAnVoipCallerTestEntry
        MAX-ACCESS  not-accessible
        STATUS      current
        DESCRIPTION
            "The table listing caller test entries. An entry indicates a test
            ."
        REFERENCE
            "Used by MAP"
        ::= { zxAnVoipCallTest 2 }

    zxAnVoipCallerTestEntry OBJECT-TYPE
        SYNTAX      ZxAnVoipCallerTestEntry
        MAX-ACCESS  not-accessible
        STATUS      current
        DESCRIPTION
            "An entry in the zxAnVoipCallerTestTable."
        INDEX       { zxAnVoipCallerTestRack,
                      zxAnVoipCallerTestShelf,
                      zxAnVoipCallerTestSlot,
                      zxAnVoipCallerTestPort,
                      zxAnVoipCallerTestOnu,
                      zxAnVoipCallerTestCircuitType,
                      zxAnVoipCallerTestLogicalId }
        ::= { zxAnVoipCallerTestTable 1 }

    ZxAnVoipCallerTestEntry ::= SEQUENCE {
        zxAnVoipCallerTestRack           Integer32,
        zxAnVoipCallerTestShelf          Integer32,
        zxAnVoipCallerTestSlot           Integer32,
        zxAnVoipCallerTestPort           Integer32,
        zxAnVoipCallerTestOnu            Integer32,
        zxAnVoipCallerTestCircuitType    INTEGER,
        zxAnVoipCallerTestLogicalId      OBJECT IDENTIFIER,
        zxAnVoipCallerTestAction         INTEGER,
        zxAnVoipCallerTestTimeout        INTEGER,
        zxAnVoipCallerTestDialedNumber   DisplayString,
        zxAnVoipCallerTestStatus         INTEGER,
        zxAnVoipCallerTestPortStatus     INTEGER,
        zxAnVoipCallerTestFailReason     INTEGER,
        zxAnVoipCallerTestFailDetail     DisplayString,
        zxAnVoipCallerTestSipFailReason  INTEGER,
        zxAnVoipCallerTestSipErrorCode   INTEGER,
        zxAnVoipCallerTestSipDelay       Integer32,
        zxAnVoipCallerTestMode           INTEGER,
        zxAnVoipCallerTestRowStatus      RowStatus
    }

    zxAnVoipCallerTestRack OBJECT-TYPE
        SYNTAX      Integer32
        MAX-ACCESS  not-accessible
        STATUS      current
        DESCRIPTION
            "This object indicates the rack number."
        ::= { zxAnVoipCallerTestEntry 1 }

    zxAnVoipCallerTestShelf OBJECT-TYPE
        SYNTAX      Integer32
        MAX-ACCESS  not-accessible
        STATUS      current
        DESCRIPTION
            "This object indicates the shelf number."
        ::= { zxAnVoipCallerTestEntry 2 }

    zxAnVoipCallerTestSlot OBJECT-TYPE
        SYNTAX      Integer32
        MAX-ACCESS  not-accessible
        STATUS      current
        DESCRIPTION
            "This object indicates the slot number."
        ::= { zxAnVoipCallerTestEntry 3 }

    zxAnVoipCallerTestPort OBJECT-TYPE
        SYNTAX      Integer32
        MAX-ACCESS  not-accessible
        STATUS      current
        DESCRIPTION
            "This object indicates the physical port number."
        ::= { zxAnVoipCallerTestEntry 4 }

    zxAnVoipCallerTestOnu OBJECT-TYPE
        SYNTAX      Integer32
        MAX-ACCESS  not-accessible
        STATUS      current
        DESCRIPTION
            "When zxAnVoipCallerTestCircuitType are 'onu' or 'gemportOrLlid' or
            'servicePort', this object indicates 'onu ID'.
            When zxAnVoipCallerTestCircuitType are 'physicalPort' or
            'bridgePort', its value is '0'."
        ::= { zxAnVoipCallerTestEntry 5 }

    zxAnVoipCallerTestCircuitType OBJECT-TYPE
        SYNTAX      INTEGER {    
                        physicalPort(1),
                        bridgePort(2),
                        onu(3),
                        gemportOrLlid(4),
                        onuUni(5),
                        servicePort(11)
                    }
        MAX-ACCESS  not-accessible
        STATUS      current
        DESCRIPTION
            "This object indicates the type of port."
        ::= { zxAnVoipCallerTestEntry 6 }

    zxAnVoipCallerTestLogicalId OBJECT-TYPE
        SYNTAX      OBJECT IDENTIFIER
        MAX-ACCESS  not-accessible
        STATUS      current
        DESCRIPTION
            "This value is an oid which indicats the logical index.

            When zxAnVoipCallerTestCircuitType is 'physicalPort', its value is
            '0'.
            When zxAnVoipCallerTestCircuitType is 'bridgePort', this object
            includes {pvc}, such as oid {1} indicates pvc1.
            When zxAnVoipCallerTestCircuitType is 'onu', its value is '0'.
            When zxAnVoipCallerTestCircuitType is 'gemportOrLlid', this object
            includes {gemport/llid}, such as oid {1} indicates gemport1/llid1.
            When zxAnVoipCallerTestCircuitType is 'onuUni', this object
            includes {ONU slot and UNIID}, this type is used for SFU only.
            When the slotNo is not cared about, the slotNo should be 0, 
            such as oid{0.1}, which indicates slotNo0 and UNIID1.
            When zxAnVoipCallerTestCircuitType is 'servicePort', this object
            includes {serviceportID}, such as oid {1} indicates serviceportID1."
        ::= { zxAnVoipCallerTestEntry 7 }

    zxAnVoipCallerTestAction OBJECT-TYPE
        SYNTAX      INTEGER {
                        start(1),
                        stop(2)
                    }
        MAX-ACCESS  read-create
        STATUS      current
        DESCRIPTION
            "The object is used to start or stop test. The object could be
            specified when creating an entry, also could be specified alone in a
            SET operation.

            start(1) - Start the test.
            stop(2) - Stop the test. Agent should stop test following regular
            on-hook procedure.
            "
        DEFVAL { stop }
        ::= { zxAnVoipCallerTestEntry 8 }

    zxAnVoipCallerTestTimeout OBJECT-TYPE
        SYNTAX      INTEGER(60..300)
        UNITS       "seconds"
        MAX-ACCESS  read-create
        STATUS      current
        DESCRIPTION
            "The time-out of test. Agent should stop test following regular
            on-hook procedure, if the test hasn't completed after time-out yet."
        DEFVAL{90}
        ::= { zxAnVoipCallerTestEntry 9 }

    zxAnVoipCallerTestDialedNumber OBJECT-TYPE
        SYNTAX      DisplayString (SIZE (0..63))
        MAX-ACCESS  read-create
        STATUS      current
        DESCRIPTION
            "The number that user dial. Here it is set by manager.
            When zxAnVoipCallerTestDialedNumber is used to SFU,
            it's size is 1 to 63.
            "
        ::= { zxAnVoipCallerTestEntry 10 }

    zxAnVoipCallerTestStatus OBJECT-TYPE
        SYNTAX      INTEGER {
                        notStarted(1),
                        inProgress(2),
                        success(3),
                        failed(4),
                        notForced(5)
                    }
        MAX-ACCESS  read-only
        STATUS      current
        DESCRIPTION
            "The status of test. Agent need keep this parameter updated so that
            manager can get the latest status of test by polling.

            notStarted(1) - Test is not started.
            inProgress(2) - Test is in progress.
            success(3)    - Test is successful. It means that the voice path of
                            call is well, while the on-hook operation is 
                            successful.
            failed(4)     - Test failed.
            notForced(5)  - Test is not attempted because the POTS line is busy.
            "
        ::= { zxAnVoipCallerTestEntry 11 }

    zxAnVoipCallerTestPortStatus OBJECT-TYPE
        SYNTAX      INTEGER {    
                        idle(1),
                        offHook(2),
                        dialTone(3),
                        receiveNumber(4),
                        receiveEnd(5),
                        ringBackTone(6),
                        connected(7),
                        busyTone(8),
                        onHook(9),
                        testEnd(10)
                    }
        MAX-ACCESS  read-only
        STATUS      current
        DESCRIPTION
            "This object indicates the current status of port.

            idle(1) - The state of port is idle.
            offHook(2) - The state of port is off-hook.
            dialTone(3) - The port is playing dial tone.
            receiveNumber(4) - The port is receiving number.
            receiveEnd(5) - Receiving number ended.
            ringBackTone(6) - The port is playing ring back tone.
            connected(7) - Voice data path is established. The port can receive
            and send voice data.
            busyTone(8) - The port is playing busy tone.
            onHook(9) - The state of port is on-hook.
            testEnd(10) - Test ended. The port is available for user.
            "
        ::= { zxAnVoipCallerTestEntry 12 }

    zxAnVoipCallerTestFailReason OBJECT-TYPE
        SYNTAX      INTEGER {
                        other(1),
                        noDialTone(2),
                        noRingBack(3),
                        noAnswer(4),
                        noUpstreamVoice(5),
                        noDownstreamVoice(6),
                        noBidirectionVoice(7),
                        sipTestFailed(8),
                        noDigit(9),
                        wrongDigit(10)
                    }
        MAX-ACCESS  read-only
        STATUS      current
        DESCRIPTION
            "The failed reason of test.

            other(1) - Other reason.
            noDialTone(2) - No dial tone.
            noRingBack(3) - No ring back tone.
            noAnswer(4) - No answer.
            noUpstreamVoice(5) - No upstream voice.
            noDownstreamVoice(6) - No downstream voice.
            noBidirectionVoice(7) - No upstream and downstream voice.
            sipTestFailed(8) - SIP test failed.
            noDigit(9) - No digit.
            wrongDigit(10) - Wrong digit.
            "
        ::= { zxAnVoipCallerTestEntry 13 }

    zxAnVoipCallerTestFailDetail OBJECT-TYPE
        SYNTAX      DisplayString (SIZE (0..255))
        MAX-ACCESS  read-only
        STATUS      current
        DESCRIPTION
            "The failed detail. This field should be filled when the value of
            zxAnVoipCallerTestFailReason is 'other'."
        ::= { zxAnVoipCallerTestEntry 14 }
    
    zxAnVoipCallerTestSipFailReason  OBJECT-TYPE
        SYNTAX      INTEGER
            {
                inviteOkButNoBearerData(1),
                callTimeoutNo200Ok(2),
                noResponseToInvite(3),
                errorCodeAndReasonPhrase(4),
                callCancelledByServer(5),
                callCancelledByOnt(6),
                lineNotConfigured(7),
                lineNotInValidState(8),
                lineNotRegistered(9),
                notchFiltersRequired(10),
                dialToneTestFailure(11)
            }
        MAX-ACCESS  read-only
        STATUS      current
        DESCRIPTION
            "The failed reason of SIP test. This field should be filled when the
            value of zxAnVoipCallerTestFailReason is 'sipTestFailure'.

            inviteOkButNoBearerData(1) - No bearer traffic was received even 
            though the test call was successful.
            callTimeoutNo200Ok(2) - The test call never completed although 
            provisional response were received for the INVITE request.
            noResponseToInvite(3) - No response was received to the INVITE 
            request and attempts to retry the INVITE timed out without a 
            response.
            errorCodeAndReasonPhrase(4) - The softswitch returned an error to 
            the INVITE request.
            callCancelledByServer(5) - The softswitch sent a CANCEL for the 
            INVITE transaction.
            callCancelledByOnt(6) - The call was cancelled by the ONT.
            lineNotConfigured(7) - The POTS line is not fully configured, 
            probably due to missing SIP provisioning data.
            lineNotInValidState(8)- The POTS line is in the wrong status to 
            perform the test.
            lineNotRegistered(9) - The POTS line is not registered with the 
            softswitch.
            notchFiltersRequired(10) - The notch filter settings in the 
            configuration profile analog data were missing.
            dialToneTestFailure(11) - Dial tone test failure.
            "
        ::= { zxAnVoipCallerTestEntry 15 }  
    
    zxAnVoipCallerTestSipErrorCode OBJECT-TYPE
        SYNTAX      INTEGER {
                        unauthorized(1),
                        forbidden(2),
                        notFound(3),
                        proxyAuthenticationRequired(4),
                        requestTimeout(5),
                        temporarilyUnavailable(6),
                        addressIncomplete(7),
                        busyHere(8),
                        requestTerminated(9),
                        notAcceptableHere(10),
                        serverInternalError(11),
                        serviceUnavailable(12),
                        serverTimeout(13)                   
                    }
        MAX-ACCESS  read-only
        STATUS      current
        DESCRIPTION
            "The error code of SIP test. This field should be filled when the
            value of zxAnVoipCallerTestSipFailReason is 
            'errorCodeAndReasonPhrase'.

            unauthorized(1) - 401 Unauthorized.
            forbidden(2) - 403 Forbidden.
            notFound(3) - 404 Not found.
            proxyAuthenticationRequired(4) - 407 Proxy authentication required.
            requestTimeout(5) - 408 Request timeout.
            temporarilyUnavailable(6) - 480 Temporarily unavailable. 
            addressIncomplete(7) - 484 Address incomplete.
            busyHere(8) - 486 Busy here.
            requestTerminated(9) - 487 Request terminated.
            notAcceptableHere(10) - 488 Not acceptable here.
            serverInternalError(11) - 500 Server internal error.
            serviceUnavailable(12) - 503 Service unavailable.
            serverTimeout(13) - 504 Server time-out.
            "
        ::= { zxAnVoipCallerTestEntry 16 }
    
    zxAnVoipCallerTestSipDelay OBJECT-TYPE
        SYNTAX      Integer32(0..65535)
        UNITS       "0.1second"
        MAX-ACCESS  read-only
        STATUS      current
        DESCRIPTION
            "Specifies how long it takes to set up bearer traffic RTP packets 
            for the POTS line being tested in tenths of a second.The delay 
            measure timer starts when the INVITE is generated for a call 
            origination to the phone number specified by the PHONENO 
            parameter in the DGN-SIPDIALTONE TL1 command. The SIP 
            application at the ONT starts listening for RTP  packets. If RTP 
            packets are detected, the delay measure timer is stopped and 
            the timer value is recorded for later reporting. Range for measure
            post dial delay is 0.0 to 6553.5 in tenths of seconds."
        ::= { zxAnVoipCallerTestEntry 17 }
    

    zxAnVoipCallerTestMode OBJECT-TYPE
        SYNTAX      INTEGER {
                        interactive(1),
                        nonInteractive(2)
                    }
        MAX-ACCESS  read-create
        STATUS      current
        DESCRIPTION
            "The test mode of caller test.

            interactive(1) - normal caller test model.
            nonInteractive(2) - in this test mode, if only receive ringback 
                                tone means that test is successful.
            "
        ::= { zxAnVoipCallerTestEntry 18 }
    
    zxAnVoipCallerTestRowStatus  OBJECT-TYPE
        SYNTAX      RowStatus
        MAX-ACCESS  read-create
        STATUS      current
        DESCRIPTION
            "This object is used to create a new row or delete an existing row
            in this table. Only 'createAndGo' and 'destroy' need to be
            supported. If test is in progress, agent should reject the 'destroy'
            request from manager.

            'createAndGo' means creating an entry.
            'destroy' means deleting an entry."
        ::= { zxAnVoipCallerTestEntry 50 }

  ------------------------------------------------------------

    msagTrap          OBJECT IDENTIFIER   ::=  {  msagmajorVersion  10 }
    
    msagTrapId  OBJECT IDENTIFIER ::= { msagTrap 1 }

    zxAnNarrowbandResAvailable NOTIFICATION-TYPE
        OBJECTS { zxAnNarrowbandResCfgType, zxAnNarrowbandResActType }
        STATUS  current
        DESCRIPTION
            "It indicates the Resource is available now."
       ::= { msagTrapId 1 }

    zxAnNarrowbandResUnavailable NOTIFICATION-TYPE
        OBJECTS { zxAnNarrowbandResCfgType, zxAnNarrowbandResActType }
        STATUS  current
        DESCRIPTION
            "It indicates the Resource is unavailable now."
       ::= { msagTrapId 2 }

    zxAnIpsResource NOTIFICATION-TYPE
        OBJECTS { zxAnIpsResourceAlarmReason, a200ipsThreshold, zxAnIpsUsage }
        STATUS  current
        DESCRIPTION
            "A zxAnIpsResource trap is sent
            when the IPS resource usage is above the threshold
            or when the IPS resource usage is 100%."
       ::= { msagTrapId 3 }

    zxAnIpsResourceRestore NOTIFICATION-TYPE
        OBJECTS { zxAnIpsResourceAlarmReason, a200ipsThreshold, zxAnIpsUsage }
        STATUS  current
        DESCRIPTION
            "A zxAnIpsResourceRestore trap is sent
            when the IPS resource usage is below the threshold
            or when the IPS resource usage is from 100% to less then 100%."
       ::= { msagTrapId 4 }

    zxAnIpsChannelFault NOTIFICATION-TYPE
        OBJECTS { zxAnTrapUnit, zxAnTrapSunit, zxAnTrapPort}
        STATUS  current
        DESCRIPTION
            "IPS circuit fault."
       ::= { msagTrapId 5 }

    zxAnIpsChannelFaultRestore NOTIFICATION-TYPE
        OBJECTS { zxAnTrapUnit, zxAnTrapSunit, zxAnTrapPort}
        STATUS  current
        DESCRIPTION
            "IPS circuit fault."
       ::= { msagTrapId 6 }

    zxMsagH248Link NOTIFICATION-TYPE
        OBJECTS { msagTrapReason,msagTrapLinkState,msagTrapMgcNo }
        STATUS  current
        DESCRIPTION
            "H248 linkdown."
       ::= { msagTrapId 7 }
       
     zxMsagH248LinkRestore NOTIFICATION-TYPE
        OBJECTS { msagTrapReason,msagTrapLinkState,msagTrapMgcNo }
        STATUS  current
        DESCRIPTION
            "H248 linkrestore."
       ::= { msagTrapId 8 }  
           
     zxMsagH248ErrorCode NOTIFICATION-TYPE
        OBJECTS { msagTrapErrcode, zxAnTrapRack,zxAnTrapShelf,zxAnTrapSlot,zxAnTrapPort }
        STATUS  current
        DESCRIPTION
            "H248 Errorcode.
             ex:
             430 - Unknown TerminationID;
             433- TerminationID is already in a Context
             "
       ::= { msagTrapId 9 }

    zxAnDlccNT1Los NOTIFICATION-TYPE
        OBJECTS { zxAnTrapRack, zxAnTrapShelf, zxAnTrapSlot, zxAnTrapPort, zxAnTrapInfoType }
        STATUS  current
        DESCRIPTION ""
       ::= { msagTrapId 10 }

     zxMsagMgcpLink NOTIFICATION-TYPE
        OBJECTS { msagTrapReason,msagTrapLinkState,msagTrapMgcNo }
        STATUS  current
        DESCRIPTION
            "Mgcp linkdown."
       ::= { msagTrapId 11 }         
       
     zxMsagMgcpLinkRestore NOTIFICATION-TYPE
        OBJECTS { msagTrapReason,msagTrapLinkState,msagTrapMgcNo }
        STATUS  current
        DESCRIPTION
            "Mgcp linkRestore."
       ::= { msagTrapId 12 } 

     zxMsagMgcpAbnormal NOTIFICATION-TYPE
        OBJECTS { msagTrapReason,msagTrapLinkState,msagTrapMgcNo }
        STATUS  current
        DESCRIPTION
            "Mgcp Abnormal."
       ::= { msagTrapId 13 } 
       
     zxMsagMgcpAbnormalRestore NOTIFICATION-TYPE
        OBJECTS { msagTrapReason,msagTrapLinkState,msagTrapMgcNo }
        STATUS  current
        DESCRIPTION
            "Mgcp Abnormal."
       ::= { msagTrapId 14 }        
   
     zxMsagV5Pcm NOTIFICATION-TYPE
        OBJECTS { msagTrapUnitNo,msagTrapPcmNo,msagTrapReasionValue }
        STATUS  current
        DESCRIPTION
            "V5 PCM Alarm."
       ::= { msagTrapId 15 }     

     zxMsagV5PcmRestore NOTIFICATION-TYPE
        OBJECTS { msagTrapUnitNo,msagTrapPcmNo,msagTrapReasionValue }
        STATUS  current
        DESCRIPTION
            "V5 PCM Alarm Restore."
       ::= { msagTrapId 16 }  

     zxMsagV5Proto NOTIFICATION-TYPE
        OBJECTS { msagTrapV5InterId,msagTrapDLProType,msagTrapCurEvent,msagTrapCurState }
        STATUS  current
        DESCRIPTION
            "V5 Proto Alarm."
       ::= { msagTrapId 17 }  

     zxMsagV5ProtoRestore NOTIFICATION-TYPE
        OBJECTS { msagTrapV5InterId,msagTrapDLProType,msagTrapCurEvent,msagTrapCurState }
        STATUS  current
        DESCRIPTION
            "V5 Proto Alarm Restore."
       ::= { msagTrapId 18 }  
        
     zxMsagISDNSctpInform NOTIFICATION-TYPE
        OBJECTS { msagTrapReason,msagTrapParaLinkId,msagTrapIpAddress }
        STATUS  current
        DESCRIPTION
            "ISDN Sctp Inform."
       ::= { msagTrapId 19 }   
            
     zxMsagISDNSctpAlarm NOTIFICATION-TYPE
        OBJECTS { msagTrapReason }
        STATUS  current
        DESCRIPTION
            "ISDN Sctp Alarm."
       ::= { msagTrapId 20 }     
       
     zxMsagIUAInform NOTIFICATION-TYPE
        OBJECTS { msagTrapReason }
        STATUS  current
        DESCRIPTION
            "IUA Inform."
       ::= { msagTrapId 21 }  
       
     zxMsagIUAAlarm NOTIFICATION-TYPE
        OBJECTS { msagTrapReason }
        STATUS  current
        DESCRIPTION
            "IUA Alarm."
       ::= { msagTrapId 22 }       

     zxMsagIUAAlarmRestore NOTIFICATION-TYPE
        OBJECTS { msagTrapReason }
        STATUS  current
        DESCRIPTION
            "IUA Alarm Restore."
       ::= { msagTrapId 23 }              

     zxMsagCallAllocMemoryErrorAlarm NOTIFICATION-TYPE
        OBJECTS { msagTrapReason }
        STATUS  current
        DESCRIPTION
            "CALL Alloc Momory Error."
       ::= { msagTrapId 24 }              

     zxMsagQosPoorAlarm NOTIFICATION-TYPE
        OBJECTS { zxAnTrapUnit,zxAnTrapSunit,msagTrapPort,msagQosAlarmType,
        msagQosAlarmDetail,zxAnTrapRack,zxAnTrapShelf,zxAnTrapSlot,zxAnTrapPort}
        STATUS  current
        DESCRIPTION
            "Service Qos Poor Alarm."
       ::= { msagTrapId 25 }              

     zxMsagQosPoorRestore NOTIFICATION-TYPE
        OBJECTS { zxAnTrapUnit,zxAnTrapSunit,msagTrapPort,msagQosAlarmType,
        msagQosAlarmDetail,zxAnTrapRack,zxAnTrapShelf,zxAnTrapSlot,zxAnTrapPort}
        STATUS  current
        DESCRIPTION
            "Service Qos Poor Restore."
       ::= { msagTrapId 26 }              

     zxAnSlcFreqOffOnHookAlarm NOTIFICATION-TYPE
        OBJECTS { zxAnTrapRack,zxAnTrapShelf,zxAnTrapSlot,zxAnTrapPort }
        STATUS  current
        DESCRIPTION
            "The trap means on-hook or off-hook  is too frequently , and over threshold."
       ::= { msagTrapId 100 }              
     
     zxAnSlcFreqOffOnHookAlarmRestore NOTIFICATION-TYPE
        OBJECTS { zxAnTrapRack,zxAnTrapShelf,zxAnTrapSlot,zxAnTrapPort }
        STATUS  current
        DESCRIPTION
            "That means on-hook or off-hook  is normal."
       ::= { msagTrapId 101 }        

     zxAnSlcGroundedAlarm NOTIFICATION-TYPE
        OBJECTS { zxAnTrapRack,zxAnTrapShelf,zxAnTrapSlot,zxAnTrapPort }
        STATUS  current
        DESCRIPTION
            "The trap means  subscriber line grounded"
       ::= { msagTrapId 102 }              

     zxAnSlcGroundedRestore NOTIFICATION-TYPE
        OBJECTS { zxAnTrapRack,zxAnTrapShelf,zxAnTrapSlot,zxAnTrapPort }
        STATUS  current
        DESCRIPTION
            "The trap means  subscriber line normal."
       ::= { msagTrapId 103 }

     zxAnSlcContactedWithPower NOTIFICATION-TYPE
        OBJECTS { zxAnTrapRack,zxAnTrapShelf,zxAnTrapSlot,zxAnTrapPort }
        STATUS  current
        DESCRIPTION
            "Subscriber port contacted with power."
       ::= { msagTrapId 104 }

    zxAnDsx1ProtectionGroupSwapped NOTIFICATION-TYPE
        OBJECTS {
                    zxAnDsx1ProtectionGroupName,
                    zxAnDsx1MasterDsx1Rack,
                    zxAnDsx1MasterDsx1Shelf,
                    zxAnDsx1MasterDsx1Slot,
                    zxAnDsx1MasterDsx1LinkNo,
                    zxAnDsx1StandbyDsx1Rack,
                    zxAnDsx1StandbyDsx1Shelf,
                    zxAnDsx1StandbyDsx1Slot,
                    zxAnDsx1StandbyDsx1LinkNo,
                    zxAnDsx1CurrWorkingDsx1
                }
        STATUS             current
        DESCRIPTION
           "It indicates the master E1 and standby E1 of protection group 
            have swapped."
       ::= { msagTrapId 105 }
       
    zxAnIsdnUInterfaceLinkDown NOTIFICATION-TYPE
        OBJECTS { zxAnTrapRack,zxAnTrapShelf,zxAnTrapSlot,zxAnTrapPort }
        STATUS  current
        DESCRIPTION
            "The trap means the ISDN U-interface down.
            "
       ::= { msagTrapId 106 }              

    zxAnIsdnUInterfaceLinkUp NOTIFICATION-TYPE
        OBJECTS { zxAnTrapRack,zxAnTrapShelf,zxAnTrapSlot,zxAnTrapPort }
        STATUS  current
        DESCRIPTION
            "The trap means the ISDN U-interface up."
       ::= { msagTrapId 107 }
       
    zxAnSlcContactedWithPowerClr NOTIFICATION-TYPE
        OBJECTS { zxAnTrapRack,zxAnTrapShelf,zxAnTrapSlot,zxAnTrapPort }
        STATUS  current
        DESCRIPTION
            "A zxAnSlcContactedWithPowerClr trap is sent when the agent 
            has detected that the zxAnSlcContactedWithPower is cleared."
       ::= { msagTrapId 108 }
       
    zxAnHwTsUsageAboveThresholdAlm NOTIFICATION-TYPE
        OBJECTS { zxAnHwTimeSlotUsageThreshold, 
                  zxAnHwTimeSlotUsage }
        STATUS  current
        DESCRIPTION
            "A zxAnHwTsUsageAboveThresholdAlm trap is sent
            when the HW time slot usage 
            between master shelf and slave shelf is above the threshold."
       ::= { msagTrapId 109 }       
       
    zxAnHwTsUsageAboveThresholdClr NOTIFICATION-TYPE
        OBJECTS { zxAnHwTimeSlotUsageThreshold, 
                  zxAnHwTimeSlotUsage }
        STATUS  current
        DESCRIPTION
            "A zxAnHwTsUsageAboveThresholdClr trap is sent
            when the HW time slot usage  
            between master shelf and slave shelf is below the threshold."
       ::= { msagTrapId 110 } 

    zxAnVoicePortLockoutAlm NOTIFICATION-TYPE
        OBJECTS { zxAnTrapRack, zxAnTrapShelf, zxAnTrapSlot, zxAnTrapPort}
        STATUS  current
        DESCRIPTION
            "The trap is sent when the voice port is in lockout status."
       ::= { msagTrapId 111 }

    zxAnVoicePortLockoutClr NOTIFICATION-TYPE
        OBJECTS { zxAnTrapRack, zxAnTrapShelf, zxAnTrapSlot, zxAnTrapPort}
        STATUS  current
        DESCRIPTION
            "The trap is sent when the voice port recovered from lockout 
        status."
       ::= { msagTrapId 112 }
       
    zxAnDdiSubscriberLineBrokenAlm NOTIFICATION-TYPE
        OBJECTS { zxAnTrapRack, zxAnTrapShelf, zxAnTrapSlot, zxAnTrapPort}
        STATUS  current
        DESCRIPTION
            "The trap is sent when the subscriber line of DDI port is broken."
       ::= { msagTrapId 113 }

    zxAnDdiSubscriberLineBrokenClr NOTIFICATION-TYPE
        OBJECTS { zxAnTrapRack, zxAnTrapShelf, zxAnTrapSlot, zxAnTrapPort}
        STATUS  current
        DESCRIPTION
            "The trap is sent when the subscriber line of DDI port is not 
            broken."
       ::= { msagTrapId 114 }
 
     zxAnVoicePortHighAcVoltageAlm NOTIFICATION-TYPE
        OBJECTS { zxAnTrapRack,zxAnTrapShelf,zxAnTrapSlot,zxAnTrapPort }
        STATUS  current
        DESCRIPTION
            "The trap is sent when the voice port AC voltage is abnormal."
       ::= { msagTrapId 115 }              
     
     zxAnVoicePortHighAcVoltageClr NOTIFICATION-TYPE
        OBJECTS { zxAnTrapRack,zxAnTrapShelf,zxAnTrapSlot,zxAnTrapPort }
        STATUS  current
        DESCRIPTION
            "The trap is sent when the voice port AC voltage is normal."
       ::= { msagTrapId 116 } 
             
     zxAnVoicePortHighDcVoltageAlm NOTIFICATION-TYPE
        OBJECTS { zxAnTrapRack,zxAnTrapShelf,zxAnTrapSlot,zxAnTrapPort }
        STATUS  current
        DESCRIPTION
            "The trap is sent when the voice port DC voltage is abnormal."
       ::= { msagTrapId 117 }              
     
     zxAnVoicePortHighDcVoltageClr NOTIFICATION-TYPE
        OBJECTS { zxAnTrapRack,zxAnTrapShelf,zxAnTrapSlot,zxAnTrapPort }
        STATUS  current
        DESCRIPTION
            "The trap is sent when the voice port DC voltage is normal."
       ::= { msagTrapId 118 } 
 
    msagTrapObjectMib  OBJECT IDENTIFIER ::= { msagTrap 2 }

    zxAnNarrowbandResCfgType       OBJECT-TYPE
        SYNTAX          INTEGER
            {
             dtmf           (1),
             tone           (2),
             ipsMprb        (3),
             conference     (4),
             ipsSixty       (5),
             msdti          (6),
             odtT1          (7),
             notSourceType  (8)
            }
        MAX-ACCESS      read-only
        STATUS          current
        DESCRIPTION     "This MIB is defined for the Resource on the unit type card."
        ::=  {  msagTrapObjectMib  1  }

    zxAnNarrowbandResActType     OBJECT-TYPE
        SYNTAX          DisplayString  ( SIZE ( 0 .. 64  ) )
        MAX-ACCESS      read-only
        STATUS          current
        DESCRIPTION     "This MIB is defined for accessories type of this Resource,
               such as DTMF, TONE, IPSMPRB, CONFERENCE, IPSSIXTY,
               MSDTI etc."
        ::=  {  msagTrapObjectMib  2  }

    zxAnIpsResourceAlarmReason     OBJECT-TYPE
        SYNTAX          Integer32
        MAX-ACCESS      read-only
        STATUS          current
        DESCRIPTION     ""
        ::=  {  msagTrapObjectMib  3  }
        
    zxAnTrapRack     OBJECT-TYPE
        SYNTAX          Integer32
        MAX-ACCESS      read-only
        STATUS          current
        DESCRIPTION     ""
        ::=  {  msagTrapObjectMib  4  }

    zxAnTrapShelf     OBJECT-TYPE
        SYNTAX          Integer32
        MAX-ACCESS      read-only
        STATUS          current
        DESCRIPTION     ""
        ::=  {  msagTrapObjectMib  5  }

    zxAnTrapSlot     OBJECT-TYPE
        SYNTAX          Integer32
        MAX-ACCESS      read-only
        STATUS          current
        DESCRIPTION     ""
        ::=  {  msagTrapObjectMib  6  }        

    zxAnTrapUnit     OBJECT-TYPE
        SYNTAX          Integer32
        MAX-ACCESS      read-only
        STATUS          current
        DESCRIPTION     ""
        ::=  {  msagTrapObjectMib  7  }

    zxAnTrapSunit     OBJECT-TYPE
        SYNTAX          Integer32
        MAX-ACCESS      read-only
        STATUS          current
        DESCRIPTION     ""
        ::=  {  msagTrapObjectMib  8  }

    zxAnTrapPort     OBJECT-TYPE
        SYNTAX          Integer32
        MAX-ACCESS      read-only
        STATUS          current
        DESCRIPTION     ""
        ::=  {  msagTrapObjectMib  9  } 
    msagTrapReason     OBJECT-TYPE
        SYNTAX          Integer32
        MAX-ACCESS      read-only
        STATUS          current
        DESCRIPTION     ""
        ::=  {  msagTrapObjectMib  10  } 
        
    msagTrapLinkState  OBJECT-TYPE
        SYNTAX          Integer32
        MAX-ACCESS      read-only
        STATUS          current
        DESCRIPTION     ""
        ::=  {  msagTrapObjectMib  11  } 
        
    msagTrapMgcNo     OBJECT-TYPE
        SYNTAX          Integer32
        MAX-ACCESS      read-only
        STATUS          current
        DESCRIPTION     ""
        ::=  {  msagTrapObjectMib  12  } 

    msagTrapSLN     OBJECT-TYPE
        SYNTAX          Integer32
        MAX-ACCESS      read-only
        STATUS          current
        DESCRIPTION     ""
        ::=  {  msagTrapObjectMib  13  } 

    msagTrapFlag     OBJECT-TYPE
        SYNTAX          Integer32
        MAX-ACCESS      read-only
        STATUS          current
        DESCRIPTION     ""
        ::=  {  msagTrapObjectMib  14  } 
        
    msagTrapErrcode     OBJECT-TYPE
        SYNTAX          Integer32
        MAX-ACCESS      read-only
        STATUS          current
        DESCRIPTION     ""
        ::=  {  msagTrapObjectMib  15  } 
        
    msagTrapIpAddress     OBJECT-TYPE
        SYNTAX          Integer32
        MAX-ACCESS      read-only
        STATUS          current
        DESCRIPTION     ""
        ::=  {  msagTrapObjectMib  16  } 
        
    msagTrapBETime     OBJECT-TYPE
        SYNTAX          Integer32
        MAX-ACCESS      read-only
        STATUS          current
        DESCRIPTION     ""
        ::=  {  msagTrapObjectMib  17  } 
    zxAnTrapInfoType OBJECT-TYPE
        SYNTAX          INTEGER{ei2(1),ei3(2),lsl(3),rsy(4),fj(5)}
        MAX-ACCESS      read-only
        STATUS  current
        DESCRIPTION "        EI2, /*Error Indication 2*/
        EI3, /*Error Indication 3*/
        LSL, /*Loss of Signal Level*/
        RSY, /*Re-Synchronization*/
        FJ   /*Frame Jump*/"
       ::= { msagTrapObjectMib 18 }
                                                
    msagTrapUnitNo     OBJECT-TYPE
        SYNTAX          Integer32
        MAX-ACCESS      read-only
        STATUS          current
        DESCRIPTION     ""
        ::=  {  msagTrapObjectMib  19  } 
        
    msagTrapPcmNo     OBJECT-TYPE
        SYNTAX          Integer32
        MAX-ACCESS      read-only
        STATUS          current
        DESCRIPTION     ""
        ::=  {  msagTrapObjectMib  20  } 
        
    msagTrapReasionValue     OBJECT-TYPE
        SYNTAX          Integer32
        MAX-ACCESS      read-only
        STATUS          current
        DESCRIPTION     ""
        ::=  {  msagTrapObjectMib  21  }         
        
    msagTrapRack     OBJECT-TYPE
        SYNTAX          Integer32
        MAX-ACCESS      read-only
        STATUS          current
        DESCRIPTION     ""
        ::=  {  msagTrapObjectMib  22  }      
        
     msagTrapShelf     OBJECT-TYPE
        SYNTAX          Integer32
        MAX-ACCESS      read-only
        STATUS          current
        DESCRIPTION     ""
        ::=  {  msagTrapObjectMib  23  } 
        
    msagTrapSlot     OBJECT-TYPE
        SYNTAX          Integer32
        MAX-ACCESS      read-only
        STATUS          current
        DESCRIPTION     ""
        ::=  {  msagTrapObjectMib  24  } 

    msagTrapV5InterId     OBJECT-TYPE
        SYNTAX          Integer32
        MAX-ACCESS      read-only
        STATUS          current
        DESCRIPTION     ""
        ::=  {  msagTrapObjectMib  25  }         
        
    msagTrapDLProType     OBJECT-TYPE
        SYNTAX          Integer32
        MAX-ACCESS      read-only
        STATUS          current
        DESCRIPTION     ""
        ::=  {  msagTrapObjectMib  26  }      
        
     msagTrapCurEvent     OBJECT-TYPE
        SYNTAX          Integer32
        MAX-ACCESS      read-only
        STATUS          current
        DESCRIPTION     ""
        ::=  {  msagTrapObjectMib  27 } 
        
    msagTrapCurState     OBJECT-TYPE
        SYNTAX          Integer32
        MAX-ACCESS      read-only
        STATUS          current
        DESCRIPTION     ""
        ::=  {  msagTrapObjectMib  28  } 
        
    msagTrapParaLinkId     OBJECT-TYPE
        SYNTAX          Integer32
        MAX-ACCESS      read-only
        STATUS          current
        DESCRIPTION     ""
        ::=  {  msagTrapObjectMib  29  }         


    msagQosAlarmType     OBJECT-TYPE
        SYNTAX          Integer32
        MAX-ACCESS      read-only
        STATUS          current
        DESCRIPTION     ""
        ::=  {  msagTrapObjectMib  30  } 

    msagQosAlarmDetail     OBJECT-TYPE
        SYNTAX          Integer32
        MAX-ACCESS      read-only
        STATUS          current
        DESCRIPTION     ""
        ::=  {  msagTrapObjectMib  31  }         
    msagTrapPort          OBJECT-TYPE
        SYNTAX          Integer32
        MAX-ACCESS      read-only
        STATUS          current
        DESCRIPTION     ""
        ::=  {  msagTrapObjectMib  32  }               
END

--------------------------------------------------------------------------
-- File Name : ZTE-AN-VDSL-MIB.mib
-- Date      : 2007-08-15
-- Author    : ZTE Nms dept.

--
-- Zte VDSL Mib for Access Node
--------------------------------------------------------------------------
ZTE-AN-XDSL2-MIB DEFINITIONS ::= BEGIN

    IMPORTS
       MODULE-IDENTITY, OBJECT-TYPE, Unsigned32,Integer32, Counter32,
       NOTIFICATION-TYPE                                        FROM SNMPv2-SMI
       enterprises                                              FROM SNMPv2-SMI
       ifIndex                                                  FROM IF-MIB
       DisplayString,TEXTUAL-CONVENTION,TruthValue,RowStatus    FROM SNMPv2-TC
       HCPerfIntervalThreshold,HCPerfTimeElapsed       FROM HC-PerfHist-TC-MIB
       SnmpAdminString                                 FROM SNMP-FRAMEWORK-MIB
       
       xdsl2PMLineCurrEntry, xdsl2PMLineHist15MinEntry          FROM  VDSL2-LINE-MIB
       Xdsl2Unit, Xdsl2Direction, Xdsl2Band, Xdsl2TransmissionModeType,
       Xdsl2RaMode,Xdsl2InitResult,Xdsl2OperationModes,Xdsl2PowerMngState,
       Xdsl2ConfPmsForce, Xdsl2LinePmMode,
       Xdsl2LineLdsf,Xdsl2LdsfResult,Xdsl2SymbolProtection,
       Xdsl2MaxBer,Xdsl2ScMaskDs,Xdsl2ScMaskUs,Xdsl2CarMask,
       Xdsl2PsdMaskDs, Xdsl2PsdMaskUs, Xdsl2Tssi,
       Xdsl2LastTransmittedState, Xdsl2LineStatus,
       Xdsl2ChAtmStatus, Xdsl2ChPtmStatus, Xdsl2UpboKLF, Xdsl2BandUs,
       Xdsl2LineProfiles, Xdsl2LineUs0Mask, Xdsl2LineClassMask,
       Xdsl2LineLimitMask, Xdsl2LineUs0Disable, Xdsl2RfiBands,
       Xdsl2LineSnrMode      FROM   VDSL2-LINE-TC-MIB;

    zxAnXdsl2Mib MODULE-IDENTITY
        LAST-UPDATED    "200708161500Z"
        ORGANIZATION "ZTE Corporation"
        CONTACT-INFO "ZTE NMS dept. 
                      Su Chunshan   68896292 "
        DESCRIPTION  "This MIB defines managed objects of zte xDSL mgmt . "
        ::= { zxAn 1001 }
         
    zte OBJECT IDENTIFIER ::= { enterprises 3902 }
    zxAn OBJECT IDENTIFIER ::= { zte 1015 } 
         
    zxAnXdsl2Objects            OBJECT IDENTIFIER  ::= {zxAnXdsl2Mib 1}
    zxAnXdsl2TrapObjects        OBJECT IDENTIFIER  ::= {zxAnXdsl2Mib 3}

    zxAnXdsl2GlobalObjects      OBJECT IDENTIFIER  ::= {zxAnXdsl2Objects 1}
    zxAnXdsl2Line               OBJECT IDENTIFIER  ::= {zxAnXdsl2Objects 2}
    zxAnXdsl2LineProfile        OBJECT IDENTIFIER  ::= {zxAnXdsl2Objects 3}
    zxAnXdsl2AlarmProfile       OBJECT IDENTIFIER  ::= {zxAnXdsl2Objects 4}
    zxAnXdsl2PMLine             OBJECT IDENTIFIER  ::= {zxAnXdsl2Objects 5}



--------------------------------------------------------------------------
-- Following objects are defined.
-- 1.zxAnXdsl2LineTable
-- 2.zxAnXdsl2BaseConfProfTable
-- 3.zxAnXdsl2ServiceConfProfTable
-- 4.zxAnXdsl2DpboConfProfTable
-- 5.zxAnXdsl2UpboConfProfTable
-- 6.zxAnXdsl2AlmThreshPrfTable
-- 7.zxAnXdsl2PMLineCurrTable
-- 7.1 zxAnXdsl2PMLineHist15MinTable


-- 8.xdsl2LineBandTable         see VDSL2-LINE-MIB xdsl2LineBandTable
-- 9.xdsl2ChannelStatusTable    see VDSL2-LINE-MIB xdsl2ChannelStatusTable
-- 10.xdsl2SCStatusTable        see VDSL2-LINE-MIB xdsl2SCStatusTable
-- 11.xdsl2LineSegmentTable     see VDSL2-LINE-MIB xdsl2LineSegmentTable
-- 12.xdsl2SCStatusSegmentTable see VDSL2-LINE-MIB xdsl2SCStatusSegmentTable

-- 13.xdsl2LineInventoryTable   see VDSL2-LINE-MIB xdsl2LineInventoryTable
-- 14.xdsl2PMLineCurrTable      see VDSL2-LINE-MIB xdsl2PMLineCurrTable
-- 15.xdsl2PMLineCurrInitTable  see VDSL2-LINE-MIB xdsl2PMLineCurrInitTable
-- 16.xdsl2PMChCurrTable        see VDSL2-LINE-MIB xdsl2PMChCurrTable

-- 17.Trap
--------------------------------------------------------------------------



--------------------------------------------------------------------------
-- 1.zxAnXdsl2LineTable
--------------------------------------------------------------------------
    
    ZxAnXdsl2TransmissionModeType ::= TEXTUAL-CONVENTION
        STATUS      current
        DESCRIPTION
           "A set of xDSL line transmission modes, with one bit
            per mode.  The notes (F) and (L) denote Full-Rate
            and Lite/splitterless respectively:
               Bit 00 : Regional Std. (ANSI T1.413) (F)
               Bit 01 : Regional Std. (ETSI DTS/TM06006) (F)
               Bit 02 : G.992.1 POTS non-overlapped (F)
               Bit 03 : G.992.1 POTS overlapped (F)
               Bit 04 : G.992.1 ISDN non-overlapped (F)
               Bit 05 : G.992.1 ISDN overlapped (F)
               Bit 06 : G.992.1 TCM-ISDN non-overlapped (F)
               Bit 07 : G.992.1 TCM-ISDN overlapped (F)
               Bit 08 : G.992.2 POTS non-overlapped (L)
               Bit 09 : G.992.2 POTS overlapped (L)
               Bit 10 : G.992.2 with TCM-ISDN non-overlapped (L)
               Bit 11 : G.992.2 with TCM-ISDN overlapped (L)
               Bit 12 : G.992.1 TCM-ISDN symmetric (F) --- not in G.997.1
               Bit 13-17: Reserved
               Bit 18 : G.992.3 POTS non-overlapped (F)
               Bit 19 : G.992.3 POTS overlapped (F)
               Bit 20 : G.992.3 ISDN non-overlapped (F)
               Bit 21 : G.992.3 ISDN overlapped (F)
               Bit 22-23: Reserved
               Bit 24 : G.992.4 POTS non-overlapped (L)
               Bit 25 : G.992.4 POTS overlapped (L)
               Bit 26-27: Reserved
               Bit 28 : G.992.3 Annex I All-Digital non-overlapped (F)
               Bit 29 : G.992.3 Annex I All-Digital overlapped (F)
               Bit 30 : G.992.3 Annex J All-Digital non-overlapped (F)
               Bit 31 : G.992.3 Annex J All-Digital overlapped (F)
               Bit 32 : G.992.4 Annex I All-Digital non-overlapped (L)
               Bit 33 : G.992.4 Annex I All-Digital overlapped (L)
               Bit 34 : G.992.3 Annex L POTS non-overlapped, mode 1,
                                        wide U/S (F)
               Bit 35 : G.992.3 Annex L POTS non-overlapped, mode 2,
                                        narrow U/S(F)
               Bit 36 : G.992.3 Annex L POTS overlapped, mode 3,
                                        wide U/S (F)
               Bit 37 : G.992.3 Annex L POTS overlapped, mode 4,
                                        narrow U/S (F)
               Bit 38 : G.992.3 Annex M POTS non-overlapped (F)
               Bit 39 : G.992.3 Annex M POTS overlapped (F)
               Bit 40 : G.992.5 POTS non-overlapped (F)
               Bit 41 : G.992.5 POTS overlapped (F)
               Bit 42 : G.992.5 ISDN non-overlapped (F)
               Bit 43 : G.992.5 ISDN overlapped (F)
               Bit 44-45: Reserved
               Bit 46 : G.992.5 Annex I All-Digital non-overlapped (F)
               Bit 47 : G.992.5 Annex I All-Digital overlapped (F)
               Bit 48 : G.992.5 Annex J All-Digital non-overlapped (F)
               Bit 49 : G.992.5 Annex J All-Digital overlapped (F)
               Bit 50 : G.992.5 Annex M POTS non-overlapped (F)
               Bit 51 : G.992.5 Annex M POTS overlapped (F)
               Bit 52 : Reserved
               Bit 53 : G.993.2 Annex A Protection
               Bit 54 : G.993.2 Annex B Protection
               Bit 55 : G.993.2 Annex C Protection
               Bit 56 : G.993.2 Annex A
               Bit 57 : G.993.2 Annex B
               Bit 58 : G.993.2 Annex C
               Bit 59-60: Reserved
               Bit 61 : G.993.5 Annex A
               Bit 62 : G.993.5 Annex B
               Bit 63 : G.993.5 Annex C"
        SYNTAX      BITS {
                       ansit1413(0),
                       etsi(1),
                       g9921PotsNonOverlapped(2),
                       g9921PotsOverlapped(3),
                       g9921IsdnNonOverlapped(4),
                       g9921isdnOverlapped(5),
                       g9921tcmIsdnNonOverlapped(6),
                       g9921tcmIsdnOverlapped(7),
                       g9922potsNonOverlapeed(8),
                       g9922potsOverlapped(9),
                       g9922tcmIsdnNonOverlapped(10),
                       g9922tcmIsdnOverlapped(11),
                       g9921tcmIsdnSymmetric(12),
                       reserved1(13),
                       reserved2(14),
                       reserved3(15),
                       reserved4(16),
                       reserved5(17),
                       g9923PotsNonOverlapped(18),
                       g9923PotsOverlapped(19),
                       g9923IsdnNonOverlapped(20),
                       g9923isdnOverlapped(21),
                       reserved6(22),
                       reserved7(23),
                       g9924potsNonOverlapeed(24),
                       g9924potsOverlapped(25),
                       reserved8(26),
                       reserved9(27),
                       g9923AnnexIAllDigNonOverlapped(28),
                       g9923AnnexIAllDigOverlapped(29),
                       g9923AnnexJAllDigNonOverlapped(30),
                       g9923AnnexJAllDigOverlapped(31),
                       g9924AnnexIAllDigNonOverlapped(32),
                       g9924AnnexIAllDigOverlapped(33),
                       g9923AnnexLMode1NonOverlapped(34),
                       g9923AnnexLMode2NonOverlapped(35),
                       g9923AnnexLMode3Overlapped(36),
                       g9923AnnexLMode4Overlapped(37),
                       g9923AnnexMPotsNonOverlapped(38),
                       g9923AnnexMPotsOverlapped(39),
                       g9925PotsNonOverlapped(40),
                       g9925PotsOverlapped(41),
                       g9925IsdnNonOverlapped(42),
                       g9925isdnOverlapped(43),
                       reserved10(44),
                       reserved11(45),
                       g9925AnnexIAllDigNonOverlapped(46),
                       g9925AnnexIAllDigOverlapped(47),
                       g9925AnnexJAllDigNonOverlapped(48),
                       g9925AnnexJAllDigOverlapped(49),
                       g9925AnnexMPotsNonOverlapped(50),
                       g9925AnnexMPotsOverlapped(51),
                       reserved12(52),
                       g9932AnnexAProtection(53),
                       g9932AnnexBProtection(54),
                       g9932AnnexCProtection(55),
                       g9932AnnexA(56),
                       g9932AnnexB(57),
                       g9932AnnexC(58),
                       reserved16(59),
                       reserved17(60),
                       g9935AnnexA(61),
                       g9935AnnexB(62),
                       g9935AnnexC(63)
                    }
        
    zxAnXdsl2LineTable  OBJECT-TYPE
        SYNTAX      SEQUENCE  OF  ZxAnXdsl2LineEntry
        MAX-ACCESS  not-accessible
        STATUS      current
        DESCRIPTION
          "The table zxAnXdsl2LineTable contains configuration,
           command and status parameters of the VDSL2/ADSL/ADSL2
           or ADSL2+ line.
           The index of this table is an interface index where the
           interface has an ifType of vdsl2(xxx).
    
           Several objects in this table MUST be maintained in a
            persistent manner. "
        ::= { zxAnXdsl2Line 1 }
    
    zxAnXdsl2LineEntry  OBJECT-TYPE
        SYNTAX      ZxAnXdsl2LineEntry
        MAX-ACCESS  not-accessible
        STATUS      current
        DESCRIPTION
           "The table zxAnXdsl2LineTable contains configuration,
           commands and status parameters of the VDSL2/ADSL/ADSL2
           or ADSL2+ line."
        INDEX  { ifIndex }
        ::= { zxAnXdsl2LineTable 1 }
     
    ZxAnXdsl2LineEntry  ::=
        SEQUENCE {
           zxAnXdsl2LineBaseConfProfile         DisplayString,
           zxAnXdsl2LineSrvcConfProfile         DisplayString,
           zxAnXdsl2LineDpboConfProfile         DisplayString,
           zxAnXdsl2LineUpboConfProfile         DisplayString,
           zxAnXdsl2LineAlmThreshPrfName        DisplayString,
           zxAnXdsl2LineCmndConfPmsf            Xdsl2ConfPmsForce,
           zxAnXdsl2LineCmndConfLdsf            Xdsl2LineLdsf,
           zxAnXdsl2LineCmndConfLdsfFailReason  Xdsl2LdsfResult,
           zxAnXdsl2LineCmndAutomodeColdStart   TruthValue,
           zxAnXdsl2LineStatusXtuTransSys       ZxAnXdsl2TransmissionModeType,
           zxAnXdsl2LineStatusPwrMngState       Xdsl2PowerMngState,
           zxAnXdsl2LineStatusInitResult        INTEGER,
           zxAnXdsl2LineStatusLastStateDs       Xdsl2LastTransmittedState,
           zxAnXdsl2LineStatusLastStateUs       Xdsl2LastTransmittedState,
           zxAnXdsl2LineStatusXtur              BITS,
           zxAnXdsl2LineStatusXtuc              BITS,
           zxAnXdsl2LineStatusAttainableRateDs  Unsigned32,
           zxAnXdsl2LineStatusAttainableRateUs  Unsigned32,
           zxAnXdsl2LineStatusActPsdDs          Integer32,
           zxAnXdsl2LineStatusActPsdUs          Integer32,
           zxAnXdsl2LineStatusActAtpDs          Integer32,
           zxAnXdsl2LineStatusActAtpUs          Integer32,
           zxAnXdsl2LineStatusActStandardPrf    INTEGER,
           zxAnXdsl2LineDataPathType            INTEGER,
           zxAnXdsl2LineStatusActLimitMask      INTEGER,
           --zxAnXdsl2LineStatusActUs0Mask      Xdsl2LineUs0Mask,
           zxAnXdsl2LineStatusActSnrModeDs      Xdsl2LineSnrMode,
           zxAnXdsl2LineStatusActSnrModeUs      Xdsl2LineSnrMode,
           zxAnXdsl2LineStatusElectricalLength  Unsigned32,
           zxAnXdsl2LineStatusTrellisDs         TruthValue,
           zxAnXdsl2LineStatusTrellisUs         TruthValue,
           zxAnXdsl2LineStatusActualCe          Unsigned32,
           zxAnXdsl2LineStatusOperState         INTEGER,
           zxAnXdsl2LineStatusActDataPathType   INTEGER,
           zxAnXdsl2LineCmndPMReset             BITS,           
           zxAnXdsl2LineExtConfProfile          DisplayString,
           
           zxAnXdsl2LineStatusLnAttenDs         Integer32,
           zxAnXdsl2LineStatusLnAttenUs         Integer32,
           zxAnXdsl2LineStatusSigAttenDs        Integer32,
           zxAnXdsl2LineStatusSigAttenUs        Integer32,
           zxAnXdsl2LineStatusSnrMarginDs       Integer32,
           zxAnXdsl2LineStatusSnrMarginUs       Integer32,
           
           zxAnXdsl2LineLofStatsDs              Counter32,
           zxAnXdsl2LineLofStatsUs              Counter32,
           zxAnXdsl2LineLolStatsDs              Counter32,
           zxAnXdsl2LineLolStatsUs              Counter32,
           zxAnXdsl2LineLprStatsDs              Counter32,
           zxAnXdsl2LineLprStatsUs              Counter32
        }
     
     zxAnXdsl2LineBaseConfProfile  OBJECT-TYPE
        SYNTAX      DisplayString (SIZE(1..32))
        MAX-ACCESS  read-write
        STATUS      current
        DESCRIPTION
           "The value of this object identifies the row in the xDSL2
           Line Basic Profile Table, (zxAnZxAnXdsl2BaseConfProfTable),
            which applies for this line.
     
            This object MUST be maintained in a persistent manner."
        REFERENCE    "DSL Forum TR-129, paragraph #5.1"
        DEFVAL       { "DEFVAL" }
        ::= { zxAnXdsl2LineEntry 1 }



     zxAnXdsl2LineSrvcConfProfile  OBJECT-TYPE
        SYNTAX      DisplayString (SIZE(1..32))
        MAX-ACCESS  read-write
        STATUS      current
        DESCRIPTION
           "The value of this object identifies the row in the xDSL2
           Line Service Profile Table, (zxAnZxAnXdsl2ServiceConfProfTable),
            which applies for this line.
     
            This object MUST be maintained in a persistent manner."
        REFERENCE    "DSL Forum TR-129, paragraph #5.1"
        DEFVAL       { "DEFVAL" }
        ::= { zxAnXdsl2LineEntry 2 }
     
     
     zxAnXdsl2LineDpboConfProfile  OBJECT-TYPE
        SYNTAX      DisplayString (SIZE(1..32))
        MAX-ACCESS  read-write
        STATUS      current
        DESCRIPTION
           "The value of this object identifies the row in the xDSL2
           Line Dpbo Profile Table, (zxAnZxAnXdsl2DpboConfProfTable),
            which applies for this line.
     
            This object MUST be maintained in a persistent manner."
        REFERENCE    "DSL Forum TR-129, paragraph #5.1"
        DEFVAL       { "DEFVAL" }
        ::= { zxAnXdsl2LineEntry 3 }
     

     zxAnXdsl2LineUpboConfProfile  OBJECT-TYPE
        SYNTAX      DisplayString (SIZE(1..32))
        MAX-ACCESS  read-write
        STATUS      current
        DESCRIPTION
           "The value of this object identifies the row in the xDSL2
           Line Upbo Profile Table, (zxAnXdsl2UpboConfProfTable),
            which applies for this line.
     
            This object MUST be maintained in a persistent manner."
        REFERENCE    "DSL Forum TR-129, paragraph #5.1"
        DEFVAL       { "DEFVAL" }
        ::= { zxAnXdsl2LineEntry 4 }
     
     
     zxAnXdsl2LineAlmThreshPrfName  OBJECT-TYPE
        SYNTAX      DisplayString (SIZE(1..32))
        MAX-ACCESS  read-write
        STATUS      current
        DESCRIPTION
           "The value of this object identifies the row in the xDSL2
           Line
           Alarm Configuration Profile Table,
           (zxAnXdsl2LineAlarmConfProfTable), which applies to this line.
     
           This object MUST be maintained in a persistent manner."
        REFERENCE    "DSL Forum TR-129, paragraph #5.1"
        DEFVAL       { "DEFVAL" }
        ::= { zxAnXdsl2LineEntry 5 }
     
     zxAnXdsl2LineCmndConfPmsf  OBJECT-TYPE
        SYNTAX      Xdsl2ConfPmsForce
        MAX-ACCESS  read-write
        STATUS      current
        DESCRIPTION
           "Power management state forced (PMSF).  Defines the line
            states to be forced by the near-end xTU on this line.
            The various possible values are:
               l3toL0 (0),
               l0toL2 (2),
               l0orL2toL3 (3).
     
            This object MUST be maintained in a persistent manner."
        REFERENCE    "ITU-T G.997.1, paragraph #7.3.1.1.3"
        DEFVAL       { l3toL0 }
        ::= { zxAnXdsl2LineEntry 6 }
     
     zxAnXdsl2LineCmndConfLdsf  OBJECT-TYPE
        SYNTAX      Xdsl2LineLdsf
        MAX-ACCESS  read-write
        STATUS      current
        DESCRIPTION
           "Loop diagnostics mode forced (LDSF).  Defines whether the
           line
            should be forced into the loop diagnostics mode by the
            near-end xTU on this line or only be responsive to loop
            diagnostics initiated by the far-end xTU.
     
            This object MUST be maintained in a persistent manner.
            However, in case the operator forces loop diagnostics mode
            then the access node should reset the object (inhibit) when
            loop diagnostics mode procedures are completed."
        REFERENCE    "ITU-T G.997.1, paragraph #7.3.1.1.8"
        DEFVAL       { inhibit }
        ::= { zxAnXdsl2LineEntry 7 }
     
     zxAnXdsl2LineCmndConfLdsfFailReason  OBJECT-TYPE
        SYNTAX      Xdsl2LdsfResult
        MAX-ACCESS  read-only
        STATUS      current
        DESCRIPTION
           "The status of the recent occasion the Loop diagnostics mode
            forced (LDSF) was issued for the associated line.  Possible
            values are:
               none        (1) - The default value in case LDSF was never
                                 requested for the associated line.
               success     (2) - The recent command completed
                                 successfully.
               inProgress  (3) - The Loop Diagnostics process is in
                                 progress.
               unsupported (4) - The NE or the line card doesn't support
                                 LDSF.
               cannotRun   (5) - The NE cannot initiate the command, due
                                 to a non specific reason.
               aborted     (6) - The Loop Diagnostics process aborted.
               failed      (7) - The Loop Diagnostics process failed.
               illegalMode (8) - The NE cannot initiate the command, due
                                 to the specific mode of the relevant
                                 line.
               adminUp     (9) - The NE cannot initiate the command, as
                                 the relevant line is administratively
                                 'Up'.
               tableFull   (10)- The NE cannot initiate the command, due
                                 to reaching the maximum number of rows
                                 in the results table.
               noResources (11)- The NE cannot initiate the command, due
                                 to lack of internal memory resources."
        DEFVAL       { none }
        ::= { zxAnXdsl2LineEntry 8 }
     
        zxAnXdsl2LineCmndAutomodeColdStart   OBJECT-TYPE
           SYNTAX      TruthValue
           MAX-ACCESS  read-write
           STATUS      current
           DESCRIPTION
              "Automode cold start forced.  This parameter is defined
               in order to improve testing of the performance of xTUs
               supporting automode when it is enabled in the MIB.
               Change the value of this parameter to 'true' indicates
               a change in loop conditions applied to the devices under
               test.  The xTUs shall reset any historical information
               used for automode and for shortening G.994.1 handshake
               and initialization.
     
               Automode is the case where multiple operation-modes are
               enabled through the zxAnXdsl2LConfProfXtuTransSysEna object
               in the line configuration profile being used for the
               line, and where the selection of the actual
               operation-mode depends not only on the common
               capabilities of both xTUs (as exchanged in G.994.1), but
               also on achievable data rates under given loop
               conditions.
     
               This object MUST be maintained in a persistent manner."
     
           REFERENCE    "ITU-T G.997.1, paragraph #7.3.1.1.10"
           DEFVAL       { false }
           ::= { zxAnXdsl2LineEntry 9 }
     
     
     zxAnXdsl2LineStatusXtuTransSys  OBJECT-TYPE
        SYNTAX      ZxAnXdsl2TransmissionModeType
        MAX-ACCESS  read-only
        STATUS      current
        DESCRIPTION
           "The xTU Transmission System (xTS) in use.
            It is coded in a bit-map representation with one bit set to
            '1' (the selected coding for the DSL line).  This
            parameter
            may be derived from the handshaking procedures defined in
            Recommendation G.994.1.  A set of xDSL line transmission
            modes, with one bit per mode.  "
        REFERENCE    "ITU-T G.997.1, paragraph #7.5.1.1"
        ::= { zxAnXdsl2LineEntry 10 }
     
     zxAnXdsl2LineStatusPwrMngState  OBJECT-TYPE
        SYNTAX      Xdsl2PowerMngState
        MAX-ACCESS  read-only
        STATUS      current
        DESCRIPTION
           "The current power management state.  One of four possible
            power management states:
               L0 - Synchronized and full transmission (i.e., Showtime),
               L1 - Low Power with reduced net data rate (G.992.2 only),
               L2 - Low Power with reduced net data rate (G.992.3 and
                    G.992.4 only),
               L3 - No power
           The various possible values are:l0(1), l1(2), l2(3), l3(4)."
        REFERENCE    "ITU-T G.997.1, paragraph #7.5.1.2"
           ::= { zxAnXdsl2LineEntry 11 }
     
     zxAnXdsl2LineStatusInitResult  OBJECT-TYPE
        SYNTAX      INTEGER {
                       noFail              (0),
                       configError         (1),
                       configNotFeasible   (2),
                       commFail            (3),
                       noPeerAtu           (4),
                       otherCause          (5),
                       protocolInitFailure (254)
                      }
        MAX-ACCESS  read-only
        STATUS      current
        DESCRIPTION
           "Indicates the result of the last full initialization
            performed on the line. It is an enumeration type with the following
            values: noFail(0), configError(1), configNotFeasible(2),
            commFail(3), noPeerAtu(4), otherCause(5), protocolInitFailure(254).
            
            noFail              (0)   - Successful initialization.
            configError         (1)   - Configuration failure.
            configNotFeasible   (2)   - Configuration details not supported.
            commFail            (3)   - Communication failure.
            noPeerAtu           (4)   - Peer ATU not detected.
            otherCause          (5)   - Other initialization failure.
            protocolInitFailure (254) - Protocol initialization failure.
            "
        ::= { zxAnXdsl2LineEntry 12 }
     
     zxAnXdsl2LineStatusLastStateDs  OBJECT-TYPE
        SYNTAX      Xdsl2LastTransmittedState
        MAX-ACCESS  read-only
        STATUS      current
        DESCRIPTION
           "The last successful transmitted initialization state in
            the downstream direction in the last full initialization
            performed on the line."
        REFERENCE    "ITU-T G.997.1, paragraph #7.5.1.4"
        ::= { zxAnXdsl2LineEntry 13 }
     
     zxAnXdsl2LineStatusLastStateUs  OBJECT-TYPE
        SYNTAX      Xdsl2LastTransmittedState
        MAX-ACCESS  read-only
        STATUS      current
        DESCRIPTION
           "The last successful transmitted initialization state in the
            upstream direction in the last full initialization performed
            on the line."
        REFERENCE    "ITU-T G.997.1, paragraph #7.5.1.5"
        ::= { zxAnXdsl2LineEntry 14 }
     
     zxAnXdsl2LineStatusXtur  OBJECT-TYPE
        SYNTAX BITS {
            noDefect            (0),
            lossOfFraming       (1),
            lossOfSignal        (2),
            lossOfPower         (3),
            unused              (4),
            lossOfSignalQuality (5)
           }
        MAX-ACCESS  read-only
        STATUS      current
        DESCRIPTION
           "Indicates current state (existing failures) of the xTU-R.
            This is a bit-map of possible conditions. 
            
            This BITS structure can report the following failures:
            
            noDefect            (0) - This bit position positively reports that 
                                      no defect or failure exist.
            
            lossOfFraming       (1) - xTU-R failure due to loss of frame 
                                      synchronization.
            
            lossOfSignal        (2) - xTU-R failure due to loss of signal.
            
            lossOfPower         (3) - xTU-R failure due to loss of power.Usually
                                      this failure may be reported for CPE units
                                      only.
            
            unused              (4) - This bit is never active on xTU-R.
                        
            lossOfSignalQuality (5) - Loss of Signal Quality is declared when 
                                      the Noise Margin falls below the Minimum 
                                      Noise Margin, or the bit-error-rate 
                                      exceeds 10^-7.
            "
        ::= { zxAnXdsl2LineEntry 15 }
     
     zxAnXdsl2LineStatusXtuc  OBJECT-TYPE
        SYNTAX BITS {
            noDefect            (0),
            lossOfFraming       (1),
            lossOfSignal        (2),
            lossOfPower         (3),
            initFailure         (4),
            lossOfSignalQuality (5),
            lossOfLink          (6)
           }
        MAX-ACCESS  read-only
        STATUS      current
        DESCRIPTION
           "Indicates current state (existing failures) of the xTU-C.
            This is a bit-map of possible conditions. 
            
            This BITS structure can report the following failures:
            
            noDefect            (0) - This bit position positively reports that
                                      no defect or failure exist.
            
            lossOfFraming       (1) - xTU-C failure due to loss of frame 
                                      synchronization.

            lossOfSignal        (2) - xTU-C failure due to loss of signal.
            
            lossOfPower         (3) - xTU-C failure due to loss of power.Usually
                                      this failure may be reported for CPE units
                                      only.

            initFailure         (4) - Recent initialization process failed.
            
            lossOfSignalQuality (5) - Loss of Signal Quality is declared when 
                                      the Noise Margin falls below the Minimum 
                                      Noise Margin, or the bit-error-rate 
                                      exceeds 10^-7.
            
            lossOfLink          (6) - xTU-C failure due to inability to link 
                                      with xTU-R.
            "
        ::= { zxAnXdsl2LineEntry 16 }
     
     zxAnXdsl2LineStatusAttainableRateDs  OBJECT-TYPE
        SYNTAX      Unsigned32
        UNITS       "kbps"
        MAX-ACCESS  read-only
        STATUS      current
        DESCRIPTION
           "Maximum Attainable Data Rate Downstream.
            The maximum downstream net data rate currently attainable by
            the xTU-C transmitter and the xTU-R receiver, coded in
            bit/s."
        REFERENCE    "ITU-T G.997.1, paragraph #7.5.1.12"
        ::= { zxAnXdsl2LineEntry 17 }
     
     zxAnXdsl2LineStatusAttainableRateUs  OBJECT-TYPE
        SYNTAX      Unsigned32
        UNITS       "kbps"
        MAX-ACCESS  read-only
        STATUS      current
        DESCRIPTION
           "Maximum Attainable Data Rate Upstream.
            The maximum upstream net data rate currently attainable by the
            xTU-R transmitter and the xTU-C receiver, coded in bit/s."
        REFERENCE    "ITU-T G.997.1, paragraph #7.5.1.13"
        ::= { zxAnXdsl2LineEntry 18 }
     
     zxAnXdsl2LineStatusActPsdDs OBJECT-TYPE
        SYNTAX      Integer32 (-900..0 | 2147483647)
        UNITS       "0.1 dBm/Hz"
        MAX-ACCESS  read-only
        STATUS      current
        DESCRIPTION
           "Actual Power Spectrum Density (PSD) Downstream.  The average
            downstream transmit PSD over the sub-carriers used for
            downstream.  It ranges from -900 to 0 units of 0.1 dB
            (Physical values are -90 to 0 dBm/Hz).
            A value of 0x7FFFFFFF (2147483647) indicates the measurement
            is out of range to be represented."
        REFERENCE    "ITU-T G.997.1, paragraph #7.5.1.14"
        ::= { zxAnXdsl2LineEntry 19 }
     
     zxAnXdsl2LineStatusActPsdUs OBJECT-TYPE
        SYNTAX      Integer32 (-900..0 | 2147483647)
        UNITS       "0.1 dBm/Hz"
        MAX-ACCESS  read-only
        STATUS      current
        DESCRIPTION
           "Actual Power Spectrum Density (PSD) Upstream.  The average
            upstream transmit PSD over the sub-carriers used for upstream.
            It ranges from -900 to 0 units of 0.1 dB (Physical values
            are -90 to 0 dBm/Hz).
            A value of 0x7FFFFFFF (2147483647) indicates the measurement
            is out of range to be represented."
        REFERENCE    "ITU-T G.997.1, paragraph #7.5.1.15"
        ::= { zxAnXdsl2LineEntry 20 }
     
     zxAnXdsl2LineStatusActAtpDs  OBJECT-TYPE
        SYNTAX      Integer32 (-310..310 | 2147483647)
        UNITS       "0.1 dBm"
        MAX-ACCESS  read-only
        STATUS      current
        DESCRIPTION
           "Actual Aggregate Transmit Power Downstream.  The total
           amount
            of transmit power delivered by the xTU-C at the U-C reference
            point, at the instant of measurement.  It ranges from -310 to
            310 units of 0.1 dB (Physical values are -31 to 31 dBm).
            A value of 0x7FFFFFFF (2147483647) indicates the measurement
            is out of range to be represented."
        REFERENCE    "ITU-T G.997.1, paragraph #7.5.1.16"
        ::= { zxAnXdsl2LineEntry 21 }
     
     zxAnXdsl2LineStatusActAtpUs  OBJECT-TYPE
        SYNTAX      Integer32 (-310..310 | 2147483647)
        UNITS       "0.1 dBm"
        MAX-ACCESS  read-only
        STATUS      current
        DESCRIPTION
           "Actual Aggregate Transmit Power Upstream.  The total amount
           of
            transmit power delivered by the xTU-R at the U-R
            reference point, at the instant of measurement.  It ranges
            from -310 to 310 units of 0.1 dB (Physical values are -31
            to 31 dBm).
            A value of 0x7FFFFFFF (2147483647) indicates the measurement
            is out of range to be represented."
        REFERENCE    "ITU-T G.997.1, paragraph #7.5.1.17"
        ::= { zxAnXdsl2LineEntry 22 }



    zxAnXdsl2LineStatusActStandardPrf  OBJECT-TYPE
        SYNTAX      INTEGER {
            g993_2_8A   (1), 
            g993_2_8B   (2), 
            g993_2_8C   (3), 
            g993_2_8D   (4), 
            g993_2_12A  (5), 
            g993_2_12B  (6), 
            g993_2_17A  (7), 
            g993_2_30A  (8) 
        }
        MAX-ACCESS  read-only
        STATUS      current
        DESCRIPTION
             "Actual Standard Profile used by this connection."
        ::= { zxAnXdsl2LineEntry 23 }


    zxAnXdsl2LineDataPathType  OBJECT-TYPE
        SYNTAX      INTEGER {
            atm(1), 
            ptm(2),
            stm(3),
            auto(4) -- negotiate automatically
        }
        MAX-ACCESS  read-write
        STATUS      current
        DESCRIPTION
             "Data path type of this line."
        ::= { zxAnXdsl2LineEntry 24 }


    zxAnXdsl2LineStatusActLimitMask  OBJECT-TYPE
        SYNTAX      INTEGER 
        {
            annexA_D32(0),
            annexA_D64(8),
            annexA_D128(16),

            annexB_B7_1_997_M1c_A_7    (32),
            annexB_B7_2_997_M1x_M_8    (33),
            annexB_B7_3_997_M1x_M      (34),
            annexB_B7_4_997_M2x_M_8    (35),
            annexB_B7_5_997_M2x_A      (36),
            annexB_B7_6_997_M2x_M      (37),
            annexB_B7_7_HPE17_M1_NUS0  (38),
            annexB_B7_8_HPE30_M1_NUS0  (39),
            annexB_B7_9_997E17_M2x_NUS0(40),
            annexB_B7_10_997E30_M2x_NUS0(41),
            
            annexB_B8_1_998_M1_x_A         (64),
            annexB_B8_2_998_M1x_B          (65),
            annexB_B8_3_998_M1x_NUS0       (66),
            annexB_B8_4_998_M2x_A          (67),
            annexB_B8_5_998_M2x_M          (68),
            annexB_B8_6_998_M2x_B          (69),
            annexB_B8_7_998_M2x_NUS0       (70),
            annexB_B8_8_998E17_M2x_NUS0    (71),
            annexB_B8_9_998E17_M2x_NUS0_M  (72),
            annexB_B8_10_998ADE17_M2x_NUS0_M(73),
            annexB_B8_11_998ADE17_M2x_A     (74),
            annexB_B8_12_998ADE17_M2x_B     (75),
            annexB_B8_13_998E30_M2x_NUS0    (76),
            annexB_B8_14_998E30_M2x_NUS0_M  (77),
            annexB_B8_15_998ADE30_M2x_NUS0_M(78),
            annexB_B8_16_998ADE30_M2x_NUS0_A(79),

            annexC_Pots(96),
            annexC_Tcm_Isdn(97)   
            }
       MAX-ACCESS  read-only
       STATUS      current
       DESCRIPTION
          "The Limit PSD mask and band plan in use.
           The configuration parameter xdsl2LConfProfLimitMask defines
           the set of allowed G.993.2 limit PSD masks.
           This parameter indicates the limit PSD mask in use on
           this line."
       REFERENCE    "ITU-T G.997.1, paragraph #7.5.1.3"
       DEFVAL       { {} }
       ::= { zxAnXdsl2LineEntry 25 }
    
--    zxAnXdsl2LineStatusActUs0Mask  OBJECT-TYPE
--       SYNTAX      Xdsl2LineUs0Mask
--       MAX-ACCESS  read-only
--       STATUS      current
--       DESCRIPTION
--          "The US0 PSD mask in use.
--           The configuration parameter xdsl2LConfProfUs0Mask defines
--           the set of allowed US0 PSD masks.
--           This parameter indicates the US0 PSD mask in use on
--           this line.
--           This parameter may be derived from the handshaking
--           procedures defined in ITU-T Rec. G.994.1."
--       REFERENCE    "ITU-T G.997.1, paragraph #7.5.1.4"
--       DEFVAL       { {} }
--       ::= { zxAnXdsl2LineEntry 26 }
    
    zxAnXdsl2LineStatusActSnrModeDs  OBJECT-TYPE
       SYNTAX      Xdsl2LineSnrMode
       MAX-ACCESS  read-only
       STATUS      current
       DESCRIPTION
          "This parameter indicates if the transmitter
           referred virtual noise is active on the line in the
           downstream direction.
           The configuration parameter xdsl2LConfProfSnrModeDs
           is used to configure referred virtual noise."
       REFERENCE    "ITU-T G.997.1, paragraph #7.5.1.15 (ACTSNRMODEds)"
       DEFVAL       { virtualNoiseDisabled }
       ::= { zxAnXdsl2LineEntry 26 }
    
    zxAnXdsl2LineStatusActSnrModeUs  OBJECT-TYPE
       SYNTAX      Xdsl2LineSnrMode
       MAX-ACCESS  read-only
       STATUS      current
       DESCRIPTION
          "This parameter indicates if the transmitter
           referred virtual noise is active on the line in the
           upstream direction.
           The configuration parameter xdsl2LConfProfSnrModeUs is
           used to configure referred virtual noise."
       REFERENCE    "ITU-T G.997.1, paragraph #7.5.1.18 (ACTSNRMODEus)"
       DEFVAL       { virtualNoiseDisabled }
       ::= { zxAnXdsl2LineEntry 27 }
    
    zxAnXdsl2LineStatusElectricalLength  OBJECT-TYPE
       SYNTAX      Unsigned32 (0..1280)
       UNITS       "0.1 dB"
       MAX-ACCESS  read-only
       STATUS      current
       DESCRIPTION
          "(UPBOKLE)
           This parameter contains the estimated electrical length
           expressed in dB at 1 MHz, kl0. This is the final electrical
           length that would have been sent from the VTU-O to VTU-R if
           the electrical length was not forced by the CO-MIB.
           The value ranges from 0 to 128 dB in steps of 0.1 dB."
       REFERENCE    "ITU-T G.997.1, paragraph #7.5.1.23"
       DEFVAL       { 0 }
       ::= { zxAnXdsl2LineEntry 28 }
    
    zxAnXdsl2LineStatusTrellisDs  OBJECT-TYPE
       SYNTAX      TruthValue
       MAX-ACCESS  read-only
       STATUS      current
       DESCRIPTION
          "This parameter reports whether trellis coding
           is in use in the downstream direction."
       REFERENCE    "ITU-T G.997.1, paragraph #7.5.1.30"
       DEFVAL       { false }
       ::= { zxAnXdsl2LineEntry 29 }
    
    zxAnXdsl2LineStatusTrellisUs  OBJECT-TYPE
       SYNTAX      TruthValue
       MAX-ACCESS  read-only
       STATUS      current
       DESCRIPTION
          "This parameter reports whether trellis coding
           is in use in the upstream direction."
       REFERENCE    "ITU-T G.997.1, paragraph #7.5.1.31"
       DEFVAL       { false }
       ::= { zxAnXdsl2LineEntry 30 }
    
    zxAnXdsl2LineStatusActualCe  OBJECT-TYPE
       SYNTAX      Unsigned32 (2..16)
       UNITS       "N/32 samples"
       MAX-ACCESS  read-only
       STATUS      current
       DESCRIPTION
          "(ACTUALCE)
           This parameter reports the cyclic extension
           used on the line. It is coded as an unsigned integer from
           2 to 16 in units of N/32 samples, where 2N is the IDFT size."
       REFERENCE    "ITU-T G.997.1, paragraph #7.5.1.32"
       DEFVAL       { 2 }
       ::= { zxAnXdsl2LineEntry 31 }

    zxAnXdsl2LineStatusOperState    OBJECT-TYPE
        SYNTAX      INTEGER 
        {
            idle(1), 
            handshake(2),
            training(3),
            testing(4), --  such as DELT,HYBRID,TX test.
            showtime(5) 
        }
        MAX-ACCESS  read-only
        STATUS      current
        DESCRIPTION
             "The operational status of the line."
        ::= { zxAnXdsl2LineEntry 32 }    

    zxAnXdsl2LineStatusActDataPathType  OBJECT-TYPE    
        SYNTAX      INTEGER {
            atm(1), 
            ptm(2),
            stm(3)
        }
        MAX-ACCESS  read-only
        STATUS      current
        DESCRIPTION
             "Actual data path type of this line."
        ::= { zxAnXdsl2LineEntry 33 } 
           
    zxAnXdsl2LineCmndPMReset  OBJECT-TYPE        
        SYNTAX BITS {  
             currentPerf(0) 
        }
        MAX-ACCESS  read-write
        STATUS      current
        DESCRIPTION
           "Reset the performance monitoring results of single line.           
           
            currentPerf(0) - reset the current performance monitoring results.
                         it will affect only current real-time PM object, 
                         such as zxAnXdsl2PMChCurrTransmittedBlks, 
                         zxAnXdsl2PMChCurrOverflowBlks and 
                         zxAnXdsl2PMChCurrErroredBlks.   
                                                  
                         The PM result of history will not be reset, 
                         and the current PM result of 15 minutes and 1 day 
                         will be unaffected too.                         
           "
        ::= { zxAnXdsl2LineEntry 34 }         
         
    zxAnXdsl2LineExtConfProfile  OBJECT-TYPE
        SYNTAX      DisplayString (SIZE(1..32))
        MAX-ACCESS  read-write
        STATUS      current
        DESCRIPTION
           "The value of this object identifies the row in the xDSL2
            Line Ext Profile Table, (zxAnXdsl2LnExtConfPrfTable),
            which applies for this line.
     
            This object MUST be maintained in a persistent manner."
        DEFVAL       { "VDEFVAL" }
        ::= { zxAnXdsl2LineEntry 35 }
        
    zxAnXdsl2LineStatusLnAttenDs  OBJECT-TYPE
        SYNTAX      Integer32(0..1270)
        UNITS       "0.1 dB"
        MAX-ACCESS  read-only
        STATUS      current
        DESCRIPTION
            "Downstream line Attenuation.
             When referring to a band in the downstream direction, it is the
             measured difference in the total power transmitted by the xTU-C
             and the total power received by the xTU-R over all sub-carriers
             of that band during initialization.

             When referring to a band in the upstream direction, it is the
             measured difference in the total power transmitted by the xTU-R
             and the total power received by the xTU-C over all sub-carriers
             of that band during initialization.

             Values range from 0 to 1270 in units of 0.1 dB (Physical values
             are 0 to 127 dB)."
        REFERENCE
            "ITU-T G.997.1, paragraph #7.5.1.9 (LATNds) 
             and paragraph #7.5.1.10 (LATNus)6"
        ::= { zxAnXdsl2LineEntry 36 }
        
    zxAnXdsl2LineStatusLnAttenUs  OBJECT-TYPE
        SYNTAX      Integer32(0..1270)
        UNITS       "0.1 dB"
        MAX-ACCESS  read-only
        STATUS      current
        DESCRIPTION
            "Upstream line Attenuation.
             When referring to a band in the downstream direction, it is the
             measured difference in the total power transmitted by the xTU-C
             and the total power received by the xTU-R over all sub-carriers
             of that band during initialization.

             When referring to a band in the upstream direction, it is the
             measured difference in the total power transmitted by the xTU-R
             and the total power received by the xTU-C over all sub-carriers
             of that band during initialization.

             Values range from 0 to 1270 in units of 0.1 dB (Physical values
             are 0 to 127 dB)."
        REFERENCE
            "ITU-T G.997.1, paragraph #7.5.1.9 (LATNds) 
             and paragraph #7.5.1.10 (LATNus)6"
        ::= { zxAnXdsl2LineEntry 37 }
        
    zxAnXdsl2LineStatusSigAttenDs  OBJECT-TYPE
        SYNTAX      Integer32(0..1270)
        UNITS       "0.1 dB"
        MAX-ACCESS  read-only
        STATUS      current
        DESCRIPTION
            "Downstream signal Attenuation.
             When referring to a band in the downstream direction, it is the
             measured difference in the total power transmitted by the xTU-C
             and the total power received by the xTU-R over all sub-carriers
             of that band during Showtime.
             
             When referring to a band in the upstream direction, it is the
             measured difference in the total power transmitted by the xTU-R
             and the total power received by the xTU-C over all sub-carriers
             of that band during Showtime.
             
             Values range from 0 to 1270 in units of 0.1 dB (Physical values
             are 0 to 127 dB)."
        REFERENCE
            "ITU-T G.997.1, paragraph #7.5.1.11 (SATNds) 
             and paragraph #7.5.1.12 (SATNus)"
        ::= { zxAnXdsl2LineEntry 38 }
        
    zxAnXdsl2LineStatusSigAttenUs  OBJECT-TYPE
        SYNTAX      Integer32(0..1270)
        UNITS       "0.1 dB"
        MAX-ACCESS  read-only
        STATUS      current
        DESCRIPTION
            "Upstream signal Attenuation.
             When referring to a band in the downstream direction, it is the
             measured difference in the total power transmitted by the xTU-C
             and the total power received by the xTU-R over all sub-carriers
             of that band during Showtime.
             
             When referring to a band in the upstream direction, it is the
             measured difference in the total power transmitted by the xTU-R
             and the total power received by the xTU-C over all sub-carriers
             of that band during Showtime.
             
             Values range from 0 to 1270 in units of 0.1 dB (Physical values
             are 0 to 127 dB)."
        REFERENCE
            "ITU-T G.997.1, paragraph #7.5.1.11 (SATNds) 
             and paragraph #7.5.1.12 (SATNus)"
        ::= { zxAnXdsl2LineEntry 39 }
        
    zxAnXdsl2LineStatusSnrMarginDs  OBJECT-TYPE
        SYNTAX      Integer32(-640..630)
        UNITS       "0.1 dB"
        MAX-ACCESS  read-only
        STATUS      current
        DESCRIPTION
            "SNR Margin is the maximum increase in dB of the noise power
             received at the XTU (xTU-R for a band in the downstream direction
             and xTU-C for a band in the upstream direction), such that
             the BER requirements are met for all bearer channels received
             at the XTU. Values range from -640 to 630 in units of 0.1 dB
             (Physical values are -64 to 63 dB)."
        REFERENCE
            "ITU-T G.997.1, paragraph #7.5.1.13 (SNRMds)
             and paragraph #7.5.1.14 (SNRMpbds) 
             and paragraph #7.5.1.16 (SNRMus) 
             and paragraph #7.5.1.17 (SNRMpbus)"             
        ::= { zxAnXdsl2LineEntry 40 }
    
    zxAnXdsl2LineStatusSnrMarginUs  OBJECT-TYPE
        SYNTAX      Integer32(-640..630)
        UNITS       "0.1 dB"
        MAX-ACCESS  read-only
        STATUS      current
        DESCRIPTION
            "SNR Margin is the maximum increase in dB of the noise power
             received at the XTU (xTU-R for a band in the downstream direction
             and xTU-C for a band in the upstream direction), such that
             the BER requirements are met for all bearer channels received
             at the XTU. Values range from -640 to 630 in units of 0.1 dB
             (Physical values are -64 to 63 dB)."
        REFERENCE
            "ITU-T G.997.1, paragraph #7.5.1.13 (SNRMds)
             and paragraph #7.5.1.14 (SNRMpbds) 
             and paragraph #7.5.1.16 (SNRMus) 
             and paragraph #7.5.1.17 (SNRMpbus)"
        ::= { zxAnXdsl2LineEntry 41 }
                
    zxAnXdsl2LineLofStatsDs  OBJECT-TYPE
        SYNTAX      Counter32
        MAX-ACCESS  read-only
        STATUS      current
        DESCRIPTION
            "Downstream count of times that there was LOF."
        REFERENCE    "ITU-T G.997.1, paragraph #7.2.1"
        ::= { zxAnXdsl2LineEntry 42 }
        
    zxAnXdsl2LineLofStatsUs  OBJECT-TYPE
        SYNTAX      Counter32
        MAX-ACCESS  read-only
        STATUS      current
        DESCRIPTION
            "Upstream count of times that there was LOF."
        REFERENCE    "ITU-T G.997.1, paragraph #7.2.1"
        ::= { zxAnXdsl2LineEntry 43 }
       
    zxAnXdsl2LineLolStatsDs  OBJECT-TYPE
        SYNTAX      Counter32
        MAX-ACCESS  read-only
        STATUS      current
        DESCRIPTION
            "Downstream count of times that there was LOL."
        REFERENCE    "ITU-T G.997.1, paragraph #7.2.1"
        ::= { zxAnXdsl2LineEntry 44 }
        
    zxAnXdsl2LineLolStatsUs  OBJECT-TYPE
        SYNTAX      Counter32
        MAX-ACCESS  read-only
        STATUS      current
        DESCRIPTION
            "Upstream count of times that there was LOF."
        REFERENCE    "ITU-T G.997.1, paragraph #7.2.1"
        ::= { zxAnXdsl2LineEntry 45 }
       
    zxAnXdsl2LineLprStatsDs  OBJECT-TYPE
        SYNTAX      Counter32
        MAX-ACCESS  read-only
        STATUS      current
        DESCRIPTION
            "Downstream count of times that there was LPR."
        REFERENCE    "ITU-T G.997.1, paragraph #7.2.1"
        ::= { zxAnXdsl2LineEntry 46 }
        
    zxAnXdsl2LineLprStatsUs  OBJECT-TYPE
        SYNTAX      Counter32
        MAX-ACCESS  read-only
        STATUS      current
        DESCRIPTION
            "Upstream count of times that there was LPR."
        REFERENCE    "ITU-T G.997.1, paragraph #7.2.1"
        ::= { zxAnXdsl2LineEntry 47 }

--------------------------------------------------------------------------
-- 2.zxAnXdsl2BaseConfProfTable
--------------------------------------------------------------------------
            
   zxAnXdsl2BaseConfProfTable  OBJECT-TYPE
        SYNTAX      SEQUENCE  OF  ZxAnXdsl2BaseConfProfEntry
        MAX-ACCESS  not-accessible
        STATUS      current
        DESCRIPTION
            "The table zxAnXdsl2BaseConfProfTable contains VDSL2/ADSL/
            ADSL2 and ADSL2+ basic configuration profile.
            Entries in this table MUST be maintained in a
            persistent manner."
        ::= { zxAnXdsl2LineProfile 1 }



   zxAnXdsl2BaseConfProfEntry  OBJECT-TYPE
        SYNTAX      ZxAnXdsl2BaseConfProfEntry
        MAX-ACCESS  not-accessible
        STATUS      current
        DESCRIPTION
         "The table zxAnXdsl2BaseConfProfTable contains VDSL2/ADSL/
          ADSL2 and ADSL2+ basic configuration profile.

          A default profile with an index of 'DEFVAL' will
          always exist and its parameters will be set to vendor-specific
          values, unless otherwise specified in this document"
        INDEX  { zxAnXdsl2BaseConfProfileName }
        ::= { zxAnXdsl2BaseConfProfTable 1 }

   ZxAnXdsl2BaseConfProfEntry  ::=
        SEQUENCE {
            zxAnXdsl2BaseConfProfileName            DisplayString,
            zxAnXdsl2LConfProfXtuTransSysEna        ZxAnXdsl2TransmissionModeType,
            zxAnXdsl2LConfProfStandardProfile       Xdsl2LineProfiles,
            zxAnXdsl2LConfProfLimitMask             BITS,
            zxAnXdsl2LConfProfUs0Disable            INTEGER,
            zxAnXdsl2LConfProfUs0Mask               Xdsl2LineUs0Mask,
            zxAnXdsl2LConfProfRfiBandsDs            Xdsl2RfiBands,
            zxAnXdsl2LConfProfVdsl2CarMask          Xdsl2CarMask,
            zxAnXdsl2LConfProfVdslMaxNomAtpDs       Unsigned32,
            zxAnXdsl2LConfProfVdslMaxNomAtpUs       Unsigned32,
            zxAnXdsl2LConfProfVdslMaxNomPsdDs       Integer32,
            zxAnXdsl2LConfProfVdslMaxNomPsdUs       Integer32,
            zxAnXdsl2LConfProfVdslMaxAggRxPwrUs     Integer32,
            zxAnXdsl2LConfProfAdslMaxNomAtpDs       Unsigned32,
            zxAnXdsl2LConfProfAdslMaxNomAtpUs       Unsigned32,
            zxAnXdsl2LConfProfAdslMaxNomPsdDs       Integer32,
            zxAnXdsl2LConfProfAdslMaxNomPsdUs       Integer32,
            zxAnXdsl2LConfProfAdslMaxAggRxPwrUs     Integer32,
            zxAnXdsl2LConfProfScMaskDs              Xdsl2ScMaskDs,
            zxAnXdsl2LConfProfScMaskUs              Xdsl2ScMaskUs,
            zxAnXdsl2LConfProfRaUsNrmDs             Unsigned32,
            zxAnXdsl2LConfProfRaUsNrmUs             Unsigned32,
            zxAnXdsl2LConfProfRaUsTimeDs            Unsigned32,
            zxAnXdsl2LConfProfRaUsTimeUs            Unsigned32,
            zxAnXdsl2LConfProfRaDsNrmsDs            Unsigned32,
            zxAnXdsl2LConfProfRaDsNrmsUs            Unsigned32,
            zxAnXdsl2LConfProfRaDsTimeDs            Unsigned32,
            zxAnXdsl2LConfProfRaDsTimeUs            Unsigned32,
            zxAnXdsl2LConfProfMsgMinUs              Unsigned32,
            zxAnXdsl2LConfProfMsgMinDs              Unsigned32,
            zxAnXdsl2LConfProfPmMode                Xdsl2LinePmMode,
            zxAnXdsl2LConfProfL0Time                Unsigned32,
            zxAnXdsl2LConfProfL2Time                Unsigned32,
            zxAnXdsl2LConfProfL2Atpr                Unsigned32,
            zxAnXdsl2LConfProfL2Atprt               Unsigned32,
            zxAnXdsl2LConfProfPsdMaskDs             Xdsl2PsdMaskDs,
            zxAnXdsl2LConfProfPsdMaskUs             Xdsl2PsdMaskUs,
            zxAnXdsl2LConfProfPsdMaskSelectUs       Unsigned32,
            zxAnXdsl2LConfProfTrellisDs             INTEGER,
            zxAnXdsl2LConfProfTrellisUs             INTEGER, 
            zxAnXdsl2LConfProfBitswapDs             INTEGER,
            zxAnXdsl2LConfProfBitswapUs             INTEGER,
            zxAnXdsl2LConfProfRetrainMode           INTEGER,
            zxAnXdsl2LconfProfSnrModeDs             INTEGER,
            zxAnXdsl2LconfProfSnrModeUs             INTEGER,
            zxAnXdsl2LConfProfTxRefVNDs             OCTET STRING ,
            zxAnXdsl2LConfProfTxRefVNUs             OCTET STRING ,
            zxAnXdsl2Ch1ConfProfMinResDataRateDs    Unsigned32,
            zxAnXdsl2Ch1ConfProfMinResDataRateUs    Unsigned32,
            zxAnXdsl2Ch1ConfProfMinDataRateLowPwrDs Unsigned32,
            zxAnXdsl2Ch1ConfProfMaxBerDs            Xdsl2MaxBer,
            zxAnXdsl2Ch1ConfProfMaxBerUs            Xdsl2MaxBer,
            zxAnXdsl2Ch1ConfProfImaEnabled          TruthValue,
            zxAnXdsl2Ch2ConfProfMinResDataRateDs    Unsigned32,
            zxAnXdsl2Ch2ConfProfMinResDataRateUs    Unsigned32,
            zxAnXdsl2Ch2ConfProfMinDataRateLowPwrDs Unsigned32,
            zxAnXdsl2Ch2ConfProfMaxBerDs            Xdsl2MaxBer,
            zxAnXdsl2Ch2ConfProfMaxBerUs            Xdsl2MaxBer,
            zxAnXdsl2Ch2ConfProfImaEnabled          TruthValue,
            zxAnXdsl2LConfProfRowStatus             RowStatus
        }
         
    zxAnXdsl2BaseConfProfileName  OBJECT-TYPE
        SYNTAX      DisplayString (SIZE(1..32))
        MAX-ACCESS  not-accessible
        STATUS      current
        DESCRIPTION
            "This object identifies a row in this table."
        ::= { zxAnXdsl2BaseConfProfEntry 1 }
        
                            
    zxAnXdsl2LConfProfXtuTransSysEna  OBJECT-TYPE
        SYNTAX      ZxAnXdsl2TransmissionModeType
        MAX-ACCESS  read-create
        STATUS      current
        DESCRIPTION
         "xTU Transmission System Enabling (xTSE).  A list of the
          different coding types enabled in this profile.  It is coded
          in a bit-map representation with 1 or more bits set.  A bit
          set to  '1' means that the xTUs may apply the respective
          coding for the DSL line.  A bit set to '0' means that
          the xTUs cannot apply the respective coding for the ADSL
          line.  All 'reserved' bits should be set to '0'."
        REFERENCE    "ITU-T G.997.1, paragraph 7.3.1.1.1"
        ::= { zxAnXdsl2BaseConfProfEntry 2 }


    zxAnXdsl2LConfProfStandardProfile  OBJECT-TYPE
        SYNTAX      Xdsl2LineProfiles
        MAX-ACCESS  read-create
        STATUS      current
        DESCRIPTION
            "The set of profiles which allows the transceivers to support 
            a subset of allowed settings, as defined in G.993.2 Recommendation."
        ::= { zxAnXdsl2BaseConfProfEntry 3 }
      

    zxAnXdsl2LConfProfLimitMask  OBJECT-TYPE
        SYNTAX      BITS {
            annexA_D32(0),
            annexA_D64(8),
            annexA_D128(16),

            annexB_B7_1_997_M1c_A_7    (32),
            annexB_B7_2_997_M1x_M_8    (33),
            annexB_B7_3_997_M1x_M      (34),
            annexB_B7_4_997_M2x_M_8    (35),
            annexB_B7_5_997_M2x_A      (36),
            annexB_B7_6_997_M2x_M      (37),
            annexB_B7_7_HPE17_M1_NUS0  (38),
            annexB_B7_8_HPE30_M1_NUS0  (39),
            annexB_B7_9_997E17_M2x_NUS0(40),
            annexB_B7_10_997E30_M2x_NUS0(41),
            
            annexB_B8_1_998_M1_x_A         (64),
            annexB_B8_2_998_M1x_B          (65),
            annexB_B8_3_998_M1x_NUS0       (66),
            annexB_B8_4_998_M2x_A          (67),
            annexB_B8_5_998_M2x_M          (68),
            annexB_B8_6_998_M2x_B          (69),
            annexB_B8_7_998_M2x_NUS0       (70),
            annexB_B8_8_998E17_M2x_NUS0    (71),
            annexB_B8_9_998E17_M2x_NUS0_M  (72),
            annexB_B8_10_998ADE17_M2x_NUS0_M(73),
            annexB_B8_11_998ADE17_M2x_A     (74),
            annexB_B8_12_998ADE17_M2x_B     (75),
            annexB_B8_13_998E30_M2x_NUS0    (76),
            annexB_B8_14_998E30_M2x_NUS0_M  (77),
            annexB_B8_15_998ADE30_M2x_NUS0_M(78),
            annexB_B8_16_998ADE30_M2x_NUS0_A(79),

            annexC_Pots(96),
            annexC_Tcm_Isdn(97)
            }
        MAX-ACCESS  read-create
        STATUS      current
        DESCRIPTION
          " Limit Mask of the line. "
        ::= { zxAnXdsl2BaseConfProfEntry 4 }
       

    zxAnXdsl2LConfProfUs0Disable  OBJECT-TYPE
        SYNTAX      INTEGER {
                enable (1),
                disable (2)                    
            }
        MAX-ACCESS  read-create
        STATUS      current
        DESCRIPTION
            " Enable or disable the use of US0."
        ::= { zxAnXdsl2BaseConfProfEntry 5 }


    zxAnXdsl2LConfProfUs0Mask  OBJECT-TYPE
        SYNTAX      Xdsl2LineUs0Mask
        MAX-ACCESS  read-create
        STATUS      current
        DESCRIPTION
            "The set of profiles which allows the transceivers to support 
            a subset of allowed settings, as defined in G.993.2 Recommendation."
        ::= { zxAnXdsl2BaseConfProfEntry 6 }


    zxAnXdsl2LConfProfRfiBandsDs  OBJECT-TYPE
        SYNTAX      Xdsl2RfiBands
        MAX-ACCESS  read-create
        STATUS      current
        DESCRIPTION
            "RfiBands configured in the downstream."
        ::= { zxAnXdsl2BaseConfProfEntry 7 }



    zxAnXdsl2LConfProfVdsl2CarMask  OBJECT-TYPE
        SYNTAX      Xdsl2CarMask
        MAX-ACCESS  read-create
        STATUS      current
        DESCRIPTION
           "(VDSL2-CARMASK).
           VDSL2 specific Sub-carriers mask.  This configuration
           parameter defines the restrictions, additional to the band
           plan, to determine the set of subcarriers allowed for
           transmission in both upstream and downstream directions.
           The parameter shall describe the not masked subcarriers as
           one or more frequency bands. Each band is represented by
           start and stop subcarrier indices with a subcarrier
           spacing of 4.3125kHz. The valid range of subcarrier indices
           run from 0 to at least the index of the highest allowed
           subcarrier in both transmission directions among all
           profiles enabled by the parameter zxAnXdsl2LConfProfProfiles.
           Up to 32 bands may be specified. Other subcarriers shall
           be masked."
        REFERENCE    "ITU-T G.997.1, paragraph #7.3.1.2.8"
        ::= { zxAnXdsl2BaseConfProfEntry 8 }

        
     zxAnXdsl2LConfProfVdslMaxNomAtpDs  OBJECT-TYPE
        SYNTAX      Unsigned32 (0..255)
        UNITS       "0.1 dBm"
        MAX-ACCESS  read-create
        STATUS      current
        DESCRIPTION
           "(MAXNOMATPds).
            The maximum nominal aggregate transmit power in the
            downstream direction during initialization and Showtime.  It
            ranges from 0 to 255 units of 0.1 dBm (physical values are 0
            to 25.5 dBm)."
        REFERENCE    "ITU-T G.997.1, paragraph #7.3.1.2.3"
        DEFVAL       { 255 }
        ::= { zxAnXdsl2BaseConfProfEntry 9 }
     
     
     zxAnXdsl2LConfProfVdslMaxNomAtpUs  OBJECT-TYPE
        SYNTAX      Unsigned32 (0..255)
        UNITS       "0.1 dBm"
        MAX-ACCESS  read-create
        STATUS      current
        DESCRIPTION
           "(MAXNOMATPus).
            The maximum nominal aggregate transmit power in the upstream
            direction during initialization and Showtime.  It ranges from
            0 to 255 units of 0.1 dBm (physical values are 0 to 25.5
            dBm)."
        REFERENCE    "ITU-T G.997.1, paragraph #7.3.1.2.4"
        DEFVAL       { 255 }
        ::= { zxAnXdsl2BaseConfProfEntry 10 }
     
     zxAnXdsl2LConfProfVdslMaxNomPsdDs  OBJECT-TYPE
        SYNTAX      Integer32(-600..-300)
        UNITS       "0.1 dBm/Hz"
        MAX-ACCESS  read-create
        STATUS      current
        DESCRIPTION
           "(MAXNOMPSDds).
            The maximum nominal transmit PSD in the downstream
            direction during initialization and Showtime.  It ranges from
            -600 to -300 units of 0.1 dBm/Hz.  (physical values are -60 to
            -30 dBm/Hz).  "
        REFERENCE    "ITU-T G.997.1, paragraph #7.3.1.2.1"
        DEFVAL       { -300 }
       ::= { zxAnXdsl2BaseConfProfEntry 11 }
     
     zxAnXdsl2LConfProfVdslMaxNomPsdUs  OBJECT-TYPE
        SYNTAX      Integer32(-600..-300)
        UNITS       "0.1 dBm/Hz"
        MAX-ACCESS  read-create
        STATUS      current
        DESCRIPTION
           "(MAXNOMPSDus).
            The maximum nominal transmit PSD in the upstream direction
            during initialization and Showtime.  It ranges from -600 to
            -300 units of 0.1 dBm/Hz.  (physical values are -60 to
            -30 dBm/Hz).  "
        REFERENCE    "ITU-T G.997.1, paragraph #7.3.1.2.2"
        DEFVAL       { -300 }
        ::= { zxAnXdsl2BaseConfProfEntry 12 }
     
     
     
     zxAnXdsl2LConfProfVdslMaxAggRxPwrUs  OBJECT-TYPE
        SYNTAX      Integer32(-255..255 | 2147483647)
        UNITS       "0.1 dBm"
        MAX-ACCESS  read-create
        STATUS      current
        DESCRIPTION
           "(MAXRXPWRus).
            The maximum upstream aggregate receive power over the relevant
            set of sub-carriers.  The xTU-C should verify that the
            upstream power cutback is such that this maximum aggregate
            receive power value is honored.  It ranges from -255 to 255
            units of 0.1 dBm (physical values are -25.5 to 25.5 dBm).
            A value of 0x7FFFFFFF (2147483647) means that there is no
            limit."
        REFERENCE    "ITU-T G.997.1, paragraph #7.3.1.2.5"
        DEFVAL       { 255 }
        ::= { zxAnXdsl2BaseConfProfEntry 13 }
     



     zxAnXdsl2LConfProfAdslMaxNomAtpDs  OBJECT-TYPE
        SYNTAX      Unsigned32 (0..255)
        UNITS       "0.1 dBm"
        MAX-ACCESS  read-create
        STATUS      current
        DESCRIPTION
           "(MAXNOMATPds).
            The maximum nominal aggregate transmit power in the
            downstream direction during initialization and Showtime.  It
            ranges from 0 to 255 units of 0.1 dBm (physical values are 0
            to 25.5 dBm)."
        REFERENCE    "ITU-T G.997.1, paragraph #7.3.1.2.3"
        DEFVAL       { 255 }
        ::= { zxAnXdsl2BaseConfProfEntry 14 }
     
     
     zxAnXdsl2LConfProfAdslMaxNomAtpUs  OBJECT-TYPE
        SYNTAX      Unsigned32 (0..255)
        UNITS       "0.1 dBm"
        MAX-ACCESS  read-create
        STATUS      current
        DESCRIPTION
           "(MAXNOMATPus).
            The maximum nominal aggregate transmit power in the upstream
            direction during initialization and Showtime.  It ranges from
            0 to 255 units of 0.1 dBm (physical values are 0 to 25.5
            dBm)."
        REFERENCE    "ITU-T G.997.1, paragraph #7.3.1.2.4"
        DEFVAL       { 255 }
        ::= { zxAnXdsl2BaseConfProfEntry 15 }
     
     zxAnXdsl2LConfProfAdslMaxNomPsdDs  OBJECT-TYPE
        SYNTAX      Integer32(-600..-300)
        UNITS       "0.1 dBm/Hz"
        MAX-ACCESS  read-create
        STATUS      current
        DESCRIPTION
           "(MAXNOMPSDds).
            The maximum nominal transmit PSD in the downstream
            direction during initialization and Showtime.  It ranges from
            -600 to -300 units of 0.1 dBm/Hz.  (physical values are -60 to
            -30 dBm/Hz).  "
        REFERENCE    "ITU-T G.997.1, paragraph #7.3.1.2.1"
        DEFVAL       { -300 }
       ::= { zxAnXdsl2BaseConfProfEntry 16 }
     
     zxAnXdsl2LConfProfAdslMaxNomPsdUs  OBJECT-TYPE
        SYNTAX      Integer32(-600..-300)
        UNITS       "0.1 dBm/Hz"
        MAX-ACCESS  read-create
        STATUS      current
        DESCRIPTION
           "(MAXNOMPSDus).
            The maximum nominal transmit PSD in the upstream direction
            during initialization and Showtime.  It ranges from -600 to
            -300 units of 0.1 dBm/Hz.  (physical values are -60 to
            -30 dBm/Hz).  "
        REFERENCE    "ITU-T G.997.1, paragraph #7.3.1.2.2"
        DEFVAL       { -300 }
        ::= { zxAnXdsl2BaseConfProfEntry 17 }
     
     
     
     zxAnXdsl2LConfProfAdslMaxAggRxPwrUs  OBJECT-TYPE
        SYNTAX      Integer32(-255..255 | 2147483647)
        UNITS       "0.1 dBm"
        MAX-ACCESS  read-create
        STATUS      current
        DESCRIPTION
           "(MAXRXPWRus).
            The maximum upstream aggregate receive power over the relevant
            set of sub-carriers.  The xTU-C should verify that the
            upstream power cutback is such that this maximum aggregate
            receive power value is honored.  It ranges from -255 to 255
            units of 0.1 dBm (physical values are -25.5 to 25.5 dBm).
            A value of 0x7FFFFFFF (2147483647) means that there is no
            limit."
        REFERENCE    "ITU-T G.997.1, paragraph #7.3.1.2.5"
        DEFVAL       { 255 }
        ::= { zxAnXdsl2BaseConfProfEntry 18 }
     
     
     zxAnXdsl2LConfProfScMaskDs  OBJECT-TYPE
        SYNTAX      Xdsl2ScMaskDs
        MAX-ACCESS  read-create
        STATUS      current
        DESCRIPTION
           "Sub-carriers mask.  A bitmap of 4096 bits that allows
           masking
            up to 4096 downstream sub-carriers, depending on NSCds.  If
            bit i (0 <= i < NSCds) is set to '1', the
            respective
            downstream sub-carrier i is masked, and if set to '0',
            the
            respective sub-carrier is unmasked.  Note that there should
            always be unmasked sub-carriers (i.e., the object cannot be
            all 1's).  Also note that if NSCds < 4096, all bits
            i (NSCds i <= 4096) should be set to '1'."
        REFERENCE    "ITU-T G.997.1, paragraph #7.3.1.2.6"
        ::= { zxAnXdsl2BaseConfProfEntry 19 }
     
     zxAnXdsl2LConfProfScMaskUs  OBJECT-TYPE
        SYNTAX      Xdsl2ScMaskUs
        MAX-ACCESS  read-create
        STATUS      current
        DESCRIPTION
           "Sub-carriers mask.  A bitmap of 4096 bits that allows
           masking
            up to 4096 downstream sub-carriers, depending on NSCds.  If
            bit i (0 <= i < NSCus) is set to '1', the
            respective
            upstream sub-carrier i is masked, and if set to '0',
            the
            respective sub-carrier is unmasked.  Note that there
            should always be unmasked sub-carriers (i.e., the object
            cannot be all 1's).  Also note that if NSCus <
            4096, all bits i (NSCus < i <= 4096) should be set to
            '1'."
        REFERENCE    "ITU-T G.997.1, paragraph #7.3.1.2.7"
        ::= { zxAnXdsl2BaseConfProfEntry 20 }
     
     zxAnXdsl2LConfProfRaUsNrmDs  OBJECT-TYPE
        SYNTAX      Unsigned32(0..310)
        UNITS       "0.1 dB"
        MAX-ACCESS  read-create
        STATUS      current
        DESCRIPTION
           "The Downstream Up-Shift Noise Margin value, to be used when
            zxAnXdsl2LConfProfRaModeDs is set to dynamicRa.  If the downstream
            noise margin is above this value and stays above it for
            more than the time specified by the zxAnXdsl2LConfProfRaUsTimeDs,
            the xTU-R shall attempt to increase the downstream net data
            rate.  The Downstream Up-shift Noise Margin ranges from 0 to
            310 units of 0.1 dB (Physical values are 0 to 31 dB)."
        REFERENCE    "ITU-T G.997.1, paragraph #7.3.1.4.3"
        DEFVAL       { 10 }
        ::= { zxAnXdsl2BaseConfProfEntry 21 }
     
     zxAnXdsl2LConfProfRaUsNrmUs  OBJECT-TYPE
        SYNTAX      Unsigned32(0..310)
        UNITS       "0.1 dB"
        MAX-ACCESS  read-create
        STATUS      current
        DESCRIPTION
           "The Upstream Up-Shift Noise Margin value, to be used when
            zxAnXdsl2LConfProfRaModeUs is set to dynamicRa.  If the upstream
            noise margin is above this value and stays above it for more
            than the time specified by the zxAnXdsl2LConfProfRaUsTimeUs, the
            xTU-C shall attempt to increase the upstream net data rate.
            The Upstream Up-shift Noise Margin ranges from 0 to 310 units
            of 0.1 dB (Physical values are 0 to 31 dB)."
        REFERENCE    "ITU-T G.997.1, paragraph #7.3.1.4.4"
        DEFVAL       { 10 }
        ::= { zxAnXdsl2BaseConfProfEntry 22 }
        
     
     zxAnXdsl2LConfProfRaUsTimeDs  OBJECT-TYPE
        SYNTAX      Unsigned32(0..16383)
        UNITS       "seconds"
        MAX-ACCESS  read-create
        STATUS      current
        DESCRIPTION
           "The Downstream Up-Shift Time Interval, to be used when
            zxAnXdsl2LConfProfRaModeDs is set to dynamicRa.  The interval of
            time that the downstream noise margin should stay above the
            Downstream Up-shift Noise Margin before the xTU-R shall
            attempt to increase the downstream net data rate.  The time
            interval ranges from 0 to 16383 seconds."
        REFERENCE    "ITU-T G.997.1, paragraph #7.3.1.4.5"
        DEFVAL       { 3600 }
        ::= { zxAnXdsl2BaseConfProfEntry 23 }
     
     zxAnXdsl2LConfProfRaUsTimeUs  OBJECT-TYPE
        SYNTAX      Unsigned32(0..16383)
        UNITS       "seconds"
        MAX-ACCESS  read-create
        STATUS      current
        DESCRIPTION
           "The Upstream Up-Shift Time Interval, to be used when
            zxAnXdsl2LConfProfRaModeUs is set to dynamicRa.  The interval of
            time the upstream noise margin should stay above the
            Upstream Up-shift Noise Margin before the xTU-C shall
            attempt to increase the upstream net data rate.  The time
            interval ranges from 0 to 16383 seconds."
        REFERENCE    "ITU-T G.997.1, paragraph #7.3.1.4.6"
        DEFVAL       { 3600 }
        ::= { zxAnXdsl2BaseConfProfEntry 24 }
     
     zxAnXdsl2LConfProfRaDsNrmsDs  OBJECT-TYPE
        SYNTAX      Unsigned32(0..310)
        UNITS       "0.1 dB"
        MAX-ACCESS  read-create
        STATUS      current
        DESCRIPTION
           "The Downstream Down-Shift Noise Margin value, to be used
           when
            zxAnXdsl2LConfProfRaModeDs is set to dynamicRa.  If the downstream
            noise margin is below this value and stays below that for more
            than the time specified by the zxAnXdsl2LConfProfRaDsTimeDs, the
            xTU-R shall attempt to decrease the downstream net data rate.
            The Downstream Down-shift Noise Margin ranges from 0 to 310
            units of 0.1 dB (Physical values are 0 to 31 dB)."
        REFERENCE    "ITU-T G.997.1, paragraph #7.3.1.4.7"
        DEFVAL       { 10 }
        ::= { zxAnXdsl2BaseConfProfEntry 25 }
     
     zxAnXdsl2LConfProfRaDsNrmsUs  OBJECT-TYPE
        SYNTAX      Unsigned32(0..310)
        UNITS       "0.1 dB"
        MAX-ACCESS  read-create
        STATUS      current
        DESCRIPTION
           "The Upstream Downshift Noise Margin value, to be used when
            zxAnXdsl2LConfProfRaModeUs is set to dynamicRa.  If the upstream
            noise margin is below this value and stays below that for more
            than the time specified by the zxAnXdsl2LConfProfRaDsTimeUs, the
            xTU-C shall attempt to decrease the upstream net data rate.
            The Upstream Down-shift Noise Margin ranges from 0 to 310
            units of 0.1 dB (Physical values are 0 to 31 dB)."
        REFERENCE    "ITU-T G.997.1, paragraph #7.3.1.4.8"
        DEFVAL       { 10 }
        ::= { zxAnXdsl2BaseConfProfEntry 26 }
     
     zxAnXdsl2LConfProfRaDsTimeDs  OBJECT-TYPE
        SYNTAX      Unsigned32(0..16383)
        UNITS       "seconds"
        MAX-ACCESS  read-create
        STATUS      current
        DESCRIPTION
           "The Downstream Downshift Time Interval, to be used when
            zxAnXdsl2LConfProfRaModeDs is set to dynamicRa.  The interval of
            time the downstream noise margin should stay below the
            Downstream Down-shift Noise Margin before the xTU-R shall
            attempt to decrease the downstream net data rate.  The time
            interval ranges from 0 to 16383 seconds."
        REFERENCE    "ITU-T G.997.1, paragraph #7.3.1.4.9"
        DEFVAL       { 3600 }
        ::= { zxAnXdsl2BaseConfProfEntry 27 }
     
     zxAnXdsl2LConfProfRaDsTimeUs  OBJECT-TYPE
        SYNTAX      Unsigned32(0..16383)
        UNITS       "seconds"
        MAX-ACCESS  read-create
        STATUS      current
        DESCRIPTION
           "The Upstream Down-Shift Time Interval, to be used when
            zxAnXdsl2LConfProfRaModeUs is set to dynamicRa.  The interval of
            time the upstream noise margin should stay below the Upstream
            Down-shift Noise Margin before the xTU-C shall attempt to
            decrease the upstream net data rate.  The time interval ranges
            from 0 to 16383 seconds."
        REFERENCE    "ITU-T G.997.1, paragraph #7.3.1.4.10"
        DEFVAL       { 3600 }
        ::= { zxAnXdsl2BaseConfProfEntry 28 }
     
     
     zxAnXdsl2LConfProfMsgMinUs  OBJECT-TYPE
        SYNTAX      Unsigned32(4..63)
        UNITS       "kbps"
        MAX-ACCESS  read-create
        STATUS      current
        DESCRIPTION
           "Minimum Overhead Rate Upstream.  Defines the minimum rate of
            the message-based overhead that shall be maintained by the xTU
            in upstream direction.  Expressed in bits per second and
            ranges from 4000 to 63000 bps."
        REFERENCE    "ITU-T G.997.1, paragraph #7.3.1.5.1"
        DEFVAL       { 4 }
       ::= { zxAnXdsl2BaseConfProfEntry 29 }
     
     zxAnXdsl2LConfProfMsgMinDs  OBJECT-TYPE
        SYNTAX      Unsigned32(4..63)
        UNITS       "kbps"
        MAX-ACCESS  read-create
        STATUS      current
        DESCRIPTION
           "Minimum Overhead Rate Downstream.  Defines the minimum rate
           of
            the message-based overhead that shall be maintained by the xTU
            in downstream direction.  Expressed in bits per second and
            ranges from 4000 to 63000 bps."
        REFERENCE    "ITU-T G.997.1, paragraph #7.3.1.5.2"
        DEFVAL       { 4 }
        ::= { zxAnXdsl2BaseConfProfEntry 30 }
     
     
     zxAnXdsl2LConfProfPmMode  OBJECT-TYPE
        SYNTAX      Xdsl2LinePmMode
        MAX-ACCESS  read-create
        STATUS      current
        DESCRIPTION
           "Power management state Enabling (PMMode).  Defines the power
            states the xTU-C or xTU-R may autonomously transition to on
            this line.
            The various bit positions are: allowTransitionsToIdle (0) and
            allowTransitionsToLowPower (1).  A bit with a '1' value
            means
            that the xTU is allowed to transit into the respective state
            and a '0' value means that the xTU is not allowed
            to transit into the respective state."
        REFERENCE    "ITU-T G.997.1, paragraph #7.3.1.1.4"
        DEFVAL  { { allowTransitionsToIdle, allowTransitionsToLowPower } }
        ::= { zxAnXdsl2BaseConfProfEntry 31 }
     
     zxAnXdsl2LConfProfL0Time  OBJECT-TYPE
        SYNTAX      Unsigned32 (0..255)
        UNITS       "seconds"
        MAX-ACCESS  read-create
        STATUS      current
        DESCRIPTION
           "The minimum time (in seconds) between an Exit from the L2
            state and the next Entry into the L2 state (L0-TIME).
            It ranges from 0 to 255 seconds."
        REFERENCE    "ITU-T G.997.1, paragraph #7.3.1.1.5"
        DEFVAL       { 255 }
        ::= { zxAnXdsl2BaseConfProfEntry 32 }
     
     zxAnXdsl2LConfProfL2Time  OBJECT-TYPE
        SYNTAX      Unsigned32 (0..255)
        UNITS       "seconds"
        MAX-ACCESS  read-create
        STATUS      current
        DESCRIPTION
           "The minimum time (in seconds) between an Entry into the
           L2 state and the first Power Trim in the L2 state and between
           two consecutive Power Trims in the L2 State (L2-TIME).
           It ranges from 0 to 255 seconds."
        REFERENCE    "ITU-T G.997.1, paragraph #7.3.1.1.6"
        DEFVAL       { 255 }
        ::= { zxAnXdsl2BaseConfProfEntry 33 }
     
     zxAnXdsl2LConfProfL2Atpr  OBJECT-TYPE
        SYNTAX      Unsigned32 (0..31)
        UNITS       "dB"
        MAX-ACCESS  read-create
        STATUS      current
        DESCRIPTION
           "The maximum aggregate transmit power reduction (in dB) that
            can be performed at transition of L0 to L2 state or through a
            single Power Trim in the L2 state (L2-ATPR).
            It ranges from 0 dB to 31 dB."
        REFERENCE    "ITU-T G.997.1, paragraph #7.3.1.1.7"
        DEFVAL       { 10 }
        ::= { zxAnXdsl2BaseConfProfEntry 34 }
     
     zxAnXdsl2LConfProfL2Atprt  OBJECT-TYPE
        SYNTAX      Unsigned32 (0..31)
        UNITS       "dB"
        MAX-ACCESS  read-create
        STATUS      current
        DESCRIPTION
           "The total maximum aggregate transmit power reduction
           (in dB) that can be performed in an L2 state. This is the
           sum of all reductions of L2 Request (i.e., at transition of
           L0 to L2 state) and Power Trims (L2-ATPRT)."
        REFERENCE    "ITU-T G.997.1, paragraph #7.3.1.1.9"
        DEFVAL       { 31 }
        ::= { zxAnXdsl2BaseConfProfEntry 35 }
     
     zxAnXdsl2LConfProfPsdMaskDs   OBJECT-TYPE
        SYNTAX      Xdsl2PsdMaskDs
        MAX-ACCESS  read-create
        STATUS      current
        DESCRIPTION
          "(PSDMASKds).
           The downstream PSD mask applicable at the U-C2 reference
           point.
          This parameter is used only for G.992.5 and it may impose PSD
          restrictions (breakpoints) in addition to the Limit PSD mask
          defined in G.992.5.
          This is a string of 32 pairs of values in the following
          structure:
          Octets 0+1 - Index of 1st sub-carrier used in the context
                       of a first breakpoint.
     
          Octet 2    - The PSD reduction for the sub-carrier indicated in
                       octets 0 and 1.
          Octets 3-5 - Same, for a 2nd breakpoint.
          Octets 6-8 - Same, for a 3rd breakpoint.
          This architecture continues until octets 94-95, which are
          associated with a 32nd breakpoint.
          Each subcarrier index is an unsigned number in the range 1 and
          NSCds.  Each PSD reduction value is in the range 0 (0dBm/Hz) to
          255 (-127.5dBm/Hz) with steps of 0.5dBm/Hz.  Valid values are
          in the range 0 to 190 (0 to -95dBm/Hz).
          When the number of breakpoints is less than 32, all remaining
          octets are set to the value 0.  Note that the content of this
          object should be correlated with the sub-carriers mask and with
          the RFI setup. "
        REFERENCE    "ITU-T G.997.1, paragraph #7.3.1.2.9"
          ::= { zxAnXdsl2BaseConfProfEntry 36 }
     
     zxAnXdsl2LConfProfPsdMaskUs   OBJECT-TYPE
        SYNTAX      Xdsl2PsdMaskUs
        MAX-ACCESS  read-create
        STATUS      current
        DESCRIPTION
          "(PSDMASKus).
           The upstream PSD mask applicable at the U-R2 reference
           point.
          This parameter is used only for G.992.5 and it may impose PSD
          restrictions (breakpoints) in addition to the Limit PSD mask
          defined in G.992.5.
          This is a string of 16 pairs of values in the following
          structure:
          Octets 0+1 - Index of 1st sub-carrier used in the context
                       of a first breakpoint.
          Octet 2    - The PSD reduction for the sub-carrier indicated in
                       octets 0 and 1.
          Octets 3-5 - Same, for a 2nd breakpoint.
          Octets 6-8 - Same, for a 3rd breakpoint.
          This architecture continues until octets 9-47, which are
          associated with a 16th breakpoint.
          Each subcarrier index is an unsigned number in the range 1 and
          NSCus.  Each PSD reduction value is in the range 0 (0dBm/Hz) to
          255 (-127.5dBm/Hz) with steps of 0.5dBm/Hz.  Valid values are
          in the range 0 to 190 (0 to -95dBm/Hz).
          When the number of breakpoints is less than 16, all remaining
          octets are set to the value 0.  Note that the content of this
          object should be correlated with the sub-carriers mask and with
          the RFI setup. "
        REFERENCE    "ITU-T G.997.1, paragraph #7.3.1.2.12"
          ::= { zxAnXdsl2BaseConfProfEntry 37 }
          
     zxAnXdsl2LConfProfPsdMaskSelectUs  OBJECT-TYPE
        SYNTAX      Unsigned32(1..9)
        MAX-ACCESS  read-create
        STATUS      current
        DESCRIPTION
          "The selected upstream PSD mask.  This parameter is used only
           for annexes J and M of G.992.3 and G.992.5, and the same
           selection is used for all relevant enabled bits in
           zxAnXdsl2LConfProfXtuTransSysEna. "
        REFERENCE    "ITU-T G.997.1, paragraph #7.3.1.2.11"
        DEFVAL       { 1 }
         ::= { zxAnXdsl2BaseConfProfEntry 38 }
         

    zxAnXdsl2LConfProfTrellisDs  OBJECT-TYPE
        SYNTAX      INTEGER {
             enabled (1),
             disabled (2)
        }
        MAX-ACCESS  read-create
        STATUS      current
        DESCRIPTION
             "Enabled or disabled the Trellis of downstream."
        ::= { zxAnXdsl2BaseConfProfEntry 39 }


    zxAnXdsl2LConfProfTrellisUs  OBJECT-TYPE
        SYNTAX      INTEGER {
         enabled (1),
         disabled (2)
        }
        MAX-ACCESS  read-create
        STATUS      current
        DESCRIPTION
             "Enabled or disabled the Trellis of upstream."
        ::= { zxAnXdsl2BaseConfProfEntry 40 }


    zxAnXdsl2LConfProfBitswapDs  OBJECT-TYPE
        SYNTAX      INTEGER {
             enabled (1),
             disabled (2)
        }
        MAX-ACCESS  read-create
        STATUS      current
        DESCRIPTION
             "Enabled or disabled the Bitswap of downstream."
        ::= { zxAnXdsl2BaseConfProfEntry 41 }


    zxAnXdsl2LConfProfBitswapUs  OBJECT-TYPE
        SYNTAX      INTEGER {
             enabled (1),
             disabled (2)
        }
        MAX-ACCESS  read-create
        STATUS      current
        DESCRIPTION
             "Enabled or disabled the Bitswap of upstream."
        ::= { zxAnXdsl2BaseConfProfEntry 42 }



    zxAnXdsl2LConfProfRetrainMode  OBJECT-TYPE
        SYNTAX      INTEGER {
             enabled (1),
             disabled (2)
        }
        MAX-ACCESS  read-create
        STATUS      current
        DESCRIPTION
             "Enabled or disabled the Retrain."
        ::= { zxAnXdsl2BaseConfProfEntry 43 }



    zxAnXdsl2LconfProfSnrModeDs  OBJECT-TYPE
        SYNTAX      INTEGER {
             enabled (1),
             disabled (2)
        }
        MAX-ACCESS  read-create
        STATUS      current
        DESCRIPTION
             "This parameter enables/disables the transmitter referred virtual 
             noise in the downstream direction. If set to 2, the virtual noise 
             is disabled. If set to 1, the virtual noise is enabled."
        ::= { zxAnXdsl2BaseConfProfEntry 44 }


    zxAnXdsl2LconfProfSnrModeUs  OBJECT-TYPE
        SYNTAX      INTEGER {
             enabled (1),
             disabled (2)
        }
        MAX-ACCESS  read-create
        STATUS      current
        DESCRIPTION
             "This parameter enables/disables the transmitter referred virtual 
             noise in the Upstream direction. If set to 2, the virtual noise 
             is disabled. If set to 1, the virtual noise is enabled."
        ::= { zxAnXdsl2BaseConfProfEntry 45 }


    zxAnXdsl2LConfProfTxRefVNDs  OBJECT-TYPE
        SYNTAX      OCTET STRING (SIZE(0..96)) 
        MAX-ACCESS  read-create
        STATUS      current
        DESCRIPTION
             "This configuration parameter defines the downstream transmitter 
        referred virtual noise (TXREFVNds). 
        The TXREFVNds shall be specified through a set of breakpoints. 
        Each breakpoint shall consist of a subcarrier index t, with a 
        sub-carrier spacing of 4.3125 kHz, and a noise PSD level (expressed 
        in dBm/Hz) at that subcarrier. The set of breakpoints can then be 
        represented as [(t1, PSD1), (t2, PSD2), ... , (tN, PSDN)]. 
        The subcarrier index shall be coded as an unsigned integer. 
        The noise level shall be coded as an 8-bit unsigned integer representing
        the noise level -40 dBm/Hz (coded as 0) to -140 dBm/Hz (coded as 200), 
        in steps of 0.5 dBm/Hz. Values from 201 to 255 are special values 
        indicating a noise level of 0 W/Hz. The maximum number of breakpoints 
        is 32."
        ::= { zxAnXdsl2BaseConfProfEntry 46 }


    zxAnXdsl2LConfProfTxRefVNUs  OBJECT-TYPE
        SYNTAX      OCTET STRING (SIZE(0..48)) 
        MAX-ACCESS  read-create
        STATUS      current
        DESCRIPTION
             "This configuration parameter defines the upstream transmitter 
             referred virtual noise (TXREFVNus). The TXREFVNus shall be 
             specified through a set of breakpoints. Each breakpoint shall 
             consist of a subcarrier index t, with a sub-carrier spacing of 
             4.3125 kHz, and a noise PSD level (expressed in dBm/Hz) at that 
             subcarrier. The set of breakpoints can then be represented as 
             [(t1, PSD1), (t2, PSD2), ... , (tN, PSDN)]. The subcarrier index 
             shall be coded as an unsigned integer. The noise level shall be 
             coded as an 8-bit unsigned integer representing the noise 
             level -40 dBm/Hz (coded as 0) to -140 dBm/Hz (coded as 200), 
             in steps of 0.5 dBm/Hz. Values from 201 to 255 are special values 
             indicating a noise level of 0 W/Hz. The maximum number of 
             breakpoints is 16."
        ::= { zxAnXdsl2BaseConfProfEntry 47 }

    zxAnXdsl2Ch1ConfProfMinResDataRateDs  OBJECT-TYPE
        SYNTAX      Unsigned32(0..200000)
        UNITS       "kbps"
        MAX-ACCESS  read-create
        STATUS      current
        DESCRIPTION
           "Minimum Reserved Data Rate on Downstream direction.  The
            minimum reserved net data rate for the bearer channel, coded
            in bit/s.  This parameter is used only if the Rate Adaptation
            Mode in the direction of the bearer channel (i.e.,
            Xdsl2LineConfRaModeDs) is set to DynamicRa."
        REFERENCE    "ITU-T G.997.1, paragraph 7.3.2.1"
        ::= { zxAnXdsl2BaseConfProfEntry 48 }
  
    zxAnXdsl2Ch1ConfProfMinResDataRateUs  OBJECT-TYPE
        SYNTAX      Unsigned32(0..200000)
        UNITS       "kbps"
        MAX-ACCESS  read-create
        STATUS      current
        DESCRIPTION
           "Minimum Reserved Data Rate on Upstream direction.  The minimum
            reserved net data rate for the bearer channel, coded in
            bit/s.  This parameter is used only if the Rate Adaptation
            Mode in the direction of the bearer channel (i.e.,
            Xdsl2LineConfRaModeUs) is set to DynamicRa."
        REFERENCE    "ITU-T G.997.1, paragraph 7.3.2.1"
        ::= { zxAnXdsl2BaseConfProfEntry 49 }
    

   zxAnXdsl2Ch1ConfProfMinDataRateLowPwrDs  OBJECT-TYPE
        SYNTAX      Unsigned32(0..200000)
        UNITS       "kbps"
        MAX-ACCESS  read-create
        STATUS      current
        DESCRIPTION
           "Minimum Data Rate in Low Power state on Downstream direction.
            The minimum net data rate for the bearer channel, coded in
            bit/s., during the low power state (L1 in G.992.2, L2 in
            G.992.3)."
        REFERENCE    "ITU-T G.997.1, paragraph 7.3.2.1"
        ::= { zxAnXdsl2BaseConfProfEntry 50 }
      


   zxAnXdsl2Ch1ConfProfMaxBerDs  OBJECT-TYPE
        SYNTAX      Xdsl2MaxBer
        MAX-ACCESS  read-create
        STATUS      current
        DESCRIPTION
           "Maximum Bit Error Ratio on Downstream direction.  The maximum
            bit error ratio for the bearer channel.  The parameter can
            take the following values (for 1E-3, 1E-5 or 1E-7):
               eminus3 (1),
               eminus5 (2),
               eminus7 (3)"
        REFERENCE    "ITU-T G.997.1, paragraph 7.3.2.4"
        DEFVAL       { eminus5 }
       ::= { zxAnXdsl2BaseConfProfEntry 51 }
  



   zxAnXdsl2Ch1ConfProfMaxBerUs  OBJECT-TYPE
        SYNTAX      Xdsl2MaxBer
        MAX-ACCESS  read-create
        STATUS      current
        DESCRIPTION
           "Maximum Bit Error Ratio on Upstream direction.  The maximum
            bit error ratio for the bearer channel.  The parameter can
            take the following values (for 1E-3, 1E-5 or 1E-7):
               eminus3 (1),
               eminus5 (2),
               eminus7 (3)"
        REFERENCE    "ITU-T G.997.1, paragraph 7.3.2.4"
        DEFVAL       { eminus5 }
        ::= { zxAnXdsl2BaseConfProfEntry 52 }
  


   zxAnXdsl2Ch1ConfProfImaEnabled  OBJECT-TYPE
        SYNTAX      TruthValue
        MAX-ACCESS  read-create
        STATUS      current
        DESCRIPTION
           "IMA Mode Enable.  The parameter enables the IMA operation mode
            in the ATM Data Path.  Relevant only if the channel is of ATM
            Data Path.  When in 'enable' state, the ATM data path should
            comply with the requirements for IMA transmission."
        REFERENCE    "ITU-T G.997.1, paragraph 7.3.4.1"
        DEFVAL       { false }
      ::= { zxAnXdsl2BaseConfProfEntry 53 }
                


    zxAnXdsl2Ch2ConfProfMinResDataRateDs  OBJECT-TYPE
        SYNTAX      Unsigned32(0..200000)
        UNITS       "kbps"
        MAX-ACCESS  read-create
        STATUS      current
        DESCRIPTION
           "Minimum Reserved Data Rate on Downstream direction.  The
            minimum reserved net data rate for the bearer channel, coded
            in bit/s.  This parameter is used only if the Rate Adaptation
            Mode in the direction of the bearer channel (i.e.,
            Xdsl2LineConfRaModeDs) is set to DynamicRa."
        REFERENCE    "ITU-T G.997.1, paragraph 7.3.2.1"
        ::= { zxAnXdsl2BaseConfProfEntry 54 }
  
    zxAnXdsl2Ch2ConfProfMinResDataRateUs  OBJECT-TYPE
        SYNTAX      Unsigned32(0..200000)
        UNITS       "kbps"
        MAX-ACCESS  read-create
        STATUS      current
        DESCRIPTION
           "Minimum Reserved Data Rate on Upstream direction.  The minimum
            reserved net data rate for the bearer channel, coded in
            bit/s.  This parameter is used only if the Rate Adaptation
            Mode in the direction of the bearer channel (i.e.,
            Xdsl2LineConfRaModeUs) is set to DynamicRa."
        REFERENCE    "ITU-T G.997.1, paragraph 7.3.2.1"
        ::= { zxAnXdsl2BaseConfProfEntry 55 }
    

   zxAnXdsl2Ch2ConfProfMinDataRateLowPwrDs  OBJECT-TYPE
        SYNTAX      Unsigned32(0..200000)
        UNITS       "kbps"
        MAX-ACCESS  read-create
        STATUS      current
        DESCRIPTION
           "Minimum Data Rate in Low Power state on Downstream direction.
            The minimum net data rate for the bearer channel, coded in
            bit/s., during the low power state (L1 in G.992.2, L2 in
            G.992.3)."
        REFERENCE    "ITU-T G.997.1, paragraph 7.3.2.1"
        ::= { zxAnXdsl2BaseConfProfEntry 56 }
      


   zxAnXdsl2Ch2ConfProfMaxBerDs  OBJECT-TYPE
        SYNTAX      Xdsl2MaxBer
        MAX-ACCESS  read-create
        STATUS      current
        DESCRIPTION
           "Maximum Bit Error Ratio on Downstream direction.  The maximum
            bit error ratio for the bearer channel.  The parameter can
            take the following values (for 1E-3, 1E-5 or 1E-7):
               eminus3 (1),
               eminus5 (2),
               eminus7 (3)"
        REFERENCE    "ITU-T G.997.1, paragraph 7.3.2.4"
        DEFVAL       { eminus5 }
       ::= { zxAnXdsl2BaseConfProfEntry 57 }
  

   zxAnXdsl2Ch2ConfProfMaxBerUs  OBJECT-TYPE
        SYNTAX      Xdsl2MaxBer
        MAX-ACCESS  read-create
        STATUS      current
        DESCRIPTION
           "Maximum Bit Error Ratio on Upstream direction.  The maximum
            bit error ratio for the bearer channel.  The parameter can
            take the following values (for 1E-3, 1E-5 or 1E-7):
               eminus3 (1),
               eminus5 (2),
               eminus7 (3)"
        REFERENCE    "ITU-T G.997.1, paragraph 7.3.2.4"
        DEFVAL       { eminus5 }
        ::= { zxAnXdsl2BaseConfProfEntry 58 }
  

   zxAnXdsl2Ch2ConfProfImaEnabled  OBJECT-TYPE
        SYNTAX      TruthValue
        MAX-ACCESS  read-create
        STATUS      current
        DESCRIPTION
           "IMA Mode Enable.  The parameter enables the IMA operation mode
            in the ATM Data Path.  Relevant only if the channel is of ATM
            Data Path.  When in 'enable' state, the ATM data path should
            comply with the requirements for IMA transmission."
        REFERENCE    "ITU-T G.997.1, paragraph 7.3.4.1"
        DEFVAL       { false }
      ::= { zxAnXdsl2BaseConfProfEntry 59 }


   zxAnXdsl2LConfProfRowStatus  OBJECT-TYPE
        SYNTAX      RowStatus
        MAX-ACCESS  read-create
        STATUS      current
        DESCRIPTION
           "This object is used to create a new row or to modify or
           delete an existing row in this table.
  
           A profile is activated by setting this object to 'active'.
           When 'active' is set, the system will validate the profile.
           Profile modification is prohibited while this object is set
           to 'active'.
  
           Before a profile can be deleted or taken out of service
           (by setting this object to 'destroy' or 'notInService'),
           it must be first unreferenced from all associated
           ports."
        ::= { zxAnXdsl2BaseConfProfEntry 64 }
  


--------------------------------------------------------------------------
-- 3.zxAnXdsl2ServiceConfProfTable
--------------------------------------------------------------------------
   zxAnXdsl2ServiceConfProfTable  OBJECT-TYPE
        SYNTAX      SEQUENCE  OF  ZxAnXdsl2ServiceConfProfEntry
        MAX-ACCESS  not-accessible
        STATUS      current
        DESCRIPTION
            "The table zxAnXdsl2ServiceConfProfTable contains VDSL2/ADSL/
            ADSL2 and ADSL2+ Service configuration profile.
            Entries in this table MUST be maintained in a
            persistent manner."
        ::= { zxAnXdsl2LineProfile 2 }


   zxAnXdsl2ServiceConfProfEntry  OBJECT-TYPE
        SYNTAX      ZxAnXdsl2ServiceConfProfEntry
        MAX-ACCESS  not-accessible
        STATUS      current
        DESCRIPTION
         "The table zxAnXdsl2ServiceConfProfTable contains VDSL2/ADSL/
          ADSL2 and ADSL2+ basic configuration profile.

          A default profile with an index of 'DEFVAL' will
          always exist and its parameters will be set to vendor-specific
          values, unless otherwise specified in this document"
        INDEX  { zxAnXdsl2ServiceConfProfileName }
        ::= { zxAnXdsl2ServiceConfProfTable 1 }

   ZxAnXdsl2ServiceConfProfEntry  ::=
        SEQUENCE {
            zxAnXdsl2ServiceConfProfileName         DisplayString,
            zxAnXdsl2LConfProfForceInp              TruthValue,
            zxAnXdsl2LConfProfRaModeDs              Xdsl2RaMode,
            zxAnXdsl2LConfProfRaModeUs              Xdsl2RaMode,
            zxAnXdsl2LConfProfTargetSnrmDs          Unsigned32,
            zxAnXdsl2LConfProfTargetSnrmUs          Unsigned32,
            zxAnXdsl2LConfProfMaxSnrmDs             Unsigned32,
            zxAnXdsl2LConfProfMaxSnrmUs             Unsigned32,
            zxAnXdsl2LConfProfMinSnrmDs             Unsigned32,
            zxAnXdsl2LConfProfMinSnrmUs             Unsigned32,
            zxAnXdsl2ConfProfCh1Enabled             TruthValue,
            zxAnXdsl2Ch1ConfChanRaRatioDs           Unsigned32,
            zxAnXdsl2Ch1ConfChanRaRatioUs           Unsigned32,
            zxAnXdsl2Ch1ConfProfMaxDataRateDs       Unsigned32,
            zxAnXdsl2Ch1ConfProfMaxDataRateUs       Unsigned32,
            zxAnXdsl2Ch1ConfProfMinDataRateDs       Unsigned32,
            zxAnXdsl2Ch1ConfProfMinDataRateUs       Unsigned32,
            zxAnXdsl2Ch1ConfProfMaxDelayDs          Unsigned32,
            zxAnXdsl2Ch1ConfProfMaxDelayUs          Unsigned32,
            zxAnXdsl2Ch1ConfProfMinProtectionDs     Xdsl2SymbolProtection,
            zxAnXdsl2Ch1ConfProfMinProtectionUs     Xdsl2SymbolProtection,
            zxAnXdsl2ConfProfCh2Enabled             TruthValue,
            zxAnXdsl2Ch2ConfChanRaRatioDs           Unsigned32,
            zxAnXdsl2Ch2ConfChanRaRatioUs           Unsigned32,
            zxAnXdsl2Ch2ConfProfMaxDataRateDs       Unsigned32,
            zxAnXdsl2Ch2ConfProfMaxDataRateUs       Unsigned32,
            zxAnXdsl2Ch2ConfProfMinDataRateDs       Unsigned32,
            zxAnXdsl2Ch2ConfProfMinDataRateUs       Unsigned32,
            zxAnXdsl2Ch2ConfProfMaxDelayDs          Unsigned32,
            zxAnXdsl2Ch2ConfProfMaxDelayUs          Unsigned32,
            zxAnXdsl2Ch2ConfProfMinProtectionDs     Xdsl2SymbolProtection,
            zxAnXdsl2Ch2ConfProfMinProtectionUs     Xdsl2SymbolProtection,
            zxAnXdsl2ServiceConfProfRowStatus       RowStatus
      }


    zxAnXdsl2ServiceConfProfileName  OBJECT-TYPE
        SYNTAX      DisplayString (SIZE(1..32))
        MAX-ACCESS  not-accessible
        STATUS      current
        DESCRIPTION
            "This object identifies a row in this table."
        ::= { zxAnXdsl2ServiceConfProfEntry 1 }
        

    zxAnXdsl2LConfProfForceInp  OBJECT-TYPE
        SYNTAX      TruthValue
        MAX-ACCESS  read-create
        STATUS      current
        DESCRIPTION
            "Enable /disable force to use INP."
        ::= { zxAnXdsl2ServiceConfProfEntry 2 }


   zxAnXdsl2LConfProfRaModeDs  OBJECT-TYPE
      SYNTAX      Xdsl2RaMode
      MAX-ACCESS  read-create
      STATUS      current
      DESCRIPTION
         "The mode of operation of a rate-adaptive xTU-C in the transmit
          direction.  The parameter can take three values:
             fixed (1),
             raInit (2),
             dynamicRa (3)."
      REFERENCE    "ITU-T G.997.1, paragraph 7.3.1.4.1"
      DEFVAL       { raInit }
      ::= { zxAnXdsl2ServiceConfProfEntry 3 }

   zxAnXdsl2LConfProfRaModeUs  OBJECT-TYPE
      SYNTAX      Xdsl2RaMode
      MAX-ACCESS  read-create
      STATUS      current
      DESCRIPTION
         "The mode of operation of a rate-adaptive xTU-R in the transmit
          direction.  The parameter can take three values:
             fixed (1),
             raInit (2),
             dynamicRa (3)."
      REFERENCE    "ITU-T G.997.1, paragraph 7.3.1.4.2"
      DEFVAL       { raInit }
      ::= { zxAnXdsl2ServiceConfProfEntry 4 }


   zxAnXdsl2LConfProfTargetSnrmDs  OBJECT-TYPE
      SYNTAX      Unsigned32(0..310)
      UNITS       "0.1 dB"
      MAX-ACCESS  read-create
      STATUS      current
      DESCRIPTION
         "The minimum Noise Margin the xTU-R receiver shall achieve,

          relative to the BER requirement for each of the downstream

          bearer channels, to successfully complete initialization.
          The target noise margin ranges from 0 to 310 units of 0.1 dB
          (Physical values are 0 to 31 dB)."
      REFERENCE    "ITU-T G.997.1, paragraph 7.3.1.3.1"
      DEFVAL       { 60 }
      ::= { zxAnXdsl2ServiceConfProfEntry 5 }

   zxAnXdsl2LConfProfTargetSnrmUs  OBJECT-TYPE
      SYNTAX      Unsigned32(0..310)
      UNITS       "0.1 dB"
      MAX-ACCESS  read-create
      STATUS      current
      DESCRIPTION
         "The minimum Noise Margin the xTU-C receiver shall achieve,

          relative to the BER requirement for each of the upstream

          bearer channels, to successfully complete initialization.
          The target noise margin ranges from 0 to 310 units of 0.1 dB
          (Physical values are 0 to 31 dB)."
      REFERENCE    "ITU-T G.997.1, paragraph 7.3.1.3.2"
      DEFVAL       { 60 }
      ::= { zxAnXdsl2ServiceConfProfEntry 6 }



zxAnXdsl2LConfProfMaxSnrmDs  OBJECT-TYPE
   SYNTAX      Unsigned32 (0..310 | 2147483647)
   UNITS       "0.1 dB"
   MAX-ACCESS  read-create
   STATUS      current
   DESCRIPTION
      "The maximum Noise Margin the xTU-R receiver shall try to
       sustain.  If the Noise Margin is above this level, the xTU-R
       shall request that the xTU-C reduce the xTU-C transmit power
       to get a noise margin below this limit (if this functionality
       is supported).  The maximum noise margin ranges from 0 to 310
       units of 0.1 dB (Physical values are 0 to 31 dB).  A value of
       0x7FFFFFFF (2147483647) means that there is no maximum."
   REFERENCE    "ITU-T G.997.1, paragraph #7.3.1.3.3"
   DEFVAL       { 310 }
   ::= { zxAnXdsl2ServiceConfProfEntry 7 }

zxAnXdsl2LConfProfMaxSnrmUs  OBJECT-TYPE
   SYNTAX      Unsigned32 (0..310 | 2147483647)
   UNITS       "0.1 dB"
   MAX-ACCESS  read-create
   STATUS      current
   DESCRIPTION
      "The maximum Noise Margin the xTU-C receiver shall try to
       sustain.  If the Noise Margin is above this level, the xTU-C
       shall request that the xTU-R reduce the xTU-R transmit power
       to get a noise margin below this limit (if this functionality
       is supported).  The maximum noise margin ranges from 0 to 310
       units of 0.1 dB (Physical values are 0 to 31 dB).  A value of
       0x7FFFFFFF (2147483647) means that there is no maximum."
   REFERENCE    "ITU-T G.997.1, paragraph #7.3.1.3.4"
   DEFVAL       { 310 }
   ::= { zxAnXdsl2ServiceConfProfEntry 8 }

zxAnXdsl2LConfProfMinSnrmDs  OBJECT-TYPE
   SYNTAX      Unsigned32(0..310)
   UNITS       "0.1 dB"
   MAX-ACCESS  read-create
   STATUS      current
   DESCRIPTION
      "The minimum Noise Margin the xTU-R receiver shall tolerate.
       If the noise margin falls below this level, the xTU-R shall
       request that the xTU-C increase the xTU-C transmit power.
       If an increase to xTU-C transmit power is not possible, a
       loss-of-margin (LOM) defect occurs, the xTU-R shall fail and
       attempt to reinitialize and the NMS shall be notified.  The
       minimum noise margin ranges from 0 to 310 units of
       0.1 dB (Physical values are 0 to 31 dB).  A value of 0 means
       that there is no minimum."
   REFERENCE    "ITU-T G.997.1, paragraph #7.3.1.3.5"
   DEFVAL       { 10 }
   ::= { zxAnXdsl2ServiceConfProfEntry 9 }

zxAnXdsl2LConfProfMinSnrmUs  OBJECT-TYPE
   SYNTAX      Unsigned32(0..310)
   UNITS       "0.1 dB"
   MAX-ACCESS  read-create
   STATUS      current
   DESCRIPTION
      "The minimum Noise Margin the xTU-C receiver shall tolerate.
       If the noise margin falls below this level, the xTU-C shall
       request that the xTU-R increase the xTU-R transmit power.
       If an increase of xTU-R transmit power is not possible, a
       loss-of-margin (LOM) defect occurs, the xTU-C shall fail and
       attempt to re-initialize and the NMS shall be notified.  The
       minimum noise margin ranges from 0 to 310 units of
       0.1 dB (Physical values are 0 to 31 dB).  A value of 0 means
       that there is no minimum."
   REFERENCE    "ITU-T G.997.1, paragraph #7.3.1.3.6"
   DEFVAL       { 10 }
   ::= { zxAnXdsl2ServiceConfProfEntry 10 }




   zxAnXdsl2ConfProfCh1Enabled  OBJECT-TYPE
        SYNTAX      TruthValue
        MAX-ACCESS  read-create
        STATUS      current
        DESCRIPTION
            "Enable /disable the bearer channel 1."
        ::= { zxAnXdsl2ServiceConfProfEntry 11 }

   zxAnXdsl2Ch1ConfChanRaRatioDs  OBJECT-TYPE
      SYNTAX      Unsigned32(0..100)
      UNITS       "percents"
      MAX-ACCESS  read-create
      STATUS      current
      DESCRIPTION
         "Rate Adaptation Ratio.  The ratio (in %) that should be taken
          into account for the bearer channel #1 when performing rate
          adaptation on Downstream.  The ratio refers to the available
          data rate in excess of the Minimum Data Rate, summed over all
          bearer channels.  Also, the 100 -
          Xdsl2ConfTemplateChan1RaRatioDs is the ratio of excess data
          rate to be assigned to all other bearer channels on Downstream
          direction.  The sum of rate adaptation ratios over all bearers
          on the same direction shall be equal to 100%."
      REFERENCE    "ITU-T G.997.1, paragraph 7.3.2.1"
      DEFVAL       { 100 }
      ::= { zxAnXdsl2ServiceConfProfEntry 12 }

   zxAnXdsl2Ch1ConfChanRaRatioUs  OBJECT-TYPE
      SYNTAX      Unsigned32(0..100)
      UNITS       "percents"
      MAX-ACCESS  read-create
      STATUS      current
      DESCRIPTION
         "Rate Adaptation Ratio.  The ratio (in %) that should be taken
          into account for the bearer channel #1 when performing rate
          adaptation on Upstream.  The ratio refers to the available
          data rate in excess of the Minimum Data Rate, summed over all
          bearer channels.  Also, the
          100 - Xdsl2ConfTemplateChan1RaRatioUs is the ratio of excess
          data rate to be assigned to all other bearer channels on
          Upstream direction.  The sum of rate adaptation ratios over
          all bearers on the same direction shall be equal to 100 %."
      REFERENCE    "ITU-T G.997.1, paragraph 7.3.2.1"
      DEFVAL       { 100 }
      ::= { zxAnXdsl2ServiceConfProfEntry 13 }

zxAnXdsl2Ch1ConfProfMaxDataRateDs  OBJECT-TYPE
   SYNTAX      Unsigned32(0..200000)
   UNITS       "kbps"
   MAX-ACCESS  read-create
   STATUS      current
   DESCRIPTION
      "Maximum Data Rate on Downstream direction.  The maximum net
       data rate for the bearer channel, coded in bit/s."
   REFERENCE    "ITU-T G.997.1, paragraph #7.3.2.1"
   ::= { zxAnXdsl2ServiceConfProfEntry 14 }

zxAnXdsl2Ch1ConfProfMaxDataRateUs  OBJECT-TYPE
   SYNTAX      Unsigned32(0..200000)
   UNITS       "kbps"
   MAX-ACCESS  read-create
   STATUS      current
   DESCRIPTION
      "Maximum Data Rate on Upstream direction.  The maximum net
      data
       rate for the bearer channel, coded in bit/s."
   REFERENCE    "ITU-T G.997.1, paragraph #7.3.2.1"
   ::= { zxAnXdsl2ServiceConfProfEntry 15 }


zxAnXdsl2Ch1ConfProfMinDataRateDs  OBJECT-TYPE
   SYNTAX      Unsigned32(0..200000)
   UNITS       "kbps"
   MAX-ACCESS  read-create
   STATUS      current
   DESCRIPTION
      "Minimum Data Rate on Downstream direction.  The minimum net
       data rate for the bearer channel, coded in bit/s."
   REFERENCE    "ITU-T G.997.1, paragraph #7.3.2.1"
   ::= { zxAnXdsl2ServiceConfProfEntry 16 }

zxAnXdsl2Ch1ConfProfMinDataRateUs  OBJECT-TYPE
   SYNTAX      Unsigned32(0..200000)
   UNITS       "kbps"
   MAX-ACCESS  read-create
   STATUS      current
   DESCRIPTION
      "Minimum Data Rate on Upstream direction.  The minimum net
      data
       rate for the bearer channel, coded in bit/s."
   REFERENCE    "ITU-T G.997.1, paragraph #7.3.2.1"
   ::= { zxAnXdsl2ServiceConfProfEntry 17 }



zxAnXdsl2Ch1ConfProfMaxDelayDs  OBJECT-TYPE
   SYNTAX      Unsigned32(0..63)
   UNITS       "milliseconds"
   MAX-ACCESS  read-create
   STATUS      current
   DESCRIPTION
      "Maximum Interleave Delay on Downstream direction.  The
      maximum
       one-way interleaving delay introduced by the PMS-TC on
       Downstream direction.  The xTUs shall choose the S (factor)
       and D (depth) values such that the actual one-way interleaving
       delay (zxAnXdsl2Ch1StatusActDelay) is as close as possible to,
       but less than or equal to zxAnXdsl2Ch1ConfProfMaxDelayDs.  The
       delay is coded in ms, with the value 0 indicating no delay
       bound is being imposed."
   REFERENCE    "ITU-T G.997.1, paragraph #7.3.2.2"
   ::= { zxAnXdsl2ServiceConfProfEntry 18 }

zxAnXdsl2Ch1ConfProfMaxDelayUs  OBJECT-TYPE
   SYNTAX      Unsigned32(0..63)
   UNITS       "milliseconds"
   MAX-ACCESS  read-create
   STATUS      current
   DESCRIPTION
      "Maximum Interleave Delay on Upstream direction.  The maximum
       one-way interleaving delay introduced by the PMS-TC on
       Upstream direction.  The xTUs shall choose the S (factor) and
       D (depth) values such that the actual one-way interleaving
       delay (zxAnXdsl2Ch1StatusActDelay) is as close as possible to,
       but less than or equal to zxAnXdsl2Ch1ConfProfMaxDelayUs.  The
       delay is coded in ms, with the value 0 indicating no delay
       bound is being imposed."
   REFERENCE    "ITU-T G.997.1, paragraph #7.3.2.2"
   ::= { zxAnXdsl2ServiceConfProfEntry 19 }

zxAnXdsl2Ch1ConfProfMinProtectionDs  OBJECT-TYPE
   SYNTAX      Xdsl2SymbolProtection
   UNITS       "symbols"
   MAX-ACCESS  read-create
   STATUS      current
   DESCRIPTION
      "Minimum Impulse Noise Protection on Downstream direction.
      The
       minimum impulse noise protection for the bearer channel,
       expressed in symbols.  The parameter can take the following
       values: noProtection (i.e., INP not required), halfSymbol
       (i.e., INP length is 1/2 symbol) and 1-16 symbols in steps
       of 1 symbol."
   REFERENCE    "ITU-T G.997.1, paragraph #7.3.2.3"
   DEFVAL       { noProtection }
   ::= { zxAnXdsl2ServiceConfProfEntry 20 }

zxAnXdsl2Ch1ConfProfMinProtectionUs  OBJECT-TYPE
   SYNTAX      Xdsl2SymbolProtection
   UNITS       "symbols"
   MAX-ACCESS  read-create
   STATUS      current
   DESCRIPTION
      "Minimum Impulse Noise Protection on Upstream direction.  The
       minimum impulse noise protection for the bearer channel,
       expressed in symbols. "
   REFERENCE    "ITU-T G.997.1, paragraph #7.3.2.3"
   DEFVAL       { noProtection }
   ::= { zxAnXdsl2ServiceConfProfEntry 21 }



   zxAnXdsl2ConfProfCh2Enabled  OBJECT-TYPE
        SYNTAX      TruthValue
        MAX-ACCESS  read-create
        STATUS      current
        DESCRIPTION
            "Enable /disable the bearer channel 1."
        ::= { zxAnXdsl2ServiceConfProfEntry 22 }

   zxAnXdsl2Ch2ConfChanRaRatioDs  OBJECT-TYPE
      SYNTAX      Unsigned32(0..100)
      UNITS       "percents"
      MAX-ACCESS  read-create
      STATUS      current
      DESCRIPTION
         "Rate Adaptation Ratio.  The ratio (in %) that should be taken
          into account for the bearer channel #1 when performing rate
          adaptation on Downstream.  The ratio refers to the available
          data rate in excess of the Minimum Data Rate, summed over all
          bearer channels.  Also, the 100 -
          Xdsl2ConfTemplateChan1RaRatioDs is the ratio of excess data
          rate to be assigned to all other bearer channels on Downstream
          direction.  The sum of rate adaptation ratios over all bearers
          on the same direction shall be equal to 100%."
      REFERENCE    "ITU-T G.997.1, paragraph 7.3.2.1"
      DEFVAL       { 100 }
      ::= { zxAnXdsl2ServiceConfProfEntry 23 }

   zxAnXdsl2Ch2ConfChanRaRatioUs  OBJECT-TYPE
      SYNTAX      Unsigned32(0..100)
      UNITS       "percents"
      MAX-ACCESS  read-create
      STATUS      current
      DESCRIPTION
         "Rate Adaptation Ratio.  The ratio (in %) that should be taken
          into account for the bearer channel #1 when performing rate
          adaptation on Upstream.  The ratio refers to the available
          data rate in excess of the Minimum Data Rate, summed over all
          bearer channels.  Also, the
          100 - Xdsl2ConfTemplateChan1RaRatioUs is the ratio of excess
          data rate to be assigned to all other bearer channels on
          Upstream direction.  The sum of rate adaptation ratios over
          all bearers on the same direction shall be equal to 100 %."
      REFERENCE    "ITU-T G.997.1, paragraph 7.3.2.1"
      DEFVAL       { 100 }
      ::= { zxAnXdsl2ServiceConfProfEntry 24 }   
   
   zxAnXdsl2Ch2ConfProfMaxDataRateDs  OBJECT-TYPE
   SYNTAX      Unsigned32(0..200000)
   UNITS       "kbps"
   MAX-ACCESS  read-create
   STATUS      current
   DESCRIPTION
      "Maximum Data Rate on Downstream direction.  The maximum net
       data rate for the bearer channel, coded in bit/s."
   REFERENCE    "ITU-T G.997.1, paragraph #7.3.2.1"
   ::= { zxAnXdsl2ServiceConfProfEntry 25 }

zxAnXdsl2Ch2ConfProfMaxDataRateUs  OBJECT-TYPE
   SYNTAX      Unsigned32(0..200000)
   UNITS       "kbps"
   MAX-ACCESS  read-create
   STATUS      current
   DESCRIPTION
      "Maximum Data Rate on Upstream direction.  The maximum net
      data
       rate for the bearer channel, coded in bit/s."
   REFERENCE    "ITU-T G.997.1, paragraph #7.3.2.1"
   ::= { zxAnXdsl2ServiceConfProfEntry 26 }


zxAnXdsl2Ch2ConfProfMinDataRateDs  OBJECT-TYPE
   SYNTAX      Unsigned32(0..200000)
   UNITS       "kbps"
   MAX-ACCESS  read-create
   STATUS      current
   DESCRIPTION
      "Minimum Data Rate on Downstream direction.  The minimum net
       data rate for the bearer channel, coded in bit/s."
   REFERENCE    "ITU-T G.997.1, paragraph #7.3.2.1"
   ::= { zxAnXdsl2ServiceConfProfEntry 27 }

zxAnXdsl2Ch2ConfProfMinDataRateUs  OBJECT-TYPE
   SYNTAX      Unsigned32(0..200000)
   UNITS       "kbps"
   MAX-ACCESS  read-create
   STATUS      current
   DESCRIPTION
      "Minimum Data Rate on Upstream direction.  The minimum net
      data
       rate for the bearer channel, coded in bit/s."
   REFERENCE    "ITU-T G.997.1, paragraph #7.3.2.1"
   ::= { zxAnXdsl2ServiceConfProfEntry 28 }



zxAnXdsl2Ch2ConfProfMaxDelayDs  OBJECT-TYPE
   SYNTAX      Unsigned32(0..63)
   UNITS       "milliseconds"
   MAX-ACCESS  read-create
   STATUS      current
   DESCRIPTION
      "Maximum Interleave Delay on Downstream direction.  The
      maximum
       one-way interleaving delay introduced by the PMS-TC on
       Downstream direction.  The xTUs shall choose the S (factor)
       and D (depth) values such that the actual one-way interleaving
       delay (zxAnXdsl2Ch2StatusActDelay) is as close as possible to,
       but less than or equal to zxAnXdsl2Ch2ConfProfMaxDelayDs.  The
       delay is coded in ms, with the value 0 indicating no delay
       bound is being imposed."
   REFERENCE    "ITU-T G.997.1, paragraph #7.3.2.2"
   ::= { zxAnXdsl2ServiceConfProfEntry 29 }

zxAnXdsl2Ch2ConfProfMaxDelayUs  OBJECT-TYPE
   SYNTAX      Unsigned32(0..63)
   UNITS       "milliseconds"
   MAX-ACCESS  read-create
   STATUS      current
   DESCRIPTION
      "Maximum Interleave Delay on Upstream direction.  The maximum
       one-way interleaving delay introduced by the PMS-TC on
       Upstream direction.  The xTUs shall choose the S (factor) and
       D (depth) values such that the actual one-way interleaving
       delay (zxAnXdsl2Ch2StatusActDelay) is as close as possible to,
       but less than or equal to zxAnXdsl2Ch2ConfProfMaxDelayUs.  The
       delay is coded in ms, with the value 0 indicating no delay
       bound is being imposed."
   REFERENCE    "ITU-T G.997.1, paragraph #7.3.2.2"
   ::= { zxAnXdsl2ServiceConfProfEntry 30 }

zxAnXdsl2Ch2ConfProfMinProtectionDs  OBJECT-TYPE
   SYNTAX      Xdsl2SymbolProtection
   UNITS       "symbols"
   MAX-ACCESS  read-create
   STATUS      current
   DESCRIPTION
      "Minimum Impulse Noise Protection on Downstream direction.
      The
       minimum impulse noise protection for the bearer channel,
       expressed in symbols.  The parameter can take the following
       values: noProtection (i.e., INP not required), halfSymbol
       (i.e., INP length is 1/2 symbol) and 1-16 symbols in steps
       of 1 symbol."
   REFERENCE    "ITU-T G.997.1, paragraph #7.3.2.3"
   DEFVAL       { noProtection }
   ::= { zxAnXdsl2ServiceConfProfEntry 31 }

zxAnXdsl2Ch2ConfProfMinProtectionUs  OBJECT-TYPE
   SYNTAX      Xdsl2SymbolProtection
   UNITS       "symbols"
   MAX-ACCESS  read-create
   STATUS      current
   DESCRIPTION
      "Minimum Impulse Noise Protection on Upstream direction.  The
       minimum impulse noise protection for the bearer channel,
       expressed in symbols.  "
   REFERENCE    "ITU-T G.997.1, paragraph #7.3.2.3"
   DEFVAL       { noProtection }
   ::= { zxAnXdsl2ServiceConfProfEntry 32 }
   

   zxAnXdsl2ServiceConfProfRowStatus  OBJECT-TYPE
        SYNTAX      RowStatus
        MAX-ACCESS  read-create
        STATUS      current
        DESCRIPTION
           "This object is used to create a new row or to modify or
           delete an existing row in this table.
  
           A profile is activated by setting this object to 'active'.
           When 'active' is set, the system will validate the profile.
           Profile modification is prohibited while this object is set
           to 'active'.
  
           Before a profile can be deleted or taken out of service
           (by setting this object to 'destroy' or 'notInService'),
           it must be first unreferenced from all associated
           ports."
        ::= { zxAnXdsl2ServiceConfProfEntry 40 }


  
--------------------------------------------------------------------------
-- 4.zxAnXdsl2DpboConfProfTable
--------------------------------------------------------------------------

   zxAnXdsl2DpboConfProfTable  OBJECT-TYPE
        SYNTAX      SEQUENCE  OF  ZxAnXdsl2DpboConfProfEntry
        MAX-ACCESS  not-accessible
        STATUS      current
        DESCRIPTION
            "The table zxAnXdsl2DpboConfProfTable contains VDSL2/ADSL/
            ADSL2 and ADSL2+ Dpbo configuration profile.
            Entries in this table MUST be maintained in a
            persistent manner."
        ::= { zxAnXdsl2LineProfile 3 }



   zxAnXdsl2DpboConfProfEntry  OBJECT-TYPE
        SYNTAX      ZxAnXdsl2DpboConfProfEntry
        MAX-ACCESS  not-accessible
        STATUS      current
        DESCRIPTION
         "The table zxAnXdsl2DpboConfProfTable contains VDSL2/ADSL/
          ADSL2 and ADSL2+ basic configuration profile.

          A default profile with an index of 'DEFVAL' will
          always exist and its parameters will be set to vendor-specific
          values, unless otherwise specified in this document"
        INDEX  { zxAnXdsl2DpboConfProfileName }
        ::= { zxAnXdsl2DpboConfProfTable 1 }

   ZxAnXdsl2DpboConfProfEntry  ::=
        SEQUENCE {
            zxAnXdsl2DpboConfProfileName            DisplayString,
            zxAnXdsl2LConfProfDpboEPsd              Xdsl2PsdMaskDs,
            zxAnXdsl2LConfProfDpboEsEL              Unsigned32,
            zxAnXdsl2LConfProfDpboEsCableModelA     Unsigned32,
            zxAnXdsl2LConfProfDpboEsCableModelB     Unsigned32,
            zxAnXdsl2LConfProfDpboEsCableModelC     Unsigned32,
            zxAnXdsl2LConfProfDpboMus               Unsigned32,
            zxAnXdsl2LConfProfDpboFMin              Unsigned32,
            zxAnXdsl2LConfProfDpboFMax              Unsigned32,
            zxAnXdsl2DpboConfProfRowStatus          RowStatus
            }
            


    zxAnXdsl2DpboConfProfileName  OBJECT-TYPE
        SYNTAX      DisplayString (SIZE(1..32))
        MAX-ACCESS  not-accessible
        STATUS      current
        DESCRIPTION
            "This object identifies a row in this table."
        ::= { zxAnXdsl2DpboConfProfEntry 1 }

    zxAnXdsl2LConfProfDpboEPsd  OBJECT-TYPE
        SYNTAX      Xdsl2PsdMaskDs
        MAX-ACCESS  read-create
        STATUS      current
        DESCRIPTION
           "(DPBOEPSD).
           This configuration parameter defines the PSD mask that
           is assumed to be permitted at the exchange. This parameter
           shall use the same format as zxAnXdsl2LConfProfPsdMaskDs (PSDMASKds).
           The maximum number of breakpoints for zxAnXdsl2LConfProfDpboEPsd is
           16."
        REFERENCE   "ITU-T G.997.1, paragraph #7.3.1.2.13"
        ::= { zxAnXdsl2DpboConfProfEntry 2 }
     
    zxAnXdsl2LConfProfDpboEsEL  OBJECT-TYPE
        SYNTAX      Unsigned32 (0..511)
        UNITS       "0.5 dB"
        MAX-ACCESS  read-create
        STATUS      current
        DESCRIPTION
           "(DPBOESEL).
           This configuration parameter defines the assumed
           electrical length of cables (E-side cables) connecting
           exchange based DSL services to a remote flexibility point
           (cabinet), that hosts the xTU-C that is subject to
           spectrally shaped downstream power back-off (DPBO)
           depending on this length. The electrical length is
           defined as the loss (in dB) of an equivalent length of
           hypothetical cable at a reference frequency defined by
           the network operator or in spectrum management regulations.
           This parameter shall be coded as an unsigned integer
           representing an electrical length from 0 dB (coded as 0)
           to 255.5 dB (coded as 511) in steps of 0.5 dB. All values
           in the range are valid. If this parameter is set to zero,
           the DPBO shall be disabled."
        REFERENCE   "ITU-T G.997.1, paragraph #7.3.1.2.13"
        DEFVAL      { 0 }
        ::= { zxAnXdsl2DpboConfProfEntry 3 }
     
    zxAnXdsl2LConfProfDpboEsCableModelA  OBJECT-TYPE
        SYNTAX      Unsigned32 (0..640)
        UNITS       "2^-8"
        MAX-ACCESS  read-create
        STATUS      current
        DESCRIPTION
           "(DPBOESCMA).
           The E-side Cable Model parameter A (DPBOESCMA) of the
           cable model (DPBOESCM) for cables connecting exchange based DSL
           services to a remote flexibility point (cabinet), that hosts
           the xTU-C that is subject to spectrally shaped downstream
           power back-off (DPBO) depending on this value.
           The cable model is in terms of three
           scalars zxAnXdsl2LConfProfDpboEsCableModelA (DPBOESCMA),
          zxAnXdsl2LConfProfDpboEsCableModelB(DPBOESCMB),
           and zxAnXdsl2LConfProfDpboEsCableModelC (DPBOESCMC),
           that are used to estimate the frequency dependent loss of E-side
           cables calculated from the zxAnXdsl2LConfProfDpboEsEL (DPBOESEL)
           parameter. Possible values shall be coded as unsigned integers
           representing a scalar value from -1 (coded as 0) to
           1.5 (coded as 640) in steps of 2^-8. All values in the range are
           valid. This parameter is used only for G.993.2."
        REFERENCE   "ITU-T G.997.1, paragraph #7.3.1.2.13"
        DEFVAL      { 0 }
        ::= { zxAnXdsl2DpboConfProfEntry 4 }
     
    zxAnXdsl2LConfProfDpboEsCableModelB  OBJECT-TYPE
        SYNTAX      Unsigned32 (0..640)
        UNITS       "2^-8"
        MAX-ACCESS  read-create
        STATUS      current
        DESCRIPTION
           "(DPBOESCMB).
           The E-side Cable Model parameter B (DPBOESCMB) of the
           cable model (DPBOESCM) for cables connecting exchange based DSL
           services to a remote flexibility point (cabinet), that hosts
           the xTU-C that is subject to spectrally shaped downstream
           power back-off (DPBO) depending on this value.
           The cable model is in terms of three
           scalars zxAnXdsl2LConfProfDpboEsCableModelA (DPBOESCMA),
           zxAnXdsl2LConfProfDpboEsCableModelB(DPBOESCMB),
           and zxAnXdsl2LConfProfDpboEsCableModelC (DPBOESCMC),
           that are used to estimate the frequency dependent loss of E-side
           cables calculated from the zxAnXdsl2LConfProfDpboEsEL (DPBOESEL)
           parameter. Possible values shall be coded as unsigned integers
           representing a scalar value from -1 (coded as 0) to
           1.5 (coded as 640) in steps of 2^-8. All values in the range are
           valid. This parameter is used only for G.993.2."
        REFERENCE   "ITU-T G.997.1, paragraph #7.3.1.2.13"
        DEFVAL      { 0 }
        ::= { zxAnXdsl2DpboConfProfEntry 5 }
     
    zxAnXdsl2LConfProfDpboEsCableModelC  OBJECT-TYPE
        SYNTAX      Unsigned32 (0..640)
        UNITS       "2^-8"
        MAX-ACCESS  read-create
        STATUS      current
        DESCRIPTION
           "(DPBOESCMC).
           The E-side Cable Model parameter C (DPBOESCMC) of the
           cable model (DPBOESCM) for cables connecting exchange based DSL
           services to a remote flexibility point (cabinet), that hosts
           the xTU-C that is subject to spectrally shaped downstream
           power back-off (DPBO) depending on this value.
           The cable model is in terms of three
           scalars zxAnXdsl2LConfProfDpboEsCableModelA (DPBOESCMA),
           zxAnXdsl2LConfProfDpboEsCableModelB(DPBOESCMB),
           and zxAnXdsl2LConfProfDpboEsCableModelC (DPBOESCMC),
           that are used to estimate the frequency dependent loss of E-side
           cables calculated from the zxAnXdsl2LConfProfDpboEsEL (DPBOESEL)
           parameter. Possible values shall be coded as unsigned integers
           representing a scalar value from -1 (coded as 0) to
           1.5 (coded as 640) in steps of 2^-8. All values in the range are
           valid. This parameter is used only for G.993.2."
        REFERENCE   "ITU-T G.997.1, paragraph #7.3.1.2.13"
        DEFVAL      { 0 }
        ::= { zxAnXdsl2DpboConfProfEntry 6 }
     
    zxAnXdsl2LConfProfDpboMus OBJECT-TYPE
        SYNTAX      Unsigned32 (0..255)
        UNITS       "0.5 dB"
        MAX-ACCESS  read-create
        STATUS      current
        DESCRIPTION
           "(DPBOMUS).
           This configuration parameter defines the assumed Minimum Usable
           receive PSD mask (in dBm/Hz) for exchange based services,
           used to modify parameter zxAnXdsl2LConfProfDpboFMax (DPBOFMAX) defined
           below [to determine the DPBO]. It shall be coded as an unsigned
           integer representing a PSD mask level from 0 dBm/Hz (coded as 0)
           to -127.5 dBm/Hz (coded as 255) in steps of 0.5 dB. All values
           in the range are valid.
           NOTE - The PSD mask level is 3.5 dB above the signal PSD
           level. This parameter is used only for G.993.2."
        REFERENCE   "ITU-T G.997.1, paragraph #7.3.1.2.13"
        DEFVAL      { 0 }
        ::= { zxAnXdsl2DpboConfProfEntry 7 }
     
    zxAnXdsl2LConfProfDpboFMin OBJECT-TYPE
        SYNTAX      Unsigned32 (0..2048)
        UNITS       "4.3125 kHz"
        MAX-ACCESS  read-create
        STATUS      current
        DESCRIPTION
           "(DPBOFMIN).
           This configuration parameter defines the minimum frequency
           from which the DPBO shall be applied. It ranges from
           0 kHz (coded as 0) to 8832 kHz (coded as 2048) in steps
           of 4.3125 kHz. This parameter is used only for G.993.2."
        REFERENCE   "ITU-T G.997.1, paragraph #7.3.1.2.13"
        DEFVAL      { 32 }
        ::= { zxAnXdsl2DpboConfProfEntry 8 }
     
    zxAnXdsl2LConfProfDpboFMax OBJECT-TYPE
        SYNTAX      Unsigned32 (32..6956)
        UNITS       "4.3125 kHz"
        MAX-ACCESS  read-create
        STATUS      current
        DESCRIPTION
           "(DPBOFMAX).
           This configuration parameter defines the maximum frequency at
           which DPBO may be applied. It ranges from 138 kHz (coded as 32)
           to 29997.75 kHz (coded as 6956) in steps of 4.3125 kHz.
           This parameter is used only for G.993.2."
        REFERENCE   "ITU-T G.997.1, paragraph #7.3.1.2.13"
        DEFVAL      { 512 }
        ::= { zxAnXdsl2DpboConfProfEntry 9 }
     
     
     
     
   zxAnXdsl2DpboConfProfRowStatus  OBJECT-TYPE
        SYNTAX      RowStatus
        MAX-ACCESS  read-create
        STATUS      current
        DESCRIPTION
           "This object is used to create a new row or to modify or
           delete an existing row in this table.
  
           A profile is activated by setting this object to 'active'.
           When 'active' is set, the system will validate the profile.
           Profile modification is prohibited while this object is set
           to 'active'.
  
           Before a profile can be deleted or taken out of Dpbo
           (by setting this object to 'destroy' or 'notInService'),
           it must be first unreferenced from all associated
           ports."
        ::= { zxAnXdsl2DpboConfProfEntry 20 }


--------------------------------------------------------------------------
-- 5.zxAnXdsl2UpboConfProfTable
--------------------------------------------------------------------------

   zxAnXdsl2UpboConfProfTable  OBJECT-TYPE
        SYNTAX      SEQUENCE  OF  ZxAnXdsl2UpboConfProfEntry
        MAX-ACCESS  not-accessible
        STATUS      current
        DESCRIPTION
            "The table xdsl2UpboConfProfTable contains VDSL2/ADSL/
            ADSL2 and ADSL2+ Upbo configuration profile.
            Entries in this table MUST be maintained in a
            persistent manner."
        ::= { zxAnXdsl2LineProfile 4 }



   zxAnXdsl2UpboConfProfEntry  OBJECT-TYPE
        SYNTAX      ZxAnXdsl2UpboConfProfEntry
        MAX-ACCESS  not-accessible
        STATUS      current
        DESCRIPTION
         "The table xdsl2UpboConfProfTable contains VDSL2/ADSL/
          ADSL2 and ADSL2+ basic configuration profile.

          A default profile with an index of 'DEFVAL' will
          always exist and its parameters will be set to vendor-specific
          values, unless otherwise specified in this document"
        INDEX  { zxAnXdsl2LUpboConfProfileName }
        ::= { zxAnXdsl2UpboConfProfTable 1 }

   ZxAnXdsl2UpboConfProfEntry  ::=
        SEQUENCE {
            zxAnXdsl2LUpboConfProfileName        DisplayString,
            zxAnXdsl2LConfProfUpboKL             Unsigned32,
            zxAnXdsl2LConfProfUpboKLF            Xdsl2UpboKLF,
            zxAnXdsl2LConfProfUpboU0bandPsdA     Unsigned32,
            zxAnXdsl2LConfProfUpboU0bandPsdB     Unsigned32,
            zxAnXdsl2LConfProfUpboU1bandPsdA     Unsigned32,
            zxAnXdsl2LConfProfUpboU1bandPsdB     Unsigned32,
            zxAnXdsl2LConfProfUpboU2bandPsdA     Unsigned32,
            zxAnXdsl2LConfProfUpboU2bandPsdB     Unsigned32,
            zxAnXdsl2LConfProfUpboU3bandPsdA     Unsigned32,
            zxAnXdsl2LConfProfUpboU3bandPsdB     Unsigned32,
            zxAnXdsl2LConfProfUpboU4bandPsdA     Unsigned32,
            zxAnXdsl2LConfProfUpboU4bandPsdB     Unsigned32,
            zxAnXdsl2LUpboConfProfRowStatus      RowStatus
            }
            
    zxAnXdsl2LUpboConfProfileName  OBJECT-TYPE
        SYNTAX      DisplayString (SIZE(1..32))
        MAX-ACCESS  not-accessible
        STATUS      current
        DESCRIPTION
            "This object identifies a row in this table."
        ::= { zxAnXdsl2UpboConfProfEntry 1 }

             
    zxAnXdsl2LConfProfUpboKL  OBJECT-TYPE
        SYNTAX      Unsigned32 (0..1280)
        UNITS       "0.1 dB"
        MAX-ACCESS  read-create
        STATUS      current
        DESCRIPTION
           "(UPBOKL).
           This configuration parameter defines the electrical length
           expressed in dB at 1MHz, kl0, configured by the CO-MIB.
           The value ranges from 0 (coded as 0) to 128 dB (coded as 1280)
           in steps of 0.1 dB. This parameter is relevant only if
           zxAnXdsl2LConfProfUpboKLF is set to override(2), which indicates
           that this parameter's value will override the VTUs'
           determination of the electrical length. If zxAnXdsl2LConfProfUpboKLF
           is set either to auto(1) or disableUpbo(3), then this parameter
           will be ignored."
        REFERENCE   "ITU-T G.997.1, paragraph #7.3.1.2.14"
        DEFVAL      { 0 }
        ::= { zxAnXdsl2UpboConfProfEntry 2 }
     
    zxAnXdsl2LConfProfUpboKLF OBJECT-TYPE
        SYNTAX      Xdsl2UpboKLF
        MAX-ACCESS  read-create
        STATUS      current
        DESCRIPTION
           "Defines the upstream power backoff force mode (UPBOKLF).
           The three possible mode values are:
               auto(1),
               override(2), &
               disableUpbo(3)."
        REFERENCE   "ITU-T G.997.1, paragraph #7.3.1.2.14"
        DEFVAL      { disableUpbo }
        ::= { zxAnXdsl2UpboConfProfEntry 3 }
     
    zxAnXdsl2LConfProfUpboU0bandPsdA  OBJECT-TYPE
        SYNTAX      Unsigned32(4000..8095)
        UNITS       "0.01 dBm/Hz"
        MAX-ACCESS  read-create
        STATUS      current
        DESCRIPTION
           "(UPBOPSD-pb).
           This configuration parameter defines the 'a' reference parameter
           of the UPBO reference PSD used to compute the upstream power
           back-off for the upstream band. A UPBOPSD defined for each band
           shall consist of two parameters [a, b]. Parameter 'a'
           (zxAnXdsl2LConfProfUpboPsdA) ranges from 40 dBm/Hz (coded as 4000) to
           80.95 dBm/Hz (coded as 8095) in steps of 0.01 dBm/Hz; and
           parameter 'b' (zxAnXdsl2LConfProfUpboPsdB) ranges from 0 dBm/Hz
           (coded as 0) to 40.95 dBm/Hz (coded as 4095) in steps of
           0.01 dBm/Hz. The UPBO reference PSD at the frequency 'f' expressed
           in MHz shall be equal to '-a-b(SQRT(f))'. Setting
           zxAnXdsl2LConfProfUpboPsdA to 4000 and zxAnXdsl2LConfProfUpboPsdB to 0 is
           a special configuration to disable UPBO in the respective
           upstream band."
        REFERENCE   "ITU-T G.997.1, paragraph #7.3.1.2.14"
        DEFVAL      { 4000 }
       ::= { zxAnXdsl2UpboConfProfEntry 4 }
       
       
         
    zxAnXdsl2LConfProfUpboU0bandPsdB  OBJECT-TYPE
        SYNTAX      Unsigned32(0..4095)
        UNITS       "0.01 dBm/Hz"
        MAX-ACCESS  read-create
        STATUS      current
        DESCRIPTION
           "(UPBOPSD-pb).
           This configuration parameter defines the 'a' reference parameter
           of the UPBO reference PSD used to compute the upstream power
           back-off for the upstream band. A UPBOPSD defined for each band
           shall consist of two parameters [a, b]. Parameter 'a'
           (zxAnXdsl2LConfProfUpboPsdA) ranges from 40 dBm/Hz (coded as 4000) to
           80.95 dBm/Hz (coded as 8095) in steps of 0.01 dBm/Hz; and
           parameter 'b' (zxAnXdsl2LConfProfUpboPsdB) ranges from 0 dBm/Hz
           (coded as 0) to 40.95 dBm/Hz (coded as 4095) in steps of
           0.01 dBm/Hz. The UPBO reference PSD at the frequency 'f' expressed
           in MHz shall be equal to '-a-b(SQRT(f))'. Setting
           zxAnXdsl2LConfProfUpboPsdA to 4000 and zxAnXdsl2LConfProfUpboPsdB to 0 is
           a special configuration to disable UPBO in the respective
           upstream band."
        REFERENCE   "ITU-T G.997.1, paragraph #7.3.1.2.14"
        DEFVAL      { 0 }
       ::= { zxAnXdsl2UpboConfProfEntry 5 }
       
       
     
     
    zxAnXdsl2LConfProfUpboU1bandPsdA  OBJECT-TYPE
        SYNTAX      Unsigned32(4000..8095)
        UNITS       "0.01 dBm/Hz"
        MAX-ACCESS  read-create
        STATUS      current
        DESCRIPTION
           "(UPBOPSD-pb).
           This configuration parameter defines the 'a' reference parameter
           of the UPBO reference PSD used to compute the upstream power
           back-off for the upstream band. A UPBOPSD defined for each band
           shall consist of two parameters [a, b]. Parameter 'a'
           (zxAnXdsl2LConfProfUpboPsdA) ranges from 40 dBm/Hz (coded as 4000) to
           80.95 dBm/Hz (coded as 8095) in steps of 0.01 dBm/Hz; and
           parameter 'b' (zxAnXdsl2LConfProfUpboPsdB) ranges from 0 dBm/Hz
           (coded as 0) to 40.95 dBm/Hz (coded as 4095) in steps of
           0.01 dBm/Hz. The UPBO reference PSD at the frequency 'f' expressed
           in MHz shall be equal to '-a-b(SQRT(f))'. Setting
           zxAnXdsl2LConfProfUpboPsdA to 4000 and zxAnXdsl2LConfProfUpboPsdB to 0 is
           a special configuration to disable UPBO in the respective
           upstream band."
        REFERENCE   "ITU-T G.997.1, paragraph #7.3.1.2.14"
        DEFVAL      { 4000 }
       ::= { zxAnXdsl2UpboConfProfEntry 6 }
       
       
         
    zxAnXdsl2LConfProfUpboU1bandPsdB  OBJECT-TYPE
        SYNTAX      Unsigned32(0..4095)
        UNITS       "0.01 dBm/Hz"
        MAX-ACCESS  read-create
        STATUS      current
        DESCRIPTION
           "(UPBOPSD-pb).
           This configuration parameter defines the 'a' reference parameter
           of the UPBO reference PSD used to compute the upstream power
           back-off for the upstream band. A UPBOPSD defined for each band
           shall consist of two parameters [a, b]. Parameter 'a'
           (zxAnXdsl2LConfProfUpboPsdA) ranges from 40 dBm/Hz (coded as 4000) to
           80.95 dBm/Hz (coded as 8095) in steps of 0.01 dBm/Hz; and
           parameter 'b' (zxAnXdsl2LConfProfUpboPsdB) ranges from 0 dBm/Hz
           (coded as 0) to 40.95 dBm/Hz (coded as 4095) in steps of
           0.01 dBm/Hz. The UPBO reference PSD at the frequency 'f' expressed
           in MHz shall be equal to '-a-b(SQRT(f))'. Setting
           zxAnXdsl2LConfProfUpboPsdA to 4000 and zxAnXdsl2LConfProfUpboPsdB to 0 is
           a special configuration to disable UPBO in the respective
           upstream band."
        REFERENCE   "ITU-T G.997.1, paragraph #7.3.1.2.14"
        DEFVAL      { 0 }
       ::= { zxAnXdsl2UpboConfProfEntry 7 }
       
               
     
     
     
    zxAnXdsl2LConfProfUpboU2bandPsdA  OBJECT-TYPE
        SYNTAX      Unsigned32(4000..8095)
        UNITS       "0.01 dBm/Hz"
        MAX-ACCESS  read-create
        STATUS      current
        DESCRIPTION
           "(UPBOPSD-pb).
           This configuration parameter defines the 'a' reference parameter
           of the UPBO reference PSD used to compute the upstream power
           back-off for the upstream band. A UPBOPSD defined for each band
           shall consist of two parameters [a, b]. Parameter 'a'
           (zxAnXdsl2LConfProfUpboPsdA) ranges from 40 dBm/Hz (coded as 4000) to
           80.95 dBm/Hz (coded as 8095) in steps of 0.01 dBm/Hz; and
           parameter 'b' (zxAnXdsl2LConfProfUpboPsdB) ranges from 0 dBm/Hz
           (coded as 0) to 40.95 dBm/Hz (coded as 4095) in steps of
           0.01 dBm/Hz. The UPBO reference PSD at the frequency 'f' expressed
           in MHz shall be equal to '-a-b(SQRT(f))'. Setting
           zxAnXdsl2LConfProfUpboPsdA to 4000 and zxAnXdsl2LConfProfUpboPsdB to 0 is
           a special configuration to disable UPBO in the respective
           upstream band."
        REFERENCE   "ITU-T G.997.1, paragraph #7.3.1.2.14"
        DEFVAL      { 4000 }
       ::= { zxAnXdsl2UpboConfProfEntry 8 }
       
       
         
    zxAnXdsl2LConfProfUpboU2bandPsdB  OBJECT-TYPE
        SYNTAX      Unsigned32(0..4095)
        UNITS       "0.01 dBm/Hz"
        MAX-ACCESS  read-create
        STATUS      current
        DESCRIPTION
           "(UPBOPSD-pb).
           This configuration parameter defines the 'a' reference parameter
           of the UPBO reference PSD used to compute the upstream power
           back-off for the upstream band. A UPBOPSD defined for each band
           shall consist of two parameters [a, b]. Parameter 'a'
           (zxAnXdsl2LConfProfUpboPsdA) ranges from 40 dBm/Hz (coded as 4000) to
           80.95 dBm/Hz (coded as 8095) in steps of 0.01 dBm/Hz; and
           parameter 'b' (zxAnXdsl2LConfProfUpboPsdB) ranges from 0 dBm/Hz
           (coded as 0) to 40.95 dBm/Hz (coded as 4095) in steps of
           0.01 dBm/Hz. The UPBO reference PSD at the frequency 'f' expressed
           in MHz shall be equal to '-a-b(SQRT(f))'. Setting
           zxAnXdsl2LConfProfUpboPsdA to 4000 and zxAnXdsl2LConfProfUpboPsdB to 0 is
           a special configuration to disable UPBO in the respective
           upstream band."
        REFERENCE   "ITU-T G.997.1, paragraph #7.3.1.2.14"
        DEFVAL      { 0 }
       ::= { zxAnXdsl2UpboConfProfEntry 9 }
       
       
     
    zxAnXdsl2LConfProfUpboU3bandPsdA  OBJECT-TYPE
        SYNTAX      Unsigned32(4000..8095)
        UNITS       "0.01 dBm/Hz"
        MAX-ACCESS  read-create
        STATUS      current
        DESCRIPTION
           "(UPBOPSD-pb).
           This configuration parameter defines the 'a' reference parameter
           of the UPBO reference PSD used to compute the upstream power
           back-off for the upstream band. A UPBOPSD defined for each band
           shall consist of two parameters [a, b]. Parameter 'a'
           (zxAnXdsl2LConfProfUpboPsdA) ranges from 40 dBm/Hz (coded as 4000) to
           80.95 dBm/Hz (coded as 8095) in steps of 0.01 dBm/Hz; and
           parameter 'b' (zxAnXdsl2LConfProfUpboPsdB) ranges from 0 dBm/Hz
           (coded as 0) to 40.95 dBm/Hz (coded as 4095) in steps of
           0.01 dBm/Hz. The UPBO reference PSD at the frequency 'f' expressed
           in MHz shall be equal to '-a-b(SQRT(f))'. Setting
           zxAnXdsl2LConfProfUpboPsdA to 4000 and zxAnXdsl2LConfProfUpboPsdB to 0 is
           a special configuration to disable UPBO in the respective
           upstream band."
        REFERENCE   "ITU-T G.997.1, paragraph #7.3.1.2.14"
        DEFVAL      { 4000 }
       ::= { zxAnXdsl2UpboConfProfEntry 10 }
       
       
         
    zxAnXdsl2LConfProfUpboU3bandPsdB  OBJECT-TYPE
        SYNTAX      Unsigned32(0..4095)
        UNITS       "0.01 dBm/Hz"
        MAX-ACCESS  read-create
        STATUS      current
        DESCRIPTION
           "(UPBOPSD-pb).
           This configuration parameter defines the 'a' reference parameter
           of the UPBO reference PSD used to compute the upstream power
           back-off for the upstream band. A UPBOPSD defined for each band
           shall consist of two parameters [a, b]. Parameter 'a'
           (zxAnXdsl2LConfProfUpboPsdA) ranges from 40 dBm/Hz (coded as 4000) to
           80.95 dBm/Hz (coded as 8095) in steps of 0.01 dBm/Hz; and
           parameter 'b' (zxAnXdsl2LConfProfUpboPsdB) ranges from 0 dBm/Hz
           (coded as 0) to 40.95 dBm/Hz (coded as 4095) in steps of
           0.01 dBm/Hz. The UPBO reference PSD at the frequency 'f' expressed
           in MHz shall be equal to '-a-b(SQRT(f))'. Setting
           zxAnXdsl2LConfProfUpboPsdA to 4000 and zxAnXdsl2LConfProfUpboPsdB to 0 is
           a special configuration to disable UPBO in the respective
           upstream band."
        REFERENCE   "ITU-T G.997.1, paragraph #7.3.1.2.14"
        DEFVAL      { 0 }
       ::= { zxAnXdsl2UpboConfProfEntry 11 }



    zxAnXdsl2LConfProfUpboU4bandPsdA  OBJECT-TYPE
        SYNTAX      Unsigned32(4000..8095)
        UNITS       "0.01 dBm/Hz"
        MAX-ACCESS  read-create
        STATUS      current
        DESCRIPTION
           "(UPBOPSD-pb).
           This configuration parameter defines the 'a' reference parameter
           of the UPBO reference PSD used to compute the upstream power
           back-off for the upstream band. A UPBOPSD defined for each band
           shall consist of two parameters [a, b]. Parameter 'a'
           (zxAnXdsl2LConfProfUpboPsdA) ranges from 40 dBm/Hz (coded as 4000) to
           80.95 dBm/Hz (coded as 8095) in steps of 0.01 dBm/Hz; and
           parameter 'b' (zxAnXdsl2LConfProfUpboPsdB) ranges from 0 dBm/Hz
           (coded as 0) to 40.95 dBm/Hz (coded as 4095) in steps of
           0.01 dBm/Hz. The UPBO reference PSD at the frequency 'f' expressed
           in MHz shall be equal to '-a-b(SQRT(f))'. Setting
           zxAnXdsl2LConfProfUpboPsdA to 4000 and zxAnXdsl2LConfProfUpboPsdB to 0 is
           a special configuration to disable UPBO in the respective
           upstream band."
        REFERENCE   "ITU-T G.997.1, paragraph #7.3.1.2.14"
        DEFVAL      { 4000 }
       ::= { zxAnXdsl2UpboConfProfEntry 12 }
       
       
         
    zxAnXdsl2LConfProfUpboU4bandPsdB  OBJECT-TYPE
        SYNTAX      Unsigned32(0..4095)
        UNITS       "0.01 dBm/Hz"
        MAX-ACCESS  read-create
        STATUS      current
        DESCRIPTION
           "(UPBOPSD-pb).
           This configuration parameter defines the 'a' reference parameter
           of the UPBO reference PSD used to compute the upstream power
           back-off for the upstream band. A UPBOPSD defined for each band
           shall consist of two parameters [a, b]. Parameter 'a'
           (zxAnXdsl2LConfProfUpboPsdA) ranges from 40 dBm/Hz (coded as 4000) to
           80.95 dBm/Hz (coded as 8095) in steps of 0.01 dBm/Hz; and
           parameter 'b' (zxAnXdsl2LConfProfUpboPsdB) ranges from 0 dBm/Hz
           (coded as 0) to 40.95 dBm/Hz (coded as 4095) in steps of
           0.01 dBm/Hz. The UPBO reference PSD at the frequency 'f' expressed
           in MHz shall be equal to '-a-b(SQRT(f))'. Setting
           zxAnXdsl2LConfProfUpboPsdA to 4000 and zxAnXdsl2LConfProfUpboPsdB to 0 is
           a special configuration to disable UPBO in the respective
           upstream band."
        REFERENCE   "ITU-T G.997.1, paragraph #7.3.1.2.14"
        DEFVAL      { 0 }
       ::= { zxAnXdsl2UpboConfProfEntry 13 }         
         
  
    zxAnXdsl2LUpboConfProfRowStatus  OBJECT-TYPE
        SYNTAX      RowStatus
        MAX-ACCESS  read-create
        STATUS      current
        DESCRIPTION
           "This object is used to create a new row or to modify or
           delete an existing row in this table.
  
           A profile is activated by setting this object to 'active'.
           When 'active' is set, the system will validate the profile.
           Profile modification is prohibited while this object is set
           to 'active'.
  
           Before a profile can be deleted or taken out of Upbo
           (by setting this object to 'destroy' or 'notInService'),
           it must be first unreferenced from all associated
           ports."
        ::= { zxAnXdsl2UpboConfProfEntry 20 }


--------------------------------------------------------------------------
-- 6.zxAnXdsl2AlmThreshPrfTable
--------------------------------------------------------------------------

    zxAnXdsl2AlmThreshPrfTable  OBJECT-TYPE
         SYNTAX      SEQUENCE  OF  ZxAnXdsl2AlmThreshPrfEntry
         MAX-ACCESS  not-accessible
         STATUS      current
         DESCRIPTION
          "The table zxAnXdsl2AlmThreshPrfTable contains DSL
          line PM thresholds profiles.
    
           Entries in this table MUST be maintained in a
           persistent manner."
         ::= { zxAnXdsl2AlarmProfile 1 }
    
    zxAnXdsl2AlmThreshPrfEntry  OBJECT-TYPE
         SYNTAX      ZxAnXdsl2AlmThreshPrfEntry
         MAX-ACCESS  not-accessible
         STATUS      current
         DESCRIPTION
          "The table zxAnXdsl2AlmThreshPrfTable contains DSL
          line PM thresholds profiles.
          A default profile with an index of 'DEFVAL' will
          always exist and its parameters will be set to vendor
          specific values, unless otherwise specified in this
          document"
         INDEX  { zxAnXdsl2AlmThreshPrfName }
         ::= { zxAnXdsl2AlmThreshPrfTable 1 }
    
    ZxAnXdsl2AlmThreshPrfEntry ::=
         SEQUENCE {
         zxAnXdsl2AlmThreshPrfName SnmpAdminString,
         zxAnXdsl2XtucThreshFecs   HCPerfIntervalThreshold,
         zxAnXdsl2XtucThreshEs     HCPerfIntervalThreshold,
         zxAnXdsl2XtucThreshSes    HCPerfIntervalThreshold,
         zxAnXdsl2XtucThreshLoss   HCPerfIntervalThreshold,
         zxAnXdsl2XtucThreshLofs   HCPerfIntervalThreshold,
         zxAnXdsl2XtucThreshLols   HCPerfIntervalThreshold,
         zxAnXdsl2XtucThreshLprs   HCPerfIntervalThreshold,
         zxAnXdsl2XtucThreshUas    HCPerfIntervalThreshold,
         zxAnXdsl2XtucThreshPtmCrcErrs Unsigned32,
         zxAnXdsl2XtucThreshPtmCodViol Unsigned32,
         zxAnXdsl2XturThreshFecs   HCPerfIntervalThreshold,
         zxAnXdsl2XturThreshEs     HCPerfIntervalThreshold,
         zxAnXdsl2XturThreshSes    HCPerfIntervalThreshold,
         zxAnXdsl2XturThreshLoss   HCPerfIntervalThreshold,
         zxAnXdsl2XturThreshLofs   HCPerfIntervalThreshold,
--         zxAnXdsl2XturThreshLols   HCPerfIntervalThreshold,
         zxAnXdsl2XturThreshLprs   HCPerfIntervalThreshold,
         zxAnXdsl2XturThreshUas    HCPerfIntervalThreshold,
         zxAnXdsl2XturThreshPtmCrcErrs Unsigned32,
         zxAnXdsl2XturThreshPtmCodViol Unsigned32,
         zxAnXdsl2ThreshFailedFullInt   Unsigned32,
         zxAnXdsl2ThreshFailedShrtInt   Unsigned32,
         zxAnXdsl2Ch1XtucThrshCodeViol  Unsigned32,
         zxAnXdsl2Ch1XtucThrshCorrected Unsigned32,
         zxAnXdsl2Ch1XturThrshCodeViol  Unsigned32,
         zxAnXdsl2Ch1XturThrshCorrected Unsigned32,
         zxAnXdsl2Ch2XtucThrshCodeViol  Unsigned32,
         zxAnXdsl2Ch2XtucThrshCorrected Unsigned32,
         zxAnXdsl2Ch2XturThrshCodeViol  Unsigned32,
         zxAnXdsl2Ch2XturThrshCorrected Unsigned32,
         zxAnXdsl2AlmThreshPrfRowStatus RowStatus,
         zxAnXdsl2XtucLowDataRateTolerance INTEGER,                
         zxAnXdsl2XturLowDataRateTolerance INTEGER,   
         zxAnXdsl2XtucLowDataRateThresh    Integer32,       
         zxAnXdsl2XturLowDataRateThresh    Integer32,
         zxAnXdsl2XtucInitFailTrapEnable   BITS,
         zxAnXdsl2XturInitFailTrapEnable   BITS                              
         }
    
    zxAnXdsl2AlmThreshPrfName  OBJECT-TYPE
         SYNTAX      SnmpAdminString (SIZE(1..32))
         MAX-ACCESS  not-accessible
         STATUS      current
         DESCRIPTION
         "This object identifies a row in this table."
         ::= { zxAnXdsl2AlmThreshPrfEntry 1 }
    
    zxAnXdsl2XtucThreshFecs  OBJECT-TYPE
         SYNTAX      HCPerfIntervalThreshold
         UNITS       "seconds"
         MAX-ACCESS  read-create
         STATUS      current
         DESCRIPTION
         "A threshold for the xdsl2PMLCurr15MFecs counter,
         when xdsl2PMLCurrUnit is xtuc {1}.
         The value 0 means that no threshold is specified for the
         associated counter."
       REFERENCE    "ITU-T G.997.1, paragraph #7.3.1"
       DEFVAL       { 0 }
         ::= { zxAnXdsl2AlmThreshPrfEntry 2 }
    
    zxAnXdsl2XtucThreshEs  OBJECT-TYPE
         SYNTAX      HCPerfIntervalThreshold
         UNITS       "seconds"
         MAX-ACCESS  read-create
         STATUS      current
         DESCRIPTION
         "A threshold for the xdsl2PMLCurr15MEs counter,
         when xdsl2PMLCurrUnit is xtuc {1}.
         The value 0 means that no threshold is specified for the
         associated counter."
       REFERENCE    "ITU-T G.997.1, paragraph #7.3.1"
       DEFVAL       { 0 }
         ::= { zxAnXdsl2AlmThreshPrfEntry 3 }
    
    zxAnXdsl2XtucThreshSes  OBJECT-TYPE
         SYNTAX      HCPerfIntervalThreshold
         UNITS       "seconds"
         MAX-ACCESS  read-create
         STATUS      current
         DESCRIPTION
         "A threshold for the xdsl2PMLCurr15MSes counter,
         when xdsl2PMLCurrUnit is xtuc {1}.
         The value 0 means that no threshold is specified for the
         associated counter."
       REFERENCE    "ITU-T G.997.1, paragraph #7.3.1"
       DEFVAL       { 0 }
         ::= { zxAnXdsl2AlmThreshPrfEntry 4 }
    
    zxAnXdsl2XtucThreshLoss  OBJECT-TYPE
         SYNTAX      HCPerfIntervalThreshold
         UNITS       "seconds"
         MAX-ACCESS  read-create
         STATUS      current
         DESCRIPTION
         "A threshold for the zxAnXdsl2PMLCurr15MLoss counter,
         when xdsl2PMLCurrUnit is xtuc {1}.
         The value 0 means that no threshold is specified for the
         associated counter."
       REFERENCE    "ITU-T G.997.1, paragraph #7.3.1"
       DEFVAL       { 0 }
         ::= { zxAnXdsl2AlmThreshPrfEntry 5 }

    zxAnXdsl2XtucThreshLofs OBJECT-TYPE
        SYNTAX      HCPerfIntervalThreshold
        UNITS       "seconds"
        MAX-ACCESS  read-create
        STATUS      current
        DESCRIPTION
             "A threshold for the xdsl2PMLCurr15MLoss counter,
             when xdsl2PMLCurrUnit is xtuc {1}.
             The value 0 means that no threshold is specified for the
             associated counter."
       DEFVAL       { 0 }
        ::= { zxAnXdsl2AlmThreshPrfEntry 6}
    
    
    zxAnXdsl2XtucThreshLols  OBJECT-TYPE
        SYNTAX      HCPerfIntervalThreshold
        UNITS       "seconds"
        MAX-ACCESS  read-create
        STATUS      current
        DESCRIPTION
             "A threshold for the xdsl2PMLCurr15MLoss counter,
             when xdsl2PMLCurrUnit is xtuc {1}.
             The value 0 means that no threshold is specified for the
             associated counter."
       DEFVAL       { 0 }
        ::= { zxAnXdsl2AlmThreshPrfEntry 7}
    
    zxAnXdsl2XtucThreshLprs  OBJECT-TYPE
        SYNTAX      HCPerfIntervalThreshold
        UNITS       "seconds"
        MAX-ACCESS  read-create
        STATUS      current
        DESCRIPTION
             "A threshold for the xdsl2PMLCurr15MLoss counter,
             when xdsl2PMLCurrUnit is xtuc {1}.
             The value 0 means that no threshold is specified for the
             associated counter."
       DEFVAL       { 0 }
        ::= { zxAnXdsl2AlmThreshPrfEntry 8}
    
    
    zxAnXdsl2XtucThreshUas  OBJECT-TYPE
         SYNTAX      HCPerfIntervalThreshold
         UNITS       "seconds"
         MAX-ACCESS  read-create
         STATUS      current
         DESCRIPTION
         "A threshold for the zxAnXdsl2PMLCurr15MUas counter,
         when xdsl2PMLCurrUnit is xtuc {1}.
         The value 0 means that no threshold is specified for the
         associated counter."
       REFERENCE    "ITU-T G.997.1, paragraph #7.3.1"
       DEFVAL       { 0 }
         ::= { zxAnXdsl2AlmThreshPrfEntry 9 }


    zxAnXdsl2XtucThreshPtmCrcErrs  OBJECT-TYPE
        SYNTAX      Unsigned32
        MAX-ACCESS  read-create
        STATUS      current
        DESCRIPTION
             "A threshold for the zxAnXdsl2PMLCurr15MPtmCrcErrs counter,
             when xdsl2PMLCurrUnit is xtuc {1}.
             The value 0 means that no threshold is specified for the
             associated counter."
       DEFVAL       { 0 }
        ::= { zxAnXdsl2AlmThreshPrfEntry 10}
    

    zxAnXdsl2XtucThreshPtmCodViol  OBJECT-TYPE
        SYNTAX      Unsigned32
        MAX-ACCESS  read-create
        STATUS      current
        DESCRIPTION
             "A threshold for the zxAnXdsl2PMLCurr15MPtmCodViol counter,
             when xdsl2PMLCurrUnit is xtuc {1}.
             The value 0 means that no threshold is specified for the
             associated counter."
       DEFVAL       { 0 }
        ::= { zxAnXdsl2AlmThreshPrfEntry 11}

    
    zxAnXdsl2XturThreshFecs  OBJECT-TYPE
         SYNTAX      HCPerfIntervalThreshold
         UNITS       "seconds"
         MAX-ACCESS  read-create
         STATUS      current
         DESCRIPTION
         "A threshold for the xdsl2PMLCurr15MFecs counter,
         when xdsl2PMLCurrUnit is xtur {2}.
         The value 0 means that no threshold is specified for the
         associated counter."
       REFERENCE    "ITU-T G.997.1, paragraph #7.3.1"
       DEFVAL       { 0 }
         ::= { zxAnXdsl2AlmThreshPrfEntry 12 }
    
    zxAnXdsl2XturThreshEs  OBJECT-TYPE
         SYNTAX      HCPerfIntervalThreshold
         UNITS       "seconds"
         MAX-ACCESS  read-create
         STATUS      current
         DESCRIPTION
         "A threshold for the xdsl2PMLCurr15MEs counter,
         when xdsl2PMLCurrUnit is xtur {2}.
         The value 0 means that no threshold is specified for the
         associated counter."
       REFERENCE    "ITU-T G.997.1, paragraph #7.3.1"
       DEFVAL       { 0 }
         ::= { zxAnXdsl2AlmThreshPrfEntry 13 }
    
    
    zxAnXdsl2XturThreshSes  OBJECT-TYPE
         SYNTAX      HCPerfIntervalThreshold
         UNITS       "seconds"
         MAX-ACCESS  read-create
         STATUS      current
         DESCRIPTION
         "A threshold for the xdsl2PMLCurr15MSes counter,
         when xdsl2PMLCurrUnit is xtur {2}.
         The value 0 means that no threshold is specified for the
         associated counter."
       REFERENCE    "ITU-T G.997.1, paragraph #7.3.1"
       DEFVAL       { 0 }
         ::= { zxAnXdsl2AlmThreshPrfEntry 14 }
    
    zxAnXdsl2XturThreshLoss  OBJECT-TYPE
         SYNTAX      HCPerfIntervalThreshold
         UNITS       "seconds"
         MAX-ACCESS  read-create
         STATUS      current
         DESCRIPTION
         "A threshold for the xdsl2PMLCurr15MLoss counter,
         when xdsl2PMLCurrUnit is xtur {2}.
         The value 0 means that no threshold is specified for the
         associated counter."
       REFERENCE    "ITU-T G.997.1, paragraph #7.3.1"
       DEFVAL       { 0 }
         ::= { zxAnXdsl2AlmThreshPrfEntry 15 }


    zxAnXdsl2XturThreshLofs OBJECT-TYPE
        SYNTAX      HCPerfIntervalThreshold
        UNITS       "seconds"
        MAX-ACCESS  read-create
        STATUS      current
        DESCRIPTION
             "A threshold for the xdsl2PMLCurr15MLoss counter,
             when xdsl2PMLCurrUnit is xtur {2}.
             The value 0 means that no threshold is specified for the
             associated counter."
       DEFVAL       { 0 }
        ::= { zxAnXdsl2AlmThreshPrfEntry 16}
    
    
--    zxAnXdsl2XturThreshLols  OBJECT-TYPE
--        SYNTAX      HCPerfIntervalThreshold
--        UNITS       "seconds"
--        MAX-ACCESS  read-create
--        STATUS      current
--        DESCRIPTION
--             "A threshold for the xdsl2PMLCurr15MLoss counter,
--             when xdsl2PMLCurrUnit is xtur {2}.
--             The value 0 means that no threshold is specified for the
--             associated counter."
--       DEFVAL       { 0 }
--        ::= { zxAnXdsl2AlmThreshPrfEntry 17}
    
    zxAnXdsl2XturThreshLprs  OBJECT-TYPE
        SYNTAX      HCPerfIntervalThreshold
        UNITS       "seconds"
        MAX-ACCESS  read-create
        STATUS      current
        DESCRIPTION
             "A threshold for the xdsl2PMLCurr15MLoss counter,
             when xdsl2PMLCurrUnit is xtur {2}.
             The value 0 means that no threshold is specified for the
             associated counter."
       DEFVAL       { 0 }
        ::= { zxAnXdsl2AlmThreshPrfEntry 18}
    
    
    zxAnXdsl2XturThreshUas  OBJECT-TYPE
         SYNTAX      HCPerfIntervalThreshold
         UNITS       "seconds"
         MAX-ACCESS  read-create
         STATUS      current
         DESCRIPTION
         "A threshold for the xdsl2PMLCurr15MUas counter,
         when xdsl2PMLCurrUnit is xtur {2}.
         The value 0 means that no threshold is specified for the
         associated counter."
       REFERENCE    "ITU-T G.997.1, paragraph #7.3.1"
       DEFVAL       { 0 }
         ::= { zxAnXdsl2AlmThreshPrfEntry 19 }
    
    zxAnXdsl2XturThreshPtmCrcErrs  OBJECT-TYPE
        SYNTAX      Unsigned32
        MAX-ACCESS  read-create
        STATUS      current
        DESCRIPTION
             "A threshold for the zxAnXdsl2PMLCurr15MPtmCrcErrs counter,
             when xdsl2PMLCurrUnit is xtur {2}.
             The value 0 means that no threshold is specified for the
             associated counter."
       DEFVAL       { 0 }
        ::= { zxAnXdsl2AlmThreshPrfEntry 20}
    

    zxAnXdsl2XturThreshPtmCodViol  OBJECT-TYPE
        SYNTAX      Unsigned32
        MAX-ACCESS  read-create
        STATUS      current
        DESCRIPTION
             "A threshold for the zxAnXdsl2PMLCurr15MPtmCodViol counter,
             when xdsl2PMLCurrUnit is xtur {2}.
             The value 0 means that no threshold is specified for the
             associated counter."
       DEFVAL       { 0 }
        ::= { zxAnXdsl2AlmThreshPrfEntry 21}
        

    zxAnXdsl2ThreshFailedFullInt  OBJECT-TYPE
         SYNTAX      Unsigned32
         MAX-ACCESS  read-create
         STATUS      current
         DESCRIPTION
         "A threshold for the xdsl2PMLCurrInit15MfailedFullInits
         counter.
         The value 0 means that no threshold is specified for the
         associated counter."
       REFERENCE    "ITU-T G.997.1, paragraph #7.3.1"
       DEFVAL       { 0 }
         ::= { zxAnXdsl2AlmThreshPrfEntry 22 }
    
    zxAnXdsl2ThreshFailedShrtInt  OBJECT-TYPE
         SYNTAX      Unsigned32
         MAX-ACCESS  read-create
         STATUS      current
         DESCRIPTION
         "A threshold for the xdsl2PMLCurrInit15MFailedShortInits
         counter.
         The value 0 means that no threshold is specified for the
         associated counter."
       REFERENCE    "ITU-T G.997.1, paragraph #7.3.1"
       DEFVAL       { 0 }
         ::= { zxAnXdsl2AlmThreshPrfEntry 23 }
    
    zxAnXdsl2Ch1XtucThrshCodeViol OBJECT-TYPE
         SYNTAX      Unsigned32
         MAX-ACCESS  read-create
         STATUS      current
         DESCRIPTION
         "A threshold for the xdsl2PMChCurr15MCodingViolations
         counter, when xdsl2PMChCurrUnit is xtuc {1}.
         The value 0 means that no threshold is specified for the
         associated counter."
       REFERENCE    "ITU-T G.997.1, paragraph #7.3.2"
       DEFVAL       { 0 }
         ::= { zxAnXdsl2AlmThreshPrfEntry 24 }
    
    zxAnXdsl2Ch1XtucThrshCorrected  OBJECT-TYPE
         SYNTAX      Unsigned32
         MAX-ACCESS  read-create
         STATUS      current
         DESCRIPTION
         "A threshold for the xdsl2PMChCurr15MCorrectedBlocks
         counter, when xdsl2PMChCurrUnit is xtuc {1}.
         The value 0 means that no threshold is specified for the
         associated counter."
       REFERENCE    "ITU-T G.997.1, paragraph #7.3.2"
       DEFVAL       { 0 }
         ::= { zxAnXdsl2AlmThreshPrfEntry 25 }
    
    zxAnXdsl2Ch1XturThrshCodeViol  OBJECT-TYPE
         SYNTAX      Unsigned32
         MAX-ACCESS  read-create
         STATUS      current
         DESCRIPTION
         "A threshold for the xdsl2PMChCurr15MCodingViolations
         counter, when xdsl2PMChCurrUnit is xtur {2}.
         The value 0 means that no threshold is specified for the
         associated counter."
       REFERENCE    "ITU-T G.997.1, paragraph #7.3.2"
       DEFVAL       { 0 }
         ::= { zxAnXdsl2AlmThreshPrfEntry 26 }
    
    zxAnXdsl2Ch1XturThrshCorrected  OBJECT-TYPE
         SYNTAX      Unsigned32
         MAX-ACCESS  read-create
         STATUS      current
         DESCRIPTION
         "A threshold for the xdsl2PMChCurr15MCorrectedBlocks
         counter, when xdsl2PMChCurrUnit is xtur {2}.
         The value 0 means that no threshold is specified for the
         associated counter."
       REFERENCE    "ITU-T G.997.1, paragraph #7.3.2"
       DEFVAL       { 0 }
         ::= { zxAnXdsl2AlmThreshPrfEntry 27 }
    
    zxAnXdsl2Ch2XtucThrshCodeViol OBJECT-TYPE
         SYNTAX      Unsigned32
         MAX-ACCESS  read-create
         STATUS      current
         DESCRIPTION
         "A threshold for the xdsl2PMChCurr15MCodingViolations
         counter, when xdsl2PMChCurrUnit is xtuc {1}.
         The value 0 means that no threshold is specified for the
         associated counter."
       REFERENCE    "ITU-T G.997.1, paragraph #7.3.2"
       DEFVAL       { 0 }
         ::= { zxAnXdsl2AlmThreshPrfEntry 28 }
    
    zxAnXdsl2Ch2XtucThrshCorrected  OBJECT-TYPE
         SYNTAX      Unsigned32
         MAX-ACCESS  read-create
         STATUS      current
         DESCRIPTION
         "A threshold for the xdsl2PMChCurr15MCorrectedBlocks
         counter, when xdsl2PMChCurrUnit is xtuc {1}.
         The value 0 means that no threshold is specified for the
         associated counter."
       REFERENCE    "ITU-T G.997.1, paragraph #7.3.2"
       DEFVAL       { 0 }
         ::= { zxAnXdsl2AlmThreshPrfEntry 29 }
    
    zxAnXdsl2Ch2XturThrshCodeViol  OBJECT-TYPE
         SYNTAX      Unsigned32
         MAX-ACCESS  read-create
         STATUS      current
         DESCRIPTION
         "A threshold for the xdsl2PMChCurr15MCodingViolations
         counter, when xdsl2PMChCurrUnit is xtur {2}.
         The value 0 means that no threshold is specified for the
         associated counter."
       REFERENCE    "ITU-T G.997.1, paragraph #7.3.2"
       DEFVAL       { 0 }
         ::= { zxAnXdsl2AlmThreshPrfEntry 30 }
    
    zxAnXdsl2Ch2XturThrshCorrected  OBJECT-TYPE
         SYNTAX      Unsigned32
         MAX-ACCESS  read-create
         STATUS      current
         DESCRIPTION
         "A threshold for the xdsl2PMChCurr15MCorrectedBlocks
         counter, when xdsl2PMChCurrUnit is xtur {2}.
         The value 0 means that no threshold is specified for the
         associated counter."
       REFERENCE    "ITU-T G.997.1, paragraph #7.3.2"
       DEFVAL       { 0 }
         ::= { zxAnXdsl2AlmThreshPrfEntry 31 }
    
    
    zxAnXdsl2AlmThreshPrfRowStatus  OBJECT-TYPE
         SYNTAX      RowStatus
         MAX-ACCESS  read-create
         STATUS      current
         DESCRIPTION
          "This object is used to create a new row or to modify or
          delete an existing row in this table.
    
          A profile is activated by setting this object to 'active'.
          When 'active' is set, the system will validate the profile.
    
          Before a profile can be deleted or taken out of service
          (by setting this object to 'destroy' or 'notInService'),
          it must be first unreferenced from all associated
          templates."
         ::= { zxAnXdsl2AlmThreshPrfEntry 32 }
   
    zxAnXdsl2XtucLowDataRateTolerance  OBJECT-TYPE
        SYNTAX      INTEGER(0..100)
        UNITS       "%"
        MAX-ACCESS  read-create
        STATUS      current
        DESCRIPTION
            " Tolerance between zxAnXdsl2ChConfMaxDataRateDs and
              xdsl2ChStatusActDataRate(xtuc).                   
              Calculation:
                           100*(zxAnXdsl2ChConfMaxDataRateDs - xdsl2ChStatusActDataRate(xtuc))
                Difference =-------------------------------------------------------------------
                                     zxAnXdsl2ChConfMaxDataRateDs
              If Difference  is larger than zxAnXdsl2XtucLowDataRateTolerance, 
              zxAnXdsl2LineXtucLowDataRateTrap will be sent.                 
              A value of `0' will disable the trap. "                  
        DEFVAL { 0 }
        ::= { zxAnXdsl2AlmThreshPrfEntry 33 } 
   
    zxAnXdsl2XturLowDataRateTolerance  OBJECT-TYPE
        SYNTAX      INTEGER(0..100)
        UNITS       "%"
        MAX-ACCESS  read-create
        STATUS      current
        DESCRIPTION
            " Tolerance between zxAnXdsl2ChConfMaxDataRateUs and
              xdsl2ChStatusActDataRate(xtur).                   
              Calculation:
                           100*(zxAnXdsl2ChConfMaxDataRateUs - xdsl2ChStatusActDataRate(xtur))
                Difference =-------------------------------------------------------------------
                                     zxAnXdsl2ChConfMaxDataRateUs
              If Difference  is larger than zxAnXdsl2XturLowDataRateTolerance, 
              zxAnXdsl2LineXturLowDataRateTrap will be sent.                 
              A value of `0' will disable the trap. "  
        DEFVAL { 0 }
        ::= { zxAnXdsl2AlmThreshPrfEntry 34 }
                     
    zxAnXdsl2XtucLowDataRateThresh  OBJECT-TYPE
        SYNTAX      Integer32
        UNITS       "kbps"
        MAX-ACCESS  read-create
        STATUS      current
        DESCRIPTION
            " Threshold of xtuc data rate. 
              If xdsl2ChStatusActDataRate(xtuc) is lower than zxAnXdsl2XtucLowDataRateThresh, 
              zxAnXdsl2LineXtucLowDataRateTrap will be sent.
              A value of `0' will disable the trap. "
        DEFVAL { 0 }
        ::= { zxAnXdsl2AlmThreshPrfEntry 35 }  
    
    zxAnXdsl2XturLowDataRateThresh  OBJECT-TYPE
        SYNTAX      Integer32
        UNITS       "kbps"
        MAX-ACCESS  read-create
        STATUS      current
        DESCRIPTION
            " Threshold of xtur data rate. 
              If xdsl2ChStatusActDataRate(xtur) is lower than zxAnXdsl2XturLowDataRateThresh, 
              zxAnXdsl2LineXturLowDataRateTrap will be sent.
              A value of `0' will disable the trap. "
        DEFVAL { 0 }
        ::= { zxAnXdsl2AlmThreshPrfEntry 36 }
        
    zxAnXdsl2XtucInitFailTrapEnable OBJECT-TYPE
        SYNTAX      BITS {
            unused1             (0),
            lossOfFraming       (1),
            lossOfSignal        (2),
            lossOfPower         (3),
            initFailure         (4),
            lossOfSignalQuality (5),
            lossOfLink          (6),
            lossOfSignalAlm     (7)
        }
        MAX-ACCESS  read-create
        STATUS      current
        DESCRIPTION
            "Enables and disables the InitFailureTrap on the xTU-C interface.
             
             unused1             (0) - This bit is no use to enable or disable
                                       the InitFailureTrap on the xTU-C
                                        interface.

             lossOfFraming       (1) - Value 0 means disable the loss of frame 
                                       synchronization trap on the xTU-C
                                       interface.
                                    
             lossOfSignal        (2) - Value 0 means disable the loss of signal
                                       trap on the xTU-C interface.
                               
             lossOfPower         (3) - Value 0 means disable the loss of power 
                                       trap on the xTU-C interface.
                                              
             initFailure         (4) - Value 0 means disable the initialization
                                       failure trap on the xTU-C interface.
                              
             lossOfSignalQuality (5) - Value 0 means disable the loss of signal
                                       quality trap on the xTU-C interface.
                                       
             lossOfLink          (6) - Value 0 means disable the loss of link 
                                       quality trap on the xTU-C interface.
             
             lossOfSignalAlm     (7) - Value 0 means disable the loss of signal
                                       alarm on the xTU-C interface.
            "
        ::= { zxAnXdsl2AlmThreshPrfEntry 37 }
    
    zxAnXdsl2XturInitFailTrapEnable OBJECT-TYPE
        SYNTAX      BITS{
            unused1             (0),
            lossOfFraming       (1),
            lossOfSignal        (2),
            lossOfPower         (3),
            unused2             (4),
            lossOfSignalQuality (5),
            unused3             (6),
            lossOfSignalAlm     (7),
            lossOfPowerAlm      (8)
        }
        MAX-ACCESS  read-create
        STATUS      current
        DESCRIPTION
            "Enables and disables the InitFailureTrap on the xTU-R interface.
            
             unused1             (0) - This bit is no use to enable or disable
                                       the InitFailureTrap on the xTU-R
                                       interface.
             
             lossOfFraming       (1) - Value 0 means disable the loss of frame 
                                       synchronization trap on the xTU-R
                                       interface.
                                    
             lossOfSignal        (2) - Value 0 means disable the loss of signal
                                       trap on the xTU-R interface.
             
             lossOfPower         (3) - Value 0 means disable the loss of power
                                       trap on the xTU-R interface.
             
             unused2             (4) - This bit is no use to enable or disable
                                       the InitFailureTrap on the xTU-R
                                       interface.
                         
             lossOfSignalQuality (5) - Value 0 means disable the loss of signal
                                       quality trap on the xTU-R interface.
             
             unused3             (6) - This bit is no use to enable or disable
                                       the InitFailureTrap on the xTU-R
                                       interface.
                                       
             lossOfSignalAlm     (7) - Value 0 means disable the loss of signal
                                       alarm on the xTU-R interface.
                                       
             lossOfPowerAlm      (8) - Value 0 means disable the loss of power
                                       alarm on the xTU-R interface."
        ::= { zxAnXdsl2AlmThreshPrfEntry 38 }
        
--------------------------------------------------------------------------
-- 7.zxAnXdsl2PMLineCurrTable
--------------------------------------------------------------------------

    zxAnXdsl2PMLineCurrTable  OBJECT-TYPE
       SYNTAX      SEQUENCE  OF  ZxAnXdsl2PMLineCurrEntry
       MAX-ACCESS  not-accessible
       STATUS      current
       DESCRIPTION
          "The table zxAnXdsl2PMLineCurrTable contains current Performance
           Monitoring results of DSL line. "
       ::= { zxAnXdsl2PMLine 1 }
    
    zxAnXdsl2PMLineCurrEntry  OBJECT-TYPE
       SYNTAX      ZxAnXdsl2PMLineCurrEntry
       MAX-ACCESS  not-accessible
       STATUS      current
       DESCRIPTION
          "The table zxAnXdsl2PMLineCurrTable contains current Performance
           Monitoring results of DSL line.
           The index of this table is an interface index where the
           interface has an ifType of vdsl2(xxx) and the termination
           unit."
       AUGMENTS  { xdsl2PMLineCurrEntry }
       ::= { zxAnXdsl2PMLineCurrTable 1 }
    
    ZxAnXdsl2PMLineCurrEntry  ::=
       SEQUENCE {
          zxAnXdsl2PMLCurr15MLofs                 Counter32,
          zxAnXdsl2PMLCurr15MLols                 Counter32,
          zxAnXdsl2PMLCurr15MLprs                 Counter32,
          zxAnXdsl2PMLCurr15MPtmCrcErrs           Counter32,
          zxAnXdsl2PMLCurr15MPtmCodViol           Counter32,
          zxAnXdsl2PMLCurr1DayLofs                Counter32,
          zxAnXdsl2PMLCurr1DayLols                Counter32,
          zxAnXdsl2PMLCurr1DayLprs                Counter32,
          zxAnXdsl2PMLCurr1DayPtmCrcErrs          Counter32,
          zxAnXdsl2PMLCurr1DayPtmCodViol          Counter32
       }
    
    
    zxAnXdsl2PMLCurr15MLofs  OBJECT-TYPE
       SYNTAX      Counter32
       UNITS       "seconds"
       MAX-ACCESS  read-only
       STATUS      current
       DESCRIPTION
          "Count of seconds during this interval that there was LOF ."
       REFERENCE    "ITU-T G.997.1, paragraph #7.2.1"
       ::= { zxAnXdsl2PMLineCurrEntry 1 }
    
    zxAnXdsl2PMLCurr15MLols  OBJECT-TYPE
       SYNTAX      Counter32
       UNITS       "seconds"
       MAX-ACCESS  read-only
       STATUS      current
       DESCRIPTION
          "Count of seconds during this interval that there was LOL."
       REFERENCE    "ITU-T G.997.1, paragraph #7.2.1"
       ::= { zxAnXdsl2PMLineCurrEntry 2 }
    
    
    zxAnXdsl2PMLCurr15MLprs  OBJECT-TYPE
       SYNTAX      Counter32
       UNITS       "seconds"
       MAX-ACCESS  read-only
       STATUS      current
       DESCRIPTION
          "Count of seconds during this interval that there was LPR."
       REFERENCE    "ITU-T G.997.1, paragraph #7.2.1"
       ::= { zxAnXdsl2PMLineCurrEntry 3 }
    

    
    zxAnXdsl2PMLCurr15MPtmCrcErrs  OBJECT-TYPE
       SYNTAX      Counter32
       MAX-ACCESS  read-only
       STATUS      current
       DESCRIPTION
          "Count of the number of occurrences of Ptm Crc Errors during 
          this interval."
       REFERENCE    "ITU-T G.997.1, paragraph #7.2.5"
       ::= { zxAnXdsl2PMLineCurrEntry 4 }
    

    
    zxAnXdsl2PMLCurr15MPtmCodViol  OBJECT-TYPE
       SYNTAX      Counter32
       MAX-ACCESS  read-only
       STATUS      current
       DESCRIPTION
          "Count of the number of occurrences of Ptm coding violations  during 
          this interval."
       REFERENCE    "ITU-T G.997.1, paragraph #7.2.5"
       ::= { zxAnXdsl2PMLineCurrEntry 5 }
    

    
    zxAnXdsl2PMLCurr1DayLofs  OBJECT-TYPE
       SYNTAX      Counter32
       UNITS       "seconds"
       MAX-ACCESS  read-only
       STATUS      current
       DESCRIPTION
          "Count of seconds during this interval that there was LOF."
       REFERENCE    "ITU-T G.997.1, paragraph #7.2.1"
       ::= { zxAnXdsl2PMLineCurrEntry 6 }
    

    
    zxAnXdsl2PMLCurr1DayLols  OBJECT-TYPE
       SYNTAX      Counter32
       UNITS       "seconds"
       MAX-ACCESS  read-only
       STATUS      current
       DESCRIPTION
          "Count of seconds during this interval that there was LOL."
       REFERENCE    "ITU-T G.997.1, paragraph #7.2.1"
       ::= { zxAnXdsl2PMLineCurrEntry 7 }
    

    
    zxAnXdsl2PMLCurr1DayLprs  OBJECT-TYPE
       SYNTAX      Counter32
       UNITS       "seconds"
       MAX-ACCESS  read-only
       STATUS      current
       DESCRIPTION
          "Count of seconds during this interval that there was LPR."
       REFERENCE    "ITU-T G.997.1, paragraph #7.2.1"
       ::= { zxAnXdsl2PMLineCurrEntry 8 }
    

    
    zxAnXdsl2PMLCurr1DayPtmCrcErrs  OBJECT-TYPE
       SYNTAX      Counter32
       MAX-ACCESS  read-only
       STATUS      current
       DESCRIPTION
          "Count of the number of occurrences of Ptm Crc Errors during 
          this interval."
       REFERENCE    "ITU-T G.997.1, paragraph #7.2.5"
       ::= { zxAnXdsl2PMLineCurrEntry 9 }
    

    
    zxAnXdsl2PMLCurr1DayPtmCodViol  OBJECT-TYPE
       SYNTAX      Counter32
       MAX-ACCESS  read-only
       STATUS      current
       DESCRIPTION
          "Count of the number of occurrences of Ptm coding violations  during 
          this interval."
       REFERENCE    "ITU-T G.997.1, paragraph #7.2.5"
       ::= { zxAnXdsl2PMLineCurrEntry 10 }
    
       
       

--------------------------------------------------------------------------
-- 7.1 zxAnXdsl2PMLineHist15MinTable
--------------------------------------------------------------------------

    zxAnXdsl2PMLineHist15MinTable  OBJECT-TYPE
       SYNTAX      SEQUENCE  OF  ZxAnXdsl2PMLineHist15MinEntry
       MAX-ACCESS  not-accessible
       STATUS      current
       DESCRIPTION
          "The table zxAnXdsl2PMLineHist15MinTable contains history Performance 
           Monitoring results for 15min of DSL line. "
       ::= { zxAnXdsl2PMLine 2 }
    
    zxAnXdsl2PMLineHist15MinEntry  OBJECT-TYPE
       SYNTAX      ZxAnXdsl2PMLineHist15MinEntry
       MAX-ACCESS  not-accessible
       STATUS      current
       DESCRIPTION
          "The table zxAnXdsl2PMLineHist15MinTable contains history Performance  
           Monitoring results for 15min of DSL line.
           The index of this table is an interface index where the
           interface has an ifType of vdsl2(xxx) and the termination
           unit."
       AUGMENTS  { xdsl2PMLineHist15MinEntry }
       ::= { zxAnXdsl2PMLineHist15MinTable 1 }
    
    ZxAnXdsl2PMLineHist15MinEntry  ::=
       SEQUENCE {
          zxAnXdsl2PMLHist15MMonitoredTime        Unsigned32,
          zxAnXdsl2PMLHist15MLofs                 Counter32,
          zxAnXdsl2PMLHist15MLols                 Counter32,
          zxAnXdsl2PMLHist15MLprs                 Counter32,
          zxAnXdsl2PMLHist15MPtmCrcErrs           Counter32,
          zxAnXdsl2PMLHist15MPtmCodViol           Counter32,
          zxAnXdsl2PMLHist15MValidInterval         TruthValue
       }
      
    zxAnXdsl2PMLHist15MMonitoredTime  OBJECT-TYPE
       SYNTAX      Unsigned32
       UNITS       "seconds"
       MAX-ACCESS  read-only
       STATUS      current
       DESCRIPTION
          "Total seconds monitored in this interval."
       ::= { zxAnXdsl2PMLineHist15MinEntry 1 }
    
    zxAnXdsl2PMLHist15MLofs  OBJECT-TYPE
       SYNTAX      Counter32
       UNITS       "seconds"
       MAX-ACCESS  read-only
       STATUS      current
       DESCRIPTION
          "Count of seconds during this interval that there was LOF ."
       REFERENCE    "ITU-T G.997.1, paragraph #7.2.1"
       ::= { zxAnXdsl2PMLineHist15MinEntry 2 }
    
    zxAnXdsl2PMLHist15MLols  OBJECT-TYPE
       SYNTAX      Counter32
       UNITS       "seconds"
       MAX-ACCESS  read-only
       STATUS      current
       DESCRIPTION
          "Count of seconds during this interval that there was LOL."
       REFERENCE    "ITU-T G.997.1, paragraph #7.2.1"
       ::= { zxAnXdsl2PMLineHist15MinEntry 3 }
    
    
    zxAnXdsl2PMLHist15MLprs  OBJECT-TYPE
       SYNTAX      Counter32
       UNITS       "seconds"
       MAX-ACCESS  read-only
       STATUS      current
       DESCRIPTION
          "Count of seconds during this interval that there was LPR."
       REFERENCE    "ITU-T G.997.1, paragraph #7.2.1"
       ::= { zxAnXdsl2PMLineHist15MinEntry 4 }
    

    
    zxAnXdsl2PMLHist15MPtmCrcErrs  OBJECT-TYPE
       SYNTAX      Counter32
       MAX-ACCESS  read-only
       STATUS      current
       DESCRIPTION
          "Count of the number of occurrences of Ptm Crc Errors during 
          this interval."
       REFERENCE    "ITU-T G.997.1, paragraph #7.2.5"
       ::= { zxAnXdsl2PMLineHist15MinEntry 5 }
    

    
    zxAnXdsl2PMLHist15MPtmCodViol  OBJECT-TYPE
       SYNTAX      Counter32
       MAX-ACCESS  read-only
       STATUS      current
       DESCRIPTION
          "Count of the number of occurrences of Ptm coding violations  during 
          this interval."
       REFERENCE    "ITU-T G.997.1, paragraph #7.2.5"
       ::= { zxAnXdsl2PMLineHist15MinEntry 6 }
       
    

    zxAnXdsl2PMLHist15MValidInterval  OBJECT-TYPE
       SYNTAX      TruthValue
       MAX-ACCESS  read-only
       STATUS      current
       DESCRIPTION
          "This variable indicates if the data for this interval is
           valid."
       ::= { zxAnXdsl2PMLineHist15MinEntry 7 }



--------------------------------------------------------------------------
-- 17.Trap
--------------------------------------------------------------------------


    zxAnXdsl2LinePerfLOFSThreshXtuc NOTIFICATION-TYPE
       OBJECTS
       {
            zxAnXdsl2PMLCurr15MLofs,
            zxAnXdsl2XtucThreshLofs
       }
       STATUS     current
       DESCRIPTION
         "This notification indicates that the LOF seconds
          threshold has been reached/exceeded for the referred XTU-C."
       ::= { zxAnXdsl2TrapObjects 1 }
    
    zxAnXdsl2LinePerfLOFSThreshXtur NOTIFICATION-TYPE
       OBJECTS
       {
            zxAnXdsl2PMLCurr15MLofs,
            zxAnXdsl2XturThreshLofs
       }
       STATUS     current
       DESCRIPTION
         "This notification indicates that the LOF seconds
          threshold has been reached/exceeded for the referred XTU-R."
       ::= { zxAnXdsl2TrapObjects 2 }
       
    


    zxAnXdsl2LinePerfLOLSThreshXtuc NOTIFICATION-TYPE
       OBJECTS
       {
            zxAnXdsl2PMLCurr15MLols,
            zxAnXdsl2XtucThreshLols
       }
       STATUS     current
       DESCRIPTION
         "This notification indicates that the LOL seconds
          threshold has been reached/exceeded for the referred XTU-C."
       ::= { zxAnXdsl2TrapObjects 3 }
       
    
--    zxAnXdsl2LinePerfLOLSThreshXtur NOTIFICATION-TYPE
--       OBJECTS
--       {
--            zxAnXdsl2PMLCurr15MLols,
--            zxAnXdsl2XturThreshLols
--       }
--       STATUS     current
--       DESCRIPTION
--         "This notification indicates that the LOL seconds
--          threshold has been reached/exceeded for the referred XTU-R."
--       ::= { zxAnXdsl2TrapObjects 4 }
       
    



    zxAnXdsl2LinePerfLPRSThreshXtuc NOTIFICATION-TYPE
       OBJECTS
       {
            zxAnXdsl2PMLCurr15MLprs,
            zxAnXdsl2XtucThreshLprs
       }
       STATUS     current
       DESCRIPTION
         "This notification indicates that the LPR seconds
          threshold has been reached/exceeded for the referred XTU-C."
       ::= { zxAnXdsl2TrapObjects 5 }
       
    
    zxAnXdsl2LinePerfLPRSThreshXtur NOTIFICATION-TYPE
       OBJECTS
       {
            zxAnXdsl2PMLCurr15MLprs,
            zxAnXdsl2XturThreshLprs
       }
       STATUS     current
       DESCRIPTION
         "This notification indicates that the LPR seconds
          threshold has been reached/exceeded for the referred XTU-R."
       ::= { zxAnXdsl2TrapObjects 6 }




    zxAnXdsl2LinePerfPtmCrcErrsThreshXtuc NOTIFICATION-TYPE
       OBJECTS
       {
            zxAnXdsl2PMLCurr15MPtmCrcErrs,
            zxAnXdsl2XtucThreshPtmCrcErrs
       }
       STATUS     current
       DESCRIPTION
         "This notification indicates that the  Ptm Crc Errors
          threshold has been reached/exceeded for the referred XTU-C."
       ::= { zxAnXdsl2TrapObjects 7 }
       
    
    zxAnXdsl2LinePerfPtmCrcErrsThreshXtur NOTIFICATION-TYPE
       OBJECTS
       {
            zxAnXdsl2PMLCurr15MPtmCrcErrs,
            zxAnXdsl2XturThreshPtmCrcErrs
       }
       STATUS     current
       DESCRIPTION
         "This notification indicates that the  Ptm Crc Errors 
          threshold has been reached/exceeded for the referred XTU-R."
       ::= { zxAnXdsl2TrapObjects 8 }



    zxAnXdsl2LinePerfPtmCodViolsThreshXtuc NOTIFICATION-TYPE
       OBJECTS
       {
            zxAnXdsl2PMLCurr15MPtmCodViol,
            zxAnXdsl2XtucThreshPtmCodViol
       }
       STATUS     current
       DESCRIPTION
         "This notification indicates that the Ptm coding violations 
          threshold has been reached/exceeded for the referred XTU-C."
       ::= { zxAnXdsl2TrapObjects 9 }
       
    
    zxAnXdsl2LinePerfPtmCodViolsThreshXtur NOTIFICATION-TYPE
       OBJECTS
       {
            zxAnXdsl2PMLCurr15MPtmCodViol,
            zxAnXdsl2XturThreshPtmCodViol
       }
       STATUS     current
       DESCRIPTION
         "This notification indicates that the Ptm coding violations 
          threshold has been reached/exceeded for the referred XTU-R."
       ::= { zxAnXdsl2TrapObjects 10 }       
          
    zxAnXdsl2LineXtucLowDataRateTrap        NOTIFICATION-TYPE
        OBJECTS { zxAnXdsl2ChConfMaxDataRateDs, xdsl2ChStatusActDataRate,
                  zxAnXdsl2XtucLowDataRateTolerance, zxAnXdsl2XtucLowDataRateThresh}
        STATUS  current
        DESCRIPTION
            "zxAnXdsl2XtucLowDataRateTolerance threshold or zxAnXdsl2XtucLowDataRateThresh reached."
        ::= { zxAnXdsl2TrapObjects 11 }
            
            
    zxAnXdsl2LineXtucLowDataRateClearTrap        NOTIFICATION-TYPE
        OBJECTS { zxAnXdsl2ChConfMaxDataRateDs, xdsl2ChStatusActDataRate,
                  zxAnXdsl2XtucLowDataRateTolerance, zxAnXdsl2XtucLowDataRateThresh}
        STATUS  current
        DESCRIPTION
            " zxAnXdsl2LineXtucLowDataRateTrap clear."
        ::= { zxAnXdsl2TrapObjects 12 }            
            
    zxAnXdsl2LineXturLowDataRateTrap        NOTIFICATION-TYPE
        OBJECTS { zxAnXdsl2ChConfMaxDataRateUs, xdsl2ChStatusActDataRate,
                  zxAnXdsl2XturLowDataRateTolerance, zxAnXdsl2XturLowDataRateThresh}
        STATUS  current
        DESCRIPTION
            "zxAnXdsl2XturLowDataRateTolerance threshold or zxAnXdsl2XturLowDataRateThresh reached."
        ::= { zxAnXdsl2TrapObjects 13 }
            
            
    zxAnXdsl2LineXturLowDataRateClearTrap        NOTIFICATION-TYPE
        OBJECTS { zxAnXdsl2ChConfMaxDataRateUs, xdsl2ChStatusActDataRate,
                  zxAnXdsl2XturLowDataRateTolerance, zxAnXdsl2XturLowDataRateThresh}
        STATUS  current
        DESCRIPTION
            " zxAnXdsl2LineXturLowDataRateTrap clear."
        ::= { zxAnXdsl2TrapObjects 14 }
        
    zxAnXdsl2DataPathMismatchTrap           NOTIFICATION-TYPE
        OBJECTS 
            {
                zxAnXdsl2LnStatusDataPathType,
                zxAnXdsl2LnStatusActDataPathType
            }
        STATUS  current
        DESCRIPTION
            "This trap will be sent to managemet system when configured
             data path type is different from actual data path type on the 
             interface."
        ::= { zxAnXdsl2TrapObjects 15 }
        
    zxAnXdsl2DataPathMismatchClrTrap        NOTIFICATION-TYPE
        OBJECTS
            {
                zxAnXdsl2LnStatusDataPathType,
                zxAnXdsl2LnStatusActDataPathType
            }
        STATUS  current
        DESCRIPTION
            "zxAnXdsl2DataPathMismatchTrap will be cleared when configured
             data path type matches actual data path type on the 
             interface."
        ::= { zxAnXdsl2TrapObjects 16 }
      
END

--------------------------------------------------------------------------
-- File Name : ZTE-DSL-ATM-MIB.mib
-- Date      : 2006-09-08
-- Author    : ZTE Nms dept.

--
-- Zte Atm Mib for Dsl
-- 
-- 
--------------------------------------------------------------------------




ZTE-DSL-ATM-MIB DEFINITIONS ::= BEGIN
    IMPORTS
        MODULE-IDENTITY, OBJECT-TYPE, enterprises,
        TimeTicks,Counter32, Gauge32    FROM SNMPv2-SMI
        MODULE-COMPLIANCE, OBJECT-GROUP FROM SNMPv2-CONF
        SnmpAdminString                 FROM SNMP-FRAMEWORK-MIB
        ifIndex                         FROM IF-MIB
        RowStatus                       FROM SNMPv2-TC;


   zxDslAtmMib MODULE-IDENTITY
           LAST-UPDATED "200609081300Z"
           ORGANIZATION "zte dsl product line"
           CONTACT-INFO
               " su chunshan
                 Mail: suchunshan@zte.com.cn
                 Tel : 021-68896292,68896251"
           DESCRIPTION
               "This mib defines extended atm mo (managed object ). "
   ::= {zxDsl 26}
   

   zte OBJECT IDENTIFIER ::= { enterprises 3902 }
   zxDsl OBJECT IDENTIFIER ::= { zte 1004 }
   
   
   zxDslAtmMibObjects OBJECT IDENTIFIER ::= { zxDslAtmMib 1 }
   



--------------------------------------------------------------------------------
-- Following objects are defined.
-- 1.Atm Vc cross connect table
-- 2.
--------------------------------------------------------------------------------



    
------------------------------------------------------------------------------
-- 1.Atm Vc cross connect table
------------------------------------------------------------------------------
   
    zxDslAtmVcxTable OBJECT-TYPE
         SYNTAX         SEQUENCE OF zxDslAtmVcxEntry
         MAX-ACCESS     not-accessible
         STATUS         current
         DESCRIPTION
          "The ATM VC Cross Connect table for PVCs.
           An entry in this table models two
           cross-connected VCLs.
           Each VCL must be pvc."
         ::= { zxDslAtmMibObjects 1 }

                       
    zxDslAtmVcxEntry OBJECT-TYPE
         SYNTAX       zxDslAtmVcxEntry
         MAX-ACCESS   not-accessible
         STATUS       current
         DESCRIPTION
          "An entry in the ATM VC Cross Connect table.
           This entry is used to model a bi-directional ATM
           VC cross-connect cross-connecting two end points.
             "
         INDEX { 
               zxDslAtmVcxUserSideIfIndex,
               zxDslAtmVcxUserSideVpi,
               zxDslAtmVcxUserSideVci,
               zxDslAtmVcxWanSideIfIndex,
               zxDslAtmVcxWanSideVpi,
               zxDslAtmVcxWanSideVci }
         ::= { zxDslAtmVcxTable 1 }
    
    zxDslAtmVcxEntry ::= SEQUENCE {
         zxDslAtmVcxUserSideIfIndex    Integer32,
         zxDslAtmVcxUserSideVpi        Integer32,
         zxDslAtmVcxUserSideVci        Integer32,
         zxDslAtmVcxWanSideIfIndex     Integer32,
         zxDslAtmVcxWanSideVpi         Integer32,
         zxDslAtmVcxWanSideVci         Integer32,
         zxDslAtmVcxAdminStatus        Integer32,
         zxDslAtmVcxOperStatus         Integer32,
         zxDslAtmVcxRowStatus          RowStatus
                 }


    zxDslAtmVcxUserSideIfIndex OBJECT-TYPE
         SYNTAX         Integer32
         MAX-ACCESS     not-accessible
         STATUS         current
         DESCRIPTION
          "The ifIndex value of the ATM interface for this
           VC cross-connect. The term UserSide implies
           that this ATM interface has the numerically UserSide
           ifIndex value than the other ATM interface
           identified in the same zxDslAtmVcxEntry."
         ::= { zxDslAtmVcxEntry 1 }

    zxDslAtmVcxUserSideVpi OBJECT-TYPE
         SYNTAX         Integer32
         MAX-ACCESS     not-accessible
         STATUS         current
         DESCRIPTION
          "The VPI value at the ATM interface
           associated with the VC cross-connect that is
           identified by zxDslAtmVcxUserSideIfIndex."
         ::= { zxDslAtmVcxEntry 2 }

    zxDslAtmVcxUserSideVci OBJECT-TYPE
         SYNTAX         Integer32
         MAX-ACCESS     not-accessible
         STATUS         current
         DESCRIPTION
          "The VCI value at the ATM interface
           associated with this VC cross-connect that is
           identified by zxDslAtmVcxUserSideIfIndex."
         ::= { zxDslAtmVcxEntry 3 }

    zxDslAtmVcxWanSideIfIndex OBJECT-TYPE
         SYNTAX         Integer32
         MAX-ACCESS     not-accessible
         STATUS         current
         DESCRIPTION
          "The ifIndex value for the ATM interface for
           this VC cross-connect. The term WanSide implies
           that this ATM interface has the numerically WanSide
           ifIndex value than the other ATM interface
           identified in the same zxDslAtmVcxEntry."
         ::= { zxDslAtmVcxEntry 4 }

    zxDslAtmVcxWanSideVpi OBJECT-TYPE
         SYNTAX         Integer32
         MAX-ACCESS     not-accessible
         STATUS         current
         DESCRIPTION
          "The VPI value at the ATM interface
           associated with the VC cross-connect that is
           identified by zxDslAtmVcxWanSideIfIndex."
         ::= { zxDslAtmVcxEntry 5 }

    zxDslAtmVcxWanSideVci OBJECT-TYPE
         SYNTAX         Integer32
         MAX-ACCESS     not-accessible
         STATUS         current
         DESCRIPTION
          "The VCI value at the ATM interface
           associated with the VC cross-connect that is
           identified by zxDslAtmVcxWanSideIfIndex."
         ::= { zxDslAtmVcxEntry 6 }

    zxDslAtmVcxAdminStatus OBJECT-TYPE
         SYNTAX         Integer32
         MAX-ACCESS     read-create
         STATUS         current
         DESCRIPTION
          "The desired administrative status of this
           bi-directional VC cross-connect."
         DEFVAL { down }
         ::= { zxDslAtmVcxEntry 7 }



    zxDslAtmVcxOperStatus OBJECT-TYPE
         SYNTAX         Integer32
         MAX-ACCESS     read-only
         STATUS         current
         DESCRIPTION
          "The current operational status of the
           VC cross-connect in one direction; (i.e.,
           from the WanSide to UserSide direction)."
         ::= { zxDslAtmVcxEntry 8 }

  
    zxDslAtmVcxRowStatus OBJECT-TYPE
         SYNTAX         RowStatus
         MAX-ACCESS     read-create
         STATUS         current
         DESCRIPTION
          "The status of this entry in the
           zxDslAtmVcxTable.  This object is used to
           create a new cross-connect for cross-connecting
           VCLs which are created using the atmVclTable
           or to change or delete existing cross-connect.
           This object must be initially set to
           `createAndWait' or 'createAndGo'.
           To turn on a VC cross-connect,
           the zxDslAtmVcxAdminStatus
           is set to `up'."
         DEFVAL { createAndWait }
         ::= { zxDslAtmVcxEntry 9 }

    
            
END

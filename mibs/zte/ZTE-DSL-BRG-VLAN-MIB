--------------------------------------------------------------------------
-- File Name : ZTE-DSL-BRG-VLAN-MIB.mib
-- Date      : 2007-02-14
-- Author    : ZTE Nms dept.

--
-- Zte Bridge Port Vlan Mib for DSL
-- 
-- 
--------------------------------------------------------------------------


ZTE-DSL-BRG-VLAN-MIB DEFINITIONS ::= BEGIN

    IMPORTS
        MODULE-IDENTITY, OBJECT-TYPE, Integer32, Unsigned32
                                                    FROM SNMPv2-SMI
        RowStatus,DisplayString,
        TEXTUAL-CONVENTION                          FROM SNMPv2-TC
        ifIndex                                     FROM IF-MIB
        enterprises                                 FROM RFC1155-SMI;


    zxDslBrgVlanMib MODULE-IDENTITY
        LAST-UPDATED    "200702141500Z"
        ORGANIZATION "ZTE Corporation"
        CONTACT-INFO "ZTE NMS dept. 
                      Su Chunshan   68896292 "
        DESCRIPTION  "This MIB defines managed objects of DSL bridge port vlan mgmt."
         ::= {zxDsl 31}
         


   zte    OBJECT IDENTIFIER ::= { enterprises 3902 }
   zxDsl  OBJECT IDENTIFIER ::= { zte 1004 }


--------------------------------------------------------------------------------
-- Following objects are defined.
-- 1.Bridge Port Vlan Realation Table
-- 2.User-Side Bridge Port Vlan Realation Table
--------------------------------------------------------------------------------



--------------------------------------------------------------------------------
-- 1.Bridge Port Vlan Realation Table
--------------------------------------------------------------------------------
 
    zxDslBrgPortVlanTable OBJECT-TYPE
        SYNTAX SEQUENCE OF ZxDslBrgPortVlanEntry
        MAX-ACCESS  not-accessible
        STATUS      current
        DESCRIPTION
            "Bridge Port Vlan Realation Table."
        ::= { zxDslBrgVlanMib  1 }


    zxDslBrgPortVlanEntry OBJECT-TYPE
        SYNTAX      ZxDslBrgPortVlanEntry
        MAX-ACCESS  not-accessible
        STATUS      current
        DESCRIPTION
            "Bridge Port Vlan Realation Table."
        INDEX { ifIndex,zxDslBrgPortId }
        ::= { zxDslBrgPortVlanTable 1 }
      
    ZxDslBrgPortVlanEntry ::= SEQUENCE {
      zxDslBrgPortId               INTEGER,
      zxDslBrgPortVlanList         BITS,
      zxDslBrgPortVlanUntagList    BITS
    }
    

    zxDslBrgPortId OBJECT-TYPE
        SYNTAX      INTEGER
        MAX-ACCESS  not-accessible
        STATUS      current
        DESCRIPTION
            "A unique value for the bridge port of a physical port.If the 
            bridge port is just a pvc,then this value is pvcId or pvcNo."
        ::= { zxDslBrgPortVlanEntry 1 }


    zxDslBrgPortVlanList OBJECT-TYPE
        SYNTAX      BITS  
        MAX-ACCESS  read-write
        STATUS      current
        DESCRIPTION
            "It is a list of vlan which this brige port joined.Each bit of this 
            variable indicates a vlan Id, BITS(0) means vlanId 1. The vlaue 0 of
            bit means this port doesn't join this vlan.
        "
      ::= { zxDslBrgPortVlanEntry 2 }


    zxDslBrgPortVlanUntagList OBJECT-TYPE
        SYNTAX      BITS  
        MAX-ACCESS  read-write
        STATUS      current
        DESCRIPTION
            "It is a list of untag which is a mode of this brige port joining the 
            vlan.Each bit of this variable indicates a vlan Id, BITS(0) means 
            vlanId 1. The vlaue 1 of bit means untag.
        "
      ::= { zxDslBrgPortVlanEntry 3 }



--------------------------------------------------------------------------------
-- 2.User-Side Bridge Port Vlan Realation Table
--------------------------------------------------------------------------------
 
    zxDslUsrBrgPortVlanTable OBJECT-TYPE
        SYNTAX SEQUENCE OF ZxDslUsrBrgPortVlanEntry
        MAX-ACCESS  not-accessible
        STATUS      current
        DESCRIPTION
            "User side bridge port vlan realation table."
        ::= { zxDslBrgVlanMib  2 }


    zxDslUsrBrgPortVlanEntry OBJECT-TYPE
        SYNTAX      ZxDslUsrBrgPortVlanEntry
        MAX-ACCESS  not-accessible
        STATUS      current
        DESCRIPTION
            "User side bridge port vlan realation table."
        INDEX { ifIndex,zxDslUsrBrgPortId }
        ::= { zxDslUsrBrgPortVlanTable 1 }
      
    ZxDslUsrBrgPortVlanEntry ::= SEQUENCE {
      zxDslUsrBrgPortId               INTEGER,
      zxDslUsrBrgPortVlanList         DisplayString
    }
    

    zxDslUsrBrgPortId OBJECT-TYPE
        SYNTAX      INTEGER
        MAX-ACCESS  not-accessible
        STATUS      current
        DESCRIPTION
            "A unique value for the user side bridge port of a physical port.If the 
            bridge port is just a pvc,then this value is pvcId or pvcNo."
        ::= { zxDslUsrBrgPortVlanEntry 1 }


    zxDslUsrBrgPortVlanList OBJECT-TYPE
        SYNTAX      DisplayString  
        MAX-ACCESS  read-only
        STATUS      current
        DESCRIPTION
            "It is a list of vlan which the user side brige port joined.
            The VLANs are seperated by comma, eg. '1,2,1023'.
        "
      ::= { zxDslUsrBrgPortVlanEntry 2 }



END

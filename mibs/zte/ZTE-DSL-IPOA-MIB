--------------------------------------------------------------------------
-- File Name : ZTE-DSL-IPOA-MIB.mib
-- Date      : 2009-01-21
-- Author    : ZTE Nms dept.

--
-- Zte Dsl IPOA Mib 
-- 
--------------------------------------------------------------------------

ZTE-DSL-IPOA-MIB DEFINITIONS ::= BEGIN 
IMPORTS 
	OBJECT-TYPE, MODULE-IDENTITY, IpAddress,
	Counter32, Integer32                    FROM SNMPv2-SMI 
	TruthValue, MacAddress, RowStatus       FROM SNMPv2-TC
	ifIndex                                 FROM RFC1213-MIB
	zxDsl                                   FROM ZTE-DSL-MIB;
    
zxDslIpoaMib  MODULE-IDENTITY 
        LAST-UPDATED    "200901211200Z"
        ORGANIZATION    "Zhongxing Telcom Co. Ltd."
        CONTACT-INFO    "E-mail: yao.huayin@zte.com.cn"
        DESCRIPTION     "IPOA MIB definition."        
        ::= { zxDsl 44 }  
        
        
zxDslIpoaMibObjects     OBJECT IDENTIFIER  ::= { zxDslIpoaMib 1 }  



--------------------------------------------------------------------------------
-- Following objects are defined.
-- 1.Ipoa Global Mgmt
-- 2.1 Ipoa User Config Table
-- 2.2 Ipoa User info Table
------------------------------------------------------------------------------



------------------------------------------------------------------------------
-- 1.Ipoa Global Mgmt
------------------------------------------------------------------------------

zxDslIpoaGlobalObjects     OBJECT IDENTIFIER  ::= { zxDslIpoaMibObjects 1 }  

zxDslIpoaDefGateway OBJECT-TYPE
	SYNTAX      IpAddress
	MAX-ACCESS  read-write
	STATUS      current
	DESCRIPTION
	  "IPOA user's default gateway"
	::= { zxDslIpoaGlobalObjects 1 }

zxDslIpoaQueryInterval OBJECT-TYPE
	SYNTAX      Integer32(1..60)
    UNITS       "minutes"
	MAX-ACCESS  read-write
	STATUS      current
    DESCRIPTION
      "IPOA InATMARP query interval"
    DEFVAL       { 10 }
	::= { zxDslIpoaGlobalObjects 2 }
	
zxDslIpoaGatewayARPInterval OBJECT-TYPE
	SYNTAX      Integer32(1..60)
    UNITS       "minutes"
	MAX-ACCESS  read-write
	STATUS      current
    DESCRIPTION
      "IPOA gateway arp query interval" 
    DEFVAL       { 10 }
	::= { zxDslIpoaGlobalObjects 3 }



------------------------------------------------------------------------------
-- 2.1 Ipoa User Config Table
------------------------------------------------------------------------------

zxDslIpoaUser     OBJECT IDENTIFIER  ::= { zxDslIpoaMibObjects 2 }

zxDslIpoaUserConfTable OBJECT-TYPE
	SYNTAX SEQUENCE OF ZxDslIpoaUserConfEntry
	MAX-ACCESS not-accessible
	STATUS current
	DESCRIPTION
	"IPOA user table"
	::= { zxDslIpoaUser 1 }	
	
zxDslIpoaUserConfEntry OBJECT-TYPE
	SYNTAX ZxDslIpoaUserConfEntry
	MAX-ACCESS not-accessible
	STATUS current
	DESCRIPTION
	"IPOA user entry "
	INDEX { ifIndex, zxDslIpoaUserConfBrgPortId }
	::= { zxDslIpoaUserConfTable 1 }
        
ZxDslIpoaUserConfEntry ::= SEQUENCE {
    zxDslIpoaUserConfBrgPortId      INTEGER,
	zxDslIpoaUserConfIp             IpAddress,
	zxDslIpoaUserConfInAtmArp       INTEGER,
	zxDslIpoaUserConfLayer          INTEGER,
	zxDslIpoaUserConfL2gatewayIp    IpAddress,
	zxDslIpoaUserConfL2gatewayMac   MacAddress,
	zxDslIpoaUserConfRowStatus      RowStatus
	}		
	
zxDslIpoaUserConfBrgPortId OBJECT-TYPE
        SYNTAX      INTEGER
        MAX-ACCESS  not-accessible
        STATUS      current
        DESCRIPTION
            "A unique value for the bridge port of a physical port.If the 
            bridge port is just a pvc,then this value is pvcId or pvcNo."
        ::= { zxDslIpoaUserConfEntry 1 }	
	
zxDslIpoaUserConfIp OBJECT-TYPE
	SYNTAX         IpAddress
	MAX-ACCESS     read-create
	STATUS         current       
	DESCRIPTION
	"IPOA user's ip address"
	::= { zxDslIpoaUserConfEntry 2 }
  
zxDslIpoaUserConfInAtmArp OBJECT-TYPE
	SYNTAX	    INTEGER
	    {   
	      enable(1),
	      disable(2)
	    }
	MAX-ACCESS  read-create
	STATUS      current
	DESCRIPTION
	  "Enable or disable getting IPOA user's ip address by InAtmARP"
	DEFVAL { enable }
	::= { zxDslIpoaUserConfEntry 3 }

zxDslIpoaUserConfLayer OBJECT-TYPE
 	SYNTAX	    INTEGER
	    {   
    		layer2(1),
    		layer3(2)
            }
 	MAX-ACCESS  read-create
 	STATUS      current
 	DESCRIPTION
 	"Layer 2 IPOA user or Layer 3 IPOA user"
 	DEFVAL { layer2 }
 	::= { zxDslIpoaUserConfEntry 4 }

zxDslIpoaUserConfL2gatewayIp OBJECT-TYPE
	SYNTAX         IpAddress
	MAX-ACCESS     read-create
	STATUS         current       
	DESCRIPTION
	"Layer 2 IPOA user's gateway ip address"
	::= { zxDslIpoaUserConfEntry 5 }

          
zxDslIpoaUserConfL2gatewayMac OBJECT-TYPE
	SYNTAX         MacAddress
	MAX-ACCESS     read-create
	STATUS         current       
	DESCRIPTION
	"Layer 2 IPOA user's gateway mac address"
	::= { zxDslIpoaUserConfEntry 6 }  
	  
zxDslIpoaUserConfRowStatus  OBJECT-TYPE 
	SYNTAX          RowStatus
	MAX-ACCESS      read-create
	STATUS          current
	DESCRIPTION     "The row status of this entry."
	::=  {  zxDslIpoaUserConfEntry 10 }   


------------------------------------------------------------------------------
-- 2.2 Ipoa User info Table
------------------------------------------------------------------------------

zxDslIpoaUserInfoTable OBJECT-TYPE
  SYNTAX SEQUENCE OF ZxDslIpoaUserInfoEntry
  MAX-ACCESS not-accessible
  STATUS current
  DESCRIPTION
  "IPOA user table"
  ::= { zxDslIpoaUser 2 }	
	
zxDslIpoaUserInfoEntry OBJECT-TYPE
  SYNTAX ZxDslIpoaUserInfoEntry
  MAX-ACCESS not-accessible
  STATUS current
  DESCRIPTION
  "IPOA user entry "
  INDEX { ifIndex, zxDslIpoaUserInfoBrgPortId  }

  ::= { zxDslIpoaUserInfoTable 1 }
        
ZxDslIpoaUserInfoEntry ::= SEQUENCE {
    zxDslIpoaUserInfoBrgPortId   INTEGER,
	zxDslIpoaUserInfoVlan        Integer32,
	zxDslIpoaUserInfoIp          IpAddress,
	zxDslIpoaUserInfoMac	     MacAddress,
	zxDslIpoaUserInfoGatewayIp   IpAddress,
	zxDslIpoaUserInfoGatewayMac  MacAddress
	}	

zxDslIpoaUserInfoBrgPortId OBJECT-TYPE
        SYNTAX      INTEGER
        MAX-ACCESS  not-accessible
        STATUS      current
        DESCRIPTION
            "A unique value for the bridge port of a physical port.If the 
            bridge port is just a pvc,then this value is pvcId or pvcNo."
        ::= { zxDslIpoaUserInfoEntry 1 }	
        
zxDslIpoaUserInfoVlan OBJECT-TYPE
	SYNTAX	    Integer32
	MAX-ACCESS  read-only
	STATUS      current
	DESCRIPTION
	"IPOA user's vlan ID"
	::= { zxDslIpoaUserInfoEntry 2 }	

zxDslIpoaUserInfoIp OBJECT-TYPE
  SYNTAX         IpAddress
  MAX-ACCESS     read-only
  STATUS         current       
  DESCRIPTION
  "IPOA user's ip address"
  ::= { zxDslIpoaUserInfoEntry 3 }
  
zxDslIpoaUserInfoMac OBJECT-TYPE
	SYNTAX         MacAddress
	MAX-ACCESS     read-only
	STATUS         current       
	DESCRIPTION
	"IPOA user's mac address"
	::= { zxDslIpoaUserInfoEntry 4 }  

zxDslIpoaUserInfoGatewayIp OBJECT-TYPE
          SYNTAX         IpAddress
          MAX-ACCESS     read-only
          STATUS         current       
          DESCRIPTION
          "IPOA user's gateway ip address"
          ::= { zxDslIpoaUserInfoEntry 5 }
          
zxDslIpoaUserInfoGatewayMac OBJECT-TYPE
	SYNTAX         MacAddress
	MAX-ACCESS     read-only
	STATUS         current       
	DESCRIPTION
	"IPOA user's gateway mac address"
	::= { zxDslIpoaUserInfoEntry 6 }  
	
	
END

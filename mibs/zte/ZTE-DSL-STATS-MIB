------------------------------------------------------------------------------
--
-- zte dsl stats mib,inculde uplink port performanc,cpu load and memory usage mo. 
-- 
------------------------------------------------------------------------------

ZTE-DSL-STATS-MIB DEFINITIONS ::= BEGIN
IMPORTS 
        MODULE-IDENTITY, OBJECT-TYPE,NOTIFICATION-TYPE      FROM SNMPv2-SMI
        RowStatus                                           FROM SNMPv2-TC
        dot1dBasePort                                       FROM BRIDGE-MIB
        ifIndex                                             FROM IF-MIB 
        zxDsl                                               FROM ZTE-DSL-MIB;


 zxDslStaticsMib MODULE-IDENTITY
    LAST-UPDATED "200407152000Z"
    ORGANIZATION "ZTE Corporation"
    CONTACT-INFO ""
    DESCRIPTION  "This MIB defines zte dsl stats managed objects. "
    ::= {zxDsl 38}


 zxDslStatsObjects     OBJECT IDENTIFIER ::= {zxDslStaticsMib 1}
 zxDslStatsTrapObjects OBJECT IDENTIFIER ::= {zxDslStaticsMib 2}


------------------------------------------------------------------------------
---
---   etherport stats table 
--- 
------------------------------------------------------------------------------
 zxDslEtherStatsTable OBJECT-TYPE
    SYNTAX SEQUENCE OF ZxDslEtherStatsEntry
    MAX-ACCESS not-accessible
    STATUS current
    DESCRIPTION
    "The ether stats Information table. "
    ::= { zxDslStatsObjects 1 }
    
 zxDslEtherStatsEntry OBJECT-TYPE
    SYNTAX ZxDslEtherStatsEntry
    MAX-ACCESS not-accessible
    STATUS current
    DESCRIPTION
    "An entry in the ether stats table . "
    INDEX { ifIndex }
    ::= { zxDslEtherStatsTable 1 }
    
 ZxDslEtherStatsEntry ::= SEQUENCE {
        zxDslEtherRxRate                    Gauge32,
        zxDslEtherTxRate                    Gauge32,
        zxDslEtherRxDiscardRatio            INTEGER,
        zxDslEtherTxDiscardRatio            INTEGER,
        zxDslEtherBroadcastRxRate           Gauge32,
        zxDslEtherBroadcastTxRate           Gauge32,
        zxDslEtherMulticastRxRate           Gauge32,
        zxDslEtherMulticastTxRate           Gauge32,
        zxDslEtherUnicastRxRate             Gauge32,
        zxDslEtherUnicastTxRate             Gauge32
  }                                     

      
 zxDslEtherRxRate OBJECT-TYPE             
    SYNTAX  Gauge32
    UNITS   "BYTES/S"
    MAX-ACCESS read-only                 
    STATUS current                        
    DESCRIPTION
        "The ethernet port receiving rate. "
    ::= { zxDslEtherStatsEntry 1 }   

 zxDslEtherTxRate OBJECT-TYPE             
    SYNTAX  Gauge32
    UNITS   "BYTES/S"
    MAX-ACCESS read-only                 
    STATUS current                        
    DESCRIPTION
        "The ethernet port transmitting rate. "
    ::= { zxDslEtherStatsEntry 2 }   

 zxDslEtherRxDiscardRatio OBJECT-TYPE             
    SYNTAX  INTEGER
    UNITS   "percent"
    MAX-ACCESS read-only                 
    STATUS current                        
    DESCRIPTION
        "The ethernet port  ratio of discarded packets in receiving direction. "
    ::= { zxDslEtherStatsEntry 3 }   

 zxDslEtherTxDiscardRatio OBJECT-TYPE             
    SYNTAX  INTEGER
    UNITS   "percent"
    MAX-ACCESS read-only                 
    STATUS current                        
    DESCRIPTION
        "The ethernet port  ratio of discarded packets in transmitting direction. "
    ::= { zxDslEtherStatsEntry 4 }   
    
 zxDslEtherBroadcastRxRate OBJECT-TYPE             
    SYNTAX  Gauge32
    UNITS   "BYTES/S"
    MAX-ACCESS read-only                 
    STATUS current                        
    DESCRIPTION
        "The ethernet port receiving broadcast packets rate."
    ::= { zxDslEtherStatsEntry 5 }   

 zxDslEtherBroadcastTxRate OBJECT-TYPE             
    SYNTAX  Gauge32
    UNITS   "BYTES/S"
    MAX-ACCESS read-only                 
    STATUS current                        
    DESCRIPTION
        "The ethernet port transmitting broadcast packets rate."
    ::= { zxDslEtherStatsEntry 6 }       
    
    
 zxDslEtherMulticastRxRate OBJECT-TYPE             
    SYNTAX  Gauge32
    UNITS   "BYTES/S"
    MAX-ACCESS read-only                 
    STATUS current                        
    DESCRIPTION
        "The ethernet port receiving multicast packets rate."
    ::= { zxDslEtherStatsEntry 7 }   

 zxDslEtherMulticastTxRate OBJECT-TYPE             
    SYNTAX  Gauge32
    UNITS   "BYTES/S"
    MAX-ACCESS read-only                 
    STATUS current                        
    DESCRIPTION
        "The ethernet port transmitting multicast packets rate."
    ::= { zxDslEtherStatsEntry 8 }           

 zxDslEtherUnicastRxRate OBJECT-TYPE             
    SYNTAX  Gauge32
    UNITS   "BYTES/S"
    MAX-ACCESS read-only                 
    STATUS current                        
    DESCRIPTION
        "The ethernet port receiving unicast packets rate."
    ::= { zxDslEtherStatsEntry 9 }   

 zxDslEtherUnicastTxRate OBJECT-TYPE             
    SYNTAX  Gauge32
    UNITS   "BYTES/S"
    MAX-ACCESS read-only                 
    STATUS current                        
    DESCRIPTION
        "The ethernet port transmitting unicast packets rate."
    ::= { zxDslEtherStatsEntry 10 }       


------------------------------------------------------------------------------
---
---   Bridge port stats table 
--- 
------------------------------------------------------------------------------

 zxDslBridgePortStatsTable OBJECT-TYPE
    SYNTAX SEQUENCE OF ZxDslBridgePortStatsEntry
    MAX-ACCESS not-accessible
    STATUS current
    DESCRIPTION
    "The bridge port stats Information table. "
    ::= { zxDslStatsObjects 2 }
    
 zxDslBridgePortStatsEntry OBJECT-TYPE
    SYNTAX ZxDslBridgePortStatsEntry
    MAX-ACCESS not-accessible
    STATUS current
    DESCRIPTION
    "An entry in the bridge port stats table . "
    INDEX { zxDslCardIndex, dot1dBasePort}
    ::= { zxDslBridgePortStatsTable 1 }
    
 ZxDslBridgePortStatsEntry ::= SEQUENCE {
        zxDslBridgePortRxRate       Gauge32,
        zxDslBridgePortTxRate       Gauge32,
        zxDslBridgePortSelfLoopPkts Counter32  
  }                                     

 zxDslBridgePortRxRate  OBJECT-TYPE   
    SYNTAX  Gauge32
    UNITS   "BYTES/S"
    MAX-ACCESS read-only                 
    STATUS current                        
    DESCRIPTION
        "The bridge port receiving rate. "
    ::= { zxDslBridgePortStatsEntry 1 }   
    
 zxDslBridgePortTxRate OBJECT-TYPE             
    SYNTAX  Gauge32
    UNITS   "BYTES/S"
    MAX-ACCESS read-only                 
    STATUS current                        
    DESCRIPTION
        "The bridge port transmitting rate. "
    ::= { zxDslBridgePortStatsEntry 2 } 
    
 zxDslBridgePortSelfLoopPkts OBJECT-TYPE             
    SYNTAX  Counter32                         
    MAX-ACCESS read-only                 
    STATUS current                        
    DESCRIPTION
        "The bridge port detected self-loop packets.If this variable is changing,
        The bridge entity or network may be existing self-loop event."
    ::= { zxDslBridgePortStatsEntry 3 } 
    
    
------------------------------------------------------------------------------
---
---   Dslam board Resources perfomance table 
--- 
------------------------------------------------------------------------------

 zxDslCardResourcesPerfTable OBJECT-TYPE
    SYNTAX SEQUENCE OF ZxDslCardResourcesPerfEntry
    MAX-ACCESS not-accessible
    STATUS current
    DESCRIPTION
    "The atm stats Information table. "
    ::= { zxDslStatsObjects 3 }
    
 zxDslCardResourcesPerfEntry OBJECT-TYPE
    SYNTAX ZxDslCardResourcesPerfEntry
    MAX-ACCESS not-accessible
    STATUS current
    DESCRIPTION
    "An entry in the Perfomance table . "
    INDEX { zxDslCardIndex }
    ::= { zxDslCardResourcesPerfTable 1 }
    
 ZxDslCardResourcesPerfEntry ::= SEQUENCE {
        zxDslCardIndex          INTEGER,
        zxDslCardCPULoad        INTEGER,
        zxDslCardMemUsage       INTEGER,
        zxDslCardActivedPortNum INTEGER
  }                                     


zxDslCardIndex  OBJECT-TYPE   
    SYNTAX  INTEGER                         
    MAX-ACCESS not-accessible                 
    STATUS current                        
    DESCRIPTION
        "card  index."
    ::= { zxDslCardResourcesPerfEntry 1 } 

    
 zxDslCardCPULoad  OBJECT-TYPE             
    SYNTAX  INTEGER
    UNITS   "percent"
    MAX-ACCESS read-only                 
    STATUS current                        
    DESCRIPTION
        "The card CPU load."
    ::= { zxDslCardResourcesPerfEntry 2 } 
    
 zxDslCardMemUsage OBJECT-TYPE             
    SYNTAX  INTEGER                         
    MAX-ACCESS read-only                 
    STATUS current                        
    DESCRIPTION
        "The card memory usage."
    ::= { zxDslCardResourcesPerfEntry 3 } 
    
 zxDslCardActivedPortNum OBJECT-TYPE             
    SYNTAX  INTEGER                         
    MAX-ACCESS read-only                 
    STATUS current                        
    DESCRIPTION
        "The actived port number in dsl card."
    ::= { zxDslCardResourcesPerfEntry 4 }   
       



------------------------------------------------------------------------------
---
---   Dslam L2 Resources Statistics  
--- 
------------------------------------------------------------------------------

    zxDslL2ResourcesStat     OBJECT IDENTIFIER ::= {zxDslStatsObjects 4}
        

    zxDslMacTableUsageMornitorPeriod   OBJECT-TYPE     
        SYNTAX      Integer32 ( 300..86400 )
        UNITS       "second"
        MAX-ACCESS  read-write
        STATUS      current
        DESCRIPTION 
              "Mornitoring period of max utilisation of the Mac Table." 
        DEFVAL { 300 }              
        ::=  {  zxDslL2ResourcesStat  1  }



    zxDslMacTableUsageMornitorTimes   OBJECT-TYPE     
        SYNTAX      Integer32 ( 0..10 )
        MAX-ACCESS  read-write
        STATUS      current
        DESCRIPTION 
              "The configured times of mornitoring period." 
        DEFVAL { 10 }              
        ::=  {  zxDslL2ResourcesStat  2  }

              

    zxDslMacTableUsageMornitorElapsedTime   OBJECT-TYPE     
        SYNTAX      Integer32 
        UNITS       "second"
        MAX-ACCESS  read-only
        STATUS      current
        DESCRIPTION 
              "The elapsed time of this mornitoring period." 
        ::=  {  zxDslL2ResourcesStat  3  }

      

    zxDslMacTableMaxSize   OBJECT-TYPE     
        SYNTAX      Integer32
        MAX-ACCESS  read-only
        STATUS      current
        DESCRIPTION 
              "Max rows of the MAC learning table." 
        ::=  {  zxDslL2ResourcesStat  4  }
    

    zxDslMacTableCurrentUsage   OBJECT-TYPE     
        SYNTAX      Integer32
        UNITS       "percent"
        MAX-ACCESS  read-only
        STATUS      current
        DESCRIPTION 
              "Current utilisation of the MAC learning table." 
        ::=  {  zxDslL2ResourcesStat  5  }


    zxDslMacTableUsageThreshold   OBJECT-TYPE     
        SYNTAX      Integer32
        UNITS       "percent"
        MAX-ACCESS  read-write
        STATUS      current
        DESCRIPTION 
              "Utilisation threshold of the MAC learning table.
          The zxDslMacTableUsageOverThreshTrap should be generated when it is 
          crossed." 
        DEFVAL { 70 }              
        ::=  {  zxDslL2ResourcesStat  6  }


     zxDslMacTableStatTable OBJECT-TYPE
        SYNTAX SEQUENCE OF ZxDslMacTableStatEntry
        MAX-ACCESS  not-accessible
        STATUS      current
        DESCRIPTION
            "The atm stats Information table. "
        ::= { zxDslL2ResourcesStat 7 }
        
     zxDslMacTableStatEntry OBJECT-TYPE
        SYNTAX      ZxDslMacTableStatEntry
        MAX-ACCESS  not-accessible
        STATUS      current
        DESCRIPTION
            "An entry in the Perfomance table . "
        INDEX { zxDslMacTableStatSampleIndex }
        ::= { zxDslMacTableStatTable 1 }
        
     ZxDslMacTableStatEntry ::= SEQUENCE 
     {
            zxDslMacTableStatSampleIndex    Integer32,
            zxDslMacTableCurrentMaxUsage    Integer32
     }                                     
          
    
    zxDslMacTableStatSampleIndex   OBJECT-TYPE     
        SYNTAX      Integer32
        MAX-ACCESS  not-accessible
        STATUS      current
        DESCRIPTION 
              "Sample Index of the statistics." 
        ::=  {  zxDslMacTableStatEntry  1  }
    


    zxDslMacTableCurrentMaxUsage   OBJECT-TYPE     
        SYNTAX      Integer32
        UNITS       "percent"
        MAX-ACCESS  read-only
        STATUS      current
        DESCRIPTION 
              "Max utilisation of the MAC learning table in current Mornitoring
          period." 
        ::=  {  zxDslMacTableStatEntry  2  }



		zxDslPortQueueSampleTable OBJECT-TYPE
        SYNTAX SEQUENCE OF ZxDslPortQueueSampleEntry
        MAX-ACCESS  not-accessible
        STATUS      current
        DESCRIPTION
            "The Port Queue Monitoring Information table. "
        ::= { zxDslL2ResourcesStat 8 }
        
     zxDslPortQueueSampleEntry OBJECT-TYPE
        SYNTAX      ZxDslPortQueueSampleEntry
        MAX-ACCESS  not-accessible
        STATUS      current
        DESCRIPTION
            "An entry in the Port Queue Monitoring table . "
        INDEX { ifIndex }
        ::= { zxDslPortQueueSampleTable 1 }
        

     ZxDslPortQueueSampleEntry ::= SEQUENCE 
     {
        zxDslQueueUsageMornitorPeriod                 Integer32,   
        zxDslQueueUsageMornitorElapsedTime            Integer32
     }  
         
     zxDslQueueUsageMornitorPeriod   OBJECT-TYPE     
        SYNTAX      Integer32 ( 300..86400 )
        UNITS       "second"
        MAX-ACCESS  read-write
        STATUS      current
        DESCRIPTION 
              "Mornitoring period of max utilisation of the L2 resources." 
        DEFVAL { 300 }              
        ::=  {  zxDslPortQueueSampleEntry  1  }


    zxDslQueueUsageMornitorElapsedTime   OBJECT-TYPE     
        SYNTAX      Integer32 
        UNITS       "second"
        MAX-ACCESS  read-only
        STATUS      current
        DESCRIPTION 
              "The elapsed time of this mornitoring period." 
        ::=  {  zxDslPortQueueSampleEntry  2  }
    
     zxDslPortQueueStatTable OBJECT-TYPE
        SYNTAX SEQUENCE OF ZxDslPortQueueStatEntry
        MAX-ACCESS  not-accessible
        STATUS      current
        DESCRIPTION
            "The Port Queue stats Information table. "
        ::= { zxDslL2ResourcesStat 9 }
        
     zxDslPortQueueStatEntry OBJECT-TYPE
        SYNTAX      ZxDslPortQueueStatEntry
        MAX-ACCESS  not-accessible
        STATUS      current
        DESCRIPTION
            "An entry in the Port Queue stats table . "
        INDEX { ifIndex,zxDslPortQueueId }
        ::= { zxDslPortQueueStatTable 1 }
        
     ZxDslPortQueueStatEntry ::= SEQUENCE 
     {
        zxDslPortQueueId                 Integer32,   
        zxDslPortQueueMaxSize            Integer32,
        zxDslPortQueueCurrentUsage       Integer32,
        zxDslPortQueueStatMinUsage       Integer32,
        zxDslPortQueueStatAverageUsage   Integer32,
        zxDslPortQueueStatMaxUsage       Integer32 
     }                                     


    zxDslPortQueueId   OBJECT-TYPE     
        SYNTAX      Integer32
        UNITS       "byte"
        MAX-ACCESS  read-only
        STATUS      current
        DESCRIPTION 
              "The index of the port queue." 
        ::=  {  zxDslPortQueueStatEntry  1  }
    

    zxDslPortQueueMaxSize   OBJECT-TYPE     
        SYNTAX      Integer32
        UNITS       "byte"
        MAX-ACCESS  read-only
        STATUS      current
        DESCRIPTION 
              "Max size of the port queue." 
        ::=  {  zxDslPortQueueStatEntry  2  }
    

    zxDslPortQueueCurrentUsage   OBJECT-TYPE     
        SYNTAX      Integer32
        UNITS       "percent"
        MAX-ACCESS  read-only
        STATUS      current
        DESCRIPTION 
              "Current utilisation of the port queue." 
        ::=  {  zxDslPortQueueStatEntry  3  }

    zxDslPortQueueStatMinUsage   OBJECT-TYPE     
        SYNTAX      Integer32
        UNITS       "percent"
        MAX-ACCESS  read-only
        STATUS      current
        DESCRIPTION 
              "Min utilisation of the port queue in current Mornitoring
          period." 
        ::=  {  zxDslPortQueueStatEntry  4  }
    
    zxDslPortQueueStatAverageUsage   OBJECT-TYPE     
        SYNTAX      Integer32
        UNITS       "percent"
        MAX-ACCESS  read-only
        STATUS      current
        DESCRIPTION 
              "Average utilisation of the port queue in current Mornitoring
          period." 
        ::=  {  zxDslPortQueueStatEntry  5  }
        
    zxDslPortQueueStatMaxUsage   OBJECT-TYPE     
        SYNTAX      Integer32
        UNITS       "percent"
        MAX-ACCESS  read-only
        STATUS      current
        DESCRIPTION 
              "Max utilisation of the port queue table in current Mornitoring
          period." 
        ::=  {  zxDslPortQueueStatEntry  6  }



    zxDslMacTablePeakValue   OBJECT-TYPE     
        SYNTAX      Integer32
        MAX-ACCESS  read-only
        STATUS      current
        DESCRIPTION 
              "The peak value of the MAC learning table in the integration period." 
        DEFVAL { 70 }              
        ::=  {  zxDslL2ResourcesStat  10  }


--------------------------------------------------------------------------------
-- 6. Trap Defination
--------------------------------------------------------------------------------

    zxDslMacTableUsageOverThreshTrap      NOTIFICATION-TYPE
            OBJECTS { zxAnMacTableCurrentUsage,
                      zxAnMacTableUsageThreshold  }
            STATUS  current
            DESCRIPTION
                "zxAnMacTableUsageThreshold is reached."
            ::= { zxDslStatsTrapObjects 1 }
       
END

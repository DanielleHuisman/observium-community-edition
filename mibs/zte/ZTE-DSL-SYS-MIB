--
--
-- Zte Dsl system mgmt Mib 
-- 
-- 


ZTE-DSL-SYS-MIB DEFINITIONS ::= BEGIN
IMPORTS
    MODULE-IDENTITY, TimeTicks, OBJECT-TYPE,
    NOTIFICATION-TYPE, enterprises,IpAddress FROM SNMPv2-SMI
    DateAndTime                             FROM SNMPv2-TC
    SnmpAdminString                         FROM SNMP-FRAMEWORK-MIB;

    zxDslSysMgmt MODULE-IDENTITY
            LAST-UPDATED "200412150900Z"
            ORGANIZATION "zte dsl product line"
            CONTACT-INFO
                " su chunshan
                  Mail: suchunshan@zte.com.cn
                  Tel : 021-68896292"
            DESCRIPTION
                "This mib defines extended dsl system mgmt mo (managed object ).
                 
                 Naming Conventions:
                 Atuc -- (ATUC) modem at near (Central) end of line
                 Atur -- (ATUR) modem at Remote end of line "
    ::= {zxDslam 14}

    zte OBJECT IDENTIFIER ::= { enterprises 3902 }
    zxDsl     OBJECT IDENTIFIER ::= { zte 1004  }
    zxDslam   OBJECT IDENTIFIER ::= { zxDsl 1    }
     
     

--------------------------------------------------------------------------------
-- Following objects are defined.
-- 1.Community Table
-- 2.IMA Link
--------------------------------------------------------------------------------



------------------------------------------------------------------------------
-- 1.Community Table
------------------------------------------------------------------------------  
     
    zxDslamCommunityTable OBJECT-TYPE
        SYNTAX SEQUENCE OF ZxDslamCommunityEntry
        MAX-ACCESS not-accessible
        STATUS current
        DESCRIPTION
            "A table of SNMPv1/v2c community string to view name mappings."
        ::= { zxDslSysMgmt 1 }

    zxDslamCommunityEntry OBJECT-TYPE
        SYNTAX ZxDslamCommunityEntry
        MAX-ACCESS not-accessible
        STATUS current
        DESCRIPTION
            "A list of community-to-view parameters."
        INDEX { zxDslamCommunityIndex }
        ::= { zxDslamCommunityTable 1 }

    ZxDslamCommunityEntry ::= SEQUENCE {
        zxDslamCommunityIndex         Integer32,
        zxDslamCommunityCommName      DisplayString,
        zxDslamCommunityViewName      SnmpAdminString,
        zxDslamCommunityPermission    INTEGER,
        zxDslamCommunityRowStatus     RowStatus
    }

    zxDslamCommunityIndex  OBJECT-TYPE
        SYNTAX Integer32 (1..8)
        MAX-ACCESS not-accessible
        STATUS current
        DESCRIPTION
            "A simple index into 'zxDslamCommunityTable'."
        ::= { zxDslamCommunityEntry 1 }

    zxDslamCommunityCommName  OBJECT-TYPE
        SYNTAX DisplayString (SIZE(1..20))
        MAX-ACCESS read-create
        STATUS current
        DESCRIPTION
            "DURABLE: { 'public','':all }
             The SNMPv1/v2c community name string.  Duplicate community
             names are not allowed in this table.  Note that a null string
             is not a valid community name (i.e., a null string forces
             'zxDslamCommunityRowStatus' to 'notReady(3)')."
        ::= { zxDslamCommunityEntry 2 }

    zxDslamCommunityViewName  OBJECT-TYPE
        SYNTAX SnmpAdminString (SIZE(1..32))
        MAX-ACCESS read-create
        STATUS current
        DESCRIPTION
            "DURABLE: { 'internet':all }
             At runtime (i.e., not when this object is SET), this view name
             is compared to the 'vacmViewTreeFamilyViewName' in the
             'vacmViewTreeFamilyTable' (see RFC2575).  If a match is
             found and the varbind(s) specify valid object type and instance,
             the 'zxDslamCommunityPermission' privilege is permitted.
             
             Note that a null string is not a valid view name value.
             Also note that the value of this object does not have to match
             an existing entry in the 'vacmViewTreeFamilyTable' (if no match,
             no access is allowed).
             
             Note that the factory default value for this object is 'internet',
             which allows access to the subtree under '1.3.6.1'."
        ::= { zxDslamCommunityEntry 3 }

    zxDslamCommunityPermission OBJECT-TYPE
        SYNTAX INTEGER {
               readOnly(1),
               readWrite(2)
        }
        MAX-ACCESS read-create
        STATUS current
        DESCRIPTION
            "DURABLE: { readWrite:all }
             This object specifies the type of access allowed. 'readOnly(1)'
             allows GET operations (i.e., GET, GET-NEXT, GET-BULK) and
             'readWrite(2)' allows both GET and SET operations."
        ::= { zxDslamCommunityEntry 4 }

    zxDslamCommunityRowStatus OBJECT-TYPE
        SYNTAX  RowStatus
        MAX-ACCESS  read-create
        STATUS  current
        DESCRIPTION
            "DURABLE:
             This object indicates the status of this entry.  A row in this
             table can be created using the 'createAndGo(4)' (i.e., all
             parameters must be valid - supplied in a single SNMP PDU or have
             default values) or the 'createAndWait(5)' action states.  Until
             all parameters are valid for a conceptual row, this object is
             'notReady(3)'.  All parameters must be valid before this object
             can be set to 'active(1)'.
             
             Any object in a conceptual row can be modified independent of the
             value of this object (e.g., can be changed while 'active(1)')."
        ::= { zxDslamCommunityEntry 5 }



--------------------------------------------------------------------------------
-- 2.Error Code for SnmpSet Operation
--------------------------------------------------------------------------------
    zxDslSnmpSetCmdErrCode   OBJECT-TYPE     
       SYNTAX      Integer32
       MAX-ACCESS  read-only
       STATUS      current
       DESCRIPTION 
          "Error code for SNMP set command.When agent executes a snmp set,
           this variable should be maintained.Value 0 means success.
          " 
       DEFVAL { 0 }              
       ::=  {  zxDslSysMgmt  2  }
    
    zxDslSnmpSetCmdErrDescr   OBJECT-TYPE     
       SYNTAX      DisplayString  (SIZE(1..256))
       MAX-ACCESS  read-only
       STATUS      current
       DESCRIPTION 
          "Error description for SNMP set command.When agent executes a snmp
           set, this variable should be maintained.
          "
       ::=  {  zxDslSysMgmt  3  }                
END

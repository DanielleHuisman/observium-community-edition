ZTE-DSL-TRAFFIC-POLICING-MIB    DEFINITIONS ::= BEGIN
    IMPORTS
        zxDsl                               FROM ZTE-DSL-MIB
        RowStatus, TEXTUAL-CONVENTION       FROM SNMPv2-TC
        ifIndex                             FROM IF-MIB
        dot1dBasePort                       FROM BRIDGE-MIB
        dot1qVlanIndex                      FROM Q-BRIDGE-MIB
        MODULE-IDENTITY, OBJECT-TYPE, Integer32, enterprises  FROM SNMPv2-SMI;

    zxDslTrafficPolicingMib    MODULE-IDENTITY
        LAST-UPDATED    "200707241100Z"
        ORGANIZATION    "ZTE Corporation"
        CONTACT-INFO    "su chunshan
                  Mail: suchunshan@zte.com.cn
                  Tel : 021-68896292"
        DESCRIPTION     "This MIB defines zte dsl managed objects."
        ::=  {  zxDsl  41  }

    zte    OBJECT IDENTIFIER ::= { enterprises 3902 }
    zxDsl  OBJECT IDENTIFIER ::= { zte 1004 }

    zxDslTrafficPolicingObjects         OBJECT IDENTIFIER   ::=  {  zxDslTrafficPolicingMib  1  }
    zxDslTrafficPolicingGlobalObjects   OBJECT IDENTIFIER   ::=  {  zxDslTrafficPolicingObjects  1  }

    zxDslTrafficScheduling              OBJECT IDENTIFIER   ::=  {  zxDslTrafficPolicingGlobalObjects  1  }


--------------------------------------------------------------------------------
-- Following objects are defined.
-- 1.Traffic Policing Mode
-- 2.Traffic Scheduling
-- 3.Traffic Policing Profile Table
-- 4.Traffic Policing Rate Limit Configuration Profile Table
-- 5.Traffic Policing Interface Table
--------------------------------------------------------------------------------



--------------------------------------------------------------------------------
-- 1.Traffic Policing Mode
--------------------------------------------------------------------------------
    zxDslTrafficPolicingMode    OBJECT-TYPE 
        SYNTAX          Integer32
            {
                normalTrafficLimit(1),
                cosbundleTrafficLimit(2),
                vlanbundleTrafficlimit(3)
            }
        MAX-ACCESS      read-write
        STATUS          current
        DESCRIPTION     "Traffic policing mode."
        ::=  {  zxDslTrafficPolicingGlobalObjects  2  }



    zxDslMultiCastRetagUplinkVlan    OBJECT-TYPE 
        SYNTAX          Integer32 (1..4094)
        MAX-ACCESS      read-write
        STATUS          current
        DESCRIPTION     "Retagged Uplink Vlan for MultiCast service."
        ::=  {  zxDslTrafficPolicingGlobalObjects  3  }


    zxDslMultiCastRetagUsrVlan    OBJECT-TYPE 
        SYNTAX          BITS
        MAX-ACCESS      read-write
        STATUS          current
        DESCRIPTION     "Retagged User Vlan for MultiCast service."
        ::=  {  zxDslTrafficPolicingGlobalObjects  4  }



    zxDslMultiCastRetagCos   OBJECT-TYPE 
        SYNTAX          Integer32 
            {
               cos0(0),
               cos1(1),
               cos2(2),
               cos3(3),
               cos4(4),
               cos5(5),
               cos6(6),
               cos7(7),
               noCosRetag(8)
            }
        MAX-ACCESS      read-write
        STATUS          current
        DESCRIPTION     "Retagged Uplink Vlan for MultiCast service."
        ::=  {  zxDslTrafficPolicingGlobalObjects  5  }


--------------------------------------------------------------------------------
-- 2.Traffic Scheduling
--------------------------------------------------------------------------------
    zxDslTraffMngulerType    OBJECT-TYPE 
        SYNTAX          Integer32
            {
                sp(1),
                wrr(2),
                spAndWrr(3)
            }
        MAX-ACCESS      read-write
        STATUS          current
        DESCRIPTION     "Traffic policing scheduling arithmetic."
        ::=  {  zxDslTrafficScheduling  1  }

    zxDslTraffMngWrrWfqParam1    OBJECT-TYPE 
        SYNTAX          Integer32 (0..15)
        MAX-ACCESS      read-write
        STATUS          current
        DESCRIPTION     "Scheduling arithmetic parameter1."
        ::=  {  zxDslTrafficScheduling  2  }



    zxDslTraffMngWrrWfqParam2    OBJECT-TYPE 
        SYNTAX          Integer32 (0..15)
        MAX-ACCESS      read-write
        STATUS          current
        DESCRIPTION     "Scheduling arithmetic parameter2."
        ::=  {  zxDslTrafficScheduling  3  }
        
    zxDslTraffMngWrrWfqParam3    OBJECT-TYPE 
        SYNTAX          Integer32 (0..15)
        MAX-ACCESS      read-write
        STATUS          current
        DESCRIPTION     "Scheduling arithmetic parameter3."
        ::=  {  zxDslTrafficScheduling  4  }
        
    zxDslTraffMngWrrWfqParam4    OBJECT-TYPE 
        SYNTAX          Integer32 (0..15)
        MAX-ACCESS      read-write
        STATUS          current
        DESCRIPTION     "Scheduling arithmetic parameter4."
        ::=  {  zxDslTrafficScheduling  5  }


    zxDslTraffMngWrrWfqParam5    OBJECT-TYPE 
        SYNTAX          Integer32 (0..15)
        MAX-ACCESS      read-write
        STATUS          current
        DESCRIPTION     "Scheduling arithmetic parameter5."
        ::=  {  zxDslTrafficScheduling  6  }


    zxDslTraffMngWrrWfqParam6    OBJECT-TYPE 
        SYNTAX          Integer32 (0..15)
        MAX-ACCESS      read-write
        STATUS          current
        DESCRIPTION     "Scheduling arithmetic parameter6."
        ::=  {  zxDslTrafficScheduling  7  }                


    zxDslTraffMngWrrWfqParam7    OBJECT-TYPE 
        SYNTAX          Integer32 (0..15)
        MAX-ACCESS      read-write
        STATUS          current
        DESCRIPTION     "Scheduling arithmetic parameter7."
        ::=  {  zxDslTrafficScheduling  8  }



    zxDslTraffMngWrrWfqParam8    OBJECT-TYPE 
        SYNTAX          Integer32 (0..15)
        MAX-ACCESS      read-write
        STATUS          current
        DESCRIPTION     "Scheduling arithmetic parameter8."
        ::=  {  zxDslTrafficScheduling  9  }



--------------------------------------------------------------------------------
-- 3.Traffic Policing Profile Table
--------------------------------------------------------------------------------
    zxDslTrafficPolicingProfileTable    OBJECT-TYPE
        SYNTAX      SEQUENCE  OF  ZxDslTrafficPolicingProfileEntry
        MAX-ACCESS  not-accessible
        STATUS      current
        DESCRIPTION "Traffic Policing Profile Table "
        ::=  { zxDslTrafficPolicingObjects  2 }

    zxDslTrafficPolicingProfileEntry    OBJECT-TYPE
        SYNTAX      ZxDslTrafficPolicingProfileEntry
        MAX-ACCESS  not-accessible
        STATUS      current
        DESCRIPTION "An entry in zxDslTrafficPolicingProfileTable."
        INDEX       {  zxDslTraffPolicPrfName  }
        ::=  { zxDslTrafficPolicingProfileTable 1 }
        
        
    ZxDslTrafficPolicingProfileEntry  ::=  SEQUENCE 
        {
            zxDslTraffPolicPrfName      DisplayString,
            zxDslTraffPolicMode         Integer32,
            zxDslTraffPolicSrvcSharedVlan     Integer32,
            zxDslTraffPolicUsBandwidth  Integer32,
            zxDslTraffPolicDsBandwidth  Integer32,
            zxDslTraffPolicRowStatus    RowStatus
            
        }

    zxDslTraffPolicPrfName    OBJECT-TYPE 
        SYNTAX          DisplayString (1..32)
        MAX-ACCESS      not-accessible
        STATUS          current
        DESCRIPTION     "Traffic policing profile name."
        ::=  {  zxDslTrafficPolicingProfileEntry  1  }

    zxDslTraffPolicMode    OBJECT-TYPE 
        SYNTAX          Integer32
            {
                cosbundleTrafficLimit(1),
                vlanbundleTrafficlimit(2)
            }
        MAX-ACCESS      read-write
        STATUS          current
        DESCRIPTION     "Traffic policing profile name."
        ::=  {  zxDslTrafficPolicingProfileEntry  2  }


    zxDslTraffPolicSrvcSharedVlan    OBJECT-TYPE 
        SYNTAX          Integer32 (0..4094) 
        MAX-ACCESS      read-write
        STATUS          current
        DESCRIPTION     "Service shared VLAN ID. This type of VLAN is used to
                 carried different service in same VLAN.
                    The value 0 means no service shared VLAN is used and service 
                 oriented VLAN will be used in 
                 table zxDslTrafficPolicingConfProfileTable.
                 "
        ::=  {  zxDslTrafficPolicingProfileEntry  3  }


    zxDslTraffPolicUsBandwidth    OBJECT-TYPE 
        SYNTAX          Integer32 (0..10000) 
        UNITS           "kbps"
        MAX-ACCESS      read-write
        STATUS          current
        DESCRIPTION     "Upstream bandwidth can be used by traffic policing."
        ::=  {  zxDslTrafficPolicingProfileEntry  4  }


    zxDslTraffPolicDsBandwidth    OBJECT-TYPE 
        SYNTAX          Integer32 (0..40000) 
        UNITS           "kbps"
        MAX-ACCESS      read-write
        STATUS          current
        DESCRIPTION     "Downstream bandwidth can be used by traffic policing."
        ::=  {  zxDslTrafficPolicingProfileEntry  5  }


    zxDslTraffPolicRowStatus  OBJECT-TYPE 
        SYNTAX          RowStatus
        MAX-ACCESS      read-write
        STATUS          current
        DESCRIPTION     "Rowstatus of this entry."
        ::=  {  zxDslTrafficPolicingProfileEntry  6  }



--------------------------------------------------------------------------------
-- 4.Traffic Policing Rate Limit Configuration Profile Table
--------------------------------------------------------------------------------
    zxDslTrafficPolicingConfProfileTable    OBJECT-TYPE
        SYNTAX      SEQUENCE  OF  ZxDslTrafficPolicingConfProfileEntry
        MAX-ACCESS  not-accessible
        STATUS      current
        DESCRIPTION "Traffic Policing Rate Limit Configuration Profile Table "
        ::=  { zxDslTrafficPolicingObjects  3 }

    zxDslTrafficPolicingConfProfileEntry    OBJECT-TYPE
        SYNTAX      ZxDslTrafficPolicingConfProfileEntry
        MAX-ACCESS  not-accessible
        STATUS      current
        DESCRIPTION "An entry in zxDslTrafficPolicingConfProfileTable."
        INDEX       {  zxDslTraffPolicPrfName,zxDslTraffPolicQueueId  }
        ::=  { zxDslTrafficPolicingConfProfileTable 1 }
        
        
    ZxDslTrafficPolicingConfProfileEntry  ::=  SEQUENCE 
        {
            zxDslTraffPolicQueueId          Integer32,
            zxDslTraffPolicSrvcOrientVlan   Integer32,
            zxDslTraffPolicUsRateLimit      Integer32,
            zxDslTraffPolicDsRateLimit      Integer32
        }


    zxDslTraffPolicQueueId    OBJECT-TYPE 
        SYNTAX          Integer32 (0..3) 
        MAX-ACCESS      not-accessible
        STATUS          current
        DESCRIPTION     "Queue ID of traffic policing."
        ::=  {  zxDslTrafficPolicingConfProfileEntry  1  }

    zxDslTraffPolicSrvcOrientVlan    OBJECT-TYPE 
        SYNTAX          Integer32 (0..4094) 
        MAX-ACCESS      read-write
        STATUS          current
        DESCRIPTION     "Service oriented VLAN ID.This type of VLAN is used to 
            specific service only.
                If zxDslTraffPolicSrvcSharedVlan=0,then SrvcOrientVlan can be 
            configured non 0 value,else it is 0.
            "
        ::=  {  zxDslTrafficPolicingConfProfileEntry  2  }


    zxDslTraffPolicUsRateLimit    OBJECT-TYPE 
        SYNTAX          Integer32 (0..10000) 
        UNITS           "kbps"
        MAX-ACCESS      read-write
        STATUS          current
        DESCRIPTION     "Upstream rate limit by traffic policing.It is less than
            zxDslTraffPolicUsBandwidth."
        ::=  {  zxDslTrafficPolicingConfProfileEntry  3  }


    zxDslTraffPolicDsRateLimit    OBJECT-TYPE 
        SYNTAX          Integer32 (0..40000) 
        UNITS           "kbps"
        MAX-ACCESS      read-write
        STATUS          current
        DESCRIPTION     "Downstream rate limit by traffic policing.It is less than
            zxDslTraffPolicDsBandwidth."
        ::=  {  zxDslTrafficPolicingConfProfileEntry  4  }




--------------------------------------------------------------------------------
-- 5.Traffic Policing Interface Table
--------------------------------------------------------------------------------

    zxDslTrafficPolicingIfTable    OBJECT-TYPE
        SYNTAX      SEQUENCE  OF  ZxDslTrafficPolicingIfEntry
        MAX-ACCESS  not-accessible
        STATUS      current
        DESCRIPTION "Traffic Policing Rate Interface Table "
        ::=  { zxDslTrafficPolicingObjects  4 }

    zxDslTrafficPolicingIfEntry    OBJECT-TYPE
        SYNTAX      ZxDslTrafficPolicingIfEntry
        MAX-ACCESS  not-accessible
        STATUS      current
        DESCRIPTION "An entry in zxDslTrafficPolicingIfTable."
        INDEX       {  ifIndex,zxDslTraffPolicingIfPrfName  }
        ::=  { zxDslTrafficPolicingIfTable 1 }
        
        
    ZxDslTrafficPolicingIfEntry  ::=  SEQUENCE 
        {
            zxDslTraffPolicingIfPrfName          Integer32,
            zxDslTraffPolicingIfRowStatus        RowStatus
        }


    zxDslTraffPolicingIfPrfName    OBJECT-TYPE 
        SYNTAX          DisplayString (1..32)
        MAX-ACCESS      not-accessible
        STATUS          current
        DESCRIPTION     "Traffic policing profile name."
        ::=  {  zxDslTrafficPolicingIfEntry  1  }
    

    zxDslTraffPolicingIfRowStatus  OBJECT-TYPE 
        SYNTAX          RowStatus
        MAX-ACCESS      read-write
        STATUS          current
        DESCRIPTION     "Rowstatus of this entry."
        ::=  {  zxDslTrafficPolicingIfEntry  2  }

    
END

ZTE-MASTER-MIB DEFINITIONS ::= BEGIN

    IMPORTS
        zxAn                                      FROM ZTE-AN-TC-MIB;
        
    zxAnPonMib             OBJECT IDENTIFIER ::= { zxAn 1010}
    zxAnCesMib             OBJECT IDENTIFIER ::= { zxAn 1013}
    
-- PON service     
    zxAnEponMib          OBJECT IDENTIFIER ::= { zxAnPonMib 1}
    zxAnGponMib          OBJECT IDENTIFIER ::= { zxAnPonMib 2}    
    zxAnPonProtection    OBJECT IDENTIFIER ::= { zxAnPonMib 3}
    zxAnVlanTrans        OBJECT IDENTIFIER ::= {zxAnPonMib 10}
    zxAnTransceiver      OBJECT IDENTIFIER ::= {zxAnPonMib 11}
    
--  zxPwStdMib          OBJECT IDENTIFIER ::= { zxAnCesMib 1}
    zxPwCSC             OBJECT IDENTIFIER ::= { zxAnCesMib 2}
    zxPwCPSN            OBJECT IDENTIFIER ::= { zxAnCesMib 3}
--  zxPwTCMib           OBJECT IDENTIFIER ::= { zxAnCesMib 4}
--  zxPwe3Mib           OBJECT IDENTIFIER ::= { zxAnCesMib 5}
    zxAnCesProtection   OBJECT IDENTIFIER ::= { zxAnCesMib 11}

    zxPwCTDM            OBJECT IDENTIFIER ::= { zxPwCSC 1}
--  zxDs1               OBJECT IDENTIFIER ::= { zxPwCTDM 1}
--  zxPwCTDMMIB         OBJECT IDENTIFIER ::= { zxPwCTDM 2}    
--  zxSonetIfMIB         OBJECT IDENTIFIER ::= { zxPwCTDM 3}    

    zxPwCETH            OBJECT IDENTIFIER ::= { zxPwCPSN 1}
--  zxCesCardPropMIB    OBJECT IDENTIFIER ::= { zxPwCETH 1}
--  zxCesoeMIB          OBJECT IDENTIFIER ::= { zxPwCETH 2}

END

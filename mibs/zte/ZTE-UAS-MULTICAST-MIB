ZTE-UAS-MULTICAST-MIB DEFINITIONS ::= BEGIN
IMPORTS
        MODULE-IDENTITY, OBJECT-TYPE, 
        Integer32,
        IpAddress, enterprises                    FROM SNMPv2-SMI
        DisplayString                 FROM SNMPv2-TC;

          
        
    zxMulticastMib  MODULE-IDENTITY
    LAST-UPDATED "200610231700Z"
    ORGANIZATION "ZTE Co."
    CONTACT-INFO ""
    DESCRIPTION  
        "This mib defines multicast management for uas"
    ::= { zxUas 2 }
    
    zte                          OBJECT IDENTIFIER ::= { enterprises 3902 }
    zxUas                        OBJECT IDENTIFIER ::= { zte 1006 } 
                                 
                                 
    zxUasMulticastMibObjects              OBJECT IDENTIFIER ::= { zxMulticastMib 1 }
    zxUasTraps                   OBJECT IDENTIFIER ::= { zxMulticastMib 2 }
      
    zxUasMulticastSwitch  OBJECT-TYPE
        SYNTAX      INTEGER{disable(1),enable(2)}
        MAX-ACCESS  read-only
        STATUS      current
        DESCRIPTION
            "The switch of multicast"
        ::= { zxUasMulticastMibObjects  1}
                                     
    zxIgmpGroup             OBJECT IDENTIFIER ::= { zxUasMulticastMibObjects 2 }
    zxPimGroup        OBJECT IDENTIFIER ::= { zxUasMulticastMibObjects 3 }
    zxIgmpUasGroup            OBJECT IDENTIFIER ::= { zxUasMulticastMibObjects 4 }
                                 
                                 
                                 
    -- group table               
    zxIgmpGroupTable    OBJECT-TYPE
        SYNTAX      SEQUENCE OF ZxIgmpGroupEntry
        MAX-ACCESS  not-accessible
        STATUS      current
        DESCRIPTION 
        "This table contains igmp group information"
        ::= { zxIgmpGroup 1 }
        
     zxIgmpGroupEntry  OBJECT-TYPE
        SYNTAX      ZxIgmpGroupEntry
        MAX-ACCESS  not-accessible
        STATUS      current
        DESCRIPTION
            "The entry of zxIgmpGroupTable"
        INDEX  { zxIgmpGroupAddr,
                 zxIgmpGroupInterface,
                 zxIgmpGroupLastReporterCircuit
                 }
        ::= { zxIgmpGroupTable  1}    
         
    ZxIgmpGroupEntry  ::= SEQUENCE  {
        zxIgmpGroupAddr                 IpAddress,
        zxIgmpGroupInterface            DisplayString,
        zxIgmpGroupFlag        		    INTEGER,
        zxIgmpGroupPresent              DisplayString,
        zxIgmpGroupExpire               DisplayString,
        zxIgmpGroupLastReporterCircuit  DisplayString
        }
 
    zxIgmpGroupAddr  OBJECT-TYPE
        SYNTAX      IpAddress
        MAX-ACCESS  read-only
        STATUS      current
        DESCRIPTION
            "IGMP group address."
        ::= { zxIgmpGroupEntry 1 }
            
    zxIgmpGroupInterface  OBJECT-TYPE
        SYNTAX      DisplayString(SIZE(0..31))
        MAX-ACCESS  read-only
        STATUS      current
        DESCRIPTION
            "IGMP group interface name,contains fei,smartgroup,vbui and so on"
        ::= { zxIgmpGroupEntry 2 }
 
    zxIgmpGroupFlag  OBJECT-TYPE
        SYNTAX      INTEGER { ppp(1),ip(2)}
        MAX-ACCESS  read-only
        STATUS      current
        DESCRIPTION
            "Subscriber type,contains PPP and IP Subscriber type."
        ::= { zxIgmpGroupEntry 3 }
       
    zxIgmpGroupPresent  OBJECT-TYPE
        SYNTAX      DisplayString
        MAX-ACCESS  read-only
        STATUS      current
        DESCRIPTION
            "The time length since the group created,such as HH:MM:SS."
        ::= { zxIgmpGroupEntry 4 }
        
    zxIgmpGroupExpire  OBJECT-TYPE
        SYNTAX      DisplayString
        MAX-ACCESS  read-only
        STATUS      current
        DESCRIPTION
            "The expire time length which the group will be expire,
            for static group the value is never,other is HH:MM:SS."
        ::= { zxIgmpGroupEntry 5 }
          
    zxIgmpGroupLastReporterCircuit  OBJECT-TYPE
        SYNTAX      DisplayString
        MAX-ACCESS  read-only
        STATUS      current
        DESCRIPTION
            "The circuit of the last reporter."
        ::= { zxIgmpGroupEntry 6 } 
        
        
    -- interface table               
    zxIgmpInterfaceTable    OBJECT-TYPE
        SYNTAX      SEQUENCE OF ZxIgmpInterfaceEntry
        MAX-ACCESS  not-accessible
        STATUS      current
        DESCRIPTION 
        "This table contains igmp interface information"
        ::= { zxIgmpGroup 2 }
        
     zxIgmpInterfaceEntry  OBJECT-TYPE
        SYNTAX      ZxIgmpInterfaceEntry
        MAX-ACCESS  not-accessible
        STATUS      current
        DESCRIPTION
            "The entry of zxIgmpInterfaceTable"
        INDEX  { zxIgmpInterface
                 }
        ::= { zxIgmpInterfaceTable  1}    
         
    ZxIgmpInterfaceEntry  ::= SEQUENCE  {
        zxIgmpInterface            DisplayString,
        zxIgmpInfIpAddr        	   IpAddress,
        zxIgmpInfMask              IpAddress,
        zxIgmpVersion              INTEGER,
        zxIgmpQueryInterval        Integer32,
        zxIgmpLastMemQueryIntvl    Integer32,
        zxIgmpMaxResponseTime      Integer32,
        zxIgmpQuerierTimeout       Integer32,
        zxIgmpQuerier              IpAddress,
        zxIgmpQuerierExpire        DisplayString,
        zxIgmpInboundAcl           Integer32,
        zxIgmpImmediateLeave       Integer32
        }
              
    zxIgmpInterface  OBJECT-TYPE
        SYNTAX      DisplayString(SIZE(0..31))
        MAX-ACCESS  read-only
        STATUS      current
        DESCRIPTION
            "IGMP interface name,contains fei,smartgroup,vbui and so on."
        ::= { zxIgmpInterfaceEntry 1 }
 
    zxIgmpInfIpAddr  OBJECT-TYPE
        SYNTAX      IpAddress
        MAX-ACCESS  read-only
        STATUS      current
        DESCRIPTION
            "The IP address of the interface."
        ::= { zxIgmpInterfaceEntry 2 }
       
    zxIgmpInfMask  OBJECT-TYPE
        SYNTAX      IpAddress
        MAX-ACCESS  read-only
        STATUS      current
        DESCRIPTION
            "The submask of the interface."
        ::= { zxIgmpInterfaceEntry 3 }
        
    zxIgmpVersion  OBJECT-TYPE
        SYNTAX      INTEGER {igmpv1(1),igmpv2(2)}
        MAX-ACCESS  read-only
        STATUS      current
        DESCRIPTION
            "The version of IGMP running on the interface"
        ::= { zxIgmpInterfaceEntry 4 }
        
    zxIgmpQueryInterval  OBJECT-TYPE
        SYNTAX      Integer32
        MAX-ACCESS  read-only
        STATUS      current
        DESCRIPTION
            "IGMP query interval,the units is second."
        ::= { zxIgmpInterfaceEntry 5 }
          
    zxIgmpLastMemQueryIntvl  OBJECT-TYPE
        SYNTAX      Integer32
        MAX-ACCESS  read-only
        STATUS      current
        DESCRIPTION
            "IGMP group-special query interval, the units is second. For Igmpv1 the value is 0."
        ::= { zxIgmpInterfaceEntry 6 } 
        
    zxIgmpMaxResponseTime  OBJECT-TYPE
        SYNTAX      Integer32
        MAX-ACCESS  read-only
        STATUS      current
        DESCRIPTION
            "Max response time of IGMP group-special query, the units is second. For Igmpv1 the value is 0."
        ::= { zxIgmpInterfaceEntry 7 } 
        
    zxIgmpQuerierTimeout  OBJECT-TYPE
        SYNTAX      Integer32
        MAX-ACCESS  read-only
        STATUS      current
        DESCRIPTION
            "The alive time that other uas can be a querier, the units is second. For Igmpv1 the value is 0."
        ::= { zxIgmpInterfaceEntry 8 } 
        
    zxIgmpQuerier  OBJECT-TYPE
        SYNTAX      IpAddress
        MAX-ACCESS  read-only
        STATUS      current
        DESCRIPTION
            "The IP address of the querier."
        ::= { zxIgmpInterfaceEntry 9 } 
        
    zxIgmpQuerierExpire  OBJECT-TYPE
        SYNTAX      DisplayString
        MAX-ACCESS  read-only
        STATUS      current
        DESCRIPTION
            "The expire time length which the querier will be expire,
            the value is never or HH:MM:SS."
        ::= { zxIgmpInterfaceEntry 10 } 
        
    zxIgmpInboundAcl  OBJECT-TYPE
        SYNTAX      Integer32
        MAX-ACCESS  read-only
        STATUS      current
        DESCRIPTION
            "IGMP access-group. 0 means Inbound IGMP access group is not set"
        ::= { zxIgmpInterfaceEntry 11 } 
        
    zxIgmpImmediateLeave  OBJECT-TYPE
        SYNTAX      Integer32
        MAX-ACCESS  read-only
        STATUS      current
        DESCRIPTION
            "Immediate leave group number when receive release packet. 
            0 means IGMP immediate leave control is not set.
            100 means IGMP immediate leave for all groups.
            other is group number."
        ::= { zxIgmpInterfaceEntry 12 }
        
      
    -- interface receive packet table               
    zxIgmpInfRevPktTable    OBJECT-TYPE
        SYNTAX      SEQUENCE OF ZxIgmpInfRevPktEntry
        MAX-ACCESS  not-accessible
        STATUS      current
        DESCRIPTION 
        "This table contains igmp interface received packets"
        ::= { zxIgmpGroup 3 }
        
     zxIgmpInfRevPktEntry  OBJECT-TYPE
        SYNTAX      ZxIgmpInfRevPktEntry
        MAX-ACCESS  not-accessible
        STATUS      current
        DESCRIPTION
            "The entry of zxIgmpInfRevPktTable"
        INDEX  { zxIgmpRevPktInterface
                 }
        ::= { zxIgmpInfRevPktTable  1}    
         
    ZxIgmpInfRevPktEntry  ::= SEQUENCE  {
        zxIgmpRevPktInterface   DisplayString,
        zxIgmpRevPktQuery       Integer32,
        zxIgmpRevPktReportV2    Integer32,
        zxIgmpRevPktLeave       Integer32,
        zxIgmpRevPktReportV1    Integer32,
        zxIgmpRevPktOther       Integer32,
        zxIgmpRevPktTotal       Integer32
        }
              
    zxIgmpRevPktInterface  OBJECT-TYPE
        SYNTAX      DisplayString(SIZE(0..31))
        MAX-ACCESS  read-only
        STATUS      current
        DESCRIPTION
            "IGMP interface name,contains fei,smartgroup,vbui and so on."
        ::= { zxIgmpInfRevPktEntry 1 } 
        
    zxIgmpRevPktQuery  OBJECT-TYPE
        SYNTAX      Integer32
        MAX-ACCESS  read-only
        STATUS      current
        DESCRIPTION
            "Received query packet count from this interface."
        ::= { zxIgmpInfRevPktEntry 2 }
        
    zxIgmpRevPktReportV2  OBJECT-TYPE
        SYNTAX      Integer32
        MAX-ACCESS  read-only
        STATUS      current
        DESCRIPTION
            "Received report IGMPv2 packet count from this interface."
        ::= { zxIgmpInfRevPktEntry 3 } 
        
    zxIgmpRevPktLeave  OBJECT-TYPE
        SYNTAX      Integer32
        MAX-ACCESS  read-only
        STATUS      current
        DESCRIPTION
            "Received leave packet count from this interface."
        ::= { zxIgmpInfRevPktEntry 4 } 
        
    zxIgmpRevPktReportV1  OBJECT-TYPE
        SYNTAX      Integer32
        MAX-ACCESS  read-only
        STATUS      current
        DESCRIPTION
            "Received report IGMPv1 packet count from this interface."
        ::= { zxIgmpInfRevPktEntry 5 } 
        
    zxIgmpRevPktOther  OBJECT-TYPE
        SYNTAX      Integer32
        MAX-ACCESS  read-only
        STATUS      current
        DESCRIPTION
            "Received other packet count from this interface."
        ::= { zxIgmpInfRevPktEntry 6 } 
        
    zxIgmpRevPktTotal  OBJECT-TYPE
        SYNTAX      Integer32
        MAX-ACCESS  read-only
        STATUS      current
        DESCRIPTION
            "Received total packet count from this interface."
        ::= { zxIgmpInfRevPktEntry 7 }   
        
        
    -- interface send packet table               
    zxIgmpInfSendPktTable    OBJECT-TYPE
        SYNTAX      SEQUENCE OF ZxIgmpInfSendPktEntry
        MAX-ACCESS  not-accessible
        STATUS      current
        DESCRIPTION 
        "This table contains igmp interface sent packets"
        ::= { zxIgmpGroup 4 }
        
     zxIgmpInfSendPktEntry  OBJECT-TYPE
        SYNTAX      ZxIgmpInfSendPktEntry
        MAX-ACCESS  not-accessible
        STATUS      current
        DESCRIPTION
            "The entry of zxIgmpInfSendPktTable"
        INDEX  { zxIgmpSendPktInterface
                 }
        ::= { zxIgmpInfSendPktTable  1}    
         
    ZxIgmpInfSendPktEntry  ::= SEQUENCE  {
        zxIgmpSendPktInterface   DisplayString,
        zxIgmpSendPktQuery       Integer32,
        zxIgmpSendPktSpec        Integer32,
        zxIgmpSendPktTotal       Integer32
        }
              
    zxIgmpSendPktInterface  OBJECT-TYPE
        SYNTAX      DisplayString(SIZE(0..31))
        MAX-ACCESS  read-only
        STATUS      current
        DESCRIPTION
            "IGMP interface name,contains fei,smartgroup,vbui and so on."
        ::= { zxIgmpInfSendPktEntry 1 } 
        
    zxIgmpSendPktQuery  OBJECT-TYPE
        SYNTAX      Integer32
        MAX-ACCESS  read-only
        STATUS      current
        DESCRIPTION
            "Sent query packet count from this interface."
        ::= { zxIgmpInfSendPktEntry 2 }
        
    zxIgmpSendPktSpec  OBJECT-TYPE
        SYNTAX      Integer32
        MAX-ACCESS  read-only
        STATUS      current
        DESCRIPTION
            "Sent special IGMP packet count from this interface."
        ::= { zxIgmpInfSendPktEntry 3 } 
        
    zxIgmpSendPktTotal  OBJECT-TYPE
        SYNTAX      Integer32
        MAX-ACCESS  read-only
        STATUS      current
        DESCRIPTION
            "Sent total packet count from this interface."
        ::= { zxIgmpInfSendPktEntry 4 } 
        
    -- server log table               
    zxIgmpServerLogTable    OBJECT-TYPE
        SYNTAX      SEQUENCE OF ZxIgmpServerLogEntry
        MAX-ACCESS  not-accessible
        STATUS      current
        DESCRIPTION 
        "This table contains igmp server log."
        ::= { zxIgmpGroup 5 }
        
     zxIgmpServerLogEntry  OBJECT-TYPE
        SYNTAX      ZxIgmpServerLogEntry
        MAX-ACCESS  not-accessible
        STATUS      current
        DESCRIPTION
            "The entry of zxIgmpServerLogTable"
        INDEX  { zxIgmpServerLogInterface,
                zxIgmpServerLogGroupAddr,
                zxIgmpServerLogSourceAddr
                 }
        ::= { zxIgmpServerLogTable  1}    
         
    ZxIgmpServerLogEntry  ::= SEQUENCE  {
        zxIgmpServerLogInterface    DisplayString,
        zxIgmpServerLogProtocol     INTEGER,
        zxIgmpServerLogVpi          Integer32,
        zxIgmpServerLogVci          Integer32,
        zxIgmpServerLogGroupAddr    IpAddress,
        zxIgmpServerLogSourceAddr   IpAddress,
        zxIgmpServerLogRecTime      DisplayString,
        zxIgmpServerLogPPPoESID     Integer32
        }
              
    zxIgmpServerLogInterface  OBJECT-TYPE
        SYNTAX      DisplayString(SIZE(0..31))
        MAX-ACCESS  read-only
        STATUS      current
        DESCRIPTION
            "The interface name where the server lies"
        ::= { zxIgmpServerLogEntry 1 } 
        
    zxIgmpServerLogProtocol  OBJECT-TYPE
        SYNTAX      INTEGER{pimSm(1),pimDm(2),other(3)}
        MAX-ACCESS  read-only
        STATUS      current
        DESCRIPTION
            "The protocol type."
        ::= { zxIgmpServerLogEntry 2 }
        
    zxIgmpServerLogVpi  OBJECT-TYPE
        SYNTAX      Integer32
        MAX-ACCESS  read-only
        STATUS      current
        DESCRIPTION
            "The circuit vpi or vlan id."
        ::= { zxIgmpServerLogEntry 3 } 
        
    zxIgmpServerLogVci  OBJECT-TYPE
        SYNTAX      Integer32
        MAX-ACCESS  read-only
        STATUS      current
        DESCRIPTION
            "The circuit vci or second vlan id."
        ::= { zxIgmpServerLogEntry 4 }
        
    zxIgmpServerLogGroupAddr  OBJECT-TYPE
        SYNTAX      IpAddress
        MAX-ACCESS  read-only
        STATUS      current
        DESCRIPTION
            "The server multicast group address."
        ::= { zxIgmpServerLogEntry 5 }
        
    zxIgmpServerLogSourceAddr  OBJECT-TYPE
        SYNTAX      IpAddress
        MAX-ACCESS  read-only
        STATUS      current
        DESCRIPTION
            "The server source address."
        ::= { zxIgmpServerLogEntry 6 }
        
    zxIgmpServerLogRecTime  OBJECT-TYPE
        SYNTAX      DisplayString
        MAX-ACCESS  read-only
        STATUS      current
        DESCRIPTION
            "The time received."
        ::= { zxIgmpServerLogEntry 7 }
        
    zxIgmpServerLogPPPoESID  OBJECT-TYPE
        SYNTAX      Integer32
        MAX-ACCESS  read-only
        STATUS      current
        DESCRIPTION
            "The PPPoE session id."
        ::= { zxIgmpServerLogEntry 8 }
        
              
    zxPimBSR    OBJECT-TYPE
        SYNTAX      DisplayString
        MAX-ACCESS  read-only
        STATUS      current
        DESCRIPTION 
        "BSR information."
        ::= { zxPimGroup 1 }
        
    zxPimCBsr    OBJECT-TYPE
        SYNTAX      DisplayString
        MAX-ACCESS  read-only
        STATUS      current
        DESCRIPTION 
        "candidate BSR information of this router."
        ::= { zxPimGroup 2 }
        
    zxPimCRP    OBJECT-TYPE
        SYNTAX      DisplayString
        MAX-ACCESS  read-only
        STATUS      current
        DESCRIPTION 
        "candidate RP information of this router."
        ::= { zxPimGroup 3 }
        
    -- pim rp map table               
    zxPimRpMapTable    OBJECT-TYPE
        SYNTAX      SEQUENCE OF ZxPimRpMapEntry
        MAX-ACCESS  not-accessible
        STATUS      current
        DESCRIPTION 
        "This table contains pim rp map."
        ::= { zxPimGroup 4 }
        
     zxPimRpMapEntry  OBJECT-TYPE
        SYNTAX      ZxPimRpMapEntry
        MAX-ACCESS  not-accessible
        STATUS      current
        DESCRIPTION
            "The entry of zxPimRpMapTable"
        INDEX  { zxPimRpMapGroupAddr,
                 zxPimRpMapGroupMask,
                 zxPimRpMapRpAddr
                 }
        ::= { zxPimRpMapTable  1}    
         
    ZxPimRpMapEntry  ::= SEQUENCE  {
        zxPimRpMapGroupAddr    IpAddress,
        zxPimRpMapGroupMask    IpAddress,
        zxPimRpMapRpAddr       IpAddress,
        zxPimRpMapRpDescr      DisplayString
        }
              
    zxPimRpMapGroupAddr  OBJECT-TYPE
        SYNTAX      IpAddress
        MAX-ACCESS  read-only
        STATUS      current
        DESCRIPTION
            "The multicast group address."
        ::= { zxPimRpMapEntry 1 } 
        
    zxPimRpMapGroupMask  OBJECT-TYPE
        SYNTAX      IpAddress
        MAX-ACCESS  read-only
        STATUS      current
        DESCRIPTION
            "The multicast group address submask."
        ::= { zxPimRpMapEntry 2 }
        
    zxPimRpMapRpAddr  OBJECT-TYPE
        SYNTAX      IpAddress
        MAX-ACCESS  read-only
        STATUS      current
        DESCRIPTION
            "The rp address."
        ::= { zxPimRpMapEntry 3 }
        
    zxPimRpMapRpDescr  OBJECT-TYPE
        SYNTAX      DisplayString
        MAX-ACCESS  read-only
        STATUS      current
        DESCRIPTION
            "The rp description,such as type and priority."
        ::= { zxPimRpMapEntry 4 }
        
    
        
    -- pimsm interface table               
    zxPimSmInterfaceTable    OBJECT-TYPE
        SYNTAX      SEQUENCE OF ZxPimSmIntfEntry
        MAX-ACCESS  not-accessible
        STATUS      current
        DESCRIPTION 
        "This table contains pimsm interface information."
        ::= { zxPimGroup 5 }
        
     zxPimSmIntfEntry  OBJECT-TYPE
        SYNTAX      ZxPimSmIntfEntry
        MAX-ACCESS  not-accessible
        STATUS      current
        DESCRIPTION
            "The entry of zxPimSmInterfaceTable"
        INDEX  { zxPimSmInterface
                 }
        ::= { zxPimSmInterfaceTable  1}    
         
    ZxPimSmIntfEntry  ::= SEQUENCE  {
        zxPimSmAddr         IpAddress,
        zxPimSmInterface    DisplayString,
        zxPimSmIntfState    INTEGER,
        zxPimSmNbrCount     Integer32,
        zxPimSmQueryIntvl   Integer32,
        zxPimSmDR    		IpAddress,
        zxPimSmDrPriority   Integer32
        }
              
    zxPimSmAddr  OBJECT-TYPE
        SYNTAX      IpAddress
        MAX-ACCESS  read-only
        STATUS      current
        DESCRIPTION
            "The interface Ip address."
        ::= { zxPimSmIntfEntry 1 }  
        
    zxPimSmInterface  OBJECT-TYPE
        SYNTAX      DisplayString(SIZE(0..31))
        MAX-ACCESS  read-only
        STATUS      current
        DESCRIPTION
            "The interface name."
        ::= { zxPimSmIntfEntry 2 }  
        
    zxPimSmIntfState  OBJECT-TYPE
        SYNTAX      INTEGER {down(1),up(2)}
        MAX-ACCESS  read-only
        STATUS      current
        DESCRIPTION
            "The interface state."
        ::= { zxPimSmIntfEntry 3 }  
        
    zxPimSmNbrCount  OBJECT-TYPE
        SYNTAX      Integer32
        MAX-ACCESS  read-only
        STATUS      current
        DESCRIPTION
            "The neighbour count."
        ::= { zxPimSmIntfEntry 4 }  
        
    zxPimSmQueryIntvl  OBJECT-TYPE
        SYNTAX      Integer32
        MAX-ACCESS  read-only
        STATUS      current
        DESCRIPTION
            "The query inerval,the units is second."
        ::= { zxPimSmIntfEntry 5 }  
        
    zxPimSmDR  OBJECT-TYPE
        SYNTAX      IpAddress
        MAX-ACCESS  read-only
        STATUS      current
        DESCRIPTION
            "The DR Ip address."
        ::= { zxPimSmIntfEntry 6 }  
        
    zxPimSmDrPriority  OBJECT-TYPE
        SYNTAX      Integer32
        MAX-ACCESS  read-only
        STATUS      current
        DESCRIPTION
            "The DR priority."
        ::= { zxPimSmIntfEntry 7 }    
        
        
    -- pimsm neighbour table               
    zxPimSmNbrTable    OBJECT-TYPE
        SYNTAX      SEQUENCE OF ZxPimSmNbrEntry
        MAX-ACCESS  not-accessible
        STATUS      current
        DESCRIPTION 
        "This table contains pimsm neighbour information."
        ::= { zxPimGroup 6 }
        
     zxPimSmNbrEntry  OBJECT-TYPE
        SYNTAX      ZxPimSmNbrEntry
        MAX-ACCESS  not-accessible
        STATUS      current
        DESCRIPTION
            "The entry of zxPimSmNbrTable"
        INDEX  { zxPimSmNbrAddr,
                 zxPimSmNbrIntf
                 }
        ::= { zxPimSmNbrTable  1}    
         
    ZxPimSmNbrEntry  ::= SEQUENCE  {
        zxPimSmNbrAddr          IpAddress,
        zxPimSmNbrIntf          DisplayString,
        zxPimSmNbrDrPriority    Integer32,
        zxPimSmNbrUptime        DisplayString,
        zxPimSmNbrExpire        DisplayString,
        zxPimSmNbrVer    		INTEGER
        }
              
    zxPimSmNbrAddr  OBJECT-TYPE
        SYNTAX      IpAddress
        MAX-ACCESS  read-only
        STATUS      current
        DESCRIPTION
            "The neighbour Ip address."
        ::= { zxPimSmNbrEntry 1 }  
        
    zxPimSmNbrIntf  OBJECT-TYPE
        SYNTAX      DisplayString(SIZE(0..31))
        MAX-ACCESS  read-only
        STATUS      current
        DESCRIPTION
            "The interface name."
        ::= { zxPimSmNbrEntry 2 }  
        
    zxPimSmNbrDrPriority  OBJECT-TYPE
        SYNTAX      Integer32
        MAX-ACCESS  read-only
        STATUS      current
        DESCRIPTION
            "The DR priority."
        ::= { zxPimSmNbrEntry 3 }  
        
    zxPimSmNbrUptime  OBJECT-TYPE
        SYNTAX      DisplayString
        MAX-ACCESS  read-only
        STATUS      current
        DESCRIPTION
            "The time of the neighbour created."
        ::= { zxPimSmNbrEntry 4 }  
        
    zxPimSmNbrExpire  OBJECT-TYPE
        SYNTAX      DisplayString
        MAX-ACCESS  read-only
        STATUS      current
        DESCRIPTION
            "The time of the neighbour expires."
        ::= { zxPimSmNbrEntry 5 }  
        
    zxPimSmNbrVer  OBJECT-TYPE
        SYNTAX      INTEGER{igmpv1(1),igmpv2(2)}
        MAX-ACCESS  read-only
        STATUS      current
        DESCRIPTION
            "The IGMP version."
        ::= { zxPimSmNbrEntry 6 }   
        
    -- pimsm packet table               
    zxPimSmPktTable    OBJECT-TYPE
        SYNTAX      SEQUENCE OF ZxPimSmPktEntry
        MAX-ACCESS  not-accessible
        STATUS      current
        DESCRIPTION 
        "This table contains pimsm packet information."
        ::= { zxPimGroup 7 }
        
     zxPimSmPktEntry  OBJECT-TYPE
        SYNTAX      ZxPimSmPktEntry
        MAX-ACCESS  not-accessible
        STATUS      current
        DESCRIPTION
            "The entry of zxPimSmPktTable"
        INDEX  { zxPimSmPktIntf,
                 zxPimSmPktType
                 }
        ::= { zxPimSmPktTable  1}    
         
    ZxPimSmPktEntry  ::= SEQUENCE  {
        zxPimSmPktIntf      DisplayString,
        zxPimSmPktType      INTEGER,
        zxPimSmPktRxOk      Integer32,
        zxPimSmPktTxOk      Integer32,
        zxPimSmPktRxError   Integer32,
        zxPimSmPktTxError   Integer32
        }
          
    zxPimSmPktIntf  OBJECT-TYPE
        SYNTAX      DisplayString(SIZE(0..31))
        MAX-ACCESS  read-only
        STATUS      current
        DESCRIPTION
            "The interface name."
        ::= { zxPimSmPktEntry 1 } 
        
    zxPimSmPktType  OBJECT-TYPE
        SYNTAX      INTEGER{hello(1),register(2),register-Stop(3),
                              joinOrPrune(4),bsr(5),assert(6),graft(7),
                              graft-ack(8),crp-adv(9),probe(10),err-type(11)}
        MAX-ACCESS  read-only
        STATUS      current
        DESCRIPTION
            "The packet type."
        ::= { zxPimSmPktEntry 2 } 
        
    zxPimSmPktRxOk  OBJECT-TYPE
        SYNTAX      Integer32
        MAX-ACCESS  read-only
        STATUS      current
        DESCRIPTION
            "The ok packet received from this interface."
        ::= { zxPimSmPktEntry 3 }  
        
    zxPimSmPktTxOk  OBJECT-TYPE
        SYNTAX      Integer32
        MAX-ACCESS  read-only
        STATUS      current
        DESCRIPTION
            "The ok packet sent from this interface."
        ::= { zxPimSmPktEntry 4 }  
        
    zxPimSmPktRxError  OBJECT-TYPE
        SYNTAX      Integer32
        MAX-ACCESS  read-only
        STATUS      current
        DESCRIPTION
            "The error packet received from this interface."
        ::= { zxPimSmPktEntry 5 }  
        
    zxPimSmPktTxError  OBJECT-TYPE
        SYNTAX      Integer32
        MAX-ACCESS  read-only
        STATUS      current
        DESCRIPTION
            "The error packet sent from this interface."
        ::= { zxPimSmPktEntry 6 }   
     
     
     zxIgmpUasAclSwitch    OBJECT-TYPE
        SYNTAX      INTEGER{disable(1),enable(2)}
        MAX-ACCESS  read-only
        STATUS      current
        DESCRIPTION 
        "The switch of IGMP ACL."
        ::= { zxIgmpUasGroup 1 } 
        
    zxIgmpUasPrivateServerLogSwitch    OBJECT-TYPE
        SYNTAX      INTEGER{disable(1),enable(2)}
        MAX-ACCESS  read-only
        STATUS      current
        DESCRIPTION 
        "The switch of IGMP private server log."
        ::= { zxIgmpUasGroup 2 }
        
        
    -- Igmp uas acl table               
    zxIgmpUasAclTable    OBJECT-TYPE
        SYNTAX      SEQUENCE OF ZxIgmpUasAclEntry
        MAX-ACCESS  not-accessible
        STATUS      current
        DESCRIPTION 
        "This table contains IGMP ACL permitted."
        ::= { zxIgmpUasGroup 3 }
        
     zxIgmpUasAclEntry  OBJECT-TYPE
        SYNTAX      ZxIgmpUasAclEntry
        MAX-ACCESS  not-accessible
        STATUS      current
        DESCRIPTION
            "The entry of zxIgmpUasAclTable"
        INDEX  { zxIgmpUasAclSourceAddr,
                 zxIgmpUasAclDestAddr
                 }
        ::= { zxIgmpUasAclTable  1}    
         
    ZxIgmpUasAclEntry  ::= SEQUENCE  {
        zxIgmpUasAclSourceAddr    IpAddress,
        zxIgmpUasAclDestAddr      DisplayString
        }  
        
    zxIgmpUasAclSourceAddr  OBJECT-TYPE
        SYNTAX      IpAddress
        MAX-ACCESS  read-only
        STATUS      current
        DESCRIPTION
            "The permitted souce IP address."
        ::= { zxIgmpUasAclEntry 1 } 
        
    zxIgmpUasAclDestAddr  OBJECT-TYPE
        SYNTAX      DisplayString(SIZE(1..31))
        MAX-ACCESS  read-only
        STATUS      current
        DESCRIPTION
            "The permitted destination IP address or any."
        ::= { zxIgmpUasAclEntry 2 } 
        
    -- Igmp uas service-profile table               
    zxIgmpUasServiceProfileTable    OBJECT-TYPE
        SYNTAX      SEQUENCE OF ZxIgmpUasServiceProfileEntry
        MAX-ACCESS  not-accessible
        STATUS      current
        DESCRIPTION 
        "This table contains IGMP service profile."
        ::= { zxIgmpUasGroup 4 }
        
     zxIgmpUasServiceProfileEntry  OBJECT-TYPE
        SYNTAX      ZxIgmpUasServiceProfileEntry
        MAX-ACCESS  not-accessible
        STATUS      current
        DESCRIPTION
            "The entry of zxIgmpUasServiceProfileTable"
        INDEX  { zxIgmpUasServiceProfileNumber,
                 zxIgmpUasServiceProfilePrwGroup,
                 zxIgmpUasServiceProfilePrwGroupMask
                 }
        ::= { zxIgmpUasServiceProfileTable  1}    
         
    ZxIgmpUasServiceProfileEntry  ::= SEQUENCE  {
        zxIgmpUasServiceProfileNumber              Integer32,
        zxIgmpUasServiceProfileAccGroup            Integer32,
        zxIgmpUasServiceProfileDescr               DisplayString,
        zxIgmpUasServiceProfileMaxGroup            Integer32,
        zxIgmpUasServiceProfileMaxPrwGroup         Integer32,
        zxIgmpUasServiceProfilePrwGroup            IpAddress,
        zxIgmpUasServiceProfilePrwGroupMask        IpAddress,
        zxIgmpUasServiceProfileMaxPrwCount         Integer32,
        zxIgmpUasServiceProfilePrwResumeIntvl      Integer32
        }  
        
    zxIgmpUasServiceProfileNumber  OBJECT-TYPE
        SYNTAX      Integer32
        MAX-ACCESS  read-only
        STATUS      current
        DESCRIPTION
            "The service profile number."
        ::= { zxIgmpUasServiceProfileEntry 1 } 
        
    zxIgmpUasServiceProfileAccGroup  OBJECT-TYPE
        SYNTAX      Integer32
        MAX-ACCESS  read-only
        STATUS      current
        DESCRIPTION
            "The service profile related security ACL."
        ::= { zxIgmpUasServiceProfileEntry 2 } 
        
    zxIgmpUasServiceProfileDescr  OBJECT-TYPE
        SYNTAX      DisplayString
        MAX-ACCESS  read-only
        STATUS      current
        DESCRIPTION
            "The service profile description."
        ::= { zxIgmpUasServiceProfileEntry 3 }
        
    zxIgmpUasServiceProfileMaxGroup  OBJECT-TYPE
        SYNTAX      Integer32
        MAX-ACCESS  read-only
        STATUS      current
        DESCRIPTION
            "The max multicast group count"
        ::= { zxIgmpUasServiceProfileEntry 4 }
        
    zxIgmpUasServiceProfileMaxPrwGroup  OBJECT-TYPE
        SYNTAX      Integer32
        MAX-ACCESS  read-only
        STATUS      current
        DESCRIPTION
            "The max preview multicast group count."
        ::= { zxIgmpUasServiceProfileEntry 5 }
        
    zxIgmpUasServiceProfilePrwGroup  OBJECT-TYPE
        SYNTAX      IpAddress
        MAX-ACCESS  read-only
        STATUS      current
        DESCRIPTION
            "The channel multicast group address."
        ::= { zxIgmpUasServiceProfileEntry 6 }
        
    zxIgmpUasServiceProfilePrwGroupMask  OBJECT-TYPE
        SYNTAX      IpAddress
        MAX-ACCESS  read-only
        STATUS      current
        DESCRIPTION
            "The channel multicast group address submask."
        ::= { zxIgmpUasServiceProfileEntry 7 }
        
    zxIgmpUasServiceProfileMaxPrwCount  OBJECT-TYPE
        SYNTAX      Integer32
        MAX-ACCESS  read-only
        STATUS      current
        DESCRIPTION
            "The max preview count. This attribute is related to zxIgmpUasServiceProfilePrwGroup."
        ::= { zxIgmpUasServiceProfileEntry 8 }
        
    zxIgmpUasServiceProfilePrwResumeIntvl  OBJECT-TYPE
        SYNTAX      Integer32
        MAX-ACCESS  read-only
        STATUS      current
        DESCRIPTION
            "The max preview time. This attribute is related to zxIgmpUasServiceProfilePrwGroup."
        ::= { zxIgmpUasServiceProfileEntry 9 }
             
END

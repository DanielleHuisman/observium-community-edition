ZX-PWE3-MIB DEFINITIONS ::= BEGIN 
     
IMPORTS 
    MODULE-IDENTITY 
       FROM SNMPv2-SMI -- [RFC2578] 
 
    TEXTUAL-CONVENTION 
       FROM SNMPv2-TC  -- [RFC2579] 
       
    zxAnCesMib
       FROM ZTE-MASTER-MIB 
    ;
 
zxPwe3MIB  MODULE-IDENTITY 
    LAST-UPDATED "200605150000Z"  -- May 15, 2006
    ORGANIZATION    "Zhongxing Telcom Co. Ltd."
    CONTACT-INFO    "Zhongxing Telcom Co. Ltd.
                     E-mail: info@mail.zte.com.cn
                     http  : www.zte.com.cn or www.zhongxing.com"
    DESCRIPTION 
        "This MIB module defines the IANAPwTypeTC and 
        IANAPwPsnTypeTC textual conventions for use in PWE3 
        MIB modules. 
 
        Any additions or changes to the contents of this MIB 
        module require either publication of an RFC, Designated  
        Expert Review as defined in RFC 2434, Guidelines for  
        Writing an IANA Considerations Section in RFCs, and should  
        be based on the procedures defined in [PWE3IANA]. The  
        Designated Expert will be selected by the IESG Area  
        Director(s) of the internet Area." 
 
    ::= { zxAnCesMib 5 } 
 
IANAPwTypeTC ::= TEXTUAL-CONVENTION  
   STATUS     current  
   DESCRIPTION  
      "Indicates the PW type (i.e. the carried service). " 
   SYNTAX   INTEGER {  
      other(0),  
      frameRelayDlci(1),  
      atmAal5SduVcc(2),  
      atmTransparent(3),  
      ethernetTagged(4),  
      ethernet(5),  
      hdlc(6),  
      ppp(7),  
      cem(8),  -- old format  
      atmCellNto1Vcc(9),  
      atmCellNto1Vpc(10),  
      ipLayer2Transport(11),  
      atmCell1to1Vcc(12),  
      atmCell1to1Vpc(13),  
      atmAal5PduVcc(14),  
      frameRelayPortMode(15),  
      cep(16),  
      e1Satop(17),  
      t1Satop(18),  
      e3Satop(19),  
      t3Satop(20),  
      basicCesPsn(21),  
      basicTdmIp(22),  
      tdmCasCesPsn(23),  
      tdmCasTdmIp(24), 
      frDlci(25),
      e1Cesop(253),
      t1Cesop(254)  
       }        
 
IANAPwPsnTypeTC ::= TEXTUAL-CONVENTION  
   STATUS      current  
   DESCRIPTION 
      "Identifies the PSN type which the PW will use over the  
       network." 
   SYNTAX   INTEGER {  
      mpls       (1),   
      l2tp       (2),  
      ip         (3),  
      mplsOverIp (4),   
      gre        (5),  
      other      (6)  
      } 
END

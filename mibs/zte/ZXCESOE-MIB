ZXCESOE-MIB DEFINITIONS ::= BEGIN

IMPORTS
   MODULE-IDENTITY, OBJECT-TYPE,
   Integer32
     FROM SNMPv2-SMI

   MacAddress, RowStatus
     FROM SNMPv2-TC

   InterfaceIndexOrZero
     FROM IF-MIB

   zxPwIndex
     FROM ZXPW-STD-MIB

   zxPwCETH
        FROM ZTE-MASTER-MIB
        
   PwVlanCfg
        FROM ZXPW-TC-STD-MIB
  ;

zxCesoeMIB        MODULE-IDENTITY
    LAST-UPDATED "200605150000Z"  -- May 15, 2006
    ORGANIZATION    "Zhongxing Telcom Co. Ltd."
    CONTACT-INFO    "Zhongxing Telcom Co. Ltd.
                     E-mail: info@mail.zte.com.cn
                     http  : www.zte.com.cn or www.zhongxing.com"

    DESCRIPTION
         "The MIB module to describe ethernet 
         configuration objects.
         "
    ::= { zxPwCETH 2 }
    
------------------------------------------------------------------------------
--  define objects in ZXCESOE-MIB
------------------------------------------------------------------------------

zxCesoeCfgTable     OBJECT-TYPE
     SYNTAX         SEQUENCE OF ZxCesoeCfgEntry
     MAX-ACCESS     not-accessible
     STATUS         current
     DESCRIPTION
            "The ethernet(PWE PSN) Configuration table."
     ::= { zxCesoeMIB 1 }

zxCesoeCfgEntry     OBJECT-TYPE
     SYNTAX         ZxCesoeCfgEntry
     MAX-ACCESS     not-accessible
     STATUS         current
     DESCRIPTION
         "This table is indexed by the same index that was
          created for the associated entry in the PW Table
          (in the ZXPW-STD-MIB).

          - The zxPwIndex.
          An entry is created in this table by the agent for every
          entry in the zxPwTable with a zxPwPsnType equal to 'other'
         "
     INDEX   { zxPwIndex }
     ::= { zxCesoeCfgTable 1 }

ZxCesoeCfgEntry ::= SEQUENCE {
               
          zxCesoeCfgDstMac                   MacAddress,
          zxCesoeCfgCardIfIndex              InterfaceIndexOrZero,
          zxCesoeCfgVlanId                   PwVlanCfg,
          zxCesoeCfgPrio                     Integer32,
          zxCesoeCfgRowStatus                RowStatus,
          zxCesoeCfgCVlanId                  PwVlanCfg               

}

zxCesoeCfgDstMac      OBJECT-TYPE
      SYNTAX          MacAddress
      MAX-ACCESS      read-create
      STATUS          current
      DESCRIPTION
          "{ '000000000000'H }
           the destination macaddress of a pseudo wire (PW) virtual  
           connection."
      REFERENCE
          "Used by MAP"       
      ::= { zxCesoeCfgEntry 1 } 
      
zxCesoeCfgCardIfIndex OBJECT-TYPE
      SYNTAX          InterfaceIndexOrZero
      MAX-ACCESS      read-create
      STATUS          current
      DESCRIPTION
          "This is a unique index within the ifTable. It represents
           the ethernet interface index of the (PW) link.
           Once set, if the ethernet ifIndex is (for some reason) later
           removed, the agent SHOULD delete the associated PW rows. 
           If the agent does not delete the rows,  
           the agent MUST set this object to
           zero."
      ::= { zxCesoeCfgEntry 2 }
      
zxCesoeCfgVlanId      OBJECT-TYPE
      SYNTAX          PwVlanCfg
      MAX-ACCESS      read-create
      STATUS          current
      DESCRIPTION
          ""
      REFERENCE
          "Used by MAP"             
      DEFVAL { 1 }
      ::= { zxCesoeCfgEntry 3 } 
      
zxCesoeCfgPrio        OBJECT-TYPE
      SYNTAX          Integer32
      MAX-ACCESS      read-create
      STATUS          current
      DESCRIPTION
          ""
      REFERENCE
          "Used by MAP"             
      ::= { zxCesoeCfgEntry 4 } 
      
zxCesoeCfgRowStatus   OBJECT-TYPE
      SYNTAX          RowStatus
      MAX-ACCESS      read-create
      STATUS          current
      DESCRIPTION
          "Once the manager set this object, the agent must send
           the pw congfiguration to the corresponding card."
      REFERENCE
          "Used by MAP"              
      ::= { zxCesoeCfgEntry 5 } 
      
zxCesoeCfgCVlanId      OBJECT-TYPE
      SYNTAX          PwVlanCfg
      MAX-ACCESS      read-create
      STATUS          current
      DESCRIPTION
          ""
      DEFVAL { 1 }
      ::= { zxCesoeCfgEntry 6 }       
      
END

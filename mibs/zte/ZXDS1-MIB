ZXDS1-MIB DEFINITIONS ::= BEGIN

IMPORTS
     MODULE-IDENTITY, OBJECT-TYPE
          FROM SNMPv2-SMI                    -- [RFC2578]
     DisplayString, TimeStamp, TruthValue
          FROM SNMPv2-TC                     -- [RFC2579]
     InterfaceIndex
          FROM IF-MIB                        -- [RFC2863]
    
     zxPwCTDM
        FROM ZTE-MASTER-MIB
    ;

zxDs1 MODULE-IDENTITY
    LAST-UPDATED "200605150000Z"  -- May 15, 2006
    ORGANIZATION    "Zhongxing Telcom Co. Ltd."
    CONTACT-INFO    "Zhongxing Telcom Co. Ltd.
                     E-mail: info@mail.zte.com.cn
                     http  : www.zte.com.cn or www.zhongxing.com"

    DESCRIPTION
         "The MIB module to describe DS1, E1, DS2, and
          E2 interfaces objects.
         "
    ::= { zxPwCTDM 1 }
    
------------------------------------------------------------------------------
--  define objects in ZXDS1-MIB
------------------------------------------------------------------------------

zxDsx1ConfigTable OBJECT-TYPE
     SYNTAX  SEQUENCE OF ZxDsx1ConfigEntry
     MAX-ACCESS  not-accessible
     STATUS  current
     DESCRIPTION
            "The DS1 Configuration table."
     ::= { zxDs1 1 }

zxDsx1ConfigEntry OBJECT-TYPE
     SYNTAX  ZxDsx1ConfigEntry
     MAX-ACCESS  not-accessible
     STATUS  current
     DESCRIPTION
            "An entry in the DS1 Configuration table."
     INDEX   { zxDsx1LineIndex }
     ::= { zxDsx1ConfigTable 1 }

ZxDsx1ConfigEntry ::=
     SEQUENCE {
           zxDsx1LineIndex                        InterfaceIndex,
           zxDsx1IfIndex                          InterfaceIndex,
           zxDsx1TimeElapsed                      INTEGER,
           zxDsx1ValidIntervals                   INTEGER,
           zxDsx1LineType                         INTEGER,
           zxDsx1LineCoding                       INTEGER,
           zxDsx1SendCode                         INTEGER,
           zxDsx1CircuitIdentifier                DisplayString,
           zxDsx1LoopbackConfig                   INTEGER,
           zxDsx1LineStatus                       INTEGER,
           zxDsx1SignalMode                       INTEGER,
           zxDsx1TransmitClockSource              INTEGER,
           zxDsx1Fdl                              INTEGER,
           zxDsx1InvalidIntervals                 INTEGER,
           zxDsx1LineLength                       INTEGER,
           zxDsx1LineStatusLastChange             TimeStamp,
           zxDsx1LineStatusChangeTrapEnable       INTEGER,
           zxDsx1LoopbackStatus                   INTEGER,
           zxDsx1Ds1ChannelNumber                 INTEGER,
           zxDsx1Channelization                   INTEGER,
           zxDsx1LineMode                         INTEGER,
           zxDsx1LineBuildOut                     INTEGER,
           zxDsx1AdminStatus                      INTEGER,
           zxDsx1OperStatus                       INTEGER,
           zxDsx1ClockStatus                      INTEGER,
           zxDsx1CfgInfoSend                      TruthValue,
           zxDsx1Retiming                         TruthValue,
           zxDsx1Impedance                        INTEGER,
           zxDsx1FrameType                        INTEGER,
           zxDsx1BER                              INTEGER,
           zxDsx1ClockStatusTrapEnable            INTEGER
}

zxDsx1LineIndex OBJECT-TYPE
     SYNTAX  InterfaceIndex
     MAX-ACCESS  not-accessible  -- read-only since originally an
                            -- SMIv1 index
     STATUS  current
     DESCRIPTION
            "This object should be made equal to ifIndex.  The
            next paragraph describes its previous usage.
            Making the object equal to ifIndex allows proper
            use of ifStackTable and ds0/ds0bundle mibs.

            Previously, this object is the identifier of a DS1
            Interface on a managed device.  If there is an
            ifEntry that is directly associated with this and
            only this DS1 interface, it should have the same
            value as ifIndex.  Otherwise, number the
            zxDsx1LineIndices with an unique identifier
            following the rules of choosing a number that is
            greater than ifNumber and numbering the inside
            interfaces (e.g., equipment side) with even
            numbers and outside interfaces (e.g., network side)
            with odd numbers."
     ::= { zxDsx1ConfigEntry 1 }

zxDsx1IfIndex OBJECT-TYPE
     SYNTAX  InterfaceIndex
     MAX-ACCESS  read-only
     STATUS  deprecated
     DESCRIPTION
            "This value for this object is equal to the value
            of ifIndex from the Interfaces table of MIB II
            (RFC 1213)."
     ::= { zxDsx1ConfigEntry 2 }

zxDsx1TimeElapsed OBJECT-TYPE
     SYNTAX  INTEGER (0..899)
     MAX-ACCESS  read-only
     STATUS  current
     DESCRIPTION
            "The number of seconds that have elapsed since the
            beginning of the near end current error-measurement
            period. If, for some reason, such as an adjustment
            in the system's time-of-day clock, the current interval
            exceeds the maximum value, the agent will return the
            maximum value."
     ::= { zxDsx1ConfigEntry 3 }

zxDsx1ValidIntervals OBJECT-TYPE
     SYNTAX  INTEGER (0..96)
     MAX-ACCESS  read-only
     STATUS  current
     DESCRIPTION
            "The number of previous near end intervals for
            which data was collected.  The value will be 96
            unless the interface was brought online within the
            last 24 hours, in which case the value will be the
            number of complete 15 minute near end intervals
            since the interface has been online.  In the case
            where the agent is a proxy, it is possible that
            some intervals are unavailable.  In this case,
            this interval is the maximum interval number for
            which data is available."
     ::= { zxDsx1ConfigEntry 4 }

zxDsx1LineType OBJECT-TYPE
     SYNTAX  INTEGER {
                other(1),
                dsx1ESF(2),
                dsx1D4(3),
                dsx1E1(4),
                dsx1E1CRC(5),
                dsx1E1MF(6),
                dsx1E1CRCMF(7),
                dsx1Unframed(8),
                dsx1E1Unframed(9),
                dsx1DS2M12(10),
                dsx1E2(11),
                dsx1E1Q50(12),
                dsx1E1Q50CRC(13)
            }
     MAX-ACCESS  read-write
     STATUS  current
     DESCRIPTION
            "This variable indicates  the  variety  of  DS1
            Line  implementing  this  circuit.  The type of
            circuit affects the number of bits  per  second
            that  the circuit can reasonably carry, as well
            as the interpretation of the  usage  and  error
            statistics. The values, in sequence, describe:

                  TITLE:         SPECIFICATION:
                  dsx1ESF        Extended SuperFrame DS1
                                       (T1.107)
                  dsx1D4         AT&T D4 format DS1 (T1.107)
                  dsx1E1         ITU-T Recommendation G.704
                                       (Table 4a)
                  dsx1E1-CRC     ITU-T Recommendation G.704
                                       (Table 4b)
                  dsxE1-MF       G.704 (Table 4a) with TS16
                                        multiframing enabled
                  dsx1E1-CRC-MF  G.704 (Table 4b) with TS16
                                       multiframing enabled
                  dsx1Unframed   DS1 with No Framing
                  dsx1E1Unframed E1 with No Framing (G.703)
                  dsx1DS2M12     DS2 frame format (T1.107)
                  dsx1E2         E2 frame format (G.704)
                  dsx1E1Q50      TS16 bits 5,7,8 set to 101, [in
                                   all other cases it is set
                                   to 111.](ITU-T G.704,table 14)
                  dsx1E1Q50CRC   E1Q50 with CRC.

            For clarification, the capacity for each E1 type
            is as listed below:
            dsx1E1Unframed - E1, no framing = 32 x 64k = 2048k
            dsx1E1 or dsx1E1CRC - E1, with framing,
               no signalling = 31 x 64k = 1984k
            dsx1E1MF or dsx1E1CRCMF - E1, with framing,
               signalling = 30 x 64k = 1920k"
    REFERENCE
            "American National Standard for telecommunications -
               digital hierarchy - formats specification,
               ANSI-T1.107 - 1988.
            CCITT Specifications Volume III, Recommendation
               G.703, Physical/Electrical Characteristics
               of Hierarchical Digital Interfaces, April 1991.
            ITU-T-G.704: Synchronous frame structures used at
               1544, 6312, 2048, 8488 and 44 736 kbit/s
               Hierarchical Levels, July 1995."
     ::= { zxDsx1ConfigEntry 5 }

zxDsx1LineCoding OBJECT-TYPE
     SYNTAX  INTEGER {
                dsx1JBZS (1),
                dsx1B8ZS (2),
                dsx1HDB3 (3),
                dsx1ZBTSI (4),
                dsx1AMI (5),
                other(6),
                dsx1B6ZS(7)
            }
     MAX-ACCESS  read-write
     STATUS  current
     DESCRIPTION
            "This variable describes the variety of Zero Code
            Suppression used on this interface, which in turn
            affects a number of its characteristics.

            dsx1JBZS refers the Jammed Bit Zero Suppression,
            in which the AT&T specification of at least one
            pulse every 8 bit periods is literally implemented
            by forcing a pulse in bit 8 of each channel.
            Thus, only seven bits per channel, or 1.344 Mbps,
            is available for data.

            dsx1B8ZS refers to the use of a specified pattern
            of normal bits and bipolar violations which are
            used to replace a sequence of eight zero bits.

            ANSI Clear Channels may use dsx1ZBTSI, or Zero
            Byte Time Slot Interchange.

            E1 links, with or without CRC, use dsx1HDB3 or
            dsx1AMI.

            dsx1AMI refers to a mode wherein no zero code
            suppression is present and the line encoding does
            not solve the problem directly.  In this
            application, the higher layer must provide data
            which meets or exceeds the pulse density
            requirements, such as inverting HDLC data.
            dsx1B6ZS refers to the user of a specified pattern
            of normal bits and bipolar violations which are
            used to replace a sequence of six zero bits.  Used
            for DS2."

     ::= { zxDsx1ConfigEntry 6 }

zxDsx1SendCode OBJECT-TYPE
     SYNTAX  INTEGER {
               dsx1SendNoCode(1),
               dsx1SendLineCode(2),
               dsx1SendPayloadCode(3),
               dsx1SendResetCode(4),
               dsx1SendQRS(5),
               dsx1Send511Pattern(6),
               dsx1Send3in24Pattern(7),
               dsx1SendOtherTestPattern(8)
               }
     MAX-ACCESS  read-write
     STATUS  current
     DESCRIPTION
            "This variable indicates what type of code is
            being sent across the DS1 interface by the device.
            Setting this variable causes the interface to send
            the code requested.  The values mean:
      dsx1SendNoCode
           sending looped or normal data

      dsx1SendLineCode
           sending a request for a line loopback

      dsx1SendPayloadCode
           sending a request for a payload loopback

      dsx1SendResetCode
           sending a loopback termination request

      dsx1SendQRS
           sending a Quasi-Random Signal  (QRS)  test
           pattern

      dsx1Send511Pattern
           sending a 511 bit fixed test pattern

      dsx1Send3in24Pattern
           sending a fixed test pattern of 3 bits set
           in 24

      dsx1SendOtherTestPattern
           sending a test pattern  other  than  those
           described by this object"
     ::= { zxDsx1ConfigEntry 7 }

zxDsx1CircuitIdentifier OBJECT-TYPE
     SYNTAX  DisplayString (SIZE (0..255))
     MAX-ACCESS  read-write
     STATUS  current
     DESCRIPTION
            "This variable contains the transmission vendor's
            circuit identifier, for the purpose of
            facilitating troubleshooting."
     REFERENCE "ITU-T M.1400"
     ::= { zxDsx1ConfigEntry 8 }

zxDsx1LoopbackConfig OBJECT-TYPE
     SYNTAX  INTEGER {
                 dsx1NoLoop(1),
                 dsx1PayloadLoop(2),
                 dsx1LineLoop(3),
                 dsx1OtherLoop(4),
                 dsx1InwardLoop(5),
                 dsx1DualLoop(6)
               }
     MAX-ACCESS  read-write
     STATUS  current
     DESCRIPTION
            "This variable represents the desired loopback
            configuration of the DS1 interface.  Agents
            supporting read/write access should return
            inconsistentValue in response to a requested
            loopback state that the interface does not
            support.  The values mean:

            dsx1NoLoop
             Not in the loopback state.  A device that is not
            capable of performing a loopback on the interface
            shall always return this as its value.

            dsx1PayloadLoop
             The received signal at this interface is looped
            through the device.  Typically the received signal
            is looped back for retransmission after it has
            passed through the device's framing function.

            dsx1LineLoop
             The received signal at this interface does not go
            through the device (minimum penetration) but is
            looped back out.

            dsx1OtherLoop
             Loopbacks that are not defined here.

            dsx1InwardLoop
             The transmitted signal at this interface is
            looped back and received by the same interface.
            What is transmitted onto the line is product
            dependent.

            dsx1DualLoop
             Both dsx1LineLoop and dsx1InwardLoop will be
            active simultaneously."
     ::= { zxDsx1ConfigEntry 9 }

zxDsx1LineStatus OBJECT-TYPE
     SYNTAX  INTEGER (1..131071)
     MAX-ACCESS  read-only
     STATUS  current
     DESCRIPTION
            "This variable indicates the Line Status of the
            interface.  It contains loopback, failure,
            received 'alarm' and transmitted 'alarms
            information.

            The zxDsx1LineStatus is a bit map represented as a
            sum, therefore, it can represent multiple failures
            (alarms) and a LoopbackState simultaneously.

            dsx1NoAlarm must be set if and only if no other
            flag is set.

            If the dsx1loopbackState bit is set, the loopback
            in effect can be determined from the
            dsx1loopbackConfig object.  The various bit
            positions are:

      1     dsx1NoAlarm           No alarm present
      2     dsx1RcvFarEndLOF      Far end LOF (a.k.a., Yellow Alarm)
      4     dsx1XmtFarEndLOF      Near end sending LOF Indication
      8     dsx1RcvAIS            Far end sending AIS
     16     dsx1XmtAIS            Near end sending AIS
     32     dsx1LossOfFrame       Near end LOF (a.k.a., Red Alarm)
     64     dsx1LossOfSignal      Near end Loss Of Signal
    128     dsx1LoopbackState     Near end is looped
    256     dsx1T16AIS            E1 TS16 AIS
    512     dsx1RcvFarEndLOMF     Far End Sending TS16 LOMF
   1024     dsx1XmtFarEndLOMF     Near End Sending TS16 LOMF
   2048     dsx1RcvTestCode       Near End detects a test code
   4096     dsx1OtherFailure      any line status not defined here
   8192     dsx1UnavailSigState   Near End in Unavailable Signal
                                  State
  16384     dsx1NetEquipOOS       Carrier Equipment Out of Service
  32768     dsx1RcvPayloadAIS     DS2 Payload AIS
  65536     dsx1Ds2PerfThreshold  DS2 Performance Threshold
                                  Exceeded"
     ::= { zxDsx1ConfigEntry 10 }

zxDsx1SignalMode OBJECT-TYPE
     SYNTAX  INTEGER {
                none (1),
                robbedBit (2),
                bitOriented (3),
                messageOriented (4),
                other (5)
            }
     MAX-ACCESS  read-write
     STATUS  current
     DESCRIPTION
       "'none' indicates that no bits are reserved for
       signaling on this channel.

       'robbedBit' indicates that DS1 Robbed Bit Signaling
       is in use.

       'bitOriented' indicates that E1 Channel
       Associated Signaling is in use.

       'messageOriented' indicates that Common
       Channel Signaling is in use either on channel 16
       of an E1 link or channel 24 of a DS1."
     ::= { zxDsx1ConfigEntry 11 }

zxDsx1TransmitClockSource OBJECT-TYPE
     SYNTAX  INTEGER {
                loopTiming(1),
                localTiming(2),
                throughTiming(3),
                adaptive (4),
                enhancedAdaptive (5),
                defferential(6)
            }
     MAX-ACCESS  read-write
     STATUS  current
     DESCRIPTION
       "The source of Transmit Clock.
        'loopTiming' indicates that the recovered
        receive clock is used as the transmit clock.

        'localTiming' indicates that a local clock
       source is used or when an external clock is
       attached to the box containing the interface.

        'throughTiming' indicates that recovered
       receive clock from another interface is used as
       the transmit clock.

        'adaptive' indicates that the clock is recovered
       based on the data flow and not based on the
       physical layer"
     ::= { zxDsx1ConfigEntry 12 }

zxDsx1Fdl OBJECT-TYPE
     SYNTAX  INTEGER (1..15)
     MAX-ACCESS  read-write
     STATUS  current
     DESCRIPTION
       "This bitmap describes the use of  the facilities
       data link, and is the sum of the capabilities.
       Set any bits that are appropriate:

       other(1),
       dsx1AnsiT1403(2),
       dsx1Att54016(4),
       dsx1FdlNone(8)

        'other' indicates that a protocol  other  than
       one following is used.

        'dsx1AnsiT1403' refers to the  FDL  exchange
       recommended by ANSI.

        'dsx1Att54016' refers to ESF FDL exchanges.

        'dsx1FdlNone' indicates that the device  does
       not use the FDL."
     ::= { zxDsx1ConfigEntry 13 }

zxDsx1InvalidIntervals OBJECT-TYPE
     SYNTAX  INTEGER (0..96)
     MAX-ACCESS  read-only
     STATUS  current
     DESCRIPTION
            " The number of intervals in the range from 0 to
            zxDsx1ValidIntervals for which no data is available.
            This object will typically be zero except in cases
            where the data for some intervals are not
            available (e.g., in proxy situations)."
     ::= { zxDsx1ConfigEntry 14 }

zxDsx1LineLength OBJECT-TYPE
     SYNTAX  INTEGER (0..64000)
     UNITS  "meters"
     MAX-ACCESS  read-write
     STATUS  current
     DESCRIPTION
            "The length of the ds1 line in meters. This
            objects provides information for line build out
            circuitry.  This object is only useful if the
            interface has configurable line build out
            circuitry."
     ::= { zxDsx1ConfigEntry 15 }

zxDsx1LineStatusLastChange OBJECT-TYPE
     SYNTAX  TimeStamp
     MAX-ACCESS  read-only
     STATUS  current
     DESCRIPTION
            "The value of MIB II's sysUpTime object at the
            time this DS1 entered its current line status
            state.  If the current state was entered prior to
            the last re-initialization of the proxy-agent,
            then this object contains a zero value."
     ::= { zxDsx1ConfigEntry 16 }

zxDsx1LineStatusChangeTrapEnable  OBJECT-TYPE
     SYNTAX      INTEGER {
                    enabled(1),
                    disabled(2)
                 }
     MAX-ACCESS  read-write
     STATUS      current
     DESCRIPTION
            "Indicates whether dsx1LineStatusChange traps
            should be generated for this interface."
     DEFVAL { disabled }
     ::= { zxDsx1ConfigEntry 17 }

zxDsx1LoopbackStatus  OBJECT-TYPE
     SYNTAX      INTEGER (1..127)
     MAX-ACCESS  read-only
     STATUS      current
     DESCRIPTION
            "This variable represents the current state of the
            loopback on the DS1 interface.  It contains
            information about loopbacks established by a
            manager and remotely from the far end.

            The zxDsx1LoopbackStatus is a bit map represented as
            a sum, therefore is can represent multiple
            loopbacks simultaneously.

            The various bit positions are:
             1  dsx1NoLoopback
             2  dsx1NearEndPayloadLoopback
             4  dsx1NearEndLineLoopback
             8  dsx1NearEndOtherLoopback
            16  dsx1NearEndInwardLoopback
            32  dsx1FarEndPayloadLoopback
            64  dsx1FarEndLineLoopback"

     ::= { zxDsx1ConfigEntry 18 }

zxDsx1Ds1ChannelNumber  OBJECT-TYPE
     SYNTAX      INTEGER (0..28)
     MAX-ACCESS  read-only
     STATUS      current
     DESCRIPTION
            "This variable represents the channel number of
            the DS1/E1 on its parent DS2/E2 or DS3/E3.  A
            value of 0 indicated this DS1/E1 does not have a
            parent DS3/E3."

     ::= { zxDsx1ConfigEntry 19 }

zxDsx1Channelization  OBJECT-TYPE
     SYNTAX      INTEGER {
                    disabled(1),
                    enabledDs0(2),
                    enabledDs1(3)
                 }
     MAX-ACCESS  read-write
     STATUS      current
     DESCRIPTION
            "Indicates whether this ds1/e1 is channelized or
            unchannelized.  The value of enabledDs0 indicates
            that this is a DS1 channelized into DS0s.  The
            value of enabledDs1 indicated that this is a DS2
            channelized into DS1s.  Setting this value will
            cause the creation or deletion of entries in the
            ifTable for the DS0s that are within the DS1."
     ::= { zxDsx1ConfigEntry 20 }

zxDsx1LineMode  OBJECT-TYPE
     SYNTAX      INTEGER {
                    csu(1),
                    dsu(2)
                  }
     MAX-ACCESS  read-write
     STATUS      current
     DESCRIPTION
            "This setting puts the T1 framer into either long
            haul (CSU) mode or short haul (DSU) mode."
     ::= { zxDsx1ConfigEntry 21 }

zxDsx1LineBuildOut  OBJECT-TYPE
     SYNTAX      INTEGER {
                    notApplicable (1),
                    neg75dB (2),
                    neg15dB (3),
                    neg225dB (4),
                    zerodB (5)
                 }
     MAX-ACCESS  read-write
     STATUS      current
     DESCRIPTION
            "Attenuation setting for T1 framer in long haul
            (CSU) mode.  The optional values are: -7.5dB,
            -15dB, -22.5dB and 0dB."
     ::= { zxDsx1ConfigEntry 22 }

zxDsx1AdminStatus  OBJECT-TYPE
     SYNTAX      INTEGER {
                    up(1),       -- ready to pass packets
                    down(2),
                    testing(3)   -- in some test mode
                 }
     MAX-ACCESS  read-write
     STATUS      current
     DESCRIPTION
            "The desired state of the interface.  The
             testing(3) state indicates that no operational
             packets can be passed."
     ::= { zxDsx1ConfigEntry 23 }
     
zxDsx1OperStatus  OBJECT-TYPE
     SYNTAX      INTEGER {
                     up(1),       -- ready to pass packets
                     down(2),
                     testing(3)   -- in some test mode
                 }
     MAX-ACCESS  read-only
     STATUS      current
     DESCRIPTION
            "The current operational state of the interface.
             The testing(3) state indicates that no operational
             packets can be passed."
     ::= { zxDsx1ConfigEntry 24 }     

zxDsx1ClockStatus  OBJECT-TYPE
     SYNTAX      INTEGER (1..127)
     MAX-ACCESS  read-only
     STATUS      current
     DESCRIPTION
            "The current clock state of the interface. the value can be:
               FREERUN 0
               HOLDOVER 1 
               ACQUIRING 2
               ACUIRED 3"
     ::= { zxDsx1ConfigEntry 25 } 

zxDsx1CfgInfoSend  OBJECT-TYPE
     SYNTAX       TruthValue
     MAX-ACCESS  read-write
     STATUS      current
     DESCRIPTION
            "The action to send the configuration on 
             Ds1/E1 interface to corresponding card."
     ::= { zxDsx1ConfigEntry 26 }    

zxDsx1Retiming  OBJECT-TYPE
     SYNTAX       TruthValue
     MAX-ACCESS  read-write
     STATUS      current
     DESCRIPTION
            "Enable or disable Ds1/E1 interface retiming."
     ::= { zxDsx1ConfigEntry 27 } 
     
zxDsx1Impedance  OBJECT-TYPE
     SYNTAX       INTEGER
     MAX-ACCESS  read-write
     STATUS      current
     DESCRIPTION
            ""
     ::= { zxDsx1ConfigEntry 28 } 
     
zxDsx1FrameType  OBJECT-TYPE
     SYNTAX      INTEGER {
                     unframe(1),     
                     doubleframe(2),
                     multiframe(3)   
                 }
     MAX-ACCESS  read-write
     STATUS      current
     DESCRIPTION
            ""
     ::= { zxDsx1ConfigEntry 29 } 
     
zxDsx1BER  OBJECT-TYPE
     SYNTAX       INTEGER (0..1000000)
     MAX-ACCESS  read-only
     STATUS      current
     DESCRIPTION
            ""
     ::= { zxDsx1ConfigEntry 30 }   
     
zxDsx1ClockStatusTrapEnable  OBJECT-TYPE
     SYNTAX      INTEGER {
                    enabled(1),
                    disabled(2)
                 }
     MAX-ACCESS  read-write
     STATUS      current
     DESCRIPTION
            "Indicates whether zxDsx1ClockStatus traps
            should be generated for this interface."
     DEFVAL { disabled }
     ::= { zxDsx1ConfigEntry 31 }     
------------------------------------------------------------------------------
--  define the trap objects in ZXDS1-MIB
------------------------------------------------------------------------------     
    zxDsx1TrapObjects      OBJECT IDENTIFIER ::= {zxPwCTDM 100}
        
    zxDsx1ClockStatusUnlock NOTIFICATION-TYPE
        OBJECTS { zxDsx1LineIndex, zxDsx1ClockStatus }
        STATUS  current
        DESCRIPTION
            "A zxDsx1ClockStatusUnlock trap is sent when the current clock 
             status of the interface has changed.NE system will automatically 
              handle the trap jitter."
        ::= { zxDsx1TrapObjects 1 }   
                     
    zxDsx1ClockStatusLock NOTIFICATION-TYPE
        OBJECTS { zxDsx1LineIndex, zxDsx1ClockStatus }
        STATUS  current
        DESCRIPTION
            " A zxDsx1ClockStatusLock trap is sent when the current clock 
             status of the interface is changeless and it was changed 
             in the past.NE system will automatically handle the trap jitter."
        ::= { zxDsx1TrapObjects 2 }                    

END

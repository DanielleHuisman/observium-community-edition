-- *****************************************************************
-- ZTE EPON PERFORMANCE MIB
--
-- 03-06-2007
--
-- Copyright(c) 2007 ZTE Corporation
-- All rights reserved.
-- *****************************************************************

ZXEPON-PERFORMANCE-MIB DEFINITIONS ::= BEGIN 
    IMPORTS 
        ifIndex                          FROM RFC1213-MIB
        MODULE-IDENTITY, Counter64, Counter32, Unsigned32, OBJECT-TYPE      FROM SNMPv2-SMI
        OwnerString, EntryStatus  FROM RMON-MIB
        zxAnEponMib                   FROM ZTE-MASTER-MIB
        zxAnEponOnuLlid               FROM ZXANEPON-ONUMGMT-MIB;

zxAnEponPm        MODULE-IDENTITY
    LAST-UPDATED "200704040000Z"
    ORGANIZATION    "Zhongxing Telcom Co. Ltd."
    CONTACT-INFO    "Zhongxing Telcom Co. Ltd.
                     E-mail: info@mail.zte.com.cn
                     http  : www.zte.com.cn or www.zhongxing.com"

    DESCRIPTION
         ""
    ::= { zxAnEponMib 9 }

    zxAnEponPmInfor   OBJECT IDENTIFIER ::= { zxAnEponPm 1}
    zxAnEponPmCurrent   OBJECT IDENTIFIER ::= { zxAnEponPm 2}
    zxAnEponPmHistory   OBJECT IDENTIFIER ::= { zxAnEponPm 3}

--zxAnEponPmInfor

    zxAnEponOltVirtualIfBERStatisticTable OBJECT-TYPE
        SYNTAX      SEQUENCE OF ZxAnEponOltVirtualIfBERStatisticEntry
        MAX-ACCESS  not-accessible
        STATUS      current
        DESCRIPTION
            "" 
        REFERENCE
            ""
        ::= { zxAnEponPmInfor 1 }

    zxAnEponOltVirtualIfBERStatisticEntry OBJECT-TYPE
        SYNTAX      ZxAnEponOltVirtualIfBERStatisticEntry
        MAX-ACCESS  not-accessible
        STATUS      current
        DESCRIPTION
            ""
        INDEX   { ifIndex }
        ::= { zxAnEponOltVirtualIfBERStatisticTable 1 }

    ZxAnEponOltVirtualIfBERStatisticEntry ::=
        SEQUENCE {
            zxAnEponOltVirtualIfBERStatisticOnuBER     OCTET STRING,
            zxAnEponOltVirtualIfBERStatisticOnuFER     OCTET STRING
        }

   zxAnEponOltVirtualIfBERStatisticOnuBER OBJECT-TYPE
        SYNTAX      OCTET STRING (SIZE (0..16))
        MAX-ACCESS  read-only
        STATUS      current
        DESCRIPTION
            ""
        ::= { zxAnEponOltVirtualIfBERStatisticEntry 1}

   zxAnEponOltVirtualIfBERStatisticOnuFER OBJECT-TYPE
        SYNTAX      OCTET STRING (SIZE (0..16))
        MAX-ACCESS  read-only
        STATUS      current
        DESCRIPTION
            ""
        ::= { zxAnEponOltVirtualIfBERStatisticEntry 2}

    zxAnEponOltPhyPortStatisticTable OBJECT-TYPE
        SYNTAX      SEQUENCE OF ZxAnEponOltPhyPortStatisticEntry
        MAX-ACCESS  not-accessible
        STATUS      current
        DESCRIPTION
            "" 
        REFERENCE
            ""
        ::= { zxAnEponPmInfor 2 }

    zxAnEponOltPhyPortStatisticEntry OBJECT-TYPE
        SYNTAX      ZxAnEponOltPhyPortStatisticEntry
        MAX-ACCESS  not-accessible
        STATUS      current
        DESCRIPTION
            ""
        INDEX   { ifIndex }
        ::= { zxAnEponOltPhyPortStatisticTable 1 }

    ZxAnEponOltPhyPortStatisticEntry ::=
        SEQUENCE {
            zxAnEponOltPhyPortStatisticOltPonAverageBER      OCTET STRING,
            zxAnEponOltPhyPortStatisticOltSysAverageBER      OCTET STRING
        }

   zxAnEponOltPhyPortStatisticOltPonAverageBER OBJECT-TYPE
        SYNTAX      OCTET STRING (SIZE (0..16))
        MAX-ACCESS  read-only
        STATUS      current
        DESCRIPTION
            ""
        ::= { zxAnEponOltPhyPortStatisticEntry 1}

   zxAnEponOltPhyPortStatisticOltSysAverageBER OBJECT-TYPE
        SYNTAX      OCTET STRING (SIZE (0..16))
        MAX-ACCESS  read-only
        STATUS      current
        DESCRIPTION
            ""
        ::= { zxAnEponOltPhyPortStatisticEntry 2}

    zxAnEponEtherStatsTable OBJECT-TYPE
        SYNTAX      SEQUENCE OF ZxAnEponEtherStatsEntry
        MAX-ACCESS  not-accessible
        STATUS      current
        DESCRIPTION
            "" 
        REFERENCE
            ""
        ::= { zxAnEponPmInfor 3 }

    zxAnEponEtherStatsEntry OBJECT-TYPE
        SYNTAX      ZxAnEponEtherStatsEntry
        MAX-ACCESS  not-accessible
        STATUS      current
        DESCRIPTION
            ""
        INDEX   { ifIndex }
        ::= { zxAnEponEtherStatsTable 1 }

    ZxAnEponEtherStatsEntry ::=
        SEQUENCE {
            zxAnEponEtherStatsDropEvents      Counter32,
            zxAnEponEtherStatsOctets      Counter32,
            zxAnEponEtherStatsPkts      Counter32,
            zxAnEponEtherStatsBroadcastPkts      Counter32,
            zxAnEponEtherStatsMulticastPkts      Counter32,
            zxAnEponEtherStatsCRCAlignErrors      Counter32,
            zxAnEponEtherStatsUndersizePkts      Counter32,
            zxAnEponEtherStatsOversizePkts      Counter32,
            zxAnEponEtherStatsFragments      Counter32,
            zxAnEponEtherStatsJabbers      Counter32,
            zxAnEponEtherStatsCollisions      Counter32,
            zxAnEponEtherStatsPkts64Octets      Counter32,
            zxAnEponEtherStatsPkts65to127Octets      Counter32,
            zxAnEponEtherStatsPkts128to255Octets      Counter32,
            zxAnEponEtherStatsPkts256to511Octets      Counter32,
            zxAnEponEtherStatsPkts512to1023Octets       Counter32,
            zxAnEponEtherStatsPkts1024to1518Octets       Counter32
        }

   zxAnEponEtherStatsDropEvents OBJECT-TYPE
        SYNTAX      Counter32
        MAX-ACCESS  read-only
        STATUS      current
        DESCRIPTION
            ""
        ::= { zxAnEponEtherStatsEntry 1}

   zxAnEponEtherStatsOctets OBJECT-TYPE
        SYNTAX      Counter32
        MAX-ACCESS  read-only
        STATUS      current
        DESCRIPTION
            ""
        ::= { zxAnEponEtherStatsEntry 2}

   zxAnEponEtherStatsPkts OBJECT-TYPE
        SYNTAX      Counter32
        MAX-ACCESS  read-only
        STATUS      current
        DESCRIPTION
            ""
        ::= { zxAnEponEtherStatsEntry 3}

   zxAnEponEtherStatsBroadcastPkts OBJECT-TYPE
        SYNTAX      Counter32
        MAX-ACCESS  read-only
        STATUS      current
        DESCRIPTION
            ""
        ::= { zxAnEponEtherStatsEntry 4}

   zxAnEponEtherStatsMulticastPkts OBJECT-TYPE
        SYNTAX      Counter32
        MAX-ACCESS  read-only
        STATUS      current
        DESCRIPTION
            ""
        ::= { zxAnEponEtherStatsEntry 5}

   zxAnEponEtherStatsCRCAlignErrors OBJECT-TYPE
        SYNTAX      Counter32
        MAX-ACCESS  read-only
        STATUS      current
        DESCRIPTION
            ""
        ::= { zxAnEponEtherStatsEntry 6}

   zxAnEponEtherStatsUndersizePkts OBJECT-TYPE
        SYNTAX      Counter32
        MAX-ACCESS  read-only
        STATUS      current
        DESCRIPTION
            ""
        ::= { zxAnEponEtherStatsEntry 7}

   zxAnEponEtherStatsOversizePkts OBJECT-TYPE
        SYNTAX      Counter32
        MAX-ACCESS  read-only
        STATUS      current
        DESCRIPTION
            ""
        ::= { zxAnEponEtherStatsEntry 8}

   zxAnEponEtherStatsFragments OBJECT-TYPE
        SYNTAX      Counter32
        MAX-ACCESS  read-only
        STATUS      current
        DESCRIPTION
            ""
        ::= { zxAnEponEtherStatsEntry 9}

   zxAnEponEtherStatsJabbers OBJECT-TYPE
        SYNTAX      Counter32
        MAX-ACCESS  read-only
        STATUS      current
        DESCRIPTION
            ""
        ::= { zxAnEponEtherStatsEntry 10}

   zxAnEponEtherStatsCollisions OBJECT-TYPE
        SYNTAX      Counter32
        MAX-ACCESS  read-only
        STATUS      current
        DESCRIPTION
            ""
        ::= { zxAnEponEtherStatsEntry 11}

   zxAnEponEtherStatsPkts64Octets OBJECT-TYPE
        SYNTAX      Counter32
        MAX-ACCESS  read-only
        STATUS      current
        DESCRIPTION
            ""
        ::= { zxAnEponEtherStatsEntry 12}

   zxAnEponEtherStatsPkts65to127Octets OBJECT-TYPE
        SYNTAX      Counter32
        MAX-ACCESS  read-only
        STATUS      current
        DESCRIPTION
            ""
        ::= { zxAnEponEtherStatsEntry 13}

   zxAnEponEtherStatsPkts128to255Octets OBJECT-TYPE
        SYNTAX      Counter32
        MAX-ACCESS  read-only
        STATUS      current
        DESCRIPTION
            ""
        ::= { zxAnEponEtherStatsEntry 14}

   zxAnEponEtherStatsPkts256to511Octets OBJECT-TYPE
        SYNTAX      Counter32
        MAX-ACCESS  read-only
        STATUS      current
        DESCRIPTION
            ""
        ::= { zxAnEponEtherStatsEntry 15}

   zxAnEponEtherStatsPkts512to1023Octets OBJECT-TYPE
        SYNTAX      Counter32
        MAX-ACCESS  read-only
        STATUS      current
        DESCRIPTION
            ""
        ::= { zxAnEponEtherStatsEntry 16}

   zxAnEponEtherStatsPkts1024to1518Octets OBJECT-TYPE
        SYNTAX      Counter32
        MAX-ACCESS  read-only
        STATUS      current
        DESCRIPTION
            ""
        ::= { zxAnEponEtherStatsEntry 17}

    zxAnEponIfTable OBJECT-TYPE
        SYNTAX      SEQUENCE OF ZxAnEponIfEntry
        MAX-ACCESS  not-accessible
        STATUS      current
        DESCRIPTION
            "" 
        REFERENCE
            ""
        ::= { zxAnEponPmInfor 4 }

    zxAnEponIfEntry OBJECT-TYPE
        SYNTAX      ZxAnEponIfEntry
        MAX-ACCESS  not-accessible
        STATUS      current
        DESCRIPTION
            ""
        INDEX   { ifIndex }
        ::= { zxAnEponIfTable 1 }

    ZxAnEponIfEntry ::=
        SEQUENCE {
            zxAnEponIfInOctets       Counter32,
            zxAnEponIfInUcastPkts       Counter32,
            zxAnEponIfInNUcastPkts       Counter32,
            zxAnEponIfInDiscards       Counter32,
            zxAnEponIfInErrors       Counter32,
            zxAnEponIfInUnknownProtos       Counter32,
            zxAnEponIfOutOctets       Counter32,
            zxAnEponIfOutUcastPkts        Counter32,
            zxAnEponIfOutNUcastPkts        Counter32,
            zxAnEponIfOutDiscards        Counter32,
            zxAnEponIfOutErrors        Counter32
        }

    zxAnEponIfInOctets OBJECT-TYPE
        SYNTAX      Counter32
        MAX-ACCESS  read-only
        STATUS      current
        DESCRIPTION
                ""
        ::= { zxAnEponIfEntry 1 }

    zxAnEponIfInUcastPkts OBJECT-TYPE
        SYNTAX      Counter32
        MAX-ACCESS  read-only
        STATUS      current
        DESCRIPTION
                ""
        ::= { zxAnEponIfEntry 2 }

    zxAnEponIfInNUcastPkts OBJECT-TYPE
        SYNTAX  Counter32
        MAX-ACCESS  read-only
        STATUS      deprecated
        DESCRIPTION
                ""
        ::= { zxAnEponIfEntry 3 }

    zxAnEponIfInDiscards OBJECT-TYPE
        SYNTAX      Counter32
        MAX-ACCESS  read-only
        STATUS      current
        DESCRIPTION
                ""
        ::= { zxAnEponIfEntry 4 }

    zxAnEponIfInErrors OBJECT-TYPE
        SYNTAX      Counter32
        MAX-ACCESS  read-only
        STATUS      current
        DESCRIPTION
                ""
        ::= { zxAnEponIfEntry 5 }

    zxAnEponIfInUnknownProtos OBJECT-TYPE
        SYNTAX      Counter32
        MAX-ACCESS  read-only
        STATUS      current
        DESCRIPTION
                ""
        ::= { zxAnEponIfEntry 6 }

    zxAnEponIfOutOctets OBJECT-TYPE
        SYNTAX      Counter32
        MAX-ACCESS  read-only
        STATUS      current
        DESCRIPTION
                ""
        ::= { zxAnEponIfEntry 7 }

    zxAnEponIfOutUcastPkts OBJECT-TYPE
        SYNTAX      Counter32
        MAX-ACCESS  read-only
        STATUS      current
        DESCRIPTION
                ""
        ::= { zxAnEponIfEntry 8 }

    zxAnEponIfOutNUcastPkts OBJECT-TYPE
        SYNTAX      Counter32
        MAX-ACCESS  read-only
        STATUS      deprecated
        DESCRIPTION
                ""
        ::= { zxAnEponIfEntry 9 }

    zxAnEponIfOutDiscards OBJECT-TYPE
        SYNTAX      Counter32
        MAX-ACCESS  read-only
        STATUS      current
        DESCRIPTION
                ""
        ::= { zxAnEponIfEntry 10 }

    zxAnEponIfOutErrors OBJECT-TYPE
        SYNTAX      Counter32
        MAX-ACCESS  read-only
        STATUS      current
        DESCRIPTION
                ""
        ::= { zxAnEponIfEntry 11 }

    zxAnEponIfXTable        OBJECT-TYPE
        SYNTAX      SEQUENCE OF ZxAnEponIfXEntry
        MAX-ACCESS  not-accessible
        STATUS      current
        DESCRIPTION
                ""
        ::= { zxAnEponPmInfor 5 }

    zxAnEponIfXEntry        OBJECT-TYPE
        SYNTAX      ZxAnEponIfXEntry
        MAX-ACCESS  not-accessible
        STATUS      current
        DESCRIPTION
                ""
        AUGMENTS    { zxAnEponIfEntry }
        ::= { zxAnEponIfXTable 1 }

    ZxAnEponIfXEntry ::=
        SEQUENCE {
            zxAnEponIfInMulticastPkts       Counter32,
            zxAnEponIfInBroadcastPkts       Counter32,
            zxAnEponIfOutMulticastPkts      Counter32,
            zxAnEponIfOutBroadcastPkts      Counter32,
            zxAnEponIfHCInOctets            Counter64,
            zxAnEponIfHCInUcastPkts         Counter64,
            zxAnEponIfHCInMulticastPkts     Counter64,
            zxAnEponIfHCInBroadcastPkts     Counter64,
            zxAnEponIfHCOutOctets           Counter64,
            zxAnEponIfHCOutUcastPkts        Counter64,
            zxAnEponIfHCOutMulticastPkts    Counter64,
            zxAnEponIfHCOutBroadcastPkts    Counter64
        }


    zxAnEponIfInMulticastPkts OBJECT-TYPE
        SYNTAX      Counter32
        MAX-ACCESS  read-only
        STATUS      current
        DESCRIPTION
                ""
        ::= { zxAnEponIfXEntry 1 }

    zxAnEponIfInBroadcastPkts OBJECT-TYPE
        SYNTAX      Counter32
        MAX-ACCESS  read-only
        STATUS      current
        DESCRIPTION
                ""
        ::= { zxAnEponIfXEntry 2 }

    zxAnEponIfOutMulticastPkts OBJECT-TYPE
        SYNTAX      Counter32
        MAX-ACCESS  read-only
        STATUS      current
        DESCRIPTION
                ""
        ::= { zxAnEponIfXEntry 3 }

    zxAnEponIfOutBroadcastPkts OBJECT-TYPE
        SYNTAX      Counter32
        MAX-ACCESS  read-only
        STATUS      current
        DESCRIPTION
                ""
        ::= { zxAnEponIfXEntry 4 }

    zxAnEponIfHCInOctets OBJECT-TYPE
        SYNTAX      Counter64
        MAX-ACCESS  read-only
        STATUS      current
        DESCRIPTION
                ""
        ::= { zxAnEponIfXEntry 5 }

    zxAnEponIfHCInUcastPkts OBJECT-TYPE
        SYNTAX      Counter64
        MAX-ACCESS  read-only
        STATUS      current
        DESCRIPTION
                ""
        ::= { zxAnEponIfXEntry 6 }

    zxAnEponIfHCInMulticastPkts OBJECT-TYPE
        SYNTAX      Counter64
        MAX-ACCESS  read-only
        STATUS      current
        DESCRIPTION
                ""
        ::= { zxAnEponIfXEntry 7 }

    zxAnEponIfHCInBroadcastPkts OBJECT-TYPE
        SYNTAX      Counter64
        MAX-ACCESS  read-only
        STATUS      current
        DESCRIPTION
                ""
        ::= { zxAnEponIfXEntry 8 }

    zxAnEponIfHCOutOctets OBJECT-TYPE
        SYNTAX      Counter64
        MAX-ACCESS  read-only
        STATUS      current
        DESCRIPTION
                ""
        ::= { zxAnEponIfXEntry 9 }

    zxAnEponIfHCOutUcastPkts OBJECT-TYPE
        SYNTAX      Counter64
        MAX-ACCESS  read-only
        STATUS      current
        DESCRIPTION
                ""
        ::= { zxAnEponIfXEntry 10 }

    zxAnEponIfHCOutMulticastPkts OBJECT-TYPE
        SYNTAX      Counter64
        MAX-ACCESS  read-only
        STATUS      current
        DESCRIPTION
                ""
        ::= { zxAnEponIfXEntry 11 }

    zxAnEponIfHCOutBroadcastPkts OBJECT-TYPE
        SYNTAX      Counter64
        MAX-ACCESS  read-only
        STATUS      current
        DESCRIPTION
                ""
        ::= { zxAnEponIfXEntry 12 }

    zxAnEponDot3PauseTable OBJECT-TYPE
        SYNTAX      SEQUENCE OF ZxAnEponDot3PauseEntry
        MAX-ACCESS  not-accessible
        STATUS      current
        DESCRIPTION
            "" 
        REFERENCE
            ""
        ::= { zxAnEponPmInfor 6 }

    zxAnEponDot3PauseEntry OBJECT-TYPE
        SYNTAX      ZxAnEponDot3PauseEntry
        MAX-ACCESS  not-accessible
        STATUS      current
        DESCRIPTION
            ""
        INDEX   { ifIndex }
        ::= { zxAnEponDot3PauseTable 1 }

    ZxAnEponDot3PauseEntry ::=
        SEQUENCE {
            zxAnEponDot3InPauseFrames        Counter32,
            zxAnEponDot3OutPauseFrames        Counter32,
            zxAnEponDot3HCInPauseFrames        Counter64,
            zxAnEponDot3HCOutPauseFrames        Counter64
        }

    zxAnEponDot3InPauseFrames OBJECT-TYPE
        SYNTAX      Counter32
        MAX-ACCESS  read-only
        STATUS      current
        DESCRIPTION
                ""
        ::= { zxAnEponDot3PauseEntry 1 }

    zxAnEponDot3OutPauseFrames OBJECT-TYPE
        SYNTAX      Counter32
        MAX-ACCESS  read-only
        STATUS      current
        DESCRIPTION
                ""
        ::= { zxAnEponDot3PauseEntry 2 }

    zxAnEponDot3HCInPauseFrames OBJECT-TYPE
        SYNTAX      Counter64
        MAX-ACCESS  read-only
        STATUS      current
        DESCRIPTION
                ""
        ::= { zxAnEponDot3PauseEntry 3 }

    zxAnEponDot3HCOutPauseFrames OBJECT-TYPE
        SYNTAX      Counter64
        MAX-ACCESS  read-only
        STATUS      current
        DESCRIPTION
                ""
        ::= { zxAnEponDot3PauseEntry 4 }

    zxAnEponDot3HCStatsTable OBJECT-TYPE
        SYNTAX      SEQUENCE OF ZxAnEponDot3HCStatsEntry
        MAX-ACCESS  not-accessible
        STATUS      current
        DESCRIPTION
            "" 
        REFERENCE
            ""
        ::= { zxAnEponPmInfor 7 }

    zxAnEponDot3HCStatsEntry OBJECT-TYPE
        SYNTAX      ZxAnEponDot3HCStatsEntry
        MAX-ACCESS  not-accessible
        STATUS      current
        DESCRIPTION
            ""
        INDEX   { ifIndex }
        ::= { zxAnEponDot3HCStatsTable 1 }

    ZxAnEponDot3HCStatsEntry ::=
        SEQUENCE {
            zxAnEponDot3HCStatsAlignmentErrors         Counter64,
            zxAnEponDot3HCStatsFCSErrors         Counter64,
            zxAnEponDot3HCStatsInternalMacTransmitErrors         Counter64,
            zxAnEponDot3HCStatsFrameTooLongs         Counter64,
            zxAnEponDot3HCStatsInternalMacReceiveErrors         Counter64,
            zxAnEponDot3HCStatsSymbolErrors         Counter64
        }

    zxAnEponDot3HCStatsAlignmentErrors OBJECT-TYPE
        SYNTAX      Counter64
        MAX-ACCESS  read-only
        STATUS      current
        DESCRIPTION
                ""
        ::= { zxAnEponDot3HCStatsEntry 1 }

    zxAnEponDot3HCStatsFCSErrors OBJECT-TYPE
        SYNTAX      Counter64
        MAX-ACCESS  read-only
        STATUS      current
        DESCRIPTION
                ""
        ::= { zxAnEponDot3HCStatsEntry 2 }

    zxAnEponDot3HCStatsInternalMacTransmitErrors OBJECT-TYPE
        SYNTAX      Counter64
        MAX-ACCESS  read-only
        STATUS      current
        DESCRIPTION
                ""
        ::= { zxAnEponDot3HCStatsEntry 3 }

    zxAnEponDot3HCStatsFrameTooLongs OBJECT-TYPE
        SYNTAX      Counter64
        MAX-ACCESS  read-only
        STATUS      current
        DESCRIPTION
                ""
        ::= { zxAnEponDot3HCStatsEntry 4 }

    zxAnEponDot3HCStatsInternalMacReceiveErrors OBJECT-TYPE
        SYNTAX      Counter64
        MAX-ACCESS  read-only
        STATUS      current
        DESCRIPTION
                ""
        ::= { zxAnEponDot3HCStatsEntry 5 }

    zxAnEponDot3HCStatsSymbolErrors OBJECT-TYPE
        SYNTAX      Counter64
        MAX-ACCESS  read-only
        STATUS      current
        DESCRIPTION
                ""
        ::= { zxAnEponDot3HCStatsEntry 6 }

    zxAnEponIfXOltTable        OBJECT-TYPE
        SYNTAX      SEQUENCE OF ZxAnEponIfXOltEntry
        MAX-ACCESS  not-accessible
        STATUS      current
        DESCRIPTION
                ""
        ::= { zxAnEponPmInfor 8 }

    zxAnEponIfXOltEntry        OBJECT-TYPE
        SYNTAX      ZxAnEponIfXOltEntry
        MAX-ACCESS  not-accessible
        STATUS      current
        DESCRIPTION
                ""
        AUGMENTS    { zxAnEponIfEntry }
        ::= { zxAnEponIfXOltTable 1 }

    ZxAnEponIfXOltEntry ::=
        SEQUENCE {
            zxAnEponIfOltInMulticastPkts       Counter32,
            zxAnEponIfOltInBroadcastPkts       Counter32,
            zxAnEponIfOltOutMulticastPkts      Counter32,
            zxAnEponIfOltOutBroadcastPkts      Counter32,
            zxAnEponIfOltHCInOctets            Counter64,
            zxAnEponIfOltHCInUcastPkts         Counter64,
            zxAnEponIfOltHCInMulticastPkts     Counter64,
            zxAnEponIfOltHCInBroadcastPkts     Counter64,
            zxAnEponIfOltHCOutOctets           Counter64,
            zxAnEponIfOltHCOutUcastPkts        Counter64,
            zxAnEponIfOltHCOutMulticastPkts    Counter64,
            zxAnEponIfOltHCOutBroadcastPkts    Counter64
        }


    zxAnEponIfOltInMulticastPkts OBJECT-TYPE
        SYNTAX      Counter32
        MAX-ACCESS  read-only
        STATUS      current
        DESCRIPTION
                ""
        ::= { zxAnEponIfXOltEntry 1 }

    zxAnEponIfOltInBroadcastPkts OBJECT-TYPE
        SYNTAX      Counter32
        MAX-ACCESS  read-only
        STATUS      current
        DESCRIPTION
                ""
        ::= { zxAnEponIfXOltEntry 2 }

    zxAnEponIfOltOutMulticastPkts OBJECT-TYPE
        SYNTAX      Counter32
        MAX-ACCESS  read-only
        STATUS      current
        DESCRIPTION
                ""
        ::= { zxAnEponIfXOltEntry 3 }

    zxAnEponIfOltOutBroadcastPkts OBJECT-TYPE
        SYNTAX      Counter32
        MAX-ACCESS  read-only
        STATUS      current
        DESCRIPTION
                ""
        ::= { zxAnEponIfXOltEntry 4 }

    zxAnEponIfOltHCInOctets OBJECT-TYPE
        SYNTAX      Counter64
        MAX-ACCESS  read-only
        STATUS      current
        DESCRIPTION
                ""
        ::= { zxAnEponIfXOltEntry 5 }

    zxAnEponIfOltHCInUcastPkts OBJECT-TYPE
        SYNTAX      Counter64
        MAX-ACCESS  read-only
        STATUS      current
        DESCRIPTION
                ""
        ::= { zxAnEponIfXOltEntry 6 }

    zxAnEponIfOltHCInMulticastPkts OBJECT-TYPE
        SYNTAX      Counter64
        MAX-ACCESS  read-only
        STATUS      current
        DESCRIPTION
                ""
        ::= { zxAnEponIfXOltEntry 7 }

    zxAnEponIfOltHCInBroadcastPkts OBJECT-TYPE
        SYNTAX      Counter64
        MAX-ACCESS  read-only
        STATUS      current
        DESCRIPTION
                ""
        ::= { zxAnEponIfXOltEntry 8 }

    zxAnEponIfOltHCOutOctets OBJECT-TYPE
        SYNTAX      Counter64
        MAX-ACCESS  read-only
        STATUS      current
        DESCRIPTION
                ""
        ::= { zxAnEponIfXOltEntry 9 }

    zxAnEponIfOltHCOutUcastPkts OBJECT-TYPE
        SYNTAX      Counter64
        MAX-ACCESS  read-only
        STATUS      current
        DESCRIPTION
                ""
        ::= { zxAnEponIfXOltEntry 10 }

    zxAnEponIfOltHCOutMulticastPkts OBJECT-TYPE
        SYNTAX      Counter64
        MAX-ACCESS  read-only
        STATUS      current
        DESCRIPTION
                ""
        ::= { zxAnEponIfXOltEntry 11 }

    zxAnEponIfOltHCOutBroadcastPkts OBJECT-TYPE
        SYNTAX      Counter64
        MAX-ACCESS  read-only
        STATUS      current
        DESCRIPTION
                ""
        ::= { zxAnEponIfXOltEntry 12 }




--zxAnEponPmCurrent

    zxAnEponDot3MpcpStatCurrentTable OBJECT-TYPE 
            SYNTAX         SEQUENCE OF ZxAnEponDot3MpcpStatCurrentEntry 
            MAX-ACCESS     not-accessible 
            STATUS         current 
            DESCRIPTION 
                ""
            ::= { zxAnEponPmCurrent 1 }
            
    zxAnEponDot3MpcpStatCurrentEntry OBJECT-TYPE
            SYNTAX         ZxAnEponDot3MpcpStatCurrentEntry 
            MAX-ACCESS     not-accessible 
            STATUS         current 
            DESCRIPTION 
                ""
            INDEX    { ifIndex } 
            ::= { zxAnEponDot3MpcpStatCurrentTable 1}
            
    ZxAnEponDot3MpcpStatCurrentEntry ::= 
        SEQUENCE {
                zxAnEponDot3MpcpMACCtrlFramesTransmittedCurrent      Counter64,
                zxAnEponDot3MpcpMACCtrlFramesReceivedCurrent         Counter64,
                zxAnEponDot3MpcpDiscoveryWindowsSentCurrent          Counter32,
                zxAnEponDot3MpcpDiscoveryTimeoutCurrent              Counter32, 
                zxAnEponDot3MpcpTxRegRequestCurrent                  Counter64, 
                zxAnEponDot3MpcpRxRegRequestCurrent                  Counter64, 
                zxAnEponDot3MpcpTxRegAckCurrent                      Counter64, 
                zxAnEponDot3MpcpRxRegAckCurrent                      Counter64, 
                zxAnEponDot3MpcpTxReportCurrent                      Counter64, 
                zxAnEponDot3MpcpRxReportCurrent                      Counter64, 
                zxAnEponDot3MpcpTxGateCurrent                        Counter64, 
                zxAnEponDot3MpcpRxGateCurrent                        Counter64, 
                zxAnEponDot3MpcpTxRegisterCurrent                    Counter64, 
                zxAnEponDot3MpcpRxRegisterCurrent                    Counter64
                } 
                
    zxAnEponDot3MpcpMACCtrlFramesTransmittedCurrent OBJECT-TYPE 
        SYNTAX       Counter64
        UNITS        "frames" 
        MAX-ACCESS   read-only 
        STATUS       current 
        DESCRIPTION
            ""
        ::= { zxAnEponDot3MpcpStatCurrentEntry 1 }
        
    zxAnEponDot3MpcpMACCtrlFramesReceivedCurrent OBJECT-TYPE 
        SYNTAX       Counter64
        UNITS        "frames" 
        MAX-ACCESS   read-only 
        STATUS       current 
        DESCRIPTION
            ""
        ::= { zxAnEponDot3MpcpStatCurrentEntry 2 }
        
    zxAnEponDot3MpcpDiscoveryWindowsSentCurrent OBJECT-TYPE 
        SYNTAX       Counter32        
        MAX-ACCESS   read-only 
        STATUS       current 
        DESCRIPTION
            ""
        ::= { zxAnEponDot3MpcpStatCurrentEntry 3 }
        
    zxAnEponDot3MpcpDiscoveryTimeoutCurrent OBJECT-TYPE 
        SYNTAX       Counter32        
        MAX-ACCESS   read-only 
        STATUS       current 
        DESCRIPTION
            ""
        ::= { zxAnEponDot3MpcpStatCurrentEntry 4 }
        
    zxAnEponDot3MpcpTxRegRequestCurrent OBJECT-TYPE 
        SYNTAX       Counter64  
        UNITS        "frames"      
        MAX-ACCESS   read-only 
        STATUS       current 
        DESCRIPTION
            ""
        ::= { zxAnEponDot3MpcpStatCurrentEntry 5 }
        
    zxAnEponDot3MpcpRxRegRequestCurrent OBJECT-TYPE 
        SYNTAX       Counter64
        UNITS        "frames"        
        MAX-ACCESS   read-only 
        STATUS       current 
        DESCRIPTION
            ""
        ::= { zxAnEponDot3MpcpStatCurrentEntry 6 }
        
    zxAnEponDot3MpcpTxRegAckCurrent OBJECT-TYPE 
        SYNTAX       Counter64
        UNITS        "frames"        
        MAX-ACCESS   read-only 
        STATUS       current 
        DESCRIPTION
            ""
        ::= { zxAnEponDot3MpcpStatCurrentEntry 7 }
        
    zxAnEponDot3MpcpRxRegAckCurrent OBJECT-TYPE 
        SYNTAX       Counter64
        UNITS        "frames"        
        MAX-ACCESS   read-only 
        STATUS       current 
        DESCRIPTION
            ""
        ::= { zxAnEponDot3MpcpStatCurrentEntry 8 }
        
    zxAnEponDot3MpcpTxReportCurrent OBJECT-TYPE 
        SYNTAX       Counter64
        UNITS        "frames"        
        MAX-ACCESS   read-only 
        STATUS       current 
        DESCRIPTION
            ""
        ::= { zxAnEponDot3MpcpStatCurrentEntry 9 }
        
    zxAnEponDot3MpcpRxReportCurrent OBJECT-TYPE 
        SYNTAX       Counter64
        UNITS        "frames"        
        MAX-ACCESS   read-only 
        STATUS       current 
        DESCRIPTION
            ""
        ::= { zxAnEponDot3MpcpStatCurrentEntry 10 }
        
    zxAnEponDot3MpcpTxGateCurrent OBJECT-TYPE 
        SYNTAX       Counter64
        UNITS        "frames"        
        MAX-ACCESS   read-only 
        STATUS       current 
        DESCRIPTION
            ""
        ::= { zxAnEponDot3MpcpStatCurrentEntry 11 }
        
    zxAnEponDot3MpcpRxGateCurrent OBJECT-TYPE 
        SYNTAX       Counter64
        UNITS        "frames"        
        MAX-ACCESS   read-only 
        STATUS       current 
        DESCRIPTION
            ""
        ::= { zxAnEponDot3MpcpStatCurrentEntry 12 }
        
    zxAnEponDot3MpcpTxRegisterCurrent OBJECT-TYPE 
        SYNTAX       Counter64
        UNITS        "frames"        
        MAX-ACCESS   read-only 
        STATUS       current 
        DESCRIPTION
            ""
        ::= { zxAnEponDot3MpcpStatCurrentEntry 13 }
        
    zxAnEponDot3MpcpRxRegisterCurrent OBJECT-TYPE 
        SYNTAX       Counter64
        UNITS        "frames"        
        MAX-ACCESS   read-only 
        STATUS       current 
        DESCRIPTION
            ""
        ::= { zxAnEponDot3MpcpStatCurrentEntry 14 }

    zxAnEponDot3OmpEmulationStatCurrentTable OBJECT-TYPE 
            SYNTAX         SEQUENCE OF ZxAnEponDot3OmpEmulationStatCurrentEntry 
            MAX-ACCESS     not-accessible 
            STATUS         current 
            DESCRIPTION 
                ""
            ::= { zxAnEponPmCurrent 2 }
              
    zxAnEponDot3OmpEmulationStatCurrentEntry OBJECT-TYPE
            SYNTAX         ZxAnEponDot3OmpEmulationStatCurrentEntry 
            MAX-ACCESS     not-accessible 
            STATUS         current 
            DESCRIPTION 
                ""
            INDEX    { ifIndex } 
            ::= { zxAnEponDot3OmpEmulationStatCurrentTable 1}
            
    ZxAnEponDot3OmpEmulationStatCurrentEntry ::= 
        SEQUENCE {                
                zxAnEponDot3OmpEmulationSLDErrorsCurrent                      Counter64, 
                zxAnEponDot3OmpEmulationCRC8ErrorsCurrent                     Counter64, 
                zxAnEponDot3OmpEmulationBadLLIDCurrent                        Counter64, 
                zxAnEponDot3OmpEmulationGoodLLIDCurrent                       Counter64, 
                zxAnEponDot3OmpEmulationOnuPonCastLLIDCurrent                 Counter64,
                zxAnEponDot3OmpEmulationOltPonCastLLIDCurrent                 Counter64, 
                zxAnEponDot3OmpEmulationBroadcastBitNotOnuLlidCurrent         Counter64, 
                zxAnEponDot3OmpEmulationOnuLLIDNotBroadcastCurrent            Counter64, 
                zxAnEponDot3OmpEmulationBroadcastBitPlusOnuLlidCurrent        Counter64, 
                zxAnEponDot3OmpEmulationNotBroadcastBitNotOnuLlidCurrent      Counter64              
                } 
                
    zxAnEponDot3OmpEmulationSLDErrorsCurrent OBJECT-TYPE 
        SYNTAX       Counter64 
        UNITS        "frames"                     
        MAX-ACCESS   read-only 
        STATUS       current 
        DESCRIPTION
            ""
        ::= { zxAnEponDot3OmpEmulationStatCurrentEntry 1 }
        
    zxAnEponDot3OmpEmulationCRC8ErrorsCurrent OBJECT-TYPE 
        SYNTAX       Counter64 
        UNITS        "frames"                     
        MAX-ACCESS   read-only 
        STATUS       current 
        DESCRIPTION
            ""
        ::= { zxAnEponDot3OmpEmulationStatCurrentEntry 2 }
        
    zxAnEponDot3OmpEmulationBadLLIDCurrent OBJECT-TYPE 
        SYNTAX       Counter64 
        UNITS        "frames"                     
        MAX-ACCESS   read-only 
        STATUS       current 
        DESCRIPTION
            ""
        ::= { zxAnEponDot3OmpEmulationStatCurrentEntry 3 }
        
    zxAnEponDot3OmpEmulationGoodLLIDCurrent OBJECT-TYPE 
        SYNTAX       Counter64 
        UNITS        "frames"                     
        MAX-ACCESS   read-only 
        STATUS       current 
        DESCRIPTION
            ""
        ::= { zxAnEponDot3OmpEmulationStatCurrentEntry 4 }
        
    zxAnEponDot3OmpEmulationOnuPonCastLLIDCurrent OBJECT-TYPE 
        SYNTAX       Counter64 
        UNITS        "frames"                     
        MAX-ACCESS   read-only 
        STATUS       current 
        DESCRIPTION
            ""
        ::= { zxAnEponDot3OmpEmulationStatCurrentEntry 5 }
        
    zxAnEponDot3OmpEmulationOltPonCastLLIDCurrent OBJECT-TYPE 
        SYNTAX       Counter64 
        UNITS        "frames"                     
        MAX-ACCESS   read-only 
        STATUS       current 
        DESCRIPTION
            ""
        ::= { zxAnEponDot3OmpEmulationStatCurrentEntry 6 }
        
    zxAnEponDot3OmpEmulationBroadcastBitNotOnuLlidCurrent OBJECT-TYPE 
        SYNTAX       Counter64 
        UNITS        "frames"                     
        MAX-ACCESS   read-only 
        STATUS       current 
        DESCRIPTION
            ""
        ::= { zxAnEponDot3OmpEmulationStatCurrentEntry 7 }
        
    zxAnEponDot3OmpEmulationOnuLLIDNotBroadcastCurrent OBJECT-TYPE 
        SYNTAX       Counter64 
        UNITS        "frames"                     
        MAX-ACCESS   read-only 
        STATUS       current 
        DESCRIPTION
            ""
        ::= { zxAnEponDot3OmpEmulationStatCurrentEntry 8 }
        
    zxAnEponDot3OmpEmulationBroadcastBitPlusOnuLlidCurrent OBJECT-TYPE 
        SYNTAX       Counter64 
        UNITS        "frames"                     
        MAX-ACCESS   read-only 
        STATUS       current 
        DESCRIPTION
            ""
        ::= { zxAnEponDot3OmpEmulationStatCurrentEntry 9 }
        
    zxAnEponDot3OmpEmulationNotBroadcastBitNotOnuLlidCurrent OBJECT-TYPE 
        SYNTAX       Counter64 
        UNITS        "frames"                     
        MAX-ACCESS   read-only 
        STATUS       current 
        DESCRIPTION
            ""
        ::= { zxAnEponDot3OmpEmulationStatCurrentEntry 10 }


    zxAnEponDot3EponFecCurrentTable OBJECT-TYPE 
            SYNTAX         SEQUENCE OF ZxAnEponDot3EponFecCurrentEntry 
            MAX-ACCESS     not-accessible 
            STATUS         current 
            DESCRIPTION 
                ""
            ::= { zxAnEponPmCurrent 3 }
              
    zxAnEponDot3EponFecCurrentEntry OBJECT-TYPE
            SYNTAX         ZxAnEponDot3EponFecCurrentEntry 
            MAX-ACCESS     not-accessible 
            STATUS         current 
            DESCRIPTION 
                ""
            INDEX    { ifIndex } 
            ::= { zxAnEponDot3EponFecCurrentTable 1}
            
    ZxAnEponDot3EponFecCurrentEntry ::= 
        SEQUENCE {                
                zxAnEponDot3EponFecPCSCodingViolationCurrent               Counter64, 
                zxAnEponDot3EponFecAbilityCurrent                          INTEGER, 
                zxAnEponDot3EponFecModeCurrent                             INTEGER, 
                zxAnEponDot3EponFecCorrectedBlocksCurrent                  Counter64, 
                zxAnEponDot3EponFecUncorrectableBlocksCurrent              Counter64, 
                zxAnEponDot3EponFecBufferHeadCodingViolationCurrent        Counter64              
                } 
                
    zxAnEponDot3EponFecPCSCodingViolationCurrent OBJECT-TYPE 
        SYNTAX       Counter64
        UNITS        "octets"                    
        MAX-ACCESS   read-only 
        STATUS       current 
        DESCRIPTION
            ""
        ::= { zxAnEponDot3EponFecCurrentEntry 1 }
        
    zxAnEponDot3EponFecAbilityCurrent OBJECT-TYPE 
        SYNTAX       INTEGER{ 
                     unknown (1), 
                     unsupported (2), 
                     supported (3)
                     }                         
        MAX-ACCESS   read-only 
        STATUS       current 
        DESCRIPTION
            ""
        ::= { zxAnEponDot3EponFecCurrentEntry 2 }
        
    zxAnEponDot3EponFecModeCurrent OBJECT-TYPE 
        SYNTAX       INTEGER{ 
                     unknown (1), 
                     disabled (2), 
                     enabled (3)
                     }                         
        MAX-ACCESS   read-write 
        STATUS       current 
        DESCRIPTION
            ""
        DEFVAL { unknown }
        ::= { zxAnEponDot3EponFecCurrentEntry 3 }
        
    zxAnEponDot3EponFecCorrectedBlocksCurrent OBJECT-TYPE 
        SYNTAX       Counter64                   
        MAX-ACCESS   read-only 
        STATUS       current 
        DESCRIPTION
            ""
        ::= { zxAnEponDot3EponFecCurrentEntry 4 }
        
    zxAnEponDot3EponFecUncorrectableBlocksCurrent OBJECT-TYPE 
        SYNTAX       Counter64                   
        MAX-ACCESS   read-only 
        STATUS       current 
        DESCRIPTION
            ""
        ::= { zxAnEponDot3EponFecCurrentEntry 5 }  
        
    zxAnEponDot3EponFecBufferHeadCodingViolationCurrent OBJECT-TYPE 
        SYNTAX       Counter64  
        UNITS        "octets"                 
        MAX-ACCESS   read-only 
        STATUS       current 
        DESCRIPTION
            ""
        ::= { zxAnEponDot3EponFecCurrentEntry 6 }  

    zxAnEponDot3ExtPkgQueueCurrentTable OBJECT-TYPE 
            SYNTAX         SEQUENCE OF ZxAnEponDot3ExtPkgQueueCurrentEntry
            MAX-ACCESS     not-accessible 
            STATUS         current 
            DESCRIPTION 
                ""
            ::= { zxAnEponPmCurrent 4 }
              
    zxAnEponDot3ExtPkgQueueCurrentEntry OBJECT-TYPE
            SYNTAX         ZxAnEponDot3ExtPkgQueueCurrentEntry 
            MAX-ACCESS     not-accessible 
            STATUS         current 
            DESCRIPTION 
                ""
            INDEX { ifIndex, zxAnEponDot3QueueIndexCurrent }
            ::= { zxAnEponDot3ExtPkgQueueCurrentTable 1}
            
    ZxAnEponDot3ExtPkgQueueCurrentEntry ::= 
        SEQUENCE {                  
                zxAnEponDot3QueueIndexCurrent                                  Unsigned32, 
                zxAnEponDot3ExtPkgObjectReportNumThresholdCurrent              Unsigned32, 
                zxAnEponDot3ExtPkgObjectReportMaximumNumThresholdCurrent       Unsigned32, 
                zxAnEponDot3ExtPkgStatTxFramesQueueCurrent                     Counter64, 
                zxAnEponDot3ExtPkgStatRxFramesQueueCurrent                     Counter64, 
                zxAnEponDot3ExtPkgStatDroppedFramesQueueCurrent                Counter64       
                } 
                
    zxAnEponDot3QueueIndexCurrent OBJECT-TYPE 
        SYNTAX       Unsigned32(0..7)                          
        MAX-ACCESS   not-accessible
        STATUS       current 
        DESCRIPTION
            ""
        ::= { zxAnEponDot3ExtPkgQueueCurrentEntry 1 }
        
    zxAnEponDot3ExtPkgObjectReportNumThresholdCurrent OBJECT-TYPE 
        SYNTAX       Unsigned32(0..7)                          
        MAX-ACCESS   read-write
        STATUS       current 
        DESCRIPTION
            ""
        ::= { zxAnEponDot3ExtPkgQueueCurrentEntry 2 }
        
    zxAnEponDot3ExtPkgObjectReportMaximumNumThresholdCurrent OBJECT-TYPE 
        SYNTAX       Unsigned32(0..7)                          
        MAX-ACCESS   read-only
        STATUS       current 
        DESCRIPTION
            ""
        ::= { zxAnEponDot3ExtPkgQueueCurrentEntry 3 }
        
    zxAnEponDot3ExtPkgStatTxFramesQueueCurrent OBJECT-TYPE 
        SYNTAX       Counter64  
        UNITS        "frames"                        
        MAX-ACCESS   read-only
        STATUS       current 
        DESCRIPTION
            ""
        ::= { zxAnEponDot3ExtPkgQueueCurrentEntry 4 }
        
    zxAnEponDot3ExtPkgStatRxFramesQueueCurrent OBJECT-TYPE 
        SYNTAX       Counter64  
        UNITS        "frames"                        
        MAX-ACCESS   read-only
        STATUS       current 
        DESCRIPTION
            ""
        ::= { zxAnEponDot3ExtPkgQueueCurrentEntry 5 }
        
    zxAnEponDot3ExtPkgStatDroppedFramesQueueCurrent OBJECT-TYPE 
        SYNTAX       Counter64  
        UNITS        "frames"                        
        MAX-ACCESS   read-only
        STATUS       current 
        DESCRIPTION
            ""
        ::= { zxAnEponDot3ExtPkgQueueCurrentEntry 6 }

     zxAnEponDot3OamStatsCurrentTable OBJECT-TYPE 
            SYNTAX         SEQUENCE OF ZxAnEponDot3OamStatsCurrentEntry 
            MAX-ACCESS     not-accessible 
            STATUS         current 
            DESCRIPTION 
                ""
            ::= { zxAnEponPmCurrent 5 }
              
    zxAnEponDot3OamStatsCurrentEntry OBJECT-TYPE
            SYNTAX         ZxAnEponDot3OamStatsCurrentEntry 
            MAX-ACCESS     not-accessible 
            STATUS         current 
            DESCRIPTION 
                ""
            INDEX    { ifIndex } 
            ::= { zxAnEponDot3OamStatsCurrentTable 1}
            
    ZxAnEponDot3OamStatsCurrentEntry ::= 
        SEQUENCE {   
                zxAnEponDot3OamInformationTxCurrent                    Counter32, 
                zxAnEponDot3OamInformationRxCurrent                    Counter32, 
                zxAnEponDot3OamUniqueEventNotificationTxCurrent        Counter32, 
                zxAnEponDot3OamUniqueEventNotificationRxCurrent        Counter32, 
                zxAnEponDot3OamDuplicateEventNotificationTxCurrent     Counter32, 
                zxAnEponDot3OamDuplicateEventNotificationRxCurrent     Counter32, 
                zxAnEponDot3OamLoopbackControlTxCurrent                Counter32, 
                zxAnEponDot3OamLoopbackControlRxCurrent                Counter32,   
                zxAnEponDot3OamVariableRequestTxCurrent                Counter32, 
                zxAnEponDot3OamVariableRequestRxCurrent                Counter32, 
                zxAnEponDot3OamVariableResponseTxCurrent               Counter32, 
                zxAnEponDot3OamVariableResponseRxCurrent               Counter32, 
                zxAnEponDot3OamOrgSpecificTxCurrent                    Counter32, 
                zxAnEponDot3OamOrgSpecificRxCurrent                    Counter32, 
                zxAnEponDot3OamUnsupportedCodesTxCurrent               Counter32, 
                zxAnEponDot3OamUnsupportedCodesRxCurrent               Counter32, 
                zxAnEponDot3OamFramesLostDueToOamCurrent               Counter32    
                } 
                
    zxAnEponDot3OamInformationTxCurrent OBJECT-TYPE 
        SYNTAX       Counter32  
        UNITS        "frames"                        
        MAX-ACCESS   read-only
        STATUS       current 
        DESCRIPTION
            ""
        ::= { zxAnEponDot3OamStatsCurrentEntry 1 }
        
    zxAnEponDot3OamInformationRxCurrent OBJECT-TYPE 
        SYNTAX       Counter32  
        UNITS        "frames"                        
        MAX-ACCESS   read-only
        STATUS       current 
        DESCRIPTION
            ""
        ::= { zxAnEponDot3OamStatsCurrentEntry 2 }
        
    zxAnEponDot3OamUniqueEventNotificationTxCurrent OBJECT-TYPE 
        SYNTAX       Counter32  
        UNITS        "frames"                        
        MAX-ACCESS   read-only
        STATUS       current 
        DESCRIPTION
            ""
        ::= { zxAnEponDot3OamStatsCurrentEntry 3 }
        
    zxAnEponDot3OamUniqueEventNotificationRxCurrent OBJECT-TYPE 
        SYNTAX       Counter32  
        UNITS        "frames"                        
        MAX-ACCESS   read-only
        STATUS       current 
        DESCRIPTION
            ""
        ::= { zxAnEponDot3OamStatsCurrentEntry 4 }
        
    zxAnEponDot3OamDuplicateEventNotificationTxCurrent OBJECT-TYPE 
        SYNTAX       Counter32  
        UNITS        "frames"                        
        MAX-ACCESS   read-only
        STATUS       current 
        DESCRIPTION
            ""
        ::= { zxAnEponDot3OamStatsCurrentEntry 5 }
        
    zxAnEponDot3OamDuplicateEventNotificationRxCurrent OBJECT-TYPE 
        SYNTAX       Counter32  
        UNITS        "frames"                        
        MAX-ACCESS   read-only
        STATUS       current 
        DESCRIPTION
            ""
        ::= { zxAnEponDot3OamStatsCurrentEntry 6 }
        
    zxAnEponDot3OamLoopbackControlTxCurrent OBJECT-TYPE 
        SYNTAX       Counter32  
        UNITS        "frames"                        
        MAX-ACCESS   read-only
        STATUS       current 
        DESCRIPTION
            ""
        ::= { zxAnEponDot3OamStatsCurrentEntry 7 }
        
    zxAnEponDot3OamLoopbackControlRxCurrent OBJECT-TYPE 
        SYNTAX       Counter32  
        UNITS        "frames"                        
        MAX-ACCESS   read-only
        STATUS       current 
        DESCRIPTION
            ""
        ::= { zxAnEponDot3OamStatsCurrentEntry 8 }
        
    zxAnEponDot3OamVariableRequestTxCurrent OBJECT-TYPE 
        SYNTAX       Counter32  
        UNITS        "frames"                        
        MAX-ACCESS   read-only
        STATUS       current 
        DESCRIPTION
            ""
        ::= { zxAnEponDot3OamStatsCurrentEntry 9 }
        
    zxAnEponDot3OamVariableRequestRxCurrent OBJECT-TYPE 
        SYNTAX       Counter32  
        UNITS        "frames"                        
        MAX-ACCESS   read-only
        STATUS       current 
        DESCRIPTION
            ""
        ::= { zxAnEponDot3OamStatsCurrentEntry 10 }
        
    zxAnEponDot3OamVariableResponseTxCurrent OBJECT-TYPE 
        SYNTAX       Counter32  
        UNITS        "frames"                        
        MAX-ACCESS   read-only
        STATUS       current 
        DESCRIPTION
            ""
        ::= { zxAnEponDot3OamStatsCurrentEntry 11 }
        
    zxAnEponDot3OamVariableResponseRxCurrent OBJECT-TYPE 
        SYNTAX       Counter32  
        UNITS        "frames"                        
        MAX-ACCESS   read-only
        STATUS       current 
        DESCRIPTION
            ""
        ::= { zxAnEponDot3OamStatsCurrentEntry 12 }
        
    zxAnEponDot3OamOrgSpecificTxCurrent OBJECT-TYPE 
        SYNTAX       Counter32  
        UNITS        "frames"                        
        MAX-ACCESS   read-only
        STATUS       current 
        DESCRIPTION
            ""
        ::= { zxAnEponDot3OamStatsCurrentEntry 13 }
        
    zxAnEponDot3OamOrgSpecificRxCurrent OBJECT-TYPE 
        SYNTAX       Counter32  
        UNITS        "frames"                        
        MAX-ACCESS   read-only
        STATUS       current 
        DESCRIPTION
            ""
        ::= { zxAnEponDot3OamStatsCurrentEntry 14 }
        
    zxAnEponDot3OamUnsupportedCodesTxCurrent OBJECT-TYPE 
        SYNTAX       Counter32  
        UNITS        "frames"                        
        MAX-ACCESS   read-only
        STATUS       current 
        DESCRIPTION
            ""
        ::= { zxAnEponDot3OamStatsCurrentEntry 15 }
        
    zxAnEponDot3OamUnsupportedCodesRxCurrent OBJECT-TYPE 
        SYNTAX       Counter32  
        UNITS        "frames"                        
        MAX-ACCESS   read-only
        STATUS       current 
        DESCRIPTION
            ""
        ::= { zxAnEponDot3OamStatsCurrentEntry 16 }
        
    zxAnEponDot3OamFramesLostDueToOamCurrent OBJECT-TYPE 
        SYNTAX       Counter32  
        UNITS        "frames"                        
        MAX-ACCESS   read-only
        STATUS       current 
        DESCRIPTION
            ""
        ::= { zxAnEponDot3OamStatsCurrentEntry 17 }


    zxAnEponOltVirtualIfBERStatisticCurrentTable OBJECT-TYPE
        SYNTAX      SEQUENCE OF ZxAnEponOltVirtualIfBERStatisticCurrentEntry
        MAX-ACCESS  not-accessible
        STATUS      current
        DESCRIPTION
            "" 
        REFERENCE
            ""
        ::= { zxAnEponPmCurrent 6 }

    zxAnEponOltVirtualIfBERStatisticCurrentEntry OBJECT-TYPE
        SYNTAX      ZxAnEponOltVirtualIfBERStatisticCurrentEntry
        MAX-ACCESS  not-accessible
        STATUS      current
        DESCRIPTION
            ""
        INDEX   { ifIndex }
        ::= { zxAnEponOltVirtualIfBERStatisticCurrentTable 1 }

    ZxAnEponOltVirtualIfBERStatisticCurrentEntry ::=
        SEQUENCE {
            zxAnEponOltVirtualIfBERStatisticOnuBERCurrent     Counter32,
            zxAnEponOltVirtualIfBERStatisticOnuFERCurrent     Counter32
        }

   zxAnEponOltVirtualIfBERStatisticOnuBERCurrent OBJECT-TYPE
        SYNTAX      Counter32
        MAX-ACCESS  read-only
        STATUS      current
        DESCRIPTION
            ""
        ::= { zxAnEponOltVirtualIfBERStatisticCurrentEntry 1}

   zxAnEponOltVirtualIfBERStatisticOnuFERCurrent OBJECT-TYPE
        SYNTAX      Counter32
        MAX-ACCESS  read-only
        STATUS      current
        DESCRIPTION
            ""
        ::= { zxAnEponOltVirtualIfBERStatisticCurrentEntry 2}

    zxAnEponOltPhyPortStatisticCurrentTable OBJECT-TYPE
        SYNTAX      SEQUENCE OF ZxAnEponOltPhyPortStatisticCurrentEntry
        MAX-ACCESS  not-accessible
        STATUS      current
        DESCRIPTION
            "" 
        REFERENCE
            ""
        ::= { zxAnEponPmCurrent 7 }

    zxAnEponOltPhyPortStatisticCurrentEntry OBJECT-TYPE
        SYNTAX      ZxAnEponOltPhyPortStatisticCurrentEntry
        MAX-ACCESS  not-accessible
        STATUS      current
        DESCRIPTION
            ""
        INDEX   { ifIndex }
        ::= { zxAnEponOltPhyPortStatisticCurrentTable 1 }

    ZxAnEponOltPhyPortStatisticCurrentEntry ::=
        SEQUENCE {
            zxAnEponOltPhyPortStatisticOltPonAverageBERCurrent      Counter32,
            zxAnEponOltPhyPortStatisticOltSysAverageBERCurrent      Counter32
        }

   zxAnEponOltPhyPortStatisticOltPonAverageBERCurrent OBJECT-TYPE
        SYNTAX      Counter32
        MAX-ACCESS  read-only
        STATUS      current
        DESCRIPTION
            ""
        ::= { zxAnEponOltPhyPortStatisticCurrentEntry 1}

   zxAnEponOltPhyPortStatisticOltSysAverageBERCurrent OBJECT-TYPE
        SYNTAX      Counter32
        MAX-ACCESS  read-only
        STATUS      current
        DESCRIPTION
            ""
        ::= { zxAnEponOltPhyPortStatisticCurrentEntry 2}

    zxAnEponEtherStatsCurrentTable OBJECT-TYPE
        SYNTAX      SEQUENCE OF ZxAnEponEtherStatsCurrentEntry
        MAX-ACCESS  not-accessible
        STATUS      current
        DESCRIPTION
            "" 
        REFERENCE
            ""
        ::= { zxAnEponPmCurrent 8 }

    zxAnEponEtherStatsCurrentEntry OBJECT-TYPE
        SYNTAX      ZxAnEponEtherStatsCurrentEntry
        MAX-ACCESS  not-accessible
        STATUS      current
        DESCRIPTION
            ""
        INDEX   { ifIndex }
        ::= { zxAnEponEtherStatsCurrentTable 1 }

    ZxAnEponEtherStatsCurrentEntry ::=
        SEQUENCE {
            zxAnEponEtherStatsDropEventsCurrent      Counter32,
            zxAnEponEtherStatsOctetsCurrent      Counter32,
            zxAnEponEtherStatsPktsCurrent      Counter32,
            zxAnEponEtherStatsBroadcastPktsCurrent      Counter32,
            zxAnEponEtherStatsMulticastPktsCurrent      Counter32,
            zxAnEponEtherStatsCRCAlignErrorsCurrent      Counter32,
            zxAnEponEtherStatsUndersizePktsCurrent      Counter32,
            zxAnEponEtherStatsOversizePktsCurrent      Counter32,
            zxAnEponEtherStatsFragmentsCurrent      Counter32,
            zxAnEponEtherStatsJabbersCurrent      Counter32,
            zxAnEponEtherStatsCollisionsCurrent      Counter32,
            zxAnEponEtherStatsPkts64OctetsCurrent      Counter32,
            zxAnEponEtherStatsPkts65to127OctetsCurrent      Counter32,
            zxAnEponEtherStatsPkts128to255OctetsCurrent      Counter32,
            zxAnEponEtherStatsPkts256to511OctetsCurrent      Counter32,
            zxAnEponEtherStatsPkts512to1023OctetsCurrent       Counter32,
            zxAnEponEtherStatsPkts1024to1518OctetsCurrent       Counter32,
            zxAnEponEtherStatsOwnerCurrent       OwnerString,
            zxAnEponEtherStatsStatusCurrent       EntryStatus
        }

   zxAnEponEtherStatsDropEventsCurrent OBJECT-TYPE
        SYNTAX      Counter32
        MAX-ACCESS  read-only
        STATUS      current
        DESCRIPTION
            ""
        ::= { zxAnEponEtherStatsCurrentEntry 1}

   zxAnEponEtherStatsOctetsCurrent OBJECT-TYPE
        SYNTAX      Counter32
        MAX-ACCESS  read-only
        STATUS      current
        DESCRIPTION
            ""
        ::= { zxAnEponEtherStatsCurrentEntry 2}

   zxAnEponEtherStatsPktsCurrent OBJECT-TYPE
        SYNTAX      Counter32
        MAX-ACCESS  read-only
        STATUS      current
        DESCRIPTION
            ""
        ::= { zxAnEponEtherStatsCurrentEntry 3}

   zxAnEponEtherStatsBroadcastPktsCurrent OBJECT-TYPE
        SYNTAX      Counter32
        MAX-ACCESS  read-only
        STATUS      current
        DESCRIPTION
            ""
        ::= { zxAnEponEtherStatsCurrentEntry 4}

   zxAnEponEtherStatsMulticastPktsCurrent OBJECT-TYPE
        SYNTAX      Counter32
        MAX-ACCESS  read-only
        STATUS      current
        DESCRIPTION
            ""
        ::= { zxAnEponEtherStatsCurrentEntry 5}

   zxAnEponEtherStatsCRCAlignErrorsCurrent OBJECT-TYPE
        SYNTAX      Counter32
        MAX-ACCESS  read-only
        STATUS      current
        DESCRIPTION
            ""
        ::= { zxAnEponEtherStatsCurrentEntry 6}

   zxAnEponEtherStatsUndersizePktsCurrent OBJECT-TYPE
        SYNTAX      Counter32
        MAX-ACCESS  read-only
        STATUS      current
        DESCRIPTION
            ""
        ::= { zxAnEponEtherStatsCurrentEntry 7}

   zxAnEponEtherStatsOversizePktsCurrent OBJECT-TYPE
        SYNTAX      Counter32
        MAX-ACCESS  read-only
        STATUS      current
        DESCRIPTION
            ""
        ::= { zxAnEponEtherStatsCurrentEntry 8}

   zxAnEponEtherStatsFragmentsCurrent OBJECT-TYPE
        SYNTAX      Counter32
        MAX-ACCESS  read-only
        STATUS      current
        DESCRIPTION
            ""
        ::= { zxAnEponEtherStatsCurrentEntry 9}

   zxAnEponEtherStatsJabbersCurrent OBJECT-TYPE
        SYNTAX      Counter32
        MAX-ACCESS  read-only
        STATUS      current
        DESCRIPTION
            ""
        ::= { zxAnEponEtherStatsCurrentEntry 10}

   zxAnEponEtherStatsCollisionsCurrent OBJECT-TYPE
        SYNTAX      Counter32
        MAX-ACCESS  read-only
        STATUS      current
        DESCRIPTION
            ""
        ::= { zxAnEponEtherStatsCurrentEntry 11}

   zxAnEponEtherStatsPkts64OctetsCurrent OBJECT-TYPE
        SYNTAX      Counter32
        MAX-ACCESS  read-only
        STATUS      current
        DESCRIPTION
            ""
        ::= { zxAnEponEtherStatsCurrentEntry 12}

   zxAnEponEtherStatsPkts65to127OctetsCurrent OBJECT-TYPE
        SYNTAX      Counter32
        MAX-ACCESS  read-only
        STATUS      current
        DESCRIPTION
            ""
        ::= { zxAnEponEtherStatsCurrentEntry 13}

   zxAnEponEtherStatsPkts128to255OctetsCurrent OBJECT-TYPE
        SYNTAX      Counter32
        MAX-ACCESS  read-only
        STATUS      current
        DESCRIPTION
            ""
        ::= { zxAnEponEtherStatsCurrentEntry 14}

   zxAnEponEtherStatsPkts256to511OctetsCurrent OBJECT-TYPE
        SYNTAX      Counter32
        MAX-ACCESS  read-only
        STATUS      current
        DESCRIPTION
            ""
        ::= { zxAnEponEtherStatsCurrentEntry 15}

   zxAnEponEtherStatsPkts512to1023OctetsCurrent OBJECT-TYPE
        SYNTAX      Counter32
        MAX-ACCESS  read-only
        STATUS      current
        DESCRIPTION
            ""
        ::= { zxAnEponEtherStatsCurrentEntry 16}

   zxAnEponEtherStatsPkts1024to1518OctetsCurrent OBJECT-TYPE
        SYNTAX      Counter32
        MAX-ACCESS  read-only
        STATUS      current
        DESCRIPTION
            ""
        ::= { zxAnEponEtherStatsCurrentEntry 17}

   zxAnEponEtherStatsOwnerCurrent OBJECT-TYPE
        SYNTAX      OwnerString
        MAX-ACCESS  read-create
        STATUS      current
        DESCRIPTION
            ""
        ::= { zxAnEponEtherStatsCurrentEntry 18}

   zxAnEponEtherStatsStatusCurrent OBJECT-TYPE
        SYNTAX      EntryStatus
        MAX-ACCESS  read-create
        STATUS      current
        DESCRIPTION
            ""
        ::= { zxAnEponEtherStatsCurrentEntry 19}

    zxAnEponIfCurrentTable OBJECT-TYPE
        SYNTAX      SEQUENCE OF ZxAnEponIfCurrentEntry
        MAX-ACCESS  not-accessible
        STATUS      current
        DESCRIPTION
            "" 
        REFERENCE
            ""
        ::= { zxAnEponPmCurrent 9 }

    zxAnEponIfCurrentEntry OBJECT-TYPE
        SYNTAX      ZxAnEponIfCurrentEntry
        MAX-ACCESS  not-accessible
        STATUS      current
        DESCRIPTION
            ""
        INDEX   { ifIndex }
        ::= { zxAnEponIfCurrentTable 1 }

    ZxAnEponIfCurrentEntry ::=
        SEQUENCE {
            zxAnEponIfInOctetsCurrent       Counter32,
            zxAnEponIfInUcastPktsCurrent       Counter32,
            zxAnEponIfInNUcastPktsCurrent       Counter32,
            zxAnEponIfInDiscardsCurrent       Counter32,
            zxAnEponIfInErrorsCurrent       Counter32,
            zxAnEponIfInUnknownProtosCurrent       Counter32,
            zxAnEponIfOutOctetsCurrent       Counter32,
            zxAnEponIfOutUcastPktsCurrent        Counter32,
            zxAnEponIfOutNUcastPktsCurrent        Counter32,
            zxAnEponIfOutDiscardsCurrent        Counter32,
            zxAnEponIfOutErrorsCurrent        Counter32
        }

    zxAnEponIfInOctetsCurrent OBJECT-TYPE
        SYNTAX      Counter32
        MAX-ACCESS  read-only
        STATUS      current
        DESCRIPTION
                ""
        ::= { zxAnEponIfCurrentEntry 1 }

    zxAnEponIfInUcastPktsCurrent OBJECT-TYPE
        SYNTAX      Counter32
        MAX-ACCESS  read-only
        STATUS      current
        DESCRIPTION
                ""
        ::= { zxAnEponIfCurrentEntry 2 }

    zxAnEponIfInNUcastPktsCurrent OBJECT-TYPE
        SYNTAX  Counter32
        MAX-ACCESS  read-only
        STATUS      deprecated
        DESCRIPTION
                ""
        ::= { zxAnEponIfCurrentEntry 3 }

    zxAnEponIfInDiscardsCurrent OBJECT-TYPE
        SYNTAX      Counter32
        MAX-ACCESS  read-only
        STATUS      current
        DESCRIPTION
                ""
        ::= { zxAnEponIfCurrentEntry 4 }

    zxAnEponIfInErrorsCurrent OBJECT-TYPE
        SYNTAX      Counter32
        MAX-ACCESS  read-only
        STATUS      current
        DESCRIPTION
                ""
        ::= { zxAnEponIfCurrentEntry 5 }

    zxAnEponIfInUnknownProtosCurrent OBJECT-TYPE
        SYNTAX      Counter32
        MAX-ACCESS  read-only
        STATUS      current
        DESCRIPTION
                ""
        ::= { zxAnEponIfCurrentEntry 6 }

    zxAnEponIfOutOctetsCurrent OBJECT-TYPE
        SYNTAX      Counter32
        MAX-ACCESS  read-only
        STATUS      current
        DESCRIPTION
                ""
        ::= { zxAnEponIfCurrentEntry 7 }

    zxAnEponIfOutUcastPktsCurrent OBJECT-TYPE
        SYNTAX      Counter32
        MAX-ACCESS  read-only
        STATUS      current
        DESCRIPTION
                ""
        ::= { zxAnEponIfCurrentEntry 8 }

    zxAnEponIfOutNUcastPktsCurrent OBJECT-TYPE
        SYNTAX      Counter32
        MAX-ACCESS  read-only
        STATUS      deprecated
        DESCRIPTION
                ""
        ::= { zxAnEponIfCurrentEntry 9 }

    zxAnEponIfOutDiscardsCurrent OBJECT-TYPE
        SYNTAX      Counter32
        MAX-ACCESS  read-only
        STATUS      current
        DESCRIPTION
                ""
        ::= { zxAnEponIfCurrentEntry 10 }

    zxAnEponIfOutErrorsCurrent OBJECT-TYPE
        SYNTAX      Counter32
        MAX-ACCESS  read-only
        STATUS      current
        DESCRIPTION
                ""
        ::= { zxAnEponIfCurrentEntry 11 }

    zxAnEponIfXCurrentTable        OBJECT-TYPE
        SYNTAX      SEQUENCE OF ZxAnEponIfXCurrentEntry
        MAX-ACCESS  not-accessible
        STATUS      current
        DESCRIPTION
                ""
        ::= { zxAnEponPmCurrent 10 }

    zxAnEponIfXCurrentEntry        OBJECT-TYPE
        SYNTAX      ZxAnEponIfXCurrentEntry
        MAX-ACCESS  not-accessible
        STATUS      current
        DESCRIPTION
                ""
        AUGMENTS    { zxAnEponIfCurrentEntry }
        ::= { zxAnEponIfXCurrentTable 1 }

    ZxAnEponIfXCurrentEntry ::=
        SEQUENCE {
            zxAnEponIfInMulticastPktsCurrent       Counter32,
            zxAnEponIfInBroadcastPktsCurrent       Counter32,
            zxAnEponIfOutMulticastPktsCurrent      Counter32,
            zxAnEponIfOutBroadcastPktsCurrent      Counter32,
            zxAnEponIfHCInOctetsCurrent            Counter64,
            zxAnEponIfHCInUcastPktsCurrent         Counter64,
            zxAnEponIfHCInMulticastPktsCurrent     Counter64,
            zxAnEponIfHCInBroadcastPktsCurrent     Counter64,
            zxAnEponIfHCOutOctetsCurrent           Counter64,
            zxAnEponIfHCOutUcastPktsCurrent        Counter64,
            zxAnEponIfHCOutMulticastPktsCurrent    Counter64,
            zxAnEponIfHCOutBroadcastPktsCurrent    Counter64
        }


    zxAnEponIfInMulticastPktsCurrent OBJECT-TYPE
        SYNTAX      Counter32
        MAX-ACCESS  read-only
        STATUS      current
        DESCRIPTION
                ""
        ::= { zxAnEponIfXCurrentEntry 1 }

    zxAnEponIfInBroadcastPktsCurrent OBJECT-TYPE
        SYNTAX      Counter32
        MAX-ACCESS  read-only
        STATUS      current
        DESCRIPTION
                ""
        ::= { zxAnEponIfXCurrentEntry 2 }

    zxAnEponIfOutMulticastPktsCurrent OBJECT-TYPE
        SYNTAX      Counter32
        MAX-ACCESS  read-only
        STATUS      current
        DESCRIPTION
                ""
        ::= { zxAnEponIfXCurrentEntry 3 }

    zxAnEponIfOutBroadcastPktsCurrent OBJECT-TYPE
        SYNTAX      Counter32
        MAX-ACCESS  read-only
        STATUS      current
        DESCRIPTION
                ""
        ::= { zxAnEponIfXCurrentEntry 4 }

    zxAnEponIfHCInOctetsCurrent OBJECT-TYPE
        SYNTAX      Counter64
        MAX-ACCESS  read-only
        STATUS      current
        DESCRIPTION
                ""
        ::= { zxAnEponIfXCurrentEntry 5 }

    zxAnEponIfHCInUcastPktsCurrent OBJECT-TYPE
        SYNTAX      Counter64
        MAX-ACCESS  read-only
        STATUS      current
        DESCRIPTION
                ""
        ::= { zxAnEponIfXCurrentEntry 6 }

    zxAnEponIfHCInMulticastPktsCurrent OBJECT-TYPE
        SYNTAX      Counter64
        MAX-ACCESS  read-only
        STATUS      current
        DESCRIPTION
                ""
        ::= { zxAnEponIfXCurrentEntry 7 }

    zxAnEponIfHCInBroadcastPktsCurrent OBJECT-TYPE
        SYNTAX      Counter64
        MAX-ACCESS  read-only
        STATUS      current
        DESCRIPTION
                ""
        ::= { zxAnEponIfXCurrentEntry 8 }

    zxAnEponIfHCOutOctetsCurrent OBJECT-TYPE
        SYNTAX      Counter64
        MAX-ACCESS  read-only
        STATUS      current
        DESCRIPTION
                ""
        ::= { zxAnEponIfXCurrentEntry 9 }

    zxAnEponIfHCOutUcastPktsCurrent OBJECT-TYPE
        SYNTAX      Counter64
        MAX-ACCESS  read-only
        STATUS      current
        DESCRIPTION
                ""
        ::= { zxAnEponIfXCurrentEntry 10 }

    zxAnEponIfHCOutMulticastPktsCurrent OBJECT-TYPE
        SYNTAX      Counter64
        MAX-ACCESS  read-only
        STATUS      current
        DESCRIPTION
                ""
        ::= { zxAnEponIfXCurrentEntry 11 }

    zxAnEponIfHCOutBroadcastPktsCurrent OBJECT-TYPE
        SYNTAX      Counter64
        MAX-ACCESS  read-only
        STATUS      current
        DESCRIPTION
                ""
        ::= { zxAnEponIfXCurrentEntry 12 }

    zxAnEponDot3PauseCurrentTable OBJECT-TYPE
        SYNTAX      SEQUENCE OF ZxAnEponDot3PauseCurrentEntry
        MAX-ACCESS  not-accessible
        STATUS      current
        DESCRIPTION
            "" 
        REFERENCE
            ""
        ::= { zxAnEponPmCurrent 11 }

    zxAnEponDot3PauseCurrentEntry OBJECT-TYPE
        SYNTAX      ZxAnEponDot3PauseCurrentEntry
        MAX-ACCESS  not-accessible
        STATUS      current
        DESCRIPTION
            ""
        INDEX   { ifIndex }
        ::= { zxAnEponDot3PauseCurrentTable 1 }

    ZxAnEponDot3PauseCurrentEntry ::=
        SEQUENCE {
            zxAnEponDot3InPauseFramesCurrent        Counter32,
            zxAnEponDot3OutPauseFramesCurrent        Counter32,
            zxAnEponDot3HCInPauseFramesCurrent        Counter64,
            zxAnEponDot3HCOutPauseFramesCurrent        Counter64
        }

    zxAnEponDot3InPauseFramesCurrent OBJECT-TYPE
        SYNTAX      Counter32
        MAX-ACCESS  read-only
        STATUS      current
        DESCRIPTION
                ""
        ::= { zxAnEponDot3PauseCurrentEntry 1 }

    zxAnEponDot3OutPauseFramesCurrent OBJECT-TYPE
        SYNTAX      Counter32
        MAX-ACCESS  read-only
        STATUS      current
        DESCRIPTION
                ""
        ::= { zxAnEponDot3PauseCurrentEntry 2 }

    zxAnEponDot3HCInPauseFramesCurrent OBJECT-TYPE
        SYNTAX      Counter64
        MAX-ACCESS  read-only
        STATUS      current
        DESCRIPTION
                ""
        ::= { zxAnEponDot3PauseCurrentEntry 3 }

    zxAnEponDot3HCOutPauseFramesCurrent OBJECT-TYPE
        SYNTAX      Counter64
        MAX-ACCESS  read-only
        STATUS      current
        DESCRIPTION
                ""
        ::= { zxAnEponDot3PauseCurrentEntry 4 }

    zxAnEponDot3HCStatsCurrentTable OBJECT-TYPE
        SYNTAX      SEQUENCE OF ZxAnEponDot3HCStatsCurrentEntry
        MAX-ACCESS  not-accessible
        STATUS      current
        DESCRIPTION
            "" 
        REFERENCE
            ""
        ::= { zxAnEponPmCurrent 12 }

    zxAnEponDot3HCStatsCurrentEntry OBJECT-TYPE
        SYNTAX      ZxAnEponDot3HCStatsCurrentEntry
        MAX-ACCESS  not-accessible
        STATUS      current
        DESCRIPTION
            ""
        INDEX   { ifIndex }
        ::= { zxAnEponDot3HCStatsCurrentTable 1 }

    ZxAnEponDot3HCStatsCurrentEntry ::=
        SEQUENCE {
            zxAnEponDot3HCStatsAlignmentErrorsCurrent         Counter64,
            zxAnEponDot3HCStatsFCSErrorsCurrent         Counter64,
            zxAnEponDot3HCStatsInternalMacTransmitErrorsCurrent         Counter64,
            zxAnEponDot3HCStatsFrameTooLongsCurrent         Counter64,
            zxAnEponDot3HCStatsInternalMacReceiveErrorsCurrent         Counter64,
            zxAnEponDot3HCStatsSymbolErrorsCurrent         Counter64
        }

    zxAnEponDot3HCStatsAlignmentErrorsCurrent OBJECT-TYPE
        SYNTAX      Counter64
        MAX-ACCESS  read-only
        STATUS      current
        DESCRIPTION
                ""
        ::= { zxAnEponDot3HCStatsCurrentEntry 1 }

    zxAnEponDot3HCStatsFCSErrorsCurrent OBJECT-TYPE
        SYNTAX      Counter64
        MAX-ACCESS  read-only
        STATUS      current
        DESCRIPTION
                ""
        ::= { zxAnEponDot3HCStatsCurrentEntry 2 }

    zxAnEponDot3HCStatsInternalMacTransmitErrorsCurrent OBJECT-TYPE
        SYNTAX      Counter64
        MAX-ACCESS  read-only
        STATUS      current
        DESCRIPTION
                ""
        ::= { zxAnEponDot3HCStatsCurrentEntry 3 }

    zxAnEponDot3HCStatsFrameTooLongsCurrent OBJECT-TYPE
        SYNTAX      Counter64
        MAX-ACCESS  read-only
        STATUS      current
        DESCRIPTION
                ""
        ::= { zxAnEponDot3HCStatsCurrentEntry 4 }

    zxAnEponDot3HCStatsInternalMacReceiveErrorsCurrent OBJECT-TYPE
        SYNTAX      Counter64
        MAX-ACCESS  read-only
        STATUS      current
        DESCRIPTION
                ""
        ::= { zxAnEponDot3HCStatsCurrentEntry 5 }

    zxAnEponDot3HCStatsSymbolErrorsCurrent OBJECT-TYPE
        SYNTAX      Counter64
        MAX-ACCESS  read-only
        STATUS      current
        DESCRIPTION
                ""
        ::= { zxAnEponDot3HCStatsCurrentEntry 6 }

------------------------------------------------------------------------------
-- EPON ONU LLID Statistics Table
------------------------------------------------------------------------------

    zxAnEponOnuLlidStatTable OBJECT-TYPE
        SYNTAX      SEQUENCE OF ZxAnEponOnuLlidStatEntry
        MAX-ACCESS  not-accessible
        STATUS      current
        DESCRIPTION
            "EPON ONU LLID real time performance statistics table." 
        REFERENCE
            ""
        ::= { zxAnEponPmCurrent 13 }

    zxAnEponOnuLlidStatEntry OBJECT-TYPE
        SYNTAX      ZxAnEponOnuLlidStatEntry
        MAX-ACCESS  not-accessible
        STATUS      current
        DESCRIPTION
            "EPON ONU LLID real time performance statistics entry."
        INDEX   { ifIndex,zxAnEponOnuLlid }
        ::= { zxAnEponOnuLlidStatTable 1 }
        
    ZxAnEponOnuLlidStatEntry ::=
        SEQUENCE {
            zxAnEponOnuLlidRxFrames                 Counter64,
            zxAnEponOnuLlidRxOctets                 Counter64,
            zxAnEponOnuLlidRxMulticastFrames        Counter64,
            zxAnEponOnuLlidRxBroadcastFrames        Counter64,
            zxAnEponOnuLlidTxFrames                 Counter64,
            zxAnEponOnuLlidTxOctets                 Counter64,
            zxAnEponOnuLlidTxMulticastFrames        Counter64,
            zxAnEponOnuLlidTxBroadcastFrames        Counter64,
            zxAnEponOnuLlidCrcErrors                Counter64,
            zxAnEponOnuLlidFecCrctedBlocks          Counter64,
            zxAnEponOnuLlidFecUncrctedBlocks        Counter64,
            zxAnEponOnuLlidMpcpRxGateFrames         Counter64,
            zxAnEponOnuLlidMpcpRxCtrlFrames         Counter64,
            zxAnEponOnuLlidMpcpRxRegFrames          Counter64,
            zxAnEponOnuLlidMpcpTxCtrlFrames         Counter64,
            zxAnEponOnuLlidMpcpTxReqFrames          Counter64,
            zxAnEponOnuLlidMpcpTxRepFrames          Counter64
        }
        
    zxAnEponOnuLlidRxFrames OBJECT-TYPE
        SYNTAX      Counter64
        MAX-ACCESS  read-only
        STATUS      current
        DESCRIPTION
                "The total number of received frames."
        ::= { zxAnEponOnuLlidStatEntry 1 }
        
    zxAnEponOnuLlidRxOctets OBJECT-TYPE
        SYNTAX      Counter64
        MAX-ACCESS  read-only
        STATUS      current
        DESCRIPTION
                "The total number of received octets."
        ::= { zxAnEponOnuLlidStatEntry 2 }
        
    zxAnEponOnuLlidRxMulticastFrames OBJECT-TYPE
        SYNTAX      Counter64
        MAX-ACCESS  read-only
        STATUS      current
        DESCRIPTION
                "The total number of received multicast frames."
        ::= { zxAnEponOnuLlidStatEntry 3 }
        
    zxAnEponOnuLlidRxBroadcastFrames OBJECT-TYPE
        SYNTAX      Counter64
        MAX-ACCESS  read-only
        STATUS      current
        DESCRIPTION
                "The total number of received broadcast frames."
        ::= { zxAnEponOnuLlidStatEntry 4 }
        
    zxAnEponOnuLlidTxFrames OBJECT-TYPE
        SYNTAX      Counter64
        MAX-ACCESS  read-only
        STATUS      current
        DESCRIPTION
                "The total number of sent frames."
        ::= { zxAnEponOnuLlidStatEntry 5 }
        
    zxAnEponOnuLlidTxOctets OBJECT-TYPE
        SYNTAX      Counter64
        MAX-ACCESS  read-only
        STATUS      current
        DESCRIPTION
                "The total number of sent octets."
        ::= { zxAnEponOnuLlidStatEntry 6 }
        
    zxAnEponOnuLlidTxMulticastFrames OBJECT-TYPE
        SYNTAX      Counter64
        MAX-ACCESS  read-only
        STATUS      current
        DESCRIPTION
                "The total number of sent multicast frames."
        ::= { zxAnEponOnuLlidStatEntry 7 }
        
    zxAnEponOnuLlidTxBroadcastFrames OBJECT-TYPE
        SYNTAX      Counter64
        MAX-ACCESS  read-only
        STATUS      current
        DESCRIPTION
                "The total number of sent broadcast frames."
        ::= { zxAnEponOnuLlidStatEntry 8 }
        
    zxAnEponOnuLlidCrcErrors OBJECT-TYPE
        SYNTAX      Counter64
        MAX-ACCESS  read-only
        STATUS      current
        DESCRIPTION
                "The total number of CRC errors."
        ::= { zxAnEponOnuLlidStatEntry 9 }
        
    zxAnEponOnuLlidFecCrctedBlocks OBJECT-TYPE
        SYNTAX      Counter64
        MAX-ACCESS  read-only
        STATUS      current
        DESCRIPTION
                "The total number of corrected FEC blocks."
        ::= { zxAnEponOnuLlidStatEntry 10 }
        
    zxAnEponOnuLlidFecUncrctedBlocks OBJECT-TYPE
        SYNTAX      Counter64
        MAX-ACCESS  read-only
        STATUS      current
        DESCRIPTION
                "The total number of uncorrected FEC blocks."
        ::= { zxAnEponOnuLlidStatEntry 11 }
        
    zxAnEponOnuLlidMpcpRxGateFrames OBJECT-TYPE
        SYNTAX      Counter64
        MAX-ACCESS  read-only
        STATUS      current
        DESCRIPTION
                "The total number of received MPCP gate frames."
        ::= { zxAnEponOnuLlidStatEntry 12 }
        
    zxAnEponOnuLlidMpcpRxCtrlFrames OBJECT-TYPE
        SYNTAX      Counter64
        MAX-ACCESS  read-only
        STATUS      current
        DESCRIPTION
                "The total number of received MPCP MAC control frames."
        ::= { zxAnEponOnuLlidStatEntry 13 }
        
    zxAnEponOnuLlidMpcpRxRegFrames OBJECT-TYPE
        SYNTAX      Counter64
        MAX-ACCESS  read-only
        STATUS      current
        DESCRIPTION
                "The total number of received MPCP register frames."
        ::= { zxAnEponOnuLlidStatEntry 14 }
        
    zxAnEponOnuLlidMpcpTxCtrlFrames OBJECT-TYPE
        SYNTAX      Counter64
        MAX-ACCESS  read-only
        STATUS      current
        DESCRIPTION
                "The total number of sent MPCP MAC control frames."
        ::= { zxAnEponOnuLlidStatEntry 15 }

    zxAnEponOnuLlidMpcpTxReqFrames OBJECT-TYPE
        SYNTAX      Counter64
        MAX-ACCESS  read-only
        STATUS      current
        DESCRIPTION
                "The total number of sent MPCP register request frames."
        ::= { zxAnEponOnuLlidStatEntry 16 }
        
    zxAnEponOnuLlidMpcpTxRepFrames OBJECT-TYPE
        SYNTAX      Counter64
        MAX-ACCESS  read-only
        STATUS      current
        DESCRIPTION
                "The total number of sent MPCP report frames."
        ::= { zxAnEponOnuLlidStatEntry 17 }
        

--zxAnEponPmHistory

     zxAnEponOltVirtualIfBERStatisticHistoryTable OBJECT-TYPE
        SYNTAX      SEQUENCE OF ZxAnEponOltVirtualIfBERStatisticHistoryEntry
        MAX-ACCESS  not-accessible
        STATUS      current
        DESCRIPTION
            "" 
        REFERENCE
            ""
        ::= { zxAnEponPmHistory 1 }

    zxAnEponOltVirtualIfBERStatisticHistoryEntry OBJECT-TYPE
        SYNTAX      ZxAnEponOltVirtualIfBERStatisticHistoryEntry
        MAX-ACCESS  not-accessible
        STATUS      current
        DESCRIPTION
            ""
        INDEX   { ifIndex }
        ::= { zxAnEponOltVirtualIfBERStatisticHistoryTable 1 }

    ZxAnEponOltVirtualIfBERStatisticHistoryEntry ::=
        SEQUENCE {
            zxAnEponOltVirtualIfBERStatisticHistoryOnuBER      OCTET STRING,
            zxAnEponOltVirtualIfBERStatisticHistoryOnuFER      OCTET STRING
        }

   zxAnEponOltVirtualIfBERStatisticHistoryOnuBER OBJECT-TYPE
        SYNTAX      OCTET STRING (SIZE (0..16))
        MAX-ACCESS  read-only
        STATUS      current
        DESCRIPTION
            ""
        ::= { zxAnEponOltVirtualIfBERStatisticHistoryEntry 1}

   zxAnEponOltVirtualIfBERStatisticHistoryOnuFER OBJECT-TYPE
        SYNTAX      OCTET STRING (SIZE (0..16))
        MAX-ACCESS  read-only
        STATUS      current
        DESCRIPTION
            ""
        ::= { zxAnEponOltVirtualIfBERStatisticHistoryEntry 2}

     zxAnEponOltPhyPortStatisticHistoryTable OBJECT-TYPE
        SYNTAX      SEQUENCE OF ZxAnEponOltPhyPortStatisticHistoryEntry
        MAX-ACCESS  not-accessible
        STATUS      current
        DESCRIPTION
            "" 
        REFERENCE
            ""
        ::= { zxAnEponPmHistory 2 }

    zxAnEponOltPhyPortStatisticHistoryEntry OBJECT-TYPE
        SYNTAX      ZxAnEponOltPhyPortStatisticHistoryEntry
        MAX-ACCESS  not-accessible
        STATUS      current
        DESCRIPTION
            ""
        INDEX   { ifIndex }
        ::= { zxAnEponOltPhyPortStatisticHistoryTable 1 }

    ZxAnEponOltPhyPortStatisticHistoryEntry ::=
        SEQUENCE {
            zxAnEponOltPhyPortStatisticHistoryOltPonAverageBER      OCTET STRING,
            zxAnEponOltPhyPortStatisticHistoryOltSysAverageBER      OCTET STRING
        }

   zxAnEponOltPhyPortStatisticHistoryOltPonAverageBER OBJECT-TYPE
        SYNTAX      OCTET STRING (SIZE (0..16))
        MAX-ACCESS  read-only
        STATUS      current
        DESCRIPTION
            ""
        ::= { zxAnEponOltPhyPortStatisticHistoryEntry 1}

   zxAnEponOltPhyPortStatisticHistoryOltSysAverageBER OBJECT-TYPE
        SYNTAX      OCTET STRING (SIZE (0..16))
        MAX-ACCESS  read-only
        STATUS      current
        DESCRIPTION
            ""
        ::= { zxAnEponOltPhyPortStatisticHistoryEntry 2}

    zxAnEponEtherStatsHistoryTable OBJECT-TYPE
        SYNTAX      SEQUENCE OF ZxAnEponEtherStatsHistoryEntry
        MAX-ACCESS  not-accessible
        STATUS      current
        DESCRIPTION
            "" 
        REFERENCE
            ""
        ::= { zxAnEponPmHistory 3 }

    zxAnEponEtherStatsHistoryEntry OBJECT-TYPE
        SYNTAX      ZxAnEponEtherStatsHistoryEntry
        MAX-ACCESS  not-accessible
        STATUS      current
        DESCRIPTION
            ""
        INDEX   { ifIndex }
        ::= { zxAnEponEtherStatsHistoryTable 1 }

    ZxAnEponEtherStatsHistoryEntry ::=
        SEQUENCE {
            zxAnEponEtherStatsDropEventsHistory      Counter32,
            zxAnEponEtherStatsOctetsHistory      Counter32,
            zxAnEponEtherStatsPktsHistory      Counter32,
            zxAnEponEtherStatsBroadcastPktsHistory      Counter32,
            zxAnEponEtherStatsMulticastPktsHistory      Counter32,
            zxAnEponEtherStatsCRCAlignErrorsHistory      Counter32,
            zxAnEponEtherStatsUndersizePktsHistory      Counter32,
            zxAnEponEtherStatsOversizePktsHistory      Counter32,
            zxAnEponEtherStatsFragmentsHistory      Counter32,
            zxAnEponEtherStatsJabbersHistory      Counter32,
            zxAnEponEtherStatsCollisionsHistory      Counter32,
            zxAnEponEtherStatsPkts64OctetsHistory      Counter32,
            zxAnEponEtherStatsPkts65to127OctetsHistory      Counter32,
            zxAnEponEtherStatsPkts128to255OctetsHistory      Counter32,
            zxAnEponEtherStatsPkts256to511OctetsHistory      Counter32,
            zxAnEponEtherStatsPkts512to1023OctetsHistory       Counter32,
            zxAnEponEtherStatsPkts1024to1518OctetsHistory       Counter32
        }

   zxAnEponEtherStatsDropEventsHistory OBJECT-TYPE
        SYNTAX      Counter32
        MAX-ACCESS  read-only
        STATUS      current
        DESCRIPTION
            ""
        ::= { zxAnEponEtherStatsHistoryEntry 1}

   zxAnEponEtherStatsOctetsHistory OBJECT-TYPE
        SYNTAX      Counter32
        MAX-ACCESS  read-only
        STATUS      current
        DESCRIPTION
            ""
        ::= { zxAnEponEtherStatsHistoryEntry 2}

   zxAnEponEtherStatsPktsHistory OBJECT-TYPE
        SYNTAX      Counter32
        MAX-ACCESS  read-only
        STATUS      current
        DESCRIPTION
            ""
        ::= { zxAnEponEtherStatsHistoryEntry 3}

   zxAnEponEtherStatsBroadcastPktsHistory OBJECT-TYPE
        SYNTAX      Counter32
        MAX-ACCESS  read-only
        STATUS      current
        DESCRIPTION
            ""
        ::= { zxAnEponEtherStatsHistoryEntry 4}

   zxAnEponEtherStatsMulticastPktsHistory OBJECT-TYPE
        SYNTAX      Counter32
        MAX-ACCESS  read-only
        STATUS      current
        DESCRIPTION
            ""
        ::= { zxAnEponEtherStatsHistoryEntry 5}

   zxAnEponEtherStatsCRCAlignErrorsHistory OBJECT-TYPE
        SYNTAX      Counter32
        MAX-ACCESS  read-only
        STATUS      current
        DESCRIPTION
            ""
        ::= { zxAnEponEtherStatsHistoryEntry 6}

   zxAnEponEtherStatsUndersizePktsHistory OBJECT-TYPE
        SYNTAX      Counter32
        MAX-ACCESS  read-only
        STATUS      current
        DESCRIPTION
            ""
        ::= { zxAnEponEtherStatsHistoryEntry 7}

   zxAnEponEtherStatsOversizePktsHistory OBJECT-TYPE
        SYNTAX      Counter32
        MAX-ACCESS  read-only
        STATUS      current
        DESCRIPTION
            ""
        ::= { zxAnEponEtherStatsHistoryEntry 8}

   zxAnEponEtherStatsFragmentsHistory OBJECT-TYPE
        SYNTAX      Counter32
        MAX-ACCESS  read-only
        STATUS      current
        DESCRIPTION
            ""
        ::= { zxAnEponEtherStatsHistoryEntry 9}

   zxAnEponEtherStatsJabbersHistory OBJECT-TYPE
        SYNTAX      Counter32
        MAX-ACCESS  read-only
        STATUS      current
        DESCRIPTION
            ""
        ::= { zxAnEponEtherStatsHistoryEntry 10}

   zxAnEponEtherStatsCollisionsHistory OBJECT-TYPE
        SYNTAX      Counter32
        MAX-ACCESS  read-only
        STATUS      current
        DESCRIPTION
            ""
        ::= { zxAnEponEtherStatsHistoryEntry 11}

   zxAnEponEtherStatsPkts64OctetsHistory OBJECT-TYPE
        SYNTAX      Counter32
        MAX-ACCESS  read-only
        STATUS      current
        DESCRIPTION
            ""
        ::= { zxAnEponEtherStatsHistoryEntry 12}

   zxAnEponEtherStatsPkts65to127OctetsHistory OBJECT-TYPE
        SYNTAX      Counter32
        MAX-ACCESS  read-only
        STATUS      current
        DESCRIPTION
            ""
        ::= { zxAnEponEtherStatsHistoryEntry 13}

   zxAnEponEtherStatsPkts128to255OctetsHistory OBJECT-TYPE
        SYNTAX      Counter32
        MAX-ACCESS  read-only
        STATUS      current
        DESCRIPTION
            ""
        ::= { zxAnEponEtherStatsHistoryEntry 14}

   zxAnEponEtherStatsPkts256to511OctetsHistory OBJECT-TYPE
        SYNTAX      Counter32
        MAX-ACCESS  read-only
        STATUS      current
        DESCRIPTION
            ""
        ::= { zxAnEponEtherStatsHistoryEntry 15}

   zxAnEponEtherStatsPkts512to1023OctetsHistory OBJECT-TYPE
        SYNTAX      Counter32
        MAX-ACCESS  read-only
        STATUS      current
        DESCRIPTION
            ""
        ::= { zxAnEponEtherStatsHistoryEntry 16}

   zxAnEponEtherStatsPkts1024to1518OctetsHistory OBJECT-TYPE
        SYNTAX      Counter32
        MAX-ACCESS  read-only
        STATUS      current
        DESCRIPTION
            ""
        ::= { zxAnEponEtherStatsHistoryEntry 17}

    zxAnEponIfXHistoryTable        OBJECT-TYPE
        SYNTAX      SEQUENCE OF ZxAnEponIfXHistoryEntry
        MAX-ACCESS  not-accessible
        STATUS      current
        DESCRIPTION
                ""
        ::= { zxAnEponPmHistory 4 }

    zxAnEponIfXHistoryEntry        OBJECT-TYPE
        SYNTAX      ZxAnEponIfXHistoryEntry
        MAX-ACCESS  not-accessible
        STATUS      current
        DESCRIPTION
                ""
        AUGMENTS    { zxAnEponIfEntry }
        ::= { zxAnEponIfXHistoryTable 1 }

    ZxAnEponIfXHistoryEntry ::=
        SEQUENCE {
            zxAnEponIfInMulticastPktsHistory       Counter32,
            zxAnEponIfInBroadcastPktsHistory       Counter32,
            zxAnEponIfOutMulticastPktsHistory      Counter32,
            zxAnEponIfOutBroadcastPktsHistory      Counter32,
            zxAnEponIfHCInOctetsHistory            Counter64,
            zxAnEponIfHCInUcastPktsHistory         Counter64,
            zxAnEponIfHCInMulticastPktsHistory     Counter64,
            zxAnEponIfHCInBroadcastPktsHistory     Counter64,
            zxAnEponIfHCOutOctetsHistory           Counter64,
            zxAnEponIfHCOutUcastPktsHistory        Counter64,
            zxAnEponIfHCOutMulticastPktsHistory    Counter64,
            zxAnEponIfHCOutBroadcastPktsHistory    Counter64
        }


    zxAnEponIfInMulticastPktsHistory OBJECT-TYPE
        SYNTAX      Counter32
        MAX-ACCESS  read-only
        STATUS      current
        DESCRIPTION
                ""
        ::= { zxAnEponIfXHistoryEntry 1 }

    zxAnEponIfInBroadcastPktsHistory OBJECT-TYPE
        SYNTAX      Counter32
        MAX-ACCESS  read-only
        STATUS      current
        DESCRIPTION
                ""
        ::= { zxAnEponIfXHistoryEntry 2 }

    zxAnEponIfOutMulticastPktsHistory OBJECT-TYPE
        SYNTAX      Counter32
        MAX-ACCESS  read-only
        STATUS      current
        DESCRIPTION
                ""
        ::= { zxAnEponIfXHistoryEntry 3 }

    zxAnEponIfOutBroadcastPktsHistory OBJECT-TYPE
        SYNTAX      Counter32
        MAX-ACCESS  read-only
        STATUS      current
        DESCRIPTION
                ""
        ::= { zxAnEponIfXHistoryEntry 4 }

    zxAnEponIfHCInOctetsHistory OBJECT-TYPE
        SYNTAX      Counter64
        MAX-ACCESS  read-only
        STATUS      current
        DESCRIPTION
                ""
        ::= { zxAnEponIfXHistoryEntry 5 }

    zxAnEponIfHCInUcastPktsHistory OBJECT-TYPE
        SYNTAX      Counter64
        MAX-ACCESS  read-only
        STATUS      current
        DESCRIPTION
                ""
        ::= { zxAnEponIfXHistoryEntry 6 }

    zxAnEponIfHCInMulticastPktsHistory OBJECT-TYPE
        SYNTAX      Counter64
        MAX-ACCESS  read-only
        STATUS      current
        DESCRIPTION
                ""
        ::= { zxAnEponIfXHistoryEntry 7 }

    zxAnEponIfHCInBroadcastPktsHistory OBJECT-TYPE
        SYNTAX      Counter64
        MAX-ACCESS  read-only
        STATUS      current
        DESCRIPTION
                ""
        ::= { zxAnEponIfXHistoryEntry 8 }

    zxAnEponIfHCOutOctetsHistory OBJECT-TYPE
        SYNTAX      Counter64
        MAX-ACCESS  read-only
        STATUS      current
        DESCRIPTION
                ""
        ::= { zxAnEponIfXHistoryEntry 9 }

    zxAnEponIfHCOutUcastPktsHistory OBJECT-TYPE
        SYNTAX      Counter64
        MAX-ACCESS  read-only
        STATUS      current
        DESCRIPTION
                ""
        ::= { zxAnEponIfXHistoryEntry 10 }

    zxAnEponIfHCOutMulticastPktsHistory OBJECT-TYPE
        SYNTAX      Counter64
        MAX-ACCESS  read-only
        STATUS      current
        DESCRIPTION
                ""
        ::= { zxAnEponIfXHistoryEntry 11 }

    zxAnEponIfHCOutBroadcastPktsHistory OBJECT-TYPE
        SYNTAX      Counter64
        MAX-ACCESS  read-only
        STATUS      current
        DESCRIPTION
                ""
        ::= { zxAnEponIfXHistoryEntry 12 }

    zxAnEponIfXOltHistoryTable        OBJECT-TYPE
        SYNTAX      SEQUENCE OF ZxAnEponIfXOltHistoryEntry
        MAX-ACCESS  not-accessible
        STATUS      current
        DESCRIPTION
                ""
        ::= { zxAnEponPmHistory 5 }

    zxAnEponIfXOltHistoryEntry        OBJECT-TYPE
        SYNTAX      ZxAnEponIfXOltHistoryEntry
        MAX-ACCESS  not-accessible
        STATUS      current
        DESCRIPTION
                ""
        AUGMENTS    { zxAnEponIfEntry }
        ::= { zxAnEponIfXOltHistoryTable 1 }

    ZxAnEponIfXOltHistoryEntry ::=
        SEQUENCE {
            zxAnEponIfOltInMulticastPktsHistory       Counter32,
            zxAnEponIfOltInBroadcastPktsHistory       Counter32,
            zxAnEponIfOltOutMulticastPktsHistory      Counter32,
            zxAnEponIfOltOutBroadcastPktsHistory      Counter32,
            zxAnEponIfOltHCInOctetsHistory            Counter64,
            zxAnEponIfOltHCInUcastPktsHistory         Counter64,
            zxAnEponIfOltHCInMulticastPktsHistory     Counter64,
            zxAnEponIfOltHCInBroadcastPktsHistory     Counter64,
            zxAnEponIfOltHCOutOctetsHistory           Counter64,
            zxAnEponIfOltHCOutUcastPktsHistory        Counter64,
            zxAnEponIfOltHCOutMulticastPktsHistory    Counter64,
            zxAnEponIfOltHCOutBroadcastPktsHistory    Counter64
        }


    zxAnEponIfOltInMulticastPktsHistory OBJECT-TYPE
        SYNTAX      Counter32
        MAX-ACCESS  read-only
        STATUS      current
        DESCRIPTION
                ""
        ::= { zxAnEponIfXOltHistoryEntry 1 }

    zxAnEponIfOltInBroadcastPktsHistory OBJECT-TYPE
        SYNTAX      Counter32
        MAX-ACCESS  read-only
        STATUS      current
        DESCRIPTION
                ""
        ::= { zxAnEponIfXOltHistoryEntry 2 }

    zxAnEponIfOltOutMulticastPktsHistory OBJECT-TYPE
        SYNTAX      Counter32
        MAX-ACCESS  read-only
        STATUS      current
        DESCRIPTION
                ""
        ::= { zxAnEponIfXOltHistoryEntry 3 }

    zxAnEponIfOltOutBroadcastPktsHistory OBJECT-TYPE
        SYNTAX      Counter32
        MAX-ACCESS  read-only
        STATUS      current
        DESCRIPTION
                ""
        ::= { zxAnEponIfXOltHistoryEntry 4 }

    zxAnEponIfOltHCInOctetsHistory OBJECT-TYPE
        SYNTAX      Counter64
        MAX-ACCESS  read-only
        STATUS      current
        DESCRIPTION
                ""
        ::= { zxAnEponIfXOltHistoryEntry 5 }

    zxAnEponIfOltHCInUcastPktsHistory OBJECT-TYPE
        SYNTAX      Counter64
        MAX-ACCESS  read-only
        STATUS      current
        DESCRIPTION
                ""
        ::= { zxAnEponIfXOltHistoryEntry 6 }

    zxAnEponIfOltHCInMulticastPktsHistory OBJECT-TYPE
        SYNTAX      Counter64
        MAX-ACCESS  read-only
        STATUS      current
        DESCRIPTION
                ""
        ::= { zxAnEponIfXOltHistoryEntry 7 }

    zxAnEponIfOltHCInBroadcastPktsHistory OBJECT-TYPE
        SYNTAX      Counter64
        MAX-ACCESS  read-only
        STATUS      current
        DESCRIPTION
                ""
        ::= { zxAnEponIfXOltHistoryEntry 8 }

    zxAnEponIfOltHCOutOctetsHistory OBJECT-TYPE
        SYNTAX      Counter64
        MAX-ACCESS  read-only
        STATUS      current
        DESCRIPTION
                ""
        ::= { zxAnEponIfXOltHistoryEntry 9 }

    zxAnEponIfOltHCOutUcastPktsHistory OBJECT-TYPE
        SYNTAX      Counter64
        MAX-ACCESS  read-only
        STATUS      current
        DESCRIPTION
                ""
        ::= { zxAnEponIfXOltHistoryEntry 10 }

    zxAnEponIfOltHCOutMulticastPktsHistory OBJECT-TYPE
        SYNTAX      Counter64
        MAX-ACCESS  read-only
        STATUS      current
        DESCRIPTION
                ""
        ::= { zxAnEponIfXOltHistoryEntry 11 }

    zxAnEponIfOltHCOutBroadcastPktsHistory OBJECT-TYPE
        SYNTAX      Counter64
        MAX-ACCESS  read-only
        STATUS      current
        DESCRIPTION
                ""
        ::= { zxAnEponIfXOltHistoryEntry 12 }

END

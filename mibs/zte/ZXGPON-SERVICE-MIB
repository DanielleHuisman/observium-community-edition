-- *****************************************************************
-- ZTE GPON MIB
--
-- 09-27-2006
--
-- Copyright(c) 2006 ZTE Corporation
-- All rights reserved.
-- *****************************************************************

ZXGPON-SERVICE-MIB DEFINITIONS ::= BEGIN 
    IMPORTS 
        enterprises                      FROM RFC1155-SMI
        RowStatus                        FROM SNMPv2-TC
        TruthValue                       FROM SNMPv2-TC
        Unsigned32                       FROM SNMPv2-SMI
        Counter64                        FROM SNMPv2-SMI
        IpAddress                        FROM SNMPv2-SMI
        DateAndTime                      FROM SNMPv2-TC
        MacAddress                       FROM SNMPv2-TC
        TEXTUAL-CONVENTION               FROM SNMPv2-TC
        MODULE-IDENTITY                  FROM SNMPv2-SMI
        OBJECT-TYPE,NOTIFICATION-TYPE    FROM SNMPv2-SMI
        ifIndex                          FROM RFC1213-MIB;
   
    zxEnterpriseMib   OBJECT IDENTIFIER ::= { enterprises 3902}
    zxPON             OBJECT IDENTIFIER ::= { zxEnterpriseMib 1012}

    zxGponRootMib MODULE-IDENTITY 
        LAST-UPDATED "200609270000Z"  -- September 27, 2006"
        ORGANIZATION 
            "ZTE Corp."
        CONTACT-INFO 
            "ZTE GPON Working Group: 
            http://www.zte.com.cn
            e-mail:
            guo.hongjian@zte.com.cn
            "
        DESCRIPTION
            "The MIB module for defining ZXGPON base OID. OID programming:
             zxGponRootMib 1     , index(zxGponMgmtIndex)
             zxGponRootMib 2-5   , reserve
             zxGponRootMib 6     , Absolut private MIB(zxGponAbsPrivate)
             zxGponRootMib 7-9   , reserve
             zxGponRootMib 10    , Standard global MIB(zxGponStandardGlobal)
             zxGponRootMib 11    , Private global MIB(zxGponPrivateGlobal)
             zxGponRootMib 12    , Standard OLT MIB(zxGponStandardOlt)
             zxGponRootMib 13    , Private OLT MIB(zxGponPrivateOlt)
             zxGponRootMib 14-20 , reserve
             zxGponRootMib 21    , ONT equipment management(zxGponOntEquipMgmt)
             zxGponRootMib 22    , ANI management(zxGponAniMgmt)
             zxGponRootMib 23    , UNI Management(zxGponUniMgmt)
             zxGponRootMib 24    , Connection Management(zxGponConnMgmt)
             zxGponRootMib 25    , Traffic management(zxGponTrafficMgmt)
             zxGponRootMib 26    , Profile management(zxGponProfileMgmt)
             zxGponRootMib 27    , Standard ONU MIB(zxGponStandardOnu)
             zxGponRootMib 28    , Private ONU MIB(zxGponPrivateOnu)
             zxGponRootMib 30    , Service management MIB(zxGponServiceMgmt)
             zxGponRootMib 45    , Private TRAP MIB(zxGponTraps)
             zxGponRootMib 100   , Dummy MIB indicating the termination of gpon mibs(zxGponTermination)
             
             zxGponUniMgmt 1-5   , reserve
             zxGponUniMgmt 6     , Video Service MIB(zxGponUniVideoService)
             zxGponUniMgmt 7     , TDM Service MIB(zxGponUniTdmService)
             zxGponUniMgmt 8     , Ethernet Service MIB(zxGponUniEthService)
             zxGponUniMgmt 9     , CES MIB(zxGponUniCesService)
            "
   
        REVISION    "200609270000Z"  -- September 27, 2006"
        DESCRIPTION "Initial version, published as ZTE enterprises MIB."
   
        ::= { zxPON 3 }

    zxGponTermination    OBJECT IDENTIFIER ::= { zxGponRootMib 100}
    
    zxGponTerminationDummy OBJECT-TYPE
        SYNTAX      INTEGER
        MAX-ACCESS  read-only
        STATUS      current
        DESCRIPTION
                "The dummy object indicats the termination of all gpon mibs."
        ::= { zxGponTermination 1 }   

    zxGponMgmtIndex    OBJECT IDENTIFIER ::= { zxGponRootMib 1}
    zxAnGponRevision     OBJECT-TYPE 
       SYNTAX           BITS 
           {
               gemportUpQueue(0)
           } 
       MAX-ACCESS       read-only
       STATUS           current
       DESCRIPTION      "Module revision flag."
       ::=  {  zxGponRootMib  2  }

    OntVendorId ::= TEXTUAL-CONVENTION
        STATUS       current
        DESCRIPTION
            "Represents the vendor of the ONT."
        SYNTAX       OCTET STRING (SIZE (4))

    OntVersionId ::= TEXTUAL-CONVENTION
        STATUS       current
        DESCRIPTION
            "Represents the version of the ONT."
        SYNTAX       OCTET STRING (SIZE (14))

    OntSerialNumber ::= TEXTUAL-CONVENTION
        STATUS       current
        DESCRIPTION
            "Represents the unique for each ONT."
        SYNTAX       OCTET STRING (SIZE (8))

    OntEquipmentId ::= TEXTUAL-CONVENTION
        STATUS       current
        DESCRIPTION
            "Represents the specific type of ONT."
        SYNTAX       OCTET STRING (SIZE (20))

    ZxGponRecordName ::= TEXTUAL-CONVENTION
        STATUS       current
        DESCRIPTION
            "Represents the specific type of templet."
        SYNTAX       OCTET STRING (SIZE (0..64))
    
    ZxOntList ::= TEXTUAL-CONVENTION
        STATUS      current
        DESCRIPTION
            "The first octet indicates one PON OLT ID number, and 
             Each four octets indicates one ONT/ONU ID number 
             that thses ONTs belong to the PON OLT, with from the
             second octet to fifth octect specifying first ONT/ONU,
             from the sixth octet to ninth octet specifying second
             ONT/ONU, etc. example, PON OLT 1, ONT 1 ONT 100, ONT 333,
             it is that '0100000001000000640000014D'."
        SYNTAX      OCTET STRING(SIZE (0..256))

    ZxPortIdList ::= TEXTUAL-CONVENTION
        STATUS      current
        DESCRIPTION
            "The first octet indicates one PON OLT ID number, and 
             Each four octets indicates one PortId number that thses 
             PortIds belong to the PON OLT, with from the second octet 
             to fifth octect specifying first PortId Number, from the 
             sixth octet to ninth octet specifying second PortId Number,
             etc. example, PON OLT 1, PortId 1 - PortId 3, it is that 
             '01000000010000000200000003'."
        SYNTAX      OCTET STRING(SIZE (0..256))

    ZxIndexList ::= TEXTUAL-CONVENTION
        STATUS      current
        DESCRIPTION
            "Each four octets indicates one table index number, with from
             the first octet to fourth octect specifying first index Number,
             from the fifth octet to eighth octet specifying second index Number,
             etc. example, index 1, index 10000, index 245678, it is that '00000001
             000027100003BFAE'."
        SYNTAX      OCTET STRING(SIZE (0..256))

    -- OLT and ONU Index table
    -- Only PONC board agent
    
    zxGponOltOnuTable OBJECT-TYPE
        SYNTAX      SEQUENCE OF ZxGponOltOnuEntry
        MAX-ACCESS  not-accessible
        STATUS      current
        DESCRIPTION
            "OLT and ONU table."
        ::= { zxGponMgmtIndex 1 }

    zxGponOltOnuEntry OBJECT-TYPE
        SYNTAX      ZxGponOltOnuEntry
        MAX-ACCESS  not-accessible
        STATUS      current
        DESCRIPTION
            "An entry in the OLT and ONU table."
        INDEX   { zxGponMgmtPonOltId, zxGponMgmtPonOnuId }
        ::= { zxGponOltOnuTable 1 }

    ZxGponOltOnuEntry ::=
        SEQUENCE {
            zxGponMgmtPonOltId               INTEGER,
            zxGponMgmtPonOnuId               INTEGER,
            zxGponMgmtPonEntryStatus         RowStatus
        }
        
    zxGponMgmtPonOltId OBJECT-TYPE
        SYNTAX      INTEGER
        MAX-ACCESS  read-only
        STATUS      current
        DESCRIPTION
            "OLT identifier, from 1 to N.
            bit 31~28?atype(1)
            bit 27~24?ashelf(0)
            bit 23~16?aslotId
            bit 16~8?aoltId
            bit 7~0?areserved(0)"
        ::= { zxGponOltOnuEntry 1}

    zxGponMgmtPonOnuId OBJECT-TYPE
        SYNTAX      INTEGER
        MAX-ACCESS  read-only
        STATUS      current
        DESCRIPTION
            "an ONU in an OLT, from 1 to M."
        ::= { zxGponOltOnuEntry 2}

    zxGponMgmtPonEntryStatus OBJECT-TYPE
        SYNTAX      RowStatus
        MAX-ACCESS  read-create
        STATUS      current
        DESCRIPTION
            ""
        ::= { zxGponOltOnuEntry 3}
        
--zxGponPrivateGlobal.mi2
    zxGponPrivateGlobal OBJECT IDENTIFIER ::= { zxGponRootMib 11 }

    zxGponOltDevInfoTable OBJECT-TYPE
        SYNTAX      SEQUENCE OF ZxGponOltDevInfoEntry
        MAX-ACCESS  not-accessible
        STATUS      current
        DESCRIPTION
            ""
        ::= { zxGponPrivateGlobal 1 }

    zxGponOltDevInfoEntry OBJECT-TYPE
        SYNTAX      ZxGponOltDevInfoEntry
        MAX-ACCESS  not-accessible
        STATUS      current
        DESCRIPTION
            "It is entry in the zxGponOltDevInfoTable."
        INDEX   { zxGponMgmtPonOltId }
        ::= { zxGponOltDevInfoTable 1 }
        
    ZxGponOltDevInfoEntry ::=
        SEQUENCE {
            zxGponDbaEnable              TruthValue
        }

    zxGponDbaEnable OBJECT-TYPE
        SYNTAX      TruthValue
        MAX-ACCESS  read-write
        STATUS      current
        DESCRIPTION
                "Enable or disable DBA on this olt ."
        ::= { zxGponOltDevInfoEntry 1 }
        
    zxGponFECTable OBJECT-TYPE
        SYNTAX      SEQUENCE OF ZxGponFECEntry
        MAX-ACCESS  not-accessible
        STATUS      current
        DESCRIPTION
            ""
        ::= { zxGponPrivateGlobal 3 }

    zxGponFECEntry OBJECT-TYPE
        SYNTAX      ZxGponFECEntry
        MAX-ACCESS  not-accessible
        STATUS      current
        DESCRIPTION
            "It is entry in the zxGponFECTable."
        INDEX   { zxGponMgmtPonOltId }
        ::= { zxGponFECTable 1 }
        
    ZxGponFECEntry ::=
        SEQUENCE {
            zxGponFECMode              INTEGER
        }

    zxGponFECMode OBJECT-TYPE
        SYNTAX      INTEGER{
                    none(1),
                    downstream(2),
                    upstream(3),
                    bidirection(4)
                    }
        MAX-ACCESS  read-write
        STATUS      current
        DESCRIPTION
                "Indicates the FEC mode on this olt ."
        ::= { zxGponFECEntry 1 }
        
    zxGponRTDTable OBJECT-TYPE
        SYNTAX      SEQUENCE OF ZxGponRTDEntry
        MAX-ACCESS  not-accessible
        STATUS      current
        DESCRIPTION
            ""
        ::= { zxGponPrivateGlobal 4 }

    zxGponRTDEntry OBJECT-TYPE
        SYNTAX      ZxGponRTDEntry
        MAX-ACCESS  not-accessible
        STATUS      current
        DESCRIPTION
            "It is entry in the zxGponRTDTable."
        INDEX   { zxGponMgmtPonOltId, zxGponMgmtPonOnuId }
        ::= { zxGponRTDTable 1 }
        
    ZxGponRTDEntry ::=
        SEQUENCE {
            zxGponRTDEqd              INTEGER,
            zxGponRTDDistance         INTEGER
        }

    zxGponRTDEqd OBJECT-TYPE
        SYNTAX      INTEGER
        MAX-ACCESS  read-only
        STATUS      current
        DESCRIPTION
                "Equalized delay of onu."
        ::= { zxGponRTDEntry 1 }
        
    zxGponRTDDistance OBJECT-TYPE
        SYNTAX      INTEGER
        MAX-ACCESS  read-only
        STATUS      current
        DESCRIPTION
                "Distance of onu."
        ::= { zxGponRTDEntry 2 }

    zxGponRangeTable OBJECT-TYPE
        SYNTAX      SEQUENCE OF ZxGponRangeEntry
        MAX-ACCESS  not-accessible
        STATUS      current
        DESCRIPTION
            ""
        ::= { zxGponPrivateGlobal 5 }

    zxGponRangeEntry OBJECT-TYPE
        SYNTAX      ZxGponRangeEntry
        MAX-ACCESS  not-accessible
        STATUS      current
        DESCRIPTION
            "It is entry in the zxGponRangeTable."
        INDEX   { zxGponMgmtPonOltId }
        ::= { zxGponRangeTable 1 }
        
    ZxGponRangeEntry ::=
        SEQUENCE {
            zxGponRangeMode              INTEGER,
            zxGponRangeBase              INTEGER,
            zxGponRangeDiff              INTEGER,
            zxGponRangeCapability        INTEGER
        }

    zxGponRangeMode OBJECT-TYPE
        SYNTAX      INTEGER{
                    mode0(1),
                    mode1(2),
                    mode2(3)
                    }
        MAX-ACCESS  read-write
        STATUS      current
        DESCRIPTION
                "Indicates the range mode of this olt .
                mode0(1): 0  - 20 km
                mode1(2): 20 - 40 km
                mode2(3): 40 - 60 km"
        ::= { zxGponRangeEntry 1 }
        
    zxGponRangeBase OBJECT-TYPE
        SYNTAX      INTEGER
        UNITS       "100m"
        MAX-ACCESS  read-write
        STATUS      current
        DESCRIPTION
                "It indicates value of the base distance of the range.
                 The distance of the range is [zxGponRangeBase,zxGponRangeBase + zxGponRangeDiff],
                 The max distance of the range is 60km"
        ::= { zxGponRangeEntry 2 }
    
    zxGponRangeDiff OBJECT-TYPE
        SYNTAX      INTEGER
        UNITS       "100m"
        MAX-ACCESS  read-write
        STATUS      current
        DESCRIPTION
                "It indicates the distance of the range coverage area."
        ::= { zxGponRangeEntry 3 }  
        
    zxGponRangeCapability OBJECT-TYPE
        SYNTAX      INTEGER{
                    fixed(1),
                    step(2)
                    }
        MAX-ACCESS  read-only
        STATUS      current
        DESCRIPTION
                "Indicates the range capability.
                fixed(1): zxGponRangeMode working,only support 0-20,20-40,40-60
                step(2): zxGponRangeBase and zxGponRangeDiff working"
        ::= { zxGponRangeEntry 4 }       
               

    zxGponPonFloodBandwidthInfoTable OBJECT-TYPE
        SYNTAX      SEQUENCE OF ZxGponPonFloodBandwidthInfoEntry
        MAX-ACCESS  not-accessible
        STATUS      current
        DESCRIPTION
            ""
        ::= { zxGponPrivateGlobal 9 }

    zxGponPonFloodBandwidthInfoEntry OBJECT-TYPE
        SYNTAX      ZxGponPonFloodBandwidthInfoEntry
        MAX-ACCESS  not-accessible
        STATUS      current
        DESCRIPTION
            ""
        INDEX   { zxGponMgmtPonOltId }
        ::= { zxGponPonFloodBandwidthInfoTable 1 }

    ZxGponPonFloodBandwidthInfoEntry ::=
        SEQUENCE {
            zxGponPonFloodBandwidth     Unsigned32
        }

    zxGponPonFloodBandwidth       OBJECT-TYPE
      SYNTAX      Unsigned32
      MAX-ACCESS  read-write
      STATUS      current 
      DESCRIPTION 
        "64-2609192 kbps"
      REFERENCE   "N/A"
      ::= { zxGponPonFloodBandwidthInfoEntry 1 }

--- SCB controled
    zxGponPonMCastBandwidthInfoTable OBJECT-TYPE
        SYNTAX      SEQUENCE OF ZxGponPonMCastBandwidthInfoEntry
        MAX-ACCESS  not-accessible
        STATUS      current
        DESCRIPTION
            ""
        ::= { zxGponPrivateGlobal 10 }

    zxGponPonMCastBandwidthInfoEntry OBJECT-TYPE
        SYNTAX      ZxGponPonMCastBandwidthInfoEntry
        MAX-ACCESS  not-accessible
        STATUS      current
        DESCRIPTION
            ""
        INDEX   { zxGponMgmtPonOltId }
        ::= { zxGponPonMCastBandwidthInfoTable 1 }

    ZxGponPonMCastBandwidthInfoEntry ::=
        SEQUENCE {
            zxGponPonMCastTotalBandwidth     Unsigned32
        }

    zxGponPonMCastTotalBandwidth       OBJECT-TYPE
      SYNTAX      Unsigned32
      MAX-ACCESS  read-write
      STATUS      current 
      DESCRIPTION 
        ""
      REFERENCE   "N/A"
      ::= { zxGponPonMCastBandwidthInfoEntry 1 }


    zxGponSCBMCastGroupTable OBJECT-TYPE
        SYNTAX      SEQUENCE OF ZxGponSCBMCastGroupEntry
        MAX-ACCESS  not-accessible
        STATUS      current
        DESCRIPTION
            "This table represents SCB multicast configuration."
        ::= { zxGponPrivateGlobal 11 }

    zxGponSCBMCastGroupEntry OBJECT-TYPE
        SYNTAX      ZxGponSCBMCastGroupEntry
        MAX-ACCESS  not-accessible
        STATUS      current
        DESCRIPTION
            "It provide a SCB multicast configuration entry."
        INDEX   { zxGponSCBMCastGroupIdx }
        ::= { zxGponSCBMCastGroupTable 1 }
        

    ZxGponSCBMCastGroupEntry ::=
        SEQUENCE {
            zxGponSCBMCastGroupIdx       INTEGER,
            zxGponSCBMCastGroupName      ZxGponRecordName,
            zxGponSCBMCastMgmtPortID     INTEGER,
            zxGponSCBMCastGroupDownBWPtr INTEGER,
            zxGponSCBMCastRealPortID     INTEGER,
            zxGponSCBMCastOntListIdx     ZxIndexList,
            zxGponSCBMCastEntryStatus    RowStatus
        }

    zxGponSCBMCastGroupIdx       OBJECT-TYPE
      SYNTAX      INTEGER
      MAX-ACCESS  not-accessible
      STATUS      current 
      DESCRIPTION 
        ""
      REFERENCE   "N/A"
      ::= { zxGponSCBMCastGroupEntry 1 }

    zxGponSCBMCastGroupName       OBJECT-TYPE
      SYNTAX      ZxGponRecordName(SIZE (0..64))
      MAX-ACCESS  read-write
      STATUS      current 
      DESCRIPTION 
        ""
      REFERENCE   "N/A"
      ::= { zxGponSCBMCastGroupEntry 2 }

    zxGponSCBMCastMgmtPortID       OBJECT-TYPE
      SYNTAX      INTEGER
      MAX-ACCESS  read-write
      STATUS      current 
      DESCRIPTION 
        ""
      REFERENCE   "N/A"
      ::= { zxGponSCBMCastGroupEntry 3 }

    zxGponSCBMCastGroupDownBWPtr       OBJECT-TYPE
      SYNTAX      INTEGER
      MAX-ACCESS  read-write
      STATUS      current 
      DESCRIPTION 
        ""
      REFERENCE   "N/A"
      ::= { zxGponSCBMCastGroupEntry 4 }

    zxGponSCBMCastRealPortID       OBJECT-TYPE
      SYNTAX      INTEGER
      MAX-ACCESS  read-only
      STATUS      current 
      DESCRIPTION 
        "If 'zxGponSCBMCastMgmtPortID' is the real gpon portid, it is equal to the 'zxGponSCBMCastMgmtPortID'"
      REFERENCE   "N/A"
      ::= { zxGponSCBMCastGroupEntry 5 }

    zxGponSCBMCastOntListIdx       OBJECT-TYPE
      SYNTAX      ZxIndexList(SIZE (0..256))
      MAX-ACCESS  read-only
      STATUS      current 
      DESCRIPTION 
        ""
      REFERENCE   "N/A"
      ::= { zxGponSCBMCastGroupEntry 6 }

    zxGponSCBMCastEntryStatus       OBJECT-TYPE
      SYNTAX      RowStatus
      MAX-ACCESS  read-create
      STATUS      current 
      DESCRIPTION 
        ""
      REFERENCE   "N/A"
      ::= { zxGponSCBMCastGroupEntry 7 }


    zxGponSCBMCastOntTable OBJECT-TYPE
        SYNTAX      SEQUENCE OF ZxGponSCBMCastOntEntry
        MAX-ACCESS  not-accessible
        STATUS      current
        DESCRIPTION
            "This table represents SCB multicast configuration in ONT."
        ::= { zxGponPrivateGlobal 12 }

    zxGponSCBMCastOntEntry OBJECT-TYPE
        SYNTAX      ZxGponSCBMCastOntEntry
        MAX-ACCESS  not-accessible
        STATUS      current
        DESCRIPTION
            "It provide a SCB multicast configuration entry."
        INDEX   { zxGponSCBMCastOntSetIdx }
        ::= { zxGponSCBMCastOntTable 1 }

    ZxGponSCBMCastOntEntry ::=
        SEQUENCE {
            zxGponSCBMCastOntSetIdx       INTEGER,
            zxGponSCBMCastOntSetGroupIdx  INTEGER,
            zxGponSCBMCastOntList         ZxOntList,
            zxGponSCBMCastOntEntryStatus  RowStatus
        }

    zxGponSCBMCastOntSetIdx       OBJECT-TYPE
      SYNTAX      INTEGER
      MAX-ACCESS  not-accessible
      STATUS      current 
      DESCRIPTION 
        ""
      REFERENCE   "N/A"
      ::= { zxGponSCBMCastOntEntry 1 }

    zxGponSCBMCastOntSetGroupIdx       OBJECT-TYPE
      SYNTAX      INTEGER
      MAX-ACCESS  read-write
      STATUS      current 
      DESCRIPTION 
        "It is equal to zxGponSCBMCastGroupIdx."
      REFERENCE   "N/A"
      ::= { zxGponSCBMCastOntEntry 2 }

    zxGponSCBMCastOntList       OBJECT-TYPE
      SYNTAX      ZxOntList(SIZE (0..256))
      MAX-ACCESS  read-write
      STATUS      current 
      DESCRIPTION 
        ""
      REFERENCE   "N/A"
      ::= { zxGponSCBMCastOntEntry 3 }

    zxGponSCBMCastOntEntryStatus       OBJECT-TYPE
      SYNTAX      RowStatus
      MAX-ACCESS  read-create
      STATUS      current 
      DESCRIPTION 
        ""
      REFERENCE   "N/A"
      ::= { zxGponSCBMCastOntEntry 4 }
      
      
    zxGponPonBroadCastBandwidthInfoTable OBJECT-TYPE
        SYNTAX      SEQUENCE OF ZxGponPonBroadCastBandwidthInfoEntry
        MAX-ACCESS  not-accessible
        STATUS      current
        DESCRIPTION
            ""
        ::= { zxGponPrivateGlobal 13 }

    zxGponPonBroadCastBandwidthInfoEntry OBJECT-TYPE
        SYNTAX      ZxGponPonBroadCastBandwidthInfoEntry
        MAX-ACCESS  not-accessible
        STATUS      current
        DESCRIPTION
            ""
        INDEX   { zxGponMgmtPonOltId }
        ::= { zxGponPonBroadCastBandwidthInfoTable 1 }

    ZxGponPonBroadCastBandwidthInfoEntry ::=
        SEQUENCE {
            zxGponPonBroadCastBandwidth     INTEGER
        }

    zxGponPonBroadCastBandwidth       OBJECT-TYPE
      SYNTAX      INTEGER
      MAX-ACCESS  read-write
      STATUS      current 
      DESCRIPTION 
        "64-2609192 kbps"
      REFERENCE   "N/A"
      ::= { zxGponPonBroadCastBandwidthInfoEntry 1 }
      
      
    zxGponPonPeakBandwidthInfoTable OBJECT-TYPE
        SYNTAX      SEQUENCE OF ZxGponPonPeakBandwidthInfoEntry
        MAX-ACCESS  not-accessible
        STATUS      current
        DESCRIPTION
            ""
        ::= { zxGponPrivateGlobal 14 }

    zxGponPonPeakBandwidthInfoEntry OBJECT-TYPE
        SYNTAX      ZxGponPonPeakBandwidthInfoEntry
        MAX-ACCESS  not-accessible
        STATUS      current
        DESCRIPTION
            ""
        INDEX   { zxGponMgmtPonOltId }
        ::= {zxGponPonPeakBandwidthInfoTable 1 }

    ZxGponPonPeakBandwidthInfoEntry ::=
        SEQUENCE {
            zxGponPonPeakBandwidth     INTEGER
        }

    zxGponPonPeakBandwidth       OBJECT-TYPE
      SYNTAX      INTEGER
      MAX-ACCESS  read-write
      STATUS      current 
      DESCRIPTION 
        "64-2609192 kbps"
      REFERENCE   "N/A"
      ::= { zxGponPonPeakBandwidthInfoEntry 1 }


    zxGponGetValidIdxTable OBJECT-TYPE
        SYNTAX      SEQUENCE OF ZxGponGetValidIdxEntry
        MAX-ACCESS  not-accessible
        STATUS      current
        DESCRIPTION
            "This table represents current valid index table."
        ::= { zxGponPrivateGlobal 16 }

    zxGponGetValidIdxEntry OBJECT-TYPE
        SYNTAX      ZxGponGetValidIdxEntry
        MAX-ACCESS  not-accessible
        STATUS      current
        DESCRIPTION
            "It provide a current valid index entry."
        INDEX   { zxGponGetValidIdxTableNameIdx, zxGponMgmtPonOltId, zxGponMgmtPonOnuId, zxGponGemPortIdx }
        ::= { zxGponGetValidIdxTable 1 }

    ZxGponGetValidIdxEntry ::=
        SEQUENCE {
            zxGponGetValidIdxTableNameIdx INTEGER,
            zxGponGetValidIdxvalue        INTEGER
        }

    zxGponGetValidIdxTableNameIdx       OBJECT-TYPE
      SYNTAX      INTEGER
      MAX-ACCESS  not-accessible
      STATUS      current 
      DESCRIPTION 
        "It is a table name ID, specifical number denotes one table.
         Only these tables are valid in which it is only one integer index.
         GPON_TBLID_BWPROFILE             1
         GPON_TBLID_THRESPROFILE          2
         GPON_TBLID_TRAFFICPROFILE        3
         GPON_TBLID_FLOWCLASSPROFILE      4
         GPON_TBLID_CLASSRULEPROFILE      5
         GPON_TBLID_TRAFFICMGMTUNIT       6
         GPON_TBLID_GEMPORT               7
         GPON_TBLID_FLOW                  8
         GPON_TBLID_VOIPMEDIAPROFILE      9
         GPON_TBLID_DIALPLANTABLE         10    
         GPON_TBLID_FILTERRULE            11
         GPON_TBLID_TREATRULE             12    
         GPON_TBLID_PWPROFLIE             13 
         "
      REFERENCE   "N/A"
      ::= { zxGponGetValidIdxEntry 1 }

    zxGponGetValidIdxvalue       OBJECT-TYPE
      SYNTAX      INTEGER
      MAX-ACCESS  read-only
      STATUS      current 
      DESCRIPTION 
        "It is a valid in the table."
      REFERENCE   "N/A"
      ::= { zxGponGetValidIdxEntry 2 }

    -- this table only used for debug.
    zxGponSpiIfPmTable OBJECT-TYPE
        SYNTAX      SEQUENCE OF ZxGponSpiIfPmEntry
        MAX-ACCESS  not-accessible
        STATUS      current
        DESCRIPTION
            "This table represents SPI PM table."
        ::= { zxGponPrivateGlobal 20 }

    zxGponSpiIfPmEntry OBJECT-TYPE
        SYNTAX      ZxGponSpiIfPmEntry
        MAX-ACCESS  not-accessible
        STATUS      current
        DESCRIPTION
            "It provide a GE port SPI PM entry."
        INDEX   { zxGponMgmtPonOltId }
        ::= { zxGponSpiIfPmTable 1 }

    ZxGponSpiIfPmEntry ::=
        SEQUENCE {
            zxGponSpiIfRxFrm         Counter64,
            zxGponSpiIfRxByte        Counter64,
            zxGponSpiIfRxDiscardFrm  Counter64,
            zxGponSpiIfRxDiscardByte Counter64,
            zxGponSpiIfTxFrm         Counter64,
            zxGponSpiIfTxByte        Counter64,
            zxGponSpiIfTxDiscardFrm  Counter64,
            zxGponSpiIfTxDiscardByte Counter64 
        }

    zxGponSpiIfRxFrm OBJECT-TYPE
        SYNTAX      Counter64
        MAX-ACCESS  read-only
        STATUS      current
        DESCRIPTION
            ""
        ::= { zxGponSpiIfPmEntry 1}

    zxGponSpiIfRxByte OBJECT-TYPE
        SYNTAX      Counter64
        MAX-ACCESS  read-only
        STATUS      current
        DESCRIPTION
            ""
        ::= { zxGponSpiIfPmEntry 2}

    zxGponSpiIfRxDiscardFrm OBJECT-TYPE
        SYNTAX      Counter64
        MAX-ACCESS  read-only
        STATUS      current
        DESCRIPTION
            ""
        ::= { zxGponSpiIfPmEntry 3}

    zxGponSpiIfRxDiscardByte OBJECT-TYPE
        SYNTAX      Counter64
        MAX-ACCESS  read-only
        STATUS      current
        DESCRIPTION
            ""
        ::= { zxGponSpiIfPmEntry 4}

    zxGponSpiIfTxFrm OBJECT-TYPE
        SYNTAX      Counter64
        MAX-ACCESS  read-only
        STATUS      current
        DESCRIPTION
            ""
        ::= { zxGponSpiIfPmEntry 5}

    zxGponSpiIfTxByte OBJECT-TYPE
        SYNTAX      Counter64
        MAX-ACCESS  read-only
        STATUS      current
        DESCRIPTION
            ""
        ::= { zxGponSpiIfPmEntry 6}

    zxGponSpiIfTxDiscardFrm OBJECT-TYPE
        SYNTAX      Counter64
        MAX-ACCESS  read-only
        STATUS      current
        DESCRIPTION
            ""
        ::= { zxGponSpiIfPmEntry 7}

    zxGponSpiIfTxDiscardByte OBJECT-TYPE
        SYNTAX      Counter64
        MAX-ACCESS  read-only
        STATUS      current
        DESCRIPTION
            ""
        ::= { zxGponSpiIfPmEntry 8}

   
  zxGponPonScheduleModeInfoTable OBJECT-TYPE
        SYNTAX      SEQUENCE OF ZxGponPonScheduleModeInfoEntry
        MAX-ACCESS  not-accessible
        STATUS      current
        DESCRIPTION
            ""
        ::= { zxGponPrivateGlobal 21}

    zxGponPonScheduleModeInfoEntry OBJECT-TYPE
        SYNTAX      ZxGponPonScheduleModeInfoEntry
        MAX-ACCESS  not-accessible
        STATUS      current
        DESCRIPTION
            ""
        INDEX   { zxGponMgmtPonSlotId }
        ::= {zxGponPonScheduleModeInfoTable 1 }

    ZxGponPonScheduleModeInfoEntry ::=
        SEQUENCE {
        zxGponMgmtPonSlotId          INTEGER,
            zxGponPonScheduleMode        INTEGER
         }
    
    zxGponMgmtPonSlotId       OBJECT-TYPE
      SYNTAX      INTEGER
      MAX-ACCESS  not-accessible
      STATUS      current 
      DESCRIPTION 
        "slot id(1-6,9-14)"
      REFERENCE   "N/A"
      ::= { zxGponPonScheduleModeInfoEntry 1 }

    zxGponPonScheduleMode       OBJECT-TYPE
      SYNTAX      INTEGER
      MAX-ACCESS  read-write
      STATUS      current 
      DESCRIPTION 
        "1:onuOrGemport  2:PON"
      REFERENCE   "N/A"
      ::= { zxGponPonScheduleModeInfoEntry 2 }
     
  zxGponPon802Dot1pMapInfoTable OBJECT-TYPE
        SYNTAX      SEQUENCE OF ZxGponPon802Dot1pMapInfoEntry
        MAX-ACCESS  not-accessible
        STATUS      current
        DESCRIPTION
            ""
        ::= { zxGponPrivateGlobal 22}

    zxGponPon802Dot1pMapInfoEntry OBJECT-TYPE
        SYNTAX      ZxGponPon802Dot1pMapInfoEntry
        MAX-ACCESS  not-accessible
        STATUS      current
        DESCRIPTION
            ""
        INDEX   { zxGponMgmtPonOltId }
        ::= {zxGponPon802Dot1pMapInfoTable 1 }

    ZxGponPon802Dot1pMapInfoEntry ::=
        SEQUENCE {
            zxGponPonDot1pMapQueue0      INTEGER,
            zxGponPonDot1pMapQueue1      INTEGER,
            zxGponPonDot1pMapQueue2      INTEGER,
            zxGponPonDot1pMapQueue3      INTEGER,
            zxGponPonDot1pMapQueue4      INTEGER,
            zxGponPonDot1pMapQueue5      INTEGER,
            zxGponPonDot1pMapQueue6      INTEGER,
            zxGponPonDot1pMapQueue7      INTEGER
        }

    zxGponPonDot1pMapQueue0     OBJECT-TYPE
      SYNTAX      INTEGER
      MAX-ACCESS  read-write
      STATUS      current 
      DESCRIPTION 
        "Cos Queue No Dot1p Map to,value range [0..7]"
      REFERENCE   "N/A"
      ::= { zxGponPon802Dot1pMapInfoEntry 1 }
      
    zxGponPonDot1pMapQueue1     OBJECT-TYPE
      SYNTAX      INTEGER
      MAX-ACCESS  read-write
      STATUS      current 
      DESCRIPTION 
        "Cos Queue No Dot1p Map to,value range [0..7]"
      REFERENCE   "N/A"
      ::= { zxGponPon802Dot1pMapInfoEntry 2}
      
    zxGponPonDot1pMapQueue2     OBJECT-TYPE
      SYNTAX      INTEGER
      MAX-ACCESS  read-write
      STATUS      current 
      DESCRIPTION 
        "Cos Queue No Dot1p Map to,value range [0..7]"
      REFERENCE   "N/A"
      ::= { zxGponPon802Dot1pMapInfoEntry 3}
      
      zxGponPonDot1pMapQueue3     OBJECT-TYPE
      SYNTAX      INTEGER
      MAX-ACCESS  read-write
      STATUS      current 
      DESCRIPTION 
        "Cos Queue No Dot1p Map to,value range [0..7]"
      REFERENCE   "N/A"
      ::= { zxGponPon802Dot1pMapInfoEntry 4}
      
      zxGponPonDot1pMapQueue4     OBJECT-TYPE
      SYNTAX      INTEGER
      MAX-ACCESS  read-write
      STATUS      current 
      DESCRIPTION 
        "Cos Queue No Dot1p Map to,value range [0..7]"
      REFERENCE   "N/A"
      ::= { zxGponPon802Dot1pMapInfoEntry 5}
      
      zxGponPonDot1pMapQueue5     OBJECT-TYPE
      SYNTAX      INTEGER
      MAX-ACCESS  read-write
      STATUS      current 
      DESCRIPTION 
        "Cos Queue No Dot1p Map to,value range [0..7]"
      REFERENCE   "N/A"
      ::= { zxGponPon802Dot1pMapInfoEntry 6}
      
      zxGponPonDot1pMapQueue6     OBJECT-TYPE
      SYNTAX      INTEGER
      MAX-ACCESS  read-write
      STATUS      current 
      DESCRIPTION 
        "Cos Queue No Dot1p Map to,value range [0..7]"
      REFERENCE   "N/A"
      ::= { zxGponPon802Dot1pMapInfoEntry 7}
      
      zxGponPonDot1pMapQueue7     OBJECT-TYPE
      SYNTAX      INTEGER
      MAX-ACCESS  read-write
      STATUS      current 
      DESCRIPTION 
        "Cos Queue No Dot1p Map to,value range [0..7]"
      REFERENCE   "N/A"
      ::= { zxGponPon802Dot1pMapInfoEntry 8}
      
      
     zxGponPonWeightMgmtInfoTable OBJECT-TYPE
        SYNTAX      SEQUENCE OF ZxGponPonWeightMgmtInfoEntry
        MAX-ACCESS  not-accessible
        STATUS      current
        DESCRIPTION
            ""
        ::= { zxGponPrivateGlobal 23}

    zxGponPonWeightMgmtInfoEntry OBJECT-TYPE
        SYNTAX      ZxGponPonWeightMgmtInfoEntry
        MAX-ACCESS  not-accessible
        STATUS      current
        DESCRIPTION
            ""
        INDEX   { zxGponMgmtPonOltId }
        ::= {zxGponPonWeightMgmtInfoTable 1 }

    ZxGponPonWeightMgmtInfoEntry ::=
        SEQUENCE {
            zxGponPonWeightMgmtQueue0      INTEGER,
            zxGponPonWeightMgmtQueue1      INTEGER,
            zxGponPonWeightMgmtQueue2      INTEGER,
            zxGponPonWeightMgmtQueue3      INTEGER,
            zxGponPonWeightMgmtQueue4      INTEGER,
            zxGponPonWeightMgmtQueue5      INTEGER,
            zxGponPonWeightMgmtQueue6      INTEGER,
            zxGponPonWeightMgmtQueue7      INTEGER
        }

    zxGponPonWeightMgmtQueue0     OBJECT-TYPE
      SYNTAX      INTEGER
      MAX-ACCESS  read-write
      STATUS      current 
      DESCRIPTION 
        "queue0 weight value[0..255]"
      REFERENCE   "N/A"
      ::= { zxGponPonWeightMgmtInfoEntry 1 }
      
    zxGponPonWeightMgmtQueue1     OBJECT-TYPE
      SYNTAX      INTEGER
      MAX-ACCESS  read-write
      STATUS      current 
      DESCRIPTION 
        "queue1 weight value[0..255]"
      REFERENCE   "N/A"
      ::= { zxGponPonWeightMgmtInfoEntry 2 }
      
    zxGponPonWeightMgmtQueue2     OBJECT-TYPE
      SYNTAX      INTEGER
      MAX-ACCESS  read-write
      STATUS      current 
      DESCRIPTION 
        "queue2 weight value[0..255]"
      REFERENCE   "N/A"
      ::= { zxGponPonWeightMgmtInfoEntry 3 }
      
      zxGponPonWeightMgmtQueue3     OBJECT-TYPE
      SYNTAX      INTEGER
      MAX-ACCESS  read-write
      STATUS      current 
      DESCRIPTION 
        "queue3 weight value[0..255]"
      REFERENCE   "N/A"
      ::= { zxGponPonWeightMgmtInfoEntry 4 }
      
      zxGponPonWeightMgmtQueue4     OBJECT-TYPE
      SYNTAX      INTEGER
      MAX-ACCESS  read-write
      STATUS      current 
      DESCRIPTION 
        "queue4 weight value[0..255]"
      REFERENCE   "N/A"
      ::= { zxGponPonWeightMgmtInfoEntry 5 }
      
      zxGponPonWeightMgmtQueue5     OBJECT-TYPE
      SYNTAX      INTEGER
      MAX-ACCESS  read-write
      STATUS      current 
      DESCRIPTION 
        "queue5 weight value[0..255]"
      REFERENCE   "N/A"
      ::= { zxGponPonWeightMgmtInfoEntry 6 }
      
      zxGponPonWeightMgmtQueue6     OBJECT-TYPE
      SYNTAX      INTEGER
      MAX-ACCESS  read-write
      STATUS      current 
      DESCRIPTION 
        "queue6 weight value[0..255]"
      REFERENCE   "N/A"
      ::= { zxGponPonWeightMgmtInfoEntry 7 }
      
      zxGponPonWeightMgmtQueue7     OBJECT-TYPE
      SYNTAX      INTEGER
      MAX-ACCESS  read-write
      STATUS      current 
      DESCRIPTION 
        "queue7 weight value[0..255]"
      REFERENCE   "N/A"
      ::= { zxGponPonWeightMgmtInfoEntry 8 }
      
      
    zxGponFloodBroadCastEnableInfoTable OBJECT-TYPE
        SYNTAX      SEQUENCE OF ZxGponFloodBroadCastEnableInfoEntry
        MAX-ACCESS  not-accessible
        STATUS      current
        DESCRIPTION
            ""
        ::= { zxGponPrivateGlobal 24}

    zxGponFloodBroadCastEnableInfoEntry OBJECT-TYPE
        SYNTAX      ZxGponFloodBroadCastEnableInfoEntry
        MAX-ACCESS  not-accessible
        STATUS      current
        DESCRIPTION
            ""
        INDEX   { zxGponMgmtPonSlotId }
        ::= {zxGponFloodBroadCastEnableInfoTable 1 }

    ZxGponFloodBroadCastEnableInfoEntry ::=
          SEQUENCE {
              zxGponFloodEnable            INTEGER,
              zxGponBroadcastEnable        INTEGER
         }
           
    zxGponFloodEnable       OBJECT-TYPE
      SYNTAX      INTEGER
      MAX-ACCESS  read-write
      STATUS      current 
      DESCRIPTION 
        "1:enalbe  2:disable"
      REFERENCE   "N/A"
      ::= { zxGponFloodBroadCastEnableInfoEntry 1 }

     zxGponBroadcastEnable       OBJECT-TYPE
      SYNTAX      INTEGER
      MAX-ACCESS  read-write
      STATUS      current 
      DESCRIPTION 
        "1:enable  2:disable"
      REFERENCE   "N/A"
      ::= { zxGponFloodBroadCastEnableInfoEntry 2 }
    
    zxGponSlotOpticalDetectInfoTable OBJECT-TYPE
        SYNTAX      SEQUENCE OF ZxGponSlotOpticalDetectInfoEntry
        MAX-ACCESS  not-accessible
        STATUS      current
        DESCRIPTION
            ""
        ::= { zxGponPrivateGlobal 25}

    zxGponSlotOpticalDetectInfoEntry OBJECT-TYPE
        SYNTAX      ZxGponSlotOpticalDetectInfoEntry
        MAX-ACCESS  not-accessible
        STATUS      current
        DESCRIPTION
            ""
        INDEX   { zxGponMgmtPonSlotId }
        ::= {zxGponSlotOpticalDetectInfoTable 1 }

    ZxGponSlotOpticalDetectInfoEntry ::=
          SEQUENCE {
              zxGponSlotOpticalDetect           TruthValue
              }
           
    zxGponSlotOpticalDetect       OBJECT-TYPE
      SYNTAX      TruthValue
      MAX-ACCESS  read-write
      STATUS      current 
      DESCRIPTION 
        "enable/disable pon Optical-Always-On detection."
      REFERENCE   "N/A"
      ::= { zxGponSlotOpticalDetectInfoEntry 1 }
 
    zxGponPortLocOnuIdFormat OBJECT-TYPE
        SYNTAX      INTEGER{
                    onusn(1),
                    onuid(2),
                    onuname(3)
        }
        MAX-ACCESS  read-write
        STATUS      current
        DESCRIPTION
                "Configure DHCP Option82 ONU ID and PPPOE Plus ONU ID Format."
        ::= {  zxGponPrivateGlobal 40}
        
--zxGponStandardOlt.mi2
    zxGponStandardOlt OBJECT IDENTIFIER ::= { zxGponRootMib 12 }

    zxGponOltInfoTable OBJECT-TYPE
        SYNTAX      SEQUENCE OF ZxGponOltInfoEntry
        MAX-ACCESS  not-accessible
        STATUS      current
        DESCRIPTION
            "" 
        REFERENCE
            ""
        ::= { zxGponStandardOlt 1 }

    zxGponOltInfoEntry OBJECT-TYPE
        SYNTAX      ZxGponOltInfoEntry
        MAX-ACCESS  not-accessible
        STATUS      current
        DESCRIPTION
            ""
        INDEX   { zxGponMgmtPonOltId }
        ::= { zxGponOltInfoTable 1 }

    ZxGponOltInfoEntry ::=
        SEQUENCE {
            zxGponOltInfoPONTransRateType       INTEGER,
            zxGponOltInfoOpticalTransceiverType INTEGER,
            zxGponOltInfoOntMgmtMode            INTEGER,
            zxGponOltInfoCurrentStatus          INTEGER,
            zxGponOltInfoFECEnable              INTEGER,
            zxGponOltInfoDBAEnable              INTEGER
        }

   zxGponOltInfoPONTransRateType OBJECT-TYPE
        SYNTAX      INTEGER{
                    ratetype1(1),
                    ratetype2(2),
                    ratetype3(3),
                    ratetype4(4),
                    ratetype5(5),
                    ratetype6(6),
                    ratetype7(7)
                    }
        MAX-ACCESS  read-only
        STATUS      current
        DESCRIPTION
            "This attribute indicate not the actual bytes rate, but the base transfer type. the map of 
             ratetype and actual bytes rate as blow:
                ratetype1(1)----------- Up 155M, Down 1.2G
                ratetype2(2)----------- Up 622M, Down 1.2G
                ratetype3(3)----------- Up 1.2G, Down 1.2G
                ratetype4(4)----------- Up 155M, Dowm 2.4G
                ratetype5(5)----------- Up 622M, Dowm 2.4G
                ratetype6(6)----------- Up 1.2G, Down 2.4G
                ratetype7(7)----------- Up 2.4G, Dowm 2.4G
             "
        ::= { zxGponOltInfoEntry 1}

   zxGponOltInfoOpticalTransceiverType OBJECT-TYPE
        SYNTAX      INTEGER
        MAX-ACCESS  read-only
        STATUS      current
        DESCRIPTION
            ""
        ::= { zxGponOltInfoEntry 2}

   zxGponOltInfoOntMgmtMode OBJECT-TYPE
        SYNTAX      INTEGER
        MAX-ACCESS  read-only
        STATUS      current
        DESCRIPTION
            ""
        ::= { zxGponOltInfoEntry 3}
        
   zxGponOltInfoCurrentStatus OBJECT-TYPE
        SYNTAX      INTEGER
        MAX-ACCESS  read-only
        STATUS      current
        DESCRIPTION
            ""
        ::= { zxGponOltInfoEntry 4}

   zxGponOltInfoFECEnable OBJECT-TYPE
        SYNTAX      INTEGER{
                    enable(1),
                    disable(2)
                    }
        MAX-ACCESS  read-only
        STATUS      current
        DESCRIPTION
            "Support ability, FEC"
        ::= { zxGponOltInfoEntry 5}

   zxGponOltInfoDBAEnable OBJECT-TYPE
        SYNTAX      INTEGER{
                    enable(1),
                    disable(2)
                    }
        MAX-ACCESS  read-only
        STATUS      current
        DESCRIPTION
            "Support ability, DBA"
        ::= { zxGponOltInfoEntry 6}


    zxGponOltStatisticInfoTable OBJECT-TYPE
        SYNTAX      SEQUENCE OF ZxGponOltStatisticInfoEntry
        MAX-ACCESS  not-accessible
        STATUS      current
        DESCRIPTION
            "" 
        REFERENCE
            ""
        ::= { zxGponStandardOlt 2 }

    zxGponOltStatisticInfoEntry OBJECT-TYPE
        SYNTAX      ZxGponOltStatisticInfoEntry
        MAX-ACCESS  not-accessible
        STATUS      current
        DESCRIPTION
            ""
        INDEX   { zxGponMgmtPonOltId }
        ::= { zxGponOltStatisticInfoTable 1 }

    ZxGponOltStatisticInfoEntry ::=
        SEQUENCE {
            zxGponOltStatisticInfoSuperframeCounter Counter64,
            zxGponOltStatisticInfoBIPCounter        Counter64
        }

   zxGponOltStatisticInfoSuperframeCounter OBJECT-TYPE
        SYNTAX      Counter64
        MAX-ACCESS  read-only
        STATUS      current
        DESCRIPTION
            "To provide error tolerance, the OLT must implement a local superframe counter"
        ::= { zxGponOltStatisticInfoEntry 1}

   zxGponOltStatisticInfoBIPCounter OBJECT-TYPE
        SYNTAX      Counter64
        MAX-ACCESS  read-only
        STATUS      current
        DESCRIPTION
            "The received BIP8 is compared with the calculated BIP8 on the received stream. In case 
             of a difference ERR counter is incremented"
        ::= { zxGponOltStatisticInfoEntry 2}


    zxGponOltPmStatisticInfoTable OBJECT-TYPE
        SYNTAX      SEQUENCE OF ZxGponOltPmStatisticInfoEntry
        MAX-ACCESS  not-accessible
        STATUS      current
        DESCRIPTION
            "" 
        REFERENCE
            ""
        ::= { zxGponStandardOlt 4 }

    zxGponOltPmStatisticInfoEntry OBJECT-TYPE
        SYNTAX      ZxGponOltPmStatisticInfoEntry
        MAX-ACCESS  not-accessible
        STATUS      current
        DESCRIPTION
            ""
        INDEX   { zxGponMgmtPonOltId }
        ::= { zxGponOltPmStatisticInfoTable 1 }

    ZxGponOltPmStatisticInfoEntry ::=
        SEQUENCE {
            zxGponOltPmStatisticInfoGemPacketTx               INTEGER,
            zxGponOltPmStatisticInfoGemPacketRxCorIdle        INTEGER,
            zxGponOltPmStatisticInfoGemPacketRxCorNoIdle      INTEGER,
            zxGponOltPmStatisticInfoGemPacketRxErr            INTEGER,
            zxGponOltPmStatisticInfoGemPayloadBytesRx         INTEGER,
            zxGponOltPmStatisticInfoEthPacketTx               INTEGER,
            zxGponOltPmStatisticInfoEthPacketRxCor            INTEGER,
            zxGponOltPmStatisticInfoEthPacketRxErr            INTEGER,
            zxGponOltPmStatisticInfoOmciPacketTx              INTEGER,
            zxGponOltPmStatisticInfoOmciPacketRxCor           INTEGER,
            zxGponOltPmStatisticInfoOmciPacketRxErr           INTEGER,
            zxGponOltPmStatisticInfoPloamTx                   INTEGER,
            zxGponOltPmStatisticInfoPloamRxCor                INTEGER,
            zxGponOltPmStatisticInfoPloamRxErr                INTEGER,
            zxGponOltPmStatisticInfoERR                       INTEGER,
            zxGponOltPmStatisticInfoREI                       INTEGER 
        }

   zxGponOltPmStatisticInfoGemPacketTx OBJECT-TYPE
        SYNTAX      INTEGER
        MAX-ACCESS  read-only
        STATUS      current
        DESCRIPTION
            ""
        ::= { zxGponOltPmStatisticInfoEntry 1}

   zxGponOltPmStatisticInfoGemPacketRxCorIdle OBJECT-TYPE
        SYNTAX      INTEGER
        MAX-ACCESS  read-only
        STATUS      current
        DESCRIPTION
            ""
        ::= { zxGponOltPmStatisticInfoEntry 2}
        
  zxGponOltPmStatisticInfoGemPacketRxCorNoIdle OBJECT-TYPE
        SYNTAX      INTEGER
        MAX-ACCESS  read-only
        STATUS      current
        DESCRIPTION
            ""
        ::= { zxGponOltPmStatisticInfoEntry 3}
        
  zxGponOltPmStatisticInfoGemPacketRxErr OBJECT-TYPE
        SYNTAX      INTEGER
        MAX-ACCESS  read-only
        STATUS      current
        DESCRIPTION
            ""
        ::= { zxGponOltPmStatisticInfoEntry 4}
        
  zxGponOltPmStatisticInfoGemPayloadBytesRx OBJECT-TYPE
        SYNTAX      INTEGER
        MAX-ACCESS  read-only
        STATUS      current
        DESCRIPTION
            ""
        ::= { zxGponOltPmStatisticInfoEntry 5}
        
  zxGponOltPmStatisticInfoEthPacketTx OBJECT-TYPE
        SYNTAX      INTEGER
        MAX-ACCESS  read-only
        STATUS      current
        DESCRIPTION
            ""
        ::= { zxGponOltPmStatisticInfoEntry 6}
        
  zxGponOltPmStatisticInfoEthPacketRxCor OBJECT-TYPE
        SYNTAX      INTEGER
        MAX-ACCESS  read-only
        STATUS      current
        DESCRIPTION
            ""
        ::= { zxGponOltPmStatisticInfoEntry 7}
        
  zxGponOltPmStatisticInfoEthPacketRxErr OBJECT-TYPE
        SYNTAX      INTEGER
        MAX-ACCESS  read-only
        STATUS      current
        DESCRIPTION
            ""
        ::= { zxGponOltPmStatisticInfoEntry 8}
        
  zxGponOltPmStatisticInfoOmciPacketTx OBJECT-TYPE
        SYNTAX      INTEGER
        MAX-ACCESS  read-only
        STATUS      current
        DESCRIPTION
            ""
        ::= { zxGponOltPmStatisticInfoEntry 9}
        
  zxGponOltPmStatisticInfoOmciPacketRxCor OBJECT-TYPE
        SYNTAX      INTEGER
        MAX-ACCESS  read-only
        STATUS      current
        DESCRIPTION
            ""
        ::= { zxGponOltPmStatisticInfoEntry 10}
        
  zxGponOltPmStatisticInfoOmciPacketRxErr OBJECT-TYPE
        SYNTAX      INTEGER
        MAX-ACCESS  read-only
        STATUS      current
        DESCRIPTION
            ""
        ::= { zxGponOltPmStatisticInfoEntry 11}
        
  zxGponOltPmStatisticInfoPloamTx OBJECT-TYPE
        SYNTAX      INTEGER
        MAX-ACCESS  read-only
        STATUS      current
        DESCRIPTION
            ""
        ::= { zxGponOltPmStatisticInfoEntry 12}
        
  zxGponOltPmStatisticInfoPloamRxCor OBJECT-TYPE
        SYNTAX      INTEGER
        MAX-ACCESS  read-only
        STATUS      current
        DESCRIPTION
            ""
        ::= { zxGponOltPmStatisticInfoEntry 13}
        
  zxGponOltPmStatisticInfoPloamRxErr OBJECT-TYPE
        SYNTAX      INTEGER
        MAX-ACCESS  read-only
        STATUS      current
        DESCRIPTION
            ""
        ::= { zxGponOltPmStatisticInfoEntry 14}
        
  zxGponOltPmStatisticInfoERR OBJECT-TYPE
        SYNTAX      INTEGER
        MAX-ACCESS  read-only
        STATUS      current
        DESCRIPTION
            ""
        ::= { zxGponOltPmStatisticInfoEntry 15}
        
  zxGponOltPmStatisticInfoREI OBJECT-TYPE
        SYNTAX      INTEGER
        MAX-ACCESS  read-only
        STATUS      current
        DESCRIPTION
            ""
        ::= { zxGponOltPmStatisticInfoEntry 16}
        
        
    zxGponDownFrameInfoTable OBJECT-TYPE
        SYNTAX      SEQUENCE OF ZxGponDownFrameInfoEntry
        MAX-ACCESS  not-accessible
        STATUS      current
        DESCRIPTION
            "" 
        REFERENCE
            ""
        ::= { zxGponStandardOlt 3 }

    zxGponDownFrameInfoEntry OBJECT-TYPE
        SYNTAX      ZxGponDownFrameInfoEntry
        MAX-ACCESS  not-accessible
        STATUS      current
        DESCRIPTION
            ""
        INDEX   { zxGponMgmtPonOltId }
        ::= { zxGponDownFrameInfoTable 1 }

    ZxGponDownFrameInfoEntry ::=
        SEQUENCE {
            zxGponDownFrameInfoServices         INTEGER,
            zxGponDownFrameInfoSIMinGranularity INTEGER,
            zxGponDownFrameInfoDbaMethod        INTEGER,
            zxGponDownFrameInfoScramblingEnable TruthValue,
            zxGponDownFrameInfoFECEnable        TruthValue,
            zxGponDownFrameInfoOnuSendDBRuMode  INTEGER
        }

   zxGponDownFrameInfoServices OBJECT-TYPE
        SYNTAX      INTEGER{
                    atm(1),
                    gem(2),
                    both(3)
                    }
        MAX-ACCESS  read-write
        STATUS      current
        DESCRIPTION
            ""
        ::= { zxGponDownFrameInfoEntry 1}

   zxGponDownFrameInfoSIMinGranularity OBJECT-TYPE
        SYNTAX      INTEGER
        MAX-ACCESS  read-write
        STATUS      current
        DESCRIPTION
            "The pointers are given in units of bytes, allowing the OLT to control the medium 
             at an effective static bandwidth granularity of 64 kbit/s."
        ::= { zxGponDownFrameInfoEntry 2}
        
   zxGponDownFrameInfoDbaMethod OBJECT-TYPE
        SYNTAX      INTEGER{
                    sr(1),
                    nsr(2)
                    }
        MAX-ACCESS  read-write
        STATUS      current
        DESCRIPTION
            "This attribute present the method of DBA(Dynamic Bandwidth Assignment), it value can be either
             sr(Status Reporting) or nsr(Non Status Reporting)"
        ::= { zxGponDownFrameInfoEntry 3}

   zxGponDownFrameInfoScramblingEnable OBJECT-TYPE
        SYNTAX      TruthValue
        MAX-ACCESS  read-write
        STATUS      current
        DESCRIPTION
            "This attribute is used to activate/deactivate the ATM cell scrambling function. This 
             attribute is only present for ATM interfaces where ATM cell scrambling may be controlled, 
             i.e. enabled(1) or disabled(2). Upon autonomous instantiation, this attribute is set 
             to 'enabled'."
        ::= { zxGponDownFrameInfoEntry 4}

   zxGponDownFrameInfoFECEnable OBJECT-TYPE
        SYNTAX      TruthValue
        MAX-ACCESS  read-write
        STATUS      current
        DESCRIPTION
            ""
        ::= { zxGponDownFrameInfoEntry 5}

   zxGponDownFrameInfoOnuSendDBRuMode OBJECT-TYPE
        SYNTAX      INTEGER{
                    notsend(1),
                    mode0(2),
                    mode1(3),
                    mode2(4)
                    }
        MAX-ACCESS  read-write
        STATUS      current
        DESCRIPTION
            "Depending on the contents of these value, the ONU will send the DBRu corresponding to the 
             allocation ID or not.  The code points defined are: 
                                1: Do not send DBRu at all.
                                2: Send the 'mode 0' DBRu (two bytes).
                                3: Send the 'mode 1' DBRu (three bytes). 
                                4: Send the 'mode 2' DBRu (five bytes). 
            The description of the syntax of the different DBRu's is given in section 8.4.  Note that 
            the ONU must respond with the required number of bytes, regardless of what mode it 
            actually supports."
        ::= { zxGponDownFrameInfoEntry 6}


    zxGponFindOnuTimerTable OBJECT-TYPE
        SYNTAX      SEQUENCE OF ZxGponFindOnuTimerEntry
        MAX-ACCESS  not-accessible
        STATUS      current
        DESCRIPTION
            "" 
        REFERENCE
            ""
        ::= { zxGponStandardOlt 7 }

    zxGponFindOnuTimerEntry OBJECT-TYPE
        SYNTAX      ZxGponFindOnuTimerEntry
        MAX-ACCESS  not-accessible
        STATUS      current
        DESCRIPTION
            ""
        INDEX   { zxGponMgmtPonOltId }
        ::= { zxGponFindOnuTimerTable 1 }

    ZxGponFindOnuTimerEntry ::=
        SEQUENCE {
            zxGPonFindOnuTimerNewOnt          INTEGER,
            zxGponFindOnuTimerMissingOnt      INTEGER,
            zxGPonFindOnuTimerOpenWindowFrame INTEGER
        }

   zxGPonFindOnuTimerNewOnt OBJECT-TYPE
        SYNTAX      INTEGER
        MAX-ACCESS  read-write
        STATUS      current
        DESCRIPTION
            ""
        ::= { zxGponFindOnuTimerEntry 1}

   zxGponFindOnuTimerMissingOnt OBJECT-TYPE
        SYNTAX      INTEGER
        MAX-ACCESS  read-write
        STATUS      current
        DESCRIPTION
            ""
        ::= { zxGponFindOnuTimerEntry 2}

   zxGPonFindOnuTimerOpenWindowFrame OBJECT-TYPE
        SYNTAX      INTEGER
        MAX-ACCESS  read-write
        STATUS      current
        DESCRIPTION
            ""
        ::= { zxGponFindOnuTimerEntry 3}


    zxGponOltAlarmTable OBJECT-TYPE
        SYNTAX      SEQUENCE OF ZxGponOltAlarmEntry
        MAX-ACCESS  not-accessible
        STATUS      current
        DESCRIPTION
            "" 
        REFERENCE
            ""
        ::= { zxGponStandardOlt 8 }

    zxGponOltAlarmEntry OBJECT-TYPE
        SYNTAX      ZxGponOltAlarmEntry
        MAX-ACCESS  not-accessible
        STATUS      current
        DESCRIPTION
            ""
        INDEX   { zxGponMgmtPonOltId }
        ::= { zxGponOltAlarmTable 1 }

    ZxGponOltAlarmEntry ::=
        SEQUENCE {
            zxGPonOltAlarmLos     TruthValue,
            zxGponOltAlarmLosMask TruthValue,
            zxGponOltAlarmTF      TruthValue,
            zxGponOltAlarmTFMask  TruthValue
        }

   zxGPonOltAlarmLos OBJECT-TYPE
        SYNTAX      TruthValue
        MAX-ACCESS  read-only
        STATUS      current
        DESCRIPTION
            ""
        ::= { zxGponOltAlarmEntry 1}

   zxGponOltAlarmLosMask OBJECT-TYPE
        SYNTAX      TruthValue
        MAX-ACCESS  read-write
        STATUS      current
        DESCRIPTION
            ""
        ::= { zxGponOltAlarmEntry 2}

   zxGponOltAlarmTF OBJECT-TYPE
        SYNTAX      TruthValue
        MAX-ACCESS  read-only
        STATUS      current
        DESCRIPTION
            ""
        ::= { zxGponOltAlarmEntry 3}

   zxGponOltAlarmTFMask OBJECT-TYPE
        SYNTAX      TruthValue
        MAX-ACCESS  read-write
        STATUS      current
        DESCRIPTION
            ""
        ::= { zxGponOltAlarmEntry 4}


    zxGponOntUpAlarmOltSideTable OBJECT-TYPE
        SYNTAX      SEQUENCE OF ZxGponOntUpAlarmOltSideEntry
        MAX-ACCESS  not-accessible
        STATUS      current
        DESCRIPTION
            "" 
        REFERENCE
            ""
        ::= { zxGponStandardOlt 9 }

    zxGponOntUpAlarmOltSideEntry OBJECT-TYPE
        SYNTAX      ZxGponOntUpAlarmOltSideEntry
        MAX-ACCESS  not-accessible
        STATUS      current
        DESCRIPTION
            ""
        INDEX   { zxGponMgmtPonOltId, zxGponMgmtPonOnuId }
        ::= { zxGponOntUpAlarmOltSideTable 1 }

    ZxGponOntUpAlarmOltSideEntry ::=
        SEQUENCE {
            zxGponOntUpAlarmOltSideLOSui         TruthValue,
            zxGponOntUpAlarmOltSideLOSuiMask     TruthValue,
            zxGponOntUpAlarmOltSideLOFui         TruthValue,
            zxGponOntUpAlarmOltSideLOFuiMask     TruthValue,
            zxGponOntUpAlarmOltSideDOWui         TruthValue,
            zxGponOntUpAlarmOltSideDOWuiMask     TruthValue,
            zxGponOntUpAlarmOltSideSFui          TruthValue,
            zxGponOntUpAlarmOltSideSFuiMask      TruthValue,
            zxGponOntUpAlarmOltSideSDui          TruthValue,
            zxGponOntUpAlarmOltSideSDuiMask      TruthValue,
            zxGponOntUpAlarmOltSideLCDAui        TruthValue,
            zxGponOntUpAlarmOltSideLCDAuiMask    TruthValue,
            zxGponOntUpAlarmOltSideLCDGui        TruthValue,
            zxGponOntUpAlarmOltSideLCDGuiMask    TruthValue,
            zxGponOntUpAlarmOltSideRDIui         TruthValue,
            zxGponOntUpAlarmOltSideRDIuiMask     TruthValue,
            zxGponOntUpAlarmOltSideSUFui         TruthValue,
            zxGponOntUpAlarmOltSideSUFuiMask     TruthValue,
            zxGponOntUpAlarmOltSideDFui          TruthValue,
            zxGponOntUpAlarmOltSideDFuiMask      TruthValue,
            zxGponOntUpAlarmOltSideLOAui         TruthValue,
            zxGponOntUpAlarmOltSideLOAuiMask     TruthValue,
            zxGponOntUpAlarmOltSideDGui          TruthValue,
            zxGponOntUpAlarmOltSideDGuiMask      TruthValue,
            zxGponOntUpAlarmOltSideLOAMui        TruthValue,
            zxGponOntUpAlarmOltSideLOAMuiMask    TruthValue,
            zxGponOntUpAlarmOltSideMEMui         TruthValue,
            zxGponOntUpAlarmOltSideMEMuiMask     TruthValue,
            zxGponOntUpAlarmOltSideMISui         TruthValue,
            zxGponOntUpAlarmOltSideMISuiMask     TruthValue,
            zxGponOntUpAlarmOltSidePEEui         TruthValue,
            zxGponOntUpAlarmOltSidePEEuiMask     TruthValue
        }

   zxGponOntUpAlarmOltSideLOSui OBJECT-TYPE
        SYNTAX      TruthValue
        MAX-ACCESS  read-only
        STATUS      current
        DESCRIPTION
            "Loss of signal for ONUi
             Detection condition : No valid optical signal from ONU when it was expected during M 
                                   consecutive frames. (M is configurable. Recommended value is 4)
             Action              : Generate Loss_of_phy_layer_I notification.
             Cancel condition    : When the OLT receives a valid optical signal from ONUi 
            "
        ::= { zxGponOntUpAlarmOltSideEntry 1}

   zxGponOntUpAlarmOltSideLOSuiMask OBJECT-TYPE
        SYNTAX      TruthValue
        MAX-ACCESS  read-write
        STATUS      current
        DESCRIPTION
            "Loss of signal for ONUi mask"
        ::= { zxGponOntUpAlarmOltSideEntry 2}

   zxGponOntUpAlarmOltSideLOFui OBJECT-TYPE
        SYNTAX      TruthValue
        MAX-ACCESS  read-only
        STATUS      current
        DESCRIPTION
            "Loss of Frame of ONUi
             Detection condition : When 4 consecutive invalid delimiters from ONUi are received.
             Action              : Send 3 times Deactivate_ONU-ID messages. Generate Loss_of_phy_layer_I 
                                   notification.
             Cancel condition    : When frame delineation for ONUi is achieved in the operating state.
            "
        ::= { zxGponOntUpAlarmOltSideEntry 3}

   zxGponOntUpAlarmOltSideLOFuiMask OBJECT-TYPE
        SYNTAX      TruthValue
        MAX-ACCESS  read-write
        STATUS      current
        DESCRIPTION
            "Loss of Frame of ONUi mask"
        ::= { zxGponOntUpAlarmOltSideEntry 4}

   zxGponOntUpAlarmOltSideDOWui OBJECT-TYPE
        SYNTAX      TruthValue
        MAX-ACCESS  read-only
        STATUS      current
        DESCRIPTION
            "Drift of Window of ONUi
             Detection condition : An ONU transmission is received at an unexpected place within the U/S 
                                   virtual frame. DOWi means the phase has shifted but is correctable 
                                   via modified EqD 
             Action              : Send modified EqD to the ONUi
             Cancel condition    : When the OLT receives the ONUi Transmission in the correct position.
            "
        ::= { zxGponOntUpAlarmOltSideEntry 5}

   zxGponOntUpAlarmOltSideDOWuiMask OBJECT-TYPE
        SYNTAX      TruthValue
        MAX-ACCESS  read-write
        STATUS      current
        DESCRIPTION
            "Drift of Window of ONUi mask"
        ::= { zxGponOntUpAlarmOltSideEntry 6}

   zxGponOntUpAlarmOltSideSFui OBJECT-TYPE
        SYNTAX      TruthValue
        MAX-ACCESS  read-only
        STATUS      current
        DESCRIPTION
            "Signal Fail of ONUi
             Detection condition : When the upstream BER of ONUi becomes ?10?y, this state is entered. Y 
                                   is configurable in the range of 3 to 8
             Action              : Send 3 times Deactivate_ONU-ID messages. Generate Loss_of_phy_layer_I 
                                   notification.
             Cancel condition    : When the upstream BER of ONUi becomes <10?y+1, this state is cleared.
            "
        ::= { zxGponOntUpAlarmOltSideEntry 7}

   zxGponOntUpAlarmOltSideSFuiMask OBJECT-TYPE
        SYNTAX      TruthValue
        MAX-ACCESS  read-write
        STATUS      current
        DESCRIPTION
            "Signal Fail of ONUi mask"
        ::= { zxGponOntUpAlarmOltSideEntry 8}

   zxGponOntUpAlarmOltSideSDui OBJECT-TYPE
        SYNTAX      TruthValue
        MAX-ACCESS  read-only
        STATUS      current
        DESCRIPTION
            "Signal Degraded of ONUi
             Detection condition : When the upstream BER of ONUi becomes ?10?x, this state is entered. 
                                   X is configurable in the range of 4 to 9. But must be higher than 
                                   Y (SF Threshold) .
             Action              : 
             Cancel condition    : When the upstream BER of ONUi becomes <10?X+1, this state is cleared.
            "
        ::= { zxGponOntUpAlarmOltSideEntry 9}

   zxGponOntUpAlarmOltSideSDuiMask OBJECT-TYPE
        SYNTAX      TruthValue
        MAX-ACCESS  read-write
        STATUS      current
        DESCRIPTION
            "Signal Degraded of ONUi mask"
        ::= { zxGponOntUpAlarmOltSideEntry 10}

   zxGponOntUpAlarmOltSideLCDAui OBJECT-TYPE
        SYNTAX      TruthValue
        MAX-ACCESS  read-only
        STATUS      current
        DESCRIPTION
            "Loss of ATM channel delineation
             Detection condition : When 8 consecutive invalid HECs from ONUi are received.
             Action              : Send 3 times Deactivate_ONU-ID messages, Generate Loss_of_phy_layer_I 
                                   notification
             Cancel condition    : When cell delineation for ONUi is achieved
            "
        ::= { zxGponOntUpAlarmOltSideEntry 11}

   zxGponOntUpAlarmOltSideLCDAuiMask OBJECT-TYPE
        SYNTAX      TruthValue
        MAX-ACCESS  read-write
        STATUS      current
        DESCRIPTION
            "Loss of ATM channel delineation mask"
        ::= { zxGponOntUpAlarmOltSideEntry 12}

   zxGponOntUpAlarmOltSideLCDGui OBJECT-TYPE
        SYNTAX      TruthValue
        MAX-ACCESS  read-only
        STATUS      current
        DESCRIPTION
            "Loss of GEM channel delineation
             Detection condition : GEM Channel could not be delineated during 3 consecutive frames.
             Action              : Send 3 times Deactivate_ONU-ID messages,Generate Loss_of_phy_layer_I 
                                   notification
             Cancel condition    : When GEM channel delineation for ONUi is achieved
            "
        ::= { zxGponOntUpAlarmOltSideEntry 13}

   zxGponOntUpAlarmOltSideLCDGuiMask OBJECT-TYPE
        SYNTAX      TruthValue
        MAX-ACCESS  read-write
        STATUS      current
        DESCRIPTION
            "Loss of GEM channel delineation mask"
        ::= { zxGponOntUpAlarmOltSideEntry 14}

   zxGponOntUpAlarmOltSideRDIui OBJECT-TYPE
        SYNTAX      TruthValue
        MAX-ACCESS  read-only
        STATUS      current
        DESCRIPTION
            "Remote Defect Indication of ONUi
             Detection condition : When the RDI field of ONUi is asserted. The OLT transmission is 
                                   received with defects at the ONUi
             Action              : 
             Cancel condition    : When the RDI field of ONUi is de-asserted
            "
        ::= { zxGponOntUpAlarmOltSideEntry 15}

   zxGponOntUpAlarmOltSideRDIuiMask OBJECT-TYPE
        SYNTAX      TruthValue
        MAX-ACCESS  read-write
        STATUS      current
        DESCRIPTION
            "Remote Defect Indication of ONUi mask"
        ::= { zxGponOntUpAlarmOltSideEntry 16}

   zxGponOntUpAlarmOltSideSUFui OBJECT-TYPE
        SYNTAX      TruthValue
        MAX-ACCESS  read-only
        STATUS      current
        DESCRIPTION
            "Start-up Failure of ONUi
             Detection condition : The ranging of ONUi has failed n times (n = 2) while the OLT has 
                                   received optical bursts from this ONU
             Action              : Send 3 times Deactivate_ONU-ID messages.
             Cancel condition    : The ONU is ranged successfully.
            "
        ::= { zxGponOntUpAlarmOltSideEntry 17}

   zxGponOntUpAlarmOltSideSUFuiMask OBJECT-TYPE
        SYNTAX      TruthValue
        MAX-ACCESS  read-write
        STATUS      current
        DESCRIPTION
            "Start-up Failure of ONUi mask"
        ::= { zxGponOntUpAlarmOltSideEntry 18}

   zxGponOntUpAlarmOltSideDFui OBJECT-TYPE
        SYNTAX      TruthValue
        MAX-ACCESS  read-only
        STATUS      current
        DESCRIPTION
            "Deactivate Failure of ONUi
             Detection condition : The ONU does not react correctly after three Deactivate_ONU-ID messages.
             Action              : 
             Cancel condition    : Cancelled by the operator.
            "
        ::= { zxGponOntUpAlarmOltSideEntry 19}

   zxGponOntUpAlarmOltSideDFuiMask OBJECT-TYPE
        SYNTAX      TruthValue
        MAX-ACCESS  read-write
        STATUS      current
        DESCRIPTION
            "Deactivate Failure of ONUi mask"
        ::= { zxGponOntUpAlarmOltSideEntry 20}

   zxGponOntUpAlarmOltSideLOAui OBJECT-TYPE
        SYNTAX      TruthValue
        MAX-ACCESS  read-only
        STATUS      current
        DESCRIPTION
            "Loss of Acknowledge with ONUi
             Detection condition : The OLT does not receive an acknowledgement from ONUi after a set 
                                   of downstream messages that imply an upstream acknowledge.
             Action              : Send 3 times Deactivate_ONU-ID messages. Generate Loss_of_phy_layer_I 
                                   notification.
             Cancel condition    : When the OLT receives an acknowledgement from the ONU.
            "
        ::= { zxGponOntUpAlarmOltSideEntry 21}

   zxGponOntUpAlarmOltSideLOAuiMask OBJECT-TYPE
        SYNTAX      TruthValue
        MAX-ACCESS  read-write
        STATUS      current
        DESCRIPTION
            "Loss of Acknowledge with ONUi mask"
        ::= { zxGponOntUpAlarmOltSideEntry 22}

   zxGponOntUpAlarmOltSideDGui OBJECT-TYPE
        SYNTAX      TruthValue
        MAX-ACCESS  read-only
        STATUS      current
        DESCRIPTION
            "Receive Dying-Gasp of ONUi
             Detection condition : When the OLT receives DG message from ONUi, DGi is asserted.
             Action              : Ignore received alarms from this ONU. Generate Loss_of_phy_layer_I 
                                   notification.
             Cancel condition    : When the OLT receives a PLOAM message during ranging process
            "
        ::= { zxGponOntUpAlarmOltSideEntry 23}

   zxGponOntUpAlarmOltSideDGuiMask OBJECT-TYPE
        SYNTAX      TruthValue
        MAX-ACCESS  read-write
        STATUS      current
        DESCRIPTION
            "Receive Dying-Gasp of ONUi mask"
        ::= { zxGponOntUpAlarmOltSideEntry 24}

   zxGponOntUpAlarmOltSideLOAMui OBJECT-TYPE
        SYNTAX      TruthValue
        MAX-ACCESS  read-only
        STATUS      current
        DESCRIPTION
            "Loss of PLOAM for ONUi
             Detection condition : When 3 consecutive PLOAM messages of ONUi are missing after the 
                                   OLT issues SendPLOAMU request for that ONU
             Action              : Send 3 times Deactivate_ONU-ID messages. Generate Loss_of_phy_layer_I 
                                   notification.
             Cancel condition    : When the OLT receives a PLOAM message corresponding to its PLOAM flag 
                                   in the Operating state.
            "
        ::= { zxGponOntUpAlarmOltSideEntry 25}

   zxGponOntUpAlarmOltSideLOAMuiMask OBJECT-TYPE
        SYNTAX      TruthValue
        MAX-ACCESS  read-write
        STATUS      current
        DESCRIPTION
            "Loss of PLOAM for ONUi mask"
        ::= { zxGponOntUpAlarmOltSideEntry 26}

   zxGponOntUpAlarmOltSideMEMui OBJECT-TYPE
        SYNTAX      TruthValue
        MAX-ACCESS  read-only
        STATUS      current
        DESCRIPTION
            "Message_Error Message from ONUi
             Detection condition : When the OLT receives an unknown message from ONUi 
             Action              : 
             Cancel condition    : When the operator is informed.
            "
        ::= { zxGponOntUpAlarmOltSideEntry 27}

   zxGponOntUpAlarmOltSideMEMuiMask OBJECT-TYPE
        SYNTAX      TruthValue
        MAX-ACCESS  read-write
        STATUS      current
        DESCRIPTION
            "Message_Error Message from ONUi mask"
        ::= { zxGponOntUpAlarmOltSideEntry 28}

   zxGponOntUpAlarmOltSideMISui OBJECT-TYPE
        SYNTAX      TruthValue
        MAX-ACCESS  read-only
        STATUS      current
        DESCRIPTION
            "Link Mismatch of ONUi
             Detection condition : The OLT detects that the received PSTi and the transmitted 
                                   PST are different.
             Action              : 
             Cancel condition    : The OLT detects that received PSTi and the transmitted PST are the same.
            "
        ::= { zxGponOntUpAlarmOltSideEntry 29}

   zxGponOntUpAlarmOltSideMISuiMask OBJECT-TYPE
        SYNTAX      TruthValue
        MAX-ACCESS  read-write
        STATUS      current
        DESCRIPTION
            "Link Mismatch of ONUi mask"
        ::= { zxGponOntUpAlarmOltSideEntry 30}
    
   zxGponOntUpAlarmOltSidePEEui OBJECT-TYPE
        SYNTAX      TruthValue
        MAX-ACCESS  read-only
        STATUS      current
        DESCRIPTION
            "Physical Equipment Error of ONUi
             Detection condition : When the OLT receives a PEE Message from the ONU
             Action              : Generate Loss_of_physical_layer_I notification
             Cancel condition    : When the OLT doesn't receive a PEE message from the ONUi in 3 s
            "
        ::= { zxGponOntUpAlarmOltSideEntry 31}

   zxGponOntUpAlarmOltSidePEEuiMask OBJECT-TYPE
        SYNTAX      TruthValue
        MAX-ACCESS  read-write
        STATUS      current
        DESCRIPTION
            "Physical Equipment Error of ONUi mask"
        ::= { zxGponOntUpAlarmOltSideEntry 32}


    zxGponBerDowThresholdTable OBJECT-TYPE
        SYNTAX      SEQUENCE OF ZxGponBerDowThresholdEntry
        MAX-ACCESS  not-accessible
        STATUS      current
        DESCRIPTION
            "" 
        REFERENCE
            ""
        ::= { zxGponStandardOlt 10 }

    zxGponBerDowThresholdEntry OBJECT-TYPE
        SYNTAX      ZxGponBerDowThresholdEntry
        MAX-ACCESS  not-accessible
        STATUS      current
        DESCRIPTION
            ""
        INDEX   { zxGponMgmtPonOltId, zxGponMgmtPonOnuId }
        ::= { zxGponBerDowThresholdTable 1 }

    ZxGponBerDowThresholdEntry ::=
        SEQUENCE {
            zxGponBerDowThresholdSDui INTEGER,
            zxGponBerDowThresholdSFui INTEGER,
            zxGponBerDowThresholdDOWi INTEGER
        }

   zxGponBerDowThresholdSDui OBJECT-TYPE
        SYNTAX      INTEGER
        MAX-ACCESS  read-write
        STATUS      current
        DESCRIPTION
            ""
        ::= { zxGponBerDowThresholdEntry 1}

   zxGponBerDowThresholdSFui OBJECT-TYPE
        SYNTAX      INTEGER
        MAX-ACCESS  read-write
        STATUS      current
        DESCRIPTION
            ""
        ::= { zxGponBerDowThresholdEntry 2}

   zxGponBerDowThresholdDOWi OBJECT-TYPE
        SYNTAX      INTEGER
        MAX-ACCESS  read-write
        STATUS      current
        DESCRIPTION
            ""
        ::= { zxGponBerDowThresholdEntry 3}


    zxGponOntUpPmOltSideTable OBJECT-TYPE
        SYNTAX      SEQUENCE OF ZxGponOntUpPmOltSideEntry
        MAX-ACCESS  not-accessible
        STATUS      current
        DESCRIPTION
            "" 
        REFERENCE
            ""
        ::= { zxGponStandardOlt 11 }

    zxGponOntUpPmOltSideEntry OBJECT-TYPE
        SYNTAX      ZxGponOntUpPmOltSideEntry
        MAX-ACCESS  not-accessible
        STATUS      current
        DESCRIPTION
            ""
        INDEX   { zxGponMgmtPonOltId, zxGponMgmtPonOnuId }
        ::= { zxGponOntUpPmOltSideTable 1 }

    ZxGponOntUpPmOltSideEntry ::=
        SEQUENCE {
            zxGponOntUpPmOltSideERRui                Counter64,
            zxGponOntUpPmOltSideREIui                Counter64,
            zxGponOntUpPmOltSideCorrNIdleGemFramesui Counter64,
            zxGponOntUpPmOltSideCorrIdleGemFramesui  Counter64,
            zxGponOntUpPmOltSideErroredGemFramesui   Counter64,
            zxGponOntUpPmOltSideGemPayloadBytesui    Counter64,
            zxGponOntUpPmOltSideCorrectEthFramesui   Counter64,
            zxGponOntUpPmOltSideErroredEthFramesui   Counter64,
            zxGponOntUpPmOltSideTotalOmciFramesui    Counter64
        }

   zxGponOntUpPmOltSideERRui OBJECT-TYPE
        SYNTAX      Counter64
        MAX-ACCESS  read-only
        STATUS      current
        DESCRIPTION
            ""
        ::= { zxGponOntUpPmOltSideEntry 1}

   zxGponOntUpPmOltSideREIui OBJECT-TYPE
        SYNTAX      Counter64
        MAX-ACCESS  read-only
        STATUS      current
        DESCRIPTION
            ""
        ::= { zxGponOntUpPmOltSideEntry 2}

   zxGponOntUpPmOltSideCorrNIdleGemFramesui OBJECT-TYPE
        SYNTAX      Counter64
        MAX-ACCESS  read-only
        STATUS      current
        DESCRIPTION
            ""
        ::= { zxGponOntUpPmOltSideEntry 3}

   zxGponOntUpPmOltSideCorrIdleGemFramesui OBJECT-TYPE
        SYNTAX      Counter64
        MAX-ACCESS  read-only
        STATUS      current
        DESCRIPTION
            ""
        ::= { zxGponOntUpPmOltSideEntry 4}

   zxGponOntUpPmOltSideErroredGemFramesui OBJECT-TYPE
        SYNTAX      Counter64
        MAX-ACCESS  read-only
        STATUS      current
        DESCRIPTION
            ""
        ::= { zxGponOntUpPmOltSideEntry 5}

   zxGponOntUpPmOltSideGemPayloadBytesui OBJECT-TYPE
        SYNTAX      Counter64
        MAX-ACCESS  read-only
        STATUS      current
        DESCRIPTION
            ""
        ::= { zxGponOntUpPmOltSideEntry 6}

   zxGponOntUpPmOltSideCorrectEthFramesui OBJECT-TYPE
        SYNTAX      Counter64
        MAX-ACCESS  read-only
        STATUS      current
        DESCRIPTION
            ""
        ::= { zxGponOntUpPmOltSideEntry 7}

   zxGponOntUpPmOltSideErroredEthFramesui OBJECT-TYPE
        SYNTAX      Counter64
        MAX-ACCESS  read-only
        STATUS      current
        DESCRIPTION
            ""
        ::= { zxGponOntUpPmOltSideEntry 8}

   zxGponOntUpPmOltSideTotalOmciFramesui OBJECT-TYPE
        SYNTAX      Counter64
        MAX-ACCESS  read-only
        STATUS      current
        DESCRIPTION
            ""
        ::= { zxGponOntUpPmOltSideEntry 9}

    zxGponOltUpPmTable OBJECT-TYPE
        SYNTAX      SEQUENCE OF ZxGponOltUpPmEntry
        MAX-ACCESS  not-accessible
        STATUS      current
        DESCRIPTION
            "" 
        REFERENCE
            ""
        ::= { zxGponStandardOlt 12 }

    zxGponOltUpPmEntry OBJECT-TYPE
        SYNTAX      ZxGponOltUpPmEntry
        MAX-ACCESS  not-accessible
        STATUS      current
        DESCRIPTION
            ""
        INDEX   { zxGponMgmtPonOltId }
        ::= { zxGponOltUpPmTable 1 }

    ZxGponOltUpPmEntry ::=
        SEQUENCE {
            zxGponOltUpPmERRu                 Counter64,
            zxGponOltUpPmREIu                 Counter64,
            zxGponOltUpPmCorrNIdleGemFramesu  Counter64,
            zxGponOltUpPmCorrIdleGemFramesu   Counter64,
            zxGponOltUpPmErroredGemFramesu    Counter64,
            zxGponOltUpPmGemPayloadBytesu     Counter64,
            zxGponOltUpPmCorrectEthFramesu    Counter64,
            zxGponOltUpPmErroredEthFramesu    Counter64,
            zxGponOltUpPmTotalOmciFramesu     Counter64
        }

   zxGponOltUpPmERRu OBJECT-TYPE
        SYNTAX      Counter64
        MAX-ACCESS  read-only
        STATUS      current
        DESCRIPTION
            ""
        ::= { zxGponOltUpPmEntry 1}

   zxGponOltUpPmREIu OBJECT-TYPE
        SYNTAX      Counter64
        MAX-ACCESS  read-only
        STATUS      current
        DESCRIPTION
            ""
        ::= { zxGponOltUpPmEntry 2}

   zxGponOltUpPmCorrNIdleGemFramesu OBJECT-TYPE
        SYNTAX      Counter64
        MAX-ACCESS  read-only
        STATUS      current
        DESCRIPTION
            ""
        ::= { zxGponOltUpPmEntry 3}

   zxGponOltUpPmCorrIdleGemFramesu OBJECT-TYPE
        SYNTAX      Counter64
        MAX-ACCESS  read-only
        STATUS      current
        DESCRIPTION
            ""
        ::= { zxGponOltUpPmEntry 4}

   zxGponOltUpPmErroredGemFramesu OBJECT-TYPE
        SYNTAX      Counter64
        MAX-ACCESS  read-only
        STATUS      current
        DESCRIPTION
            ""
        ::= { zxGponOltUpPmEntry 5}

   zxGponOltUpPmGemPayloadBytesu OBJECT-TYPE
        SYNTAX      Counter64
        MAX-ACCESS  read-only
        STATUS      current
        DESCRIPTION
            ""
        ::= { zxGponOltUpPmEntry 6}

   zxGponOltUpPmCorrectEthFramesu OBJECT-TYPE
        SYNTAX      Counter64
        MAX-ACCESS  read-only
        STATUS      current
        DESCRIPTION
            ""
        ::= { zxGponOltUpPmEntry 7}

   zxGponOltUpPmErroredEthFramesu OBJECT-TYPE
        SYNTAX      Counter64
        MAX-ACCESS  read-only
        STATUS      current
        DESCRIPTION
            ""
        ::= { zxGponOltUpPmEntry 8}

   zxGponOltUpPmTotalOmciFramesu OBJECT-TYPE
        SYNTAX      Counter64
        MAX-ACCESS  read-only
        STATUS      current
        DESCRIPTION
            ""
        ::= { zxGponOltUpPmEntry 9}

    zxGponOltPmStatisRealtimeInfoTable OBJECT-TYPE
        SYNTAX      SEQUENCE OF ZxGponOltPmStatisRealtimeInfoEntry
        MAX-ACCESS  not-accessible
        STATUS      current
        DESCRIPTION
            "" 
        REFERENCE
            ""
        ::= { zxGponStandardOlt 13 }

    zxGponOltPmStatisRealtimeInfoEntry OBJECT-TYPE
        SYNTAX      ZxGponOltPmStatisRealtimeInfoEntry
        MAX-ACCESS  not-accessible
        STATUS      current
        DESCRIPTION
            ""
        INDEX   { zxGponMgmtPonOltId }
        ::= { zxGponOltPmStatisRealtimeInfoTable 1 }

    ZxGponOltPmStatisRealtimeInfoEntry ::=
        SEQUENCE {
            zxGponOltPmStatisInfoCorrectNonIdleGemFramesUpstream                Unsigned32,
            zxGponOltPmStatisInfoCorrectIdleGemFramesUpstream         Unsigned32,
            zxGponOltPmStatisInfoErroredGemFramesUpstream       Unsigned32,
            zxGponOltPmStatisInfoGemPayloadBytesUpstream             Unsigned32,
            zxGponOltPmStatisInfoCorrectEthernetFramesUpstream          Unsigned32,
            zxGponOltPmStatisInfoErroredEthernetFramesUpstream                Unsigned32,
            zxGponOltPmStatisInfoTotalOmciFramesUpstream             Unsigned32,
            zxGponOltPmStatisInfoERR             Unsigned32,
            zxGponOltPmStatisInfoREI               Unsigned32,
            zxGponOltPmStatisInfoValidEthernetPacketDownstream               Unsigned32,
            zxGponOltPmStatisInfoCpuPacketDownstream            Unsigned32,
            zxGponOltPmStatisInfoPloamDownstream            Unsigned32,
            zxGponOltPmStatisInfoPloamUpstream                    Unsigned32,
            zxGponOltPmStatisInfoInvalidPacketUpstream                 Unsigned32
        }

   zxGponOltPmStatisInfoCorrectNonIdleGemFramesUpstream OBJECT-TYPE
        SYNTAX      Unsigned32
        MAX-ACCESS  read-only
        STATUS      current
        DESCRIPTION
            ""
        ::= { zxGponOltPmStatisRealtimeInfoEntry 1}

   zxGponOltPmStatisInfoCorrectIdleGemFramesUpstream OBJECT-TYPE
        SYNTAX      Unsigned32
        MAX-ACCESS  read-only
        STATUS      current
        DESCRIPTION
            ""
        ::= { zxGponOltPmStatisRealtimeInfoEntry 2}

   zxGponOltPmStatisInfoErroredGemFramesUpstream OBJECT-TYPE
        SYNTAX      Unsigned32
        MAX-ACCESS  read-only
        STATUS      current
        DESCRIPTION
            ""
        ::= { zxGponOltPmStatisRealtimeInfoEntry 3}

   zxGponOltPmStatisInfoGemPayloadBytesUpstream OBJECT-TYPE
        SYNTAX      Unsigned32
        MAX-ACCESS  read-only
        STATUS      current
        DESCRIPTION
            ""
        ::= { zxGponOltPmStatisRealtimeInfoEntry 4}

   zxGponOltPmStatisInfoCorrectEthernetFramesUpstream OBJECT-TYPE
        SYNTAX      Unsigned32
        MAX-ACCESS  read-only
        STATUS      current
        DESCRIPTION
            ""
        ::= { zxGponOltPmStatisRealtimeInfoEntry 5}

   zxGponOltPmStatisInfoErroredEthernetFramesUpstream OBJECT-TYPE
        SYNTAX      Unsigned32
        MAX-ACCESS  read-only
        STATUS      current
        DESCRIPTION
            ""
        ::= { zxGponOltPmStatisRealtimeInfoEntry 6}

   zxGponOltPmStatisInfoTotalOmciFramesUpstream OBJECT-TYPE
        SYNTAX      Unsigned32
        MAX-ACCESS  read-only
        STATUS      current
        DESCRIPTION
            ""
        ::= { zxGponOltPmStatisRealtimeInfoEntry 7}

   zxGponOltPmStatisInfoERR OBJECT-TYPE
        SYNTAX      Unsigned32
        MAX-ACCESS  read-only
        STATUS      current
        DESCRIPTION
            ""
        ::= { zxGponOltPmStatisRealtimeInfoEntry 8}

   zxGponOltPmStatisInfoREI OBJECT-TYPE
        SYNTAX      Unsigned32
        MAX-ACCESS  read-only
        STATUS      current
        DESCRIPTION
            ""
        ::= { zxGponOltPmStatisRealtimeInfoEntry 9}

   zxGponOltPmStatisInfoValidEthernetPacketDownstream OBJECT-TYPE
        SYNTAX      Unsigned32
        MAX-ACCESS  read-only
        STATUS      current
        DESCRIPTION
            ""
        ::= { zxGponOltPmStatisRealtimeInfoEntry 10}

   zxGponOltPmStatisInfoCpuPacketDownstream OBJECT-TYPE
        SYNTAX      Unsigned32
        MAX-ACCESS  read-only
        STATUS      current
        DESCRIPTION
            ""
        ::= { zxGponOltPmStatisRealtimeInfoEntry 11}

   zxGponOltPmStatisInfoPloamDownstream OBJECT-TYPE
        SYNTAX      Unsigned32
        MAX-ACCESS  read-only
        STATUS      current
        DESCRIPTION
            ""
        ::= { zxGponOltPmStatisRealtimeInfoEntry 12}

   zxGponOltPmStatisInfoPloamUpstream OBJECT-TYPE
        SYNTAX      Unsigned32
        MAX-ACCESS  read-only
        STATUS      current
        DESCRIPTION
            ""
        ::= { zxGponOltPmStatisRealtimeInfoEntry 13}

   zxGponOltPmStatisInfoInvalidPacketUpstream OBJECT-TYPE
        SYNTAX      Unsigned32
        MAX-ACCESS  read-only
        STATUS      current
        DESCRIPTION
            ""
        ::= { zxGponOltPmStatisRealtimeInfoEntry 14}

    zxGponOltPmStatisHistoryInfoTable OBJECT-TYPE
        SYNTAX      SEQUENCE OF ZxGponOltPmStatisHistoryInfoEntry
        MAX-ACCESS  not-accessible
        STATUS      current
        DESCRIPTION
            "" 
        REFERENCE
            ""
        ::= { zxGponStandardOlt 14 }

    zxGponOltPmStatisHistoryInfoEntry OBJECT-TYPE
        SYNTAX      ZxGponOltPmStatisHistoryInfoEntry
        MAX-ACCESS  not-accessible
        STATUS      current
        DESCRIPTION
            ""
        INDEX   { zxGponMgmtPonOltId }
        ::= { zxGponOltPmStatisHistoryInfoTable 1 }

    ZxGponOltPmStatisHistoryInfoEntry ::=
        SEQUENCE {
            zxGponOltPmStatisHistoryInfoCorrectNonIdleGemFramesUpstream                Unsigned32,
            zxGponOltPmStatisHistoryInfoCorrectIdleGemFramesUpstream         Unsigned32,
            zxGponOltPmStatisHistoryInfoErroredGemFramesUpstream       Unsigned32,
            zxGponOltPmStatisHistoryInfoGemPayloadBytesUpstream             Unsigned32,
            zxGponOltPmStatisHistoryInfoCorrectEthernetFramesUpstream          Unsigned32,
            zxGponOltPmStatisHistoryInfoErroredEthernetFramesUpstream                Unsigned32,
            zxGponOltPmStatisHistoryInfoTotalOmciFramesUpstream             Unsigned32,
            zxGponOltPmStatisHistoryInfoERR             Unsigned32,
            zxGponOltPmStatisHistoryInfoREI               Unsigned32,
            zxGponOltPmStatisHistoryInfoValidEthernetPacketDownstream               Unsigned32,
            zxGponOltPmStatisHistoryInfoCpuPacketDownstream            Unsigned32,
            zxGponOltPmStatisHistoryInfoPloamDownstream            Unsigned32,
            zxGponOltPmStatisHistoryInfoPloamUpstream                    Unsigned32,
            zxGponOltPmStatisHistoryInfoInvalidPacketUpstream                 Unsigned32
        }

   zxGponOltPmStatisHistoryInfoCorrectNonIdleGemFramesUpstream OBJECT-TYPE
        SYNTAX      Unsigned32
        MAX-ACCESS  read-only
        STATUS      current
        DESCRIPTION
            ""
        ::= { zxGponOltPmStatisHistoryInfoEntry 1}

   zxGponOltPmStatisHistoryInfoCorrectIdleGemFramesUpstream OBJECT-TYPE
        SYNTAX      Unsigned32
        MAX-ACCESS  read-only
        STATUS      current
        DESCRIPTION
            ""
        ::= { zxGponOltPmStatisHistoryInfoEntry 2}

   zxGponOltPmStatisHistoryInfoErroredGemFramesUpstream OBJECT-TYPE
        SYNTAX      Unsigned32
        MAX-ACCESS  read-only
        STATUS      current
        DESCRIPTION
            ""
        ::= { zxGponOltPmStatisHistoryInfoEntry 3}

   zxGponOltPmStatisHistoryInfoGemPayloadBytesUpstream OBJECT-TYPE
        SYNTAX      Unsigned32
        MAX-ACCESS  read-only
        STATUS      current
        DESCRIPTION
            ""
        ::= { zxGponOltPmStatisHistoryInfoEntry 4}

   zxGponOltPmStatisHistoryInfoCorrectEthernetFramesUpstream OBJECT-TYPE
        SYNTAX      Unsigned32
        MAX-ACCESS  read-only
        STATUS      current
        DESCRIPTION
            ""
        ::= { zxGponOltPmStatisHistoryInfoEntry 5}

   zxGponOltPmStatisHistoryInfoErroredEthernetFramesUpstream OBJECT-TYPE
        SYNTAX      Unsigned32
        MAX-ACCESS  read-only
        STATUS      current
        DESCRIPTION
            ""
        ::= { zxGponOltPmStatisHistoryInfoEntry 6}

   zxGponOltPmStatisHistoryInfoTotalOmciFramesUpstream OBJECT-TYPE
        SYNTAX      Unsigned32
        MAX-ACCESS  read-only
        STATUS      current
        DESCRIPTION
            ""
        ::= { zxGponOltPmStatisHistoryInfoEntry 7}

   zxGponOltPmStatisHistoryInfoERR OBJECT-TYPE
        SYNTAX      Unsigned32
        MAX-ACCESS  read-only
        STATUS      current
        DESCRIPTION
            ""
        ::= { zxGponOltPmStatisHistoryInfoEntry 8}

   zxGponOltPmStatisHistoryInfoREI OBJECT-TYPE
        SYNTAX      Unsigned32
        MAX-ACCESS  read-only
        STATUS      current
        DESCRIPTION
            ""
        ::= { zxGponOltPmStatisHistoryInfoEntry 9}

   zxGponOltPmStatisHistoryInfoValidEthernetPacketDownstream OBJECT-TYPE
        SYNTAX      Unsigned32
        MAX-ACCESS  read-only
        STATUS      current
        DESCRIPTION
            ""
        ::= { zxGponOltPmStatisHistoryInfoEntry 10}

   zxGponOltPmStatisHistoryInfoCpuPacketDownstream OBJECT-TYPE
        SYNTAX      Unsigned32
        MAX-ACCESS  read-only
        STATUS      current
        DESCRIPTION
            ""
        ::= { zxGponOltPmStatisHistoryInfoEntry 11}

   zxGponOltPmStatisHistoryInfoPloamDownstream OBJECT-TYPE
        SYNTAX      Unsigned32
        MAX-ACCESS  read-only
        STATUS      current
        DESCRIPTION
            ""
        ::= { zxGponOltPmStatisHistoryInfoEntry 12}

   zxGponOltPmStatisHistoryInfoPloamUpstream OBJECT-TYPE
        SYNTAX      Unsigned32
        MAX-ACCESS  read-only
        STATUS      current
        DESCRIPTION
            ""
        ::= { zxGponOltPmStatisHistoryInfoEntry 13}

   zxGponOltPmStatisHistoryInfoInvalidPacketUpstream OBJECT-TYPE
        SYNTAX      Unsigned32
        MAX-ACCESS  read-only
        STATUS      current
        DESCRIPTION
            ""
        ::= { zxGponOltPmStatisHistoryInfoEntry 14}

--zxGponPrivateOlt.mi2
    VlanId ::= TEXTUAL-CONVENTION
        STATUS      current
        DESCRIPTION
            "A 12-bit VLAN ID used in the VLAN Tag header."
        SYNTAX      INTEGER (1..4094)

    zxGponPrivateOlt OBJECT IDENTIFIER ::= { zxGponRootMib 13 }

    zxGponOltPonInfoTable OBJECT-TYPE
        SYNTAX      SEQUENCE OF ZxGponOltPonInfoEntry
        MAX-ACCESS  not-accessible
        STATUS      current
        DESCRIPTION
            "" 
        REFERENCE
            "G.984.3"
        ::= { zxGponPrivateOlt 1 }

    zxGponOltPonInfoEntry OBJECT-TYPE
        SYNTAX      ZxGponOltPonInfoEntry
        MAX-ACCESS  not-accessible
        STATUS      current
        DESCRIPTION
            ""
        INDEX   { zxGponMgmtPonOltId }
        ::= { zxGponOltPonInfoTable 1 }

    ZxGponOltPonInfoEntry ::=
        SEQUENCE {
            zxGponOltPonName             OCTET STRING,
            zxGponOltPonDescription      OCTET STRING,
            zxGPonOltPonOntDefaultState  INTEGER,
            zxGPonOltPonOntDefaultPwMode INTEGER,
            zxGPonOltPonOntDefaultPw     OCTET STRING,
            zxGPonOltPonOntAuthMode      INTEGER,
            zxGPonOltPonOntSnAuthMode    INTEGER,
            zxGPonOltPonOntSnMask        OCTET STRING,
            zxGponOltPonOmccPortBase     INTEGER,
            zxGPonOltPonAdminState       INTEGER,
            zxGPonOltPonOperState        INTEGER,
            zxGponOltPonSupportMaxOnts   INTEGER,
            zxGponOltPonRealLegalOnts    INTEGER,
            zxGponOltPonRealIllegalOnts  INTEGER,
            zxGponOltPonSupportMaxTConts  INTEGER,
            zxGponOltPonRealUsedTConts   INTEGER,
            zxGponOltPonOntConfigureStatus   INTEGER
        }

   zxGponOltPonName OBJECT-TYPE
        SYNTAX      OCTET STRING(SIZE(128))
        MAX-ACCESS  read-write
        STATUS      current
        DESCRIPTION
            ""
        ::= { zxGponOltPonInfoEntry 1}

   zxGponOltPonDescription OBJECT-TYPE
        SYNTAX      OCTET STRING(SIZE(127))
        MAX-ACCESS  read-write
        STATUS      current
        DESCRIPTION
            "The definition size of description does not include the termination."
        ::= { zxGponOltPonInfoEntry 2}

   zxGPonOltPonOntDefaultState OBJECT-TYPE
        SYNTAX      INTEGER{
                    deactive(1),
                    omciready(2)
                    }
        MAX-ACCESS  read-write
        STATUS      current
        DESCRIPTION
            ""
        ::= { zxGponOltPonInfoEntry 3}

   zxGPonOltPonOntDefaultPwMode OBJECT-TYPE
        SYNTAX      INTEGER{
                    nonePw(1),
                    force(2)
                    }
        MAX-ACCESS  read-write
        STATUS      current
        DESCRIPTION
            ""
        ::= { zxGponOltPonInfoEntry 4}

   zxGPonOltPonOntDefaultPw OBJECT-TYPE
        SYNTAX      OCTET STRING(SIZE(10))
        MAX-ACCESS  read-write
        STATUS      current
        DESCRIPTION
            ""
        ::= { zxGponOltPonInfoEntry 5}

   zxGPonOltPonOntAuthMode OBJECT-TYPE
        SYNTAX      INTEGER{
                    sn(1),
                    regid(2)
                    }
        MAX-ACCESS  read-write
        STATUS      current
        DESCRIPTION
            ""
        ::= { zxGponOltPonInfoEntry 6}

   zxGPonOltPonOntSnAuthMode OBJECT-TYPE
        SYNTAX      INTEGER{
                    learn(1),
                    provision(2)
                    }
        MAX-ACCESS  read-write
        STATUS      current
        DESCRIPTION
            ""
        ::= { zxGponOltPonInfoEntry 7}

   zxGPonOltPonOntSnMask OBJECT-TYPE
        SYNTAX      OCTET STRING (SIZE (8))
        MAX-ACCESS  read-write
        STATUS      current
        DESCRIPTION
            ""
        ::= { zxGponOltPonInfoEntry 8}

   zxGponOltPonOmccPortBase OBJECT-TYPE
        SYNTAX      INTEGER
        MAX-ACCESS  read-write
        STATUS      current
        DESCRIPTION
            ""
        ::= { zxGponOltPonInfoEntry 9}

   zxGPonOltPonAdminState OBJECT-TYPE
        SYNTAX      INTEGER{
                    enable(1),
                    disable(2)
                    }
        MAX-ACCESS  read-write
        STATUS      current
        DESCRIPTION
            ""
        DEFVAL { disable }
        ::= { zxGponOltPonInfoEntry 10}
    
   zxGPonOltPonOperState OBJECT-TYPE
        SYNTAX      INTEGER{
                    enable(1),
                    disable(2)
                    }
        MAX-ACCESS  read-only
        STATUS      current
        DESCRIPTION
            ""
        DEFVAL { disable }
        ::= { zxGponOltPonInfoEntry 11}

   zxGponOltPonSupportMaxOnts OBJECT-TYPE
        SYNTAX      INTEGER
        MAX-ACCESS  read-only
        STATUS      current
        DESCRIPTION
            ""
        ::= { zxGponOltPonInfoEntry 12}

   zxGponOltPonRealLegalOnts OBJECT-TYPE
        SYNTAX      INTEGER
        MAX-ACCESS  read-only
        STATUS      current
        DESCRIPTION
            ""
        ::= { zxGponOltPonInfoEntry 13}

   zxGponOltPonRealIllegalOnts OBJECT-TYPE
        SYNTAX      INTEGER
        MAX-ACCESS  read-only
        STATUS      current
        DESCRIPTION
            ""
        ::= { zxGponOltPonInfoEntry 14}
    
   zxGponOltPonSupportMaxTConts OBJECT-TYPE
        SYNTAX      INTEGER
        MAX-ACCESS  read-only
        STATUS      current
        DESCRIPTION
            ""
        ::= { zxGponOltPonInfoEntry 15}

   zxGponOltPonRealUsedTConts OBJECT-TYPE
        SYNTAX      INTEGER
        MAX-ACCESS  read-only
        STATUS      current
        DESCRIPTION
            ""
        ::= { zxGponOltPonInfoEntry 16}

   zxGponOltPonOntConfigureStatus OBJECT-TYPE
        SYNTAX      INTEGER{
                    configured(1),
                    noconfigured(2)
                    }
        MAX-ACCESS  read-only
        STATUS      current
        DESCRIPTION
            ""
        ::= { zxGponOltPonInfoEntry 17}


    zxGponOltMgmtOperTable OBJECT-TYPE
        SYNTAX      SEQUENCE OF ZxGponOltMgmtOperEntry
        MAX-ACCESS  not-accessible
        STATUS      current
        DESCRIPTION
            "" 
        REFERENCE
            "G.984.3"
        ::= { zxGponPrivateOlt 2 }

    zxGponOltMgmtOperEntry OBJECT-TYPE
        SYNTAX      ZxGponOltMgmtOperEntry
        MAX-ACCESS  not-accessible
        STATUS      current
        DESCRIPTION
            ""
        INDEX   { zxGponMgmtPonOltId }
        ::= { zxGponOltMgmtOperTable 1 }

    ZxGponOltMgmtOperEntry ::=
        SEQUENCE {
            zxGponOltReset                  TruthValue,
            zxGponOltOff                    TruthValue,
            zxGponOltOpticalDetectOnce      TruthValue
        }

   zxGponOltReset OBJECT-TYPE
        SYNTAX      TruthValue
        MAX-ACCESS  read-write
        STATUS      current
        DESCRIPTION
            ""
        ::= { zxGponOltMgmtOperEntry 1}

   zxGponOltOff OBJECT-TYPE
        SYNTAX      TruthValue
        MAX-ACCESS  read-write
        STATUS      current
        DESCRIPTION
            ""
        ::= { zxGponOltMgmtOperEntry 2}
   
   zxGponOltOpticalDetectOnce OBJECT-TYPE
        SYNTAX      TruthValue
        MAX-ACCESS  read-write
        STATUS      current
        DESCRIPTION
            "excute olt Optical-Always-ON detect once."
        ::= { zxGponOltMgmtOperEntry 3}



    zxGponUnCfgSnOntInfoTable OBJECT-TYPE
        SYNTAX      SEQUENCE OF ZxGponUnCfgSnOntInfoEntry
        MAX-ACCESS  not-accessible
        STATUS      current
        DESCRIPTION
            "" 
        REFERENCE
            "G.984.3"
        ::= { zxGponPrivateOlt 3 }

    zxGponUnCfgSnOntInfoEntry OBJECT-TYPE
        SYNTAX      ZxGponUnCfgSnOntInfoEntry
        MAX-ACCESS  not-accessible
        STATUS      current
        DESCRIPTION
            ""
        INDEX   { zxGponMgmtPonOltId, zxGponUnCfgSnIdx }
        ::= { zxGponUnCfgSnOntInfoTable 1 }

    ZxGponUnCfgSnOntInfoEntry ::=
        SEQUENCE {
            zxGponUnCfgSnIdx       INTEGER,
            zxGponUnCfgSnOntSN     OntSerialNumber,
            zxGponUnCfgSnOntRID    OCTET STRING,
            zxGponUnCfgSnOntRtd    INTEGER,
            zxGponUnCfgSnOntPsw    OCTET STRING,
            zxGponUnCfgSnOntState  INTEGER,
            zxGponUnCfgSnOntTime   DateAndTime
        }

   zxGponUnCfgSnIdx OBJECT-TYPE
        SYNTAX      INTEGER
        MAX-ACCESS  not-accessible
        STATUS      current
        DESCRIPTION
            ""
        ::= { zxGponUnCfgSnOntInfoEntry 1}
    
   zxGponUnCfgSnOntSN OBJECT-TYPE
        SYNTAX      OntSerialNumber(SIZE (8))
        MAX-ACCESS  read-only
        STATUS      current
        DESCRIPTION
            ""
        ::= { zxGponUnCfgSnOntInfoEntry 2}
    
   zxGponUnCfgSnOntRID OBJECT-TYPE
        SYNTAX      OCTET STRING(SIZE(4))
        MAX-ACCESS  read-only
        STATUS      current
        DESCRIPTION
            "The register ID of the unconfigured ONT."
        ::= { zxGponUnCfgSnOntInfoEntry 3}

   zxGponUnCfgSnOntRtd OBJECT-TYPE
        SYNTAX      INTEGER
        MAX-ACCESS  read-only
        STATUS      current
        DESCRIPTION
            "The RTD after ranging."
        ::= { zxGponUnCfgSnOntInfoEntry 4}

   zxGponUnCfgSnOntPsw OBJECT-TYPE
        SYNTAX      OCTET STRING(SIZE(10))
        MAX-ACCESS  read-only
        STATUS      current
        DESCRIPTION
            "The password reported by the ONT."
        ::= { zxGponUnCfgSnOntInfoEntry 5}
        
   zxGponUnCfgSnOntState OBJECT-TYPE
        SYNTAX      INTEGER{
                    o1-initial(1),
                    o2-standby(2),
                    o3-powersetup(3),
                    o4-serialnumber(4),
                    o5-ranging(5),
                    o6-operation(6),
                    o7-popup(7)
                    }
        MAX-ACCESS  read-only
        STATUS      current
        DESCRIPTION
            ""
        ::= { zxGponUnCfgSnOntInfoEntry 6}

   zxGponUnCfgSnOntTime OBJECT-TYPE
        SYNTAX      DateAndTime(SIZE(8))
        MAX-ACCESS  read-only
        STATUS      current
        DESCRIPTION
            ""
        ::= { zxGponUnCfgSnOntInfoEntry 7}

    zxGponOmccInfoTable OBJECT-TYPE
        SYNTAX      SEQUENCE OF ZxGponOmccInfoEntry
        MAX-ACCESS  not-accessible
        STATUS      current
        DESCRIPTION
            "" 
        REFERENCE
            "G.984.3"
        ::= { zxGponPrivateOlt 4 }

    zxGponOmccInfoEntry OBJECT-TYPE
        SYNTAX      ZxGponOmccInfoEntry
        MAX-ACCESS  not-accessible
        STATUS      current
        DESCRIPTION
            ""
        INDEX   { zxGponMgmtPonOltId, zxGponMgmtPonOnuId }
        ::= { zxGponOmccInfoTable 1 }

    ZxGponOmccInfoEntry ::=
        SEQUENCE {
            zxGponOmccChannelNum        INTEGER,
            zxGponOmccChannelBandwidth  INTEGER,
            zxGponOmccChannelAdminState INTEGER,
            zxGponOmccChannelOpState    INTEGER
        }

   zxGponOmccChannelNum OBJECT-TYPE
        SYNTAX      INTEGER
        MAX-ACCESS  read-only
        STATUS      current
        DESCRIPTION
            ""
        ::= { zxGponOmccInfoEntry 1}

   zxGponOmccChannelBandwidth OBJECT-TYPE
        SYNTAX      INTEGER
        MAX-ACCESS  read-write
        STATUS      current
        DESCRIPTION
            ""
        ::= { zxGponOmccInfoEntry 2}

   zxGponOmccChannelAdminState OBJECT-TYPE
        SYNTAX      INTEGER{
                    enable(1),
                    disable(2)
                    }
        MAX-ACCESS  read-write
        STATUS      current
        DESCRIPTION
            ""
        ::= { zxGponOmccInfoEntry 3}

   zxGponOmccChannelOpState OBJECT-TYPE
        SYNTAX      INTEGER{
                    enable(1),
                    disable(2)
                    }
        MAX-ACCESS  read-only
        STATUS      current
        DESCRIPTION
            ""
        ::= { zxGponOmccInfoEntry 4}


    zxGponOltBitErrTable OBJECT-TYPE
        SYNTAX      SEQUENCE OF ZxGponOltBitErrEntry
        MAX-ACCESS  not-accessible
        STATUS      current
        DESCRIPTION
            "" 
        REFERENCE
            "G.984.3"
        ::= { zxGponPrivateOlt 5 }

    zxGponOltBitErrEntry OBJECT-TYPE
        SYNTAX      ZxGponOltBitErrEntry
        MAX-ACCESS  not-accessible
        STATUS      current
        DESCRIPTION
            ""
        INDEX   { zxGponMgmtPonOltId }
        ::= { zxGponOltBitErrTable 1 }

    ZxGponOltBitErrEntry ::=
        SEQUENCE {
            zxGponOltUpBerEnable          INTEGER,
            zxGponOltUpBerCalcInterval    INTEGER,
            zxGponOltDownBerEnable        INTEGER,
            zxGponOltDownBerCalcInterval  INTEGER,
            zxGponOltUpSfThreshold        INTEGER,
            zxGponOltUpSdThreshold        INTEGER
        }

   zxGponOltUpBerEnable OBJECT-TYPE
        SYNTAX      INTEGER{
                    enable(1),
                    disable(2)
                    }
        MAX-ACCESS  read-write
        STATUS      current
        DESCRIPTION
            ""
        ::= { zxGponOltBitErrEntry 1}

   zxGponOltUpBerCalcInterval OBJECT-TYPE
        SYNTAX      INTEGER
        MAX-ACCESS  read-write
        STATUS      current
        DESCRIPTION
            ""
        ::= { zxGponOltBitErrEntry 2}

   zxGponOltDownBerEnable OBJECT-TYPE
        SYNTAX      INTEGER{
                    enable(1),
                    disable(2)
                    }
        MAX-ACCESS  read-write
        STATUS      current
        DESCRIPTION
            ""
        ::= { zxGponOltBitErrEntry 3}

   zxGponOltDownBerCalcInterval OBJECT-TYPE
        SYNTAX      INTEGER
        MAX-ACCESS  read-write
        STATUS      current
        DESCRIPTION
            ""
        ::= { zxGponOltBitErrEntry 4}
        
   zxGponOltUpSfThreshold OBJECT-TYPE
        SYNTAX      INTEGER
        MAX-ACCESS  read-write
        STATUS      current
        DESCRIPTION
            ""
        ::= { zxGponOltBitErrEntry 5}
        
   zxGponOltUpSdThreshold OBJECT-TYPE
        SYNTAX      INTEGER
        MAX-ACCESS  read-write
        STATUS      current
        DESCRIPTION
            ""
        ::= { zxGponOltBitErrEntry 6}

    zxGponStaticMultiPortIdInfoTable OBJECT-TYPE
        SYNTAX      SEQUENCE OF ZxGponStaticMultiPortIdInfoEntry
        MAX-ACCESS  not-accessible
        STATUS      current
        DESCRIPTION
            "The multicast address table, about the portid information." 
        ::= { zxGponPrivateOlt 10 }

    zxGponStaticMultiPortIdInfoEntry OBJECT-TYPE
        SYNTAX      ZxGponStaticMultiPortIdInfoEntry
        MAX-ACCESS  not-accessible
        STATUS      current
        DESCRIPTION
            ""
        INDEX   { zxGponStaticMultiPortIdInfoIdx }
        ::= { zxGponStaticMultiPortIdInfoTable 1 }

    ZxGponStaticMultiPortIdInfoEntry ::=
        SEQUENCE {
            zxGponStaticMultiPortIdInfoIdx INTEGER,
            zxGponStaticMultiPortIdList    ZxPortIdList,
            zxGponStaticMultiAddrIdx       INTEGER,
            zxGponStaticMultiPortIdStatus  RowStatus
        }

   zxGponStaticMultiPortIdInfoIdx OBJECT-TYPE
        SYNTAX      INTEGER
        MAX-ACCESS  not-accessible
        STATUS      current
        DESCRIPTION
            ""
        ::= { zxGponStaticMultiPortIdInfoEntry 1}

   zxGponStaticMultiPortIdList OBJECT-TYPE
        SYNTAX      ZxPortIdList(SIZE (0..256))
        MAX-ACCESS  read-write
        STATUS      current
        DESCRIPTION
            ""
        ::= { zxGponStaticMultiPortIdInfoEntry 2}

   zxGponStaticMultiAddrIdx OBJECT-TYPE
        SYNTAX      INTEGER
        MAX-ACCESS  read-write
        STATUS      current
        DESCRIPTION
            "It is some 'zxGponStaticMulticastIdx'"
        ::= { zxGponStaticMultiPortIdInfoEntry 3}

   zxGponStaticMultiPortIdStatus OBJECT-TYPE
        SYNTAX      RowStatus
        MAX-ACCESS  read-create
        STATUS      current
        DESCRIPTION
            ""
        ::= { zxGponStaticMultiPortIdInfoEntry 4}

    zxGponStaticMulticastAddressTable OBJECT-TYPE
        SYNTAX      SEQUENCE OF ZxGponStaticMulticastAddressEntry
        MAX-ACCESS  not-accessible
        STATUS      current
        DESCRIPTION
            "The multicast address table." 
        ::= { zxGponPrivateOlt 11 }

    zxGponStaticMulticastAddressEntry OBJECT-TYPE
        SYNTAX      ZxGponStaticMulticastAddressEntry
        MAX-ACCESS  not-accessible
        STATUS      current
        DESCRIPTION
            ""
        INDEX   { zxGponStaticMulticastIdx }
        ::= { zxGponStaticMulticastAddressTable 1 }

    ZxGponStaticMulticastAddressEntry ::=
        SEQUENCE {
            zxGponStaticMulticastIdx        INTEGER,
            zxGponStaticMulticastAddress    MacAddress,
            zxGponStaticMulticastVlanId     VlanId,
            zxGponStaticMulticastPortIdIdx  ZxIndexList,
            zxGponStaticMulticastStatus     INTEGER
        }

   zxGponStaticMulticastIdx OBJECT-TYPE
        SYNTAX      INTEGER
        MAX-ACCESS  not-accessible
        STATUS      current
        DESCRIPTION
            ""
        ::= { zxGponStaticMulticastAddressEntry 1}

   zxGponStaticMulticastAddress OBJECT-TYPE
        SYNTAX      MacAddress
        MAX-ACCESS  read-create
        STATUS      current
        DESCRIPTION
            ""
        ::= { zxGponStaticMulticastAddressEntry 2}

   zxGponStaticMulticastVlanId OBJECT-TYPE
        SYNTAX      VlanId
        MAX-ACCESS  read-create
        STATUS      current
        DESCRIPTION
            ""
        ::= { zxGponStaticMulticastAddressEntry 3}

   zxGponStaticMulticastPortIdIdx OBJECT-TYPE
        SYNTAX      ZxIndexList(SIZE (0..256))
        MAX-ACCESS  read-only
        STATUS      current
        DESCRIPTION
            ""
        ::= { zxGponStaticMulticastAddressEntry 4}

   zxGponStaticMulticastStatus OBJECT-TYPE
        SYNTAX      INTEGER{
                    other(1),
                    invalid(2),
                    permanent(3),
                    deleteOnReset(4),
                    deleteOnTimeout(5)
                    }
        MAX-ACCESS  read-write
        STATUS      current
        DESCRIPTION
            ""
        ::= { zxGponStaticMulticastAddressEntry 5}
  
    zxGponMulticastAddressTable OBJECT-TYPE
        SYNTAX      SEQUENCE OF ZxGponMulticastAddressEntry
        MAX-ACCESS  not-accessible
        STATUS      current
        DESCRIPTION
            "The multicast address table." 
        ::= { zxGponPrivateOlt 12 }

    zxGponMulticastAddressEntry OBJECT-TYPE
        SYNTAX      ZxGponMulticastAddressEntry
        MAX-ACCESS  not-accessible
        STATUS      current
        DESCRIPTION
            ""
        INDEX   { zxGponMulticastAddress, zxGponMulticastVlanId, zxGponMulticastIdx }
        ::= { zxGponMulticastAddressTable 1 }

    ZxGponMulticastAddressEntry ::=
        SEQUENCE {
            zxGponMulticastAddress   MacAddress,
            zxGponMulticastVlanId    VlanId,
            zxGponMulticastIdx       INTEGER,
            zxGponMulticastPortIdIdx ZxPortIdList,
            zxGponMulticastStatus    INTEGER
        }

   zxGponMulticastAddress OBJECT-TYPE
        SYNTAX      MacAddress
        MAX-ACCESS  not-accessible
        STATUS      current
        DESCRIPTION
            ""
        ::= { zxGponMulticastAddressEntry 1}

   zxGponMulticastVlanId OBJECT-TYPE
        SYNTAX      VlanId
        MAX-ACCESS  not-accessible
        STATUS      current
        DESCRIPTION
            ""
        ::= { zxGponMulticastAddressEntry 2}

   zxGponMulticastIdx OBJECT-TYPE
        SYNTAX      INTEGER
        MAX-ACCESS  not-accessible
        STATUS      current
        DESCRIPTION
            ""
        ::= { zxGponMulticastAddressEntry 3}

   zxGponMulticastPortIdIdx OBJECT-TYPE
        SYNTAX      ZxPortIdList(SIZE (0..256))
        MAX-ACCESS  read-only
        STATUS      current
        DESCRIPTION
            ""
        ::= { zxGponMulticastAddressEntry 4}

   zxGponMulticastStatus OBJECT-TYPE
        SYNTAX      INTEGER{
                    other(1),
                    invalid(2),
                    learned(3),
                    self(4),
                    mgmt(5),
                    learnedAndMgmt(6)
                    }
        MAX-ACCESS  read-only
        STATUS      current
        DESCRIPTION
            ""
        ::= { zxGponMulticastAddressEntry 5}

    zxGponDsBFPortIdInfoTable OBJECT-TYPE
        SYNTAX      SEQUENCE OF ZxGponDsBFPortIdInfoEntry
        MAX-ACCESS  not-accessible
        STATUS      current
        DESCRIPTION
            "The down broadcast flood control table ,about these portID." 
        ::= { zxGponPrivateOlt 13 }

    zxGponDsBFPortIdInfoEntry OBJECT-TYPE
        SYNTAX      ZxGponDsBFPortIdInfoEntry
        MAX-ACCESS  not-accessible
        STATUS      current
        DESCRIPTION
            ""
        INDEX   { zxGponDsBFPortIdInfoIdx }
        ::= { zxGponDsBFPortIdInfoTable 1 }

    ZxGponDsBFPortIdInfoEntry ::=
        SEQUENCE {
            zxGponDsBFPortIdInfoIdx     INTEGER,
            zxGponDsBFPortIdInfoList    ZxPortIdList,
            zxGponDsBFPortIdInfoVlanIdx INTEGER,
            zxGponDsBFPortIdInfoStatus  RowStatus
        }

   zxGponDsBFPortIdInfoIdx OBJECT-TYPE
        SYNTAX      INTEGER
        MAX-ACCESS  not-accessible
        STATUS      current
        DESCRIPTION
            ""
        ::= { zxGponDsBFPortIdInfoEntry 1}

   zxGponDsBFPortIdInfoList OBJECT-TYPE
        SYNTAX      ZxPortIdList(SIZE (0..256))
        MAX-ACCESS  read-write
        STATUS      current
        DESCRIPTION
            ""
        ::= { zxGponDsBFPortIdInfoEntry 2}

   zxGponDsBFPortIdInfoVlanIdx OBJECT-TYPE
        SYNTAX      INTEGER
        MAX-ACCESS  read-write
        STATUS      current
        DESCRIPTION
            "It is some 'zxGponDownBroadcastFloodVlanId'"
        ::= { zxGponDsBFPortIdInfoEntry 3}

   zxGponDsBFPortIdInfoStatus OBJECT-TYPE
        SYNTAX      RowStatus
        MAX-ACCESS  read-write
        STATUS      current
        DESCRIPTION
            ""
        ::= { zxGponDsBFPortIdInfoEntry 4}

    zxGponDownBroadcastFloodTable OBJECT-TYPE
        SYNTAX      SEQUENCE OF ZxGponDownBroadcastFloodEntry
        MAX-ACCESS  not-accessible
        STATUS      current
        DESCRIPTION
            "The down broadcast flood control table." 
        ::= { zxGponPrivateOlt 14 }

    zxGponDownBroadcastFloodEntry OBJECT-TYPE
        SYNTAX      ZxGponDownBroadcastFloodEntry
        MAX-ACCESS  not-accessible
        STATUS      current
        DESCRIPTION
            ""
        INDEX   { zxGponDownBroadcastFloodVlanId }
        ::= { zxGponDownBroadcastFloodTable 1 }

    ZxGponDownBroadcastFloodEntry ::=
        SEQUENCE {
            zxGponDownBroadcastFloodVlanId      VlanId,
            zxGponDownBroadcastFloodPortList    ZxIndexList,
            zxGponDownBroadcastFloodEntryStatus RowStatus
        }

   zxGponDownBroadcastFloodVlanId OBJECT-TYPE
        SYNTAX      VlanId
        MAX-ACCESS  not-accessible
        STATUS      current
        DESCRIPTION
            ""
        ::= { zxGponDownBroadcastFloodEntry 1}

   zxGponDownBroadcastFloodPortList OBJECT-TYPE
        SYNTAX      ZxIndexList(SIZE (0..256))
        MAX-ACCESS  read-only
        STATUS      current
        DESCRIPTION
            ""
        ::= { zxGponDownBroadcastFloodEntry 2}

   zxGponDownBroadcastFloodEntryStatus OBJECT-TYPE
        SYNTAX      RowStatus
        MAX-ACCESS  read-create
        STATUS      current
        DESCRIPTION
            ""
        ::= { zxGponDownBroadcastFloodEntry 3}
   
    zxGpon8021xOnOffTable OBJECT-TYPE
        SYNTAX      SEQUENCE OF ZxGpon8021xOnOffEntry
        MAX-ACCESS  not-accessible
        STATUS      current
        DESCRIPTION
            "The portId 802.1x on-off table." 
        ::= { zxGponPrivateOlt 15 }

    zxGpon8021xOnOffEntry OBJECT-TYPE
        SYNTAX      ZxGpon8021xOnOffEntry
        MAX-ACCESS  not-accessible
        STATUS      current
        DESCRIPTION
            ""
        INDEX   { zxGpon8021xOnOffIdx }
        ::= { zxGpon8021xOnOffTable 1 }

    ZxGpon8021xOnOffEntry ::=
        SEQUENCE {
            zxGpon8021xOnOffIdx         INTEGER,
            zxGpon8021xOnOffPortId      ZxPortIdList,
            zxGpon8021xOnOffEnable      INTEGER
        }

   zxGpon8021xOnOffIdx OBJECT-TYPE
        SYNTAX      INTEGER
        MAX-ACCESS  not-accessible
        STATUS      current
        DESCRIPTION
            ""
        ::= { zxGpon8021xOnOffEntry 1}

   zxGpon8021xOnOffPortId OBJECT-TYPE
        SYNTAX      ZxPortIdList(SIZE (0..256))
        MAX-ACCESS  read-write
        STATUS      current
        DESCRIPTION
            ""
        ::= { zxGpon8021xOnOffEntry 2}

   zxGpon8021xOnOffEnable OBJECT-TYPE
        SYNTAX      INTEGER{
                    enabled(1),
                    disabled(2)
                    }
        MAX-ACCESS  read-write
        STATUS      current
        DESCRIPTION
            ""
        ::= { zxGpon8021xOnOffEntry 3}
   
zxGponOltLoopbackTestInfoTable OBJECT-TYPE
        SYNTAX      SEQUENCE OF ZxGponOltLoopbackTestInfoEntry
        MAX-ACCESS  not-accessible
        STATUS      current
        DESCRIPTION
            "" 
        ::= { zxGponPrivateOlt 16 }
    zxGponOltLoopbackTestInfoEntry OBJECT-TYPE
        SYNTAX      ZxGponOltLoopbackTestInfoEntry
        MAX-ACCESS  not-accessible
        STATUS      current
        DESCRIPTION
            ""
        INDEX   { zxGponMgmtPonOltId}
        ::= { zxGponOltLoopbackTestInfoTable 1 }

    ZxGponOltLoopbackTestInfoEntry ::=
        SEQUENCE {
            zxGponOltLoopbackTestStart                INTEGER
            }

   zxGponOltLoopbackTestStart OBJECT-TYPE
        SYNTAX      INTEGER
        MAX-ACCESS  read-write
        STATUS      current
        DESCRIPTION
            "1:start loopback test 2:stop loopback test"
        ::= { zxGponOltLoopbackTestInfoEntry 1}  
        
  zxGponOltEthSwitchTable OBJECT-TYPE
        SYNTAX      SEQUENCE OF ZxGponOltEthSwitchEntry
        MAX-ACCESS  not-accessible
        STATUS      current
        DESCRIPTION
            "ETH SWITCH PROTECT STATE table." 
        ::= { zxGponPrivateOlt 17 }

    zxGponOltEthSwitchEntry OBJECT-TYPE
        SYNTAX      ZxGponOltEthSwitchEntry
        MAX-ACCESS  not-accessible
        STATUS      current
        DESCRIPTION
            ""
        INDEX   { zxGponMgmtPonOltId }
        ::= { zxGponOltEthSwitchTable 1 }

    ZxGponOltEthSwitchEntry ::=
        SEQUENCE {
            zxGponEthSwitchProtectState   INTEGER
          }

   zxGponEthSwitchProtectState OBJECT-TYPE
        SYNTAX      INTEGER(0..1)
        MAX-ACCESS  read-write
        STATUS      current
        DESCRIPTION
            "0:DISABLE 1:ENABLE"
        ::= { zxGponOltEthSwitchEntry 1}
   
   zxGponOltScbPortTable OBJECT-TYPE
        SYNTAX      SEQUENCE OF ZxGponOltScbPortEntry
        MAX-ACCESS  not-accessible
        STATUS      current
        DESCRIPTION
            "Configure SCB PORTID table." 
        ::= { zxGponPrivateOlt 18 }

    zxGponOltScbPortEntry OBJECT-TYPE
        SYNTAX      ZxGponOltScbPortEntry
        MAX-ACCESS  not-accessible
        STATUS      current
        DESCRIPTION
            ""
        INDEX   { zxGponMgmtPonOltId }
        ::= { zxGponOltScbPortTable 1 }

    ZxGponOltScbPortEntry ::=
        SEQUENCE {
            zxGponOltScbPort   INTEGER
          }

   zxGponOltScbPort OBJECT-TYPE
        SYNTAX      INTEGER(65..4095)
        MAX-ACCESS  read-write
        STATUS      current
        DESCRIPTION
            ""
        ::= { zxGponOltScbPortEntry 1}
    zxGponEthTypeVlanMapTable OBJECT-TYPE
        SYNTAX      SEQUENCE OF ZxGponEthTypeVlanMapEntry
        MAX-ACCESS  not-accessible
        STATUS      current
        DESCRIPTION
            "Ethernet Type Map to Vlan." 
        ::= { zxGponPrivateOlt 19 }

    zxGponEthTypeVlanMapEntry OBJECT-TYPE
        SYNTAX      ZxGponEthTypeVlanMapEntry
        MAX-ACCESS  not-accessible
        STATUS      current
        DESCRIPTION
            ""
        INDEX   { zxGponMgmtPonOltId,zxGponEthTypeVlanMapEthType}
        ::= { zxGponEthTypeVlanMapTable 1 }

    ZxGponEthTypeVlanMapEntry ::=
        SEQUENCE {
            zxGponEthTypeVlanMapEthType     INTEGER,
            zxGponEthTypeVlanMapVlanId      VlanId,       
            zxGponEthTypeVlanMapEntryStatus RowStatus
          }
   
    zxGponEthTypeVlanMapEthType OBJECT-TYPE
        SYNTAX      INTEGER
        MAX-ACCESS  not-accessible
        STATUS      current
        DESCRIPTION
            "Ethernet protocol type"
        ::= { zxGponEthTypeVlanMapEntry 1}
        
   zxGponEthTypeVlanMapVlanId OBJECT-TYPE
        SYNTAX      VlanId
        MAX-ACCESS  read-write
        STATUS      current
        DESCRIPTION
            "The VLAN, which ethernet type map to."
        ::= { zxGponEthTypeVlanMapEntry 2 }  
 
   zxGponEthTypeVlanMapEntryStatus OBJECT-TYPE
        SYNTAX      RowStatus
        MAX-ACCESS  read-create
        STATUS      current
        DESCRIPTION
            "RowStatus"
        ::= { zxGponEthTypeVlanMapEntry 50 }  
   zxGponOltEthVlanSwitchTable OBJECT-TYPE
        SYNTAX      SEQUENCE OF ZxGponOltEthVlanSwitchEntry
        MAX-ACCESS  not-accessible
        STATUS      current
        DESCRIPTION
            "ETH VLAN SWITCH PROTECT STATE table." 
        ::= { zxGponPrivateOlt 20 }

    zxGponOltEthVlanSwitchEntry OBJECT-TYPE
        SYNTAX      ZxGponOltEthVlanSwitchEntry
        MAX-ACCESS  not-accessible
        STATUS      current
        DESCRIPTION
            ""
        INDEX   { zxGponMgmtPonOltId,zxGponEthSwitchVlanId  }
        ::= { zxGponOltEthVlanSwitchTable 1 }

    ZxGponOltEthVlanSwitchEntry ::=
        SEQUENCE {
            zxGponEthSwitchVlanId VlanId,
            zxGponEthVlanSwitchRowStatus   RowStatus
          }
   
    zxGponEthSwitchVlanId OBJECT-TYPE
        SYNTAX      VlanId
        MAX-ACCESS  not-accessible
        STATUS      current
        DESCRIPTION
            "The VLAN, which port attached to bridge."
        ::= { zxGponOltEthVlanSwitchEntry 1 }
        
   zxGponEthVlanSwitchRowStatus OBJECT-TYPE
        SYNTAX      RowStatus
        MAX-ACCESS  read-create
        STATUS      current
        DESCRIPTION
            "RowStatus"
        ::= { zxGponOltEthVlanSwitchEntry 2 }  

--zxGponOntEquipMgmt.mi2
    zxGponOntEquipMgmt OBJECT IDENTIFIER ::= { zxGponRootMib 21 }

    zxGponOntStatusInfoTable OBJECT-TYPE
        SYNTAX      SEQUENCE OF ZxGponOntStatusInfoEntry
        MAX-ACCESS  not-accessible
        STATUS      current
        DESCRIPTION
            "An instance of this managed entity is automatically created by 
             the ONT after initialization. After the creation of this managed 
             entity, the associated attributes are updated according to the 
             data within the ONT itself."
        REFERENCE
            "G.984.4 Section 9.1.1"
        ::= { zxGponOntEquipMgmt 1 }

    zxGponOntStatusInfoEntry OBJECT-TYPE
        SYNTAX      ZxGponOntStatusInfoEntry
        MAX-ACCESS  not-accessible
        STATUS      current
        DESCRIPTION
            "An entry in the ONT equipment status information table, 
             This managed entity represents the ONT as equipment."
        INDEX   { zxGponMgmtPonOltId, zxGponMgmtPonOnuId, zxGponOntIndex }
        ::= { zxGponOntStatusInfoTable 1 }

    ZxGponOntStatusInfoEntry ::=
        SEQUENCE {
            zxGponOntIndex            INTEGER,
            zxGponOntMeId             INTEGER,
            zxGponOntVendorId         OntVendorId,
            zxGponOntVersionId        OntVersionId,
            zxGponOntSnId             OntSerialNumber,
            zxGponOntTrafficMgmtOpt   INTEGER,
            zxGponOntVpVcConnFunOpt   INTEGER,
            zxGponOntBatteryBackup    TruthValue,
            zxGponOntAdminStatus       INTEGER,
            zxGponOntOperStatus       INTEGER
        }

    zxGponOntIndex OBJECT-TYPE
        SYNTAX      INTEGER
        MAX-ACCESS  not-accessible
        STATUS      current
        DESCRIPTION
            "An arbitrary(unique) integer for identifiying an entry
             in the ONT equipment, from 1 to M."
        ::= { zxGponOntStatusInfoEntry 1}

    zxGponOntMeId OBJECT-TYPE
        SYNTAX      INTEGER
        MAX-ACCESS  read-only
        STATUS      current
        DESCRIPTION
            "A unique number for each instance of this managed entity."
        REFERENCE
            "G.984.4 Section 9.1.1"
        ::= { zxGponOntStatusInfoEntry 2}

    zxGponOntVendorId OBJECT-TYPE
        SYNTAX      OntVendorId(SIZE (4))
        MAX-ACCESS  read-only
        STATUS      current
        DESCRIPTION
            "It identifies the vendor of the ONT."
        REFERENCE
            "G.984.4 Section 9.1.1"
        ::= { zxGponOntStatusInfoEntry 3}

    zxGponOntVersionId OBJECT-TYPE
        SYNTAX      OntVersionId(SIZE (14))
        MAX-ACCESS  read-only
        STATUS      current
        DESCRIPTION
            "It identifies the version of the ONT as defined by the vendor.
             The printable value of '0' is used when version information is 
             not available or applicable to the ONT being represented."
        REFERENCE
            "G.984.4 Section 9.1.1"
        ::= { zxGponOntStatusInfoEntry 4}

    zxGponOntSnId OBJECT-TYPE
        SYNTAX      OntSerialNumber(SIZE (8))
        MAX-ACCESS  read-only
        STATUS      current
        DESCRIPTION
            "The serial number is unique for each ONT. Note that the serial 
             number of the ONT contains the vendor id and/or the version number."
        REFERENCE
            "G.984.4 Section 9.1.1"
        ::= { zxGponOntStatusInfoEntry 5}

    zxGponOntTrafficMgmtOpt OBJECT-TYPE
        SYNTAX      INTEGER{
                    usSchedulerPriMech(1),
                    usMaxTraffic(2)
                    }
        MAX-ACCESS  read-only
        STATUS      current
        DESCRIPTION
            "It identifies the upstream traffic management function implemented
             in the ONT. 1 means the traffic scheduler and priority queue mechanism 
             are used for the upstream traffic. 2 means the maximum upstream traffic 
             of each individual connection is guaranteed."
        REFERENCE
            "G.984.4 Section 9.1.1"
        ::= { zxGponOntStatusInfoEntry 6}

    zxGponOntVpVcConnFunOpt OBJECT-TYPE
        SYNTAX      INTEGER{
                    none(1),
                    vp(2),
                    vpvc(3)
                    }
        MAX-ACCESS  read-only
        STATUS      current
        DESCRIPTION
            "It identifies the support of ATM VP or VC cross-connection management
             functions for the interworking connections to non ATM UNIs. 
             0 means no cross-connection management functions are modelled. 
             1 means ATM VP cross-connection management functions are modelled.
             2 means ATM VP and VC cross-connection management functions are modelled."
        REFERENCE
            "G.984.4 Section 9.1.1"
        DEFVAL  { none }
        ::= { zxGponOntStatusInfoEntry 7}

    zxGponOntBatteryBackup OBJECT-TYPE
        SYNTAX      TruthValue
        MAX-ACCESS  read-write
        STATUS      current
        DESCRIPTION
            "It provides a Boolean indication of whether or not the ONT/NT supports
             battery backup. False(2) will indicate that no battery is provisioned; 
             true(1) indicates that a battery is provisioned."
        REFERENCE
            "G.984.4 Section 9.1.1"
        ::= { zxGponOntStatusInfoEntry 8}

    zxGponOntAdminStatus OBJECT-TYPE
        SYNTAX      INTEGER{
                    enable(1),
                    disable(2)
                    }
        MAX-ACCESS  read-write
        STATUS      current
        DESCRIPTION
            "It is used to activate (true 1) and deactivate (false 2) the functions performed
             by instances of this managed entity.It is read from ONT."
        REFERENCE
            "G.984.4 Section 9.1.1"
        DEFVAL  { disable }
        ::= { zxGponOntStatusInfoEntry 9}

    zxGponOntOperStatus OBJECT-TYPE
        SYNTAX      INTEGER{
                    enable(1),
                    disable(2)
                    }
        MAX-ACCESS  read-only
        STATUS      current
        DESCRIPTION
            "It indicates whether or not a managed entity is capable of performing its task.
             Valid values are true(1,enabled) and false(2,disabled)."
        REFERENCE
            "G.984.4 Section 9.1.1"
        DEFVAL  { disable }
        ::= { zxGponOntStatusInfoEntry 10}


    zxGponOntAlarmTable OBJECT-TYPE
        SYNTAX      SEQUENCE OF ZxGponOntAlarmEntry
        MAX-ACCESS  not-accessible
        STATUS      current
        DESCRIPTION
            "This alarm is used to notify the managed system when a
             failure has been detected or cleared."
        REFERENCE
            "G.984.4 Section 9.1.1"
        ::= { zxGponOntEquipMgmt 2 }

    zxGponOntAlarmEntry OBJECT-TYPE
        SYNTAX      ZxGponOntAlarmEntry
        MAX-ACCESS  not-accessible
        STATUS      current
        DESCRIPTION
            "An entry in the ONT equipment alarm information table."
        INDEX   { zxGponMgmtPonOltId, zxGponMgmtPonOnuId }
        ::= { zxGponOntAlarmTable 1 }

    ZxGponOntAlarmEntry ::=
        SEQUENCE {
            zxGponOntEquipmentAlarm              TruthValue,
            zxGponOntEquipmentAlarmMask          TruthValue,
            zxGponOntPoweringAlarm               TruthValue,
            zxGponOntPoweringAlarmMask           TruthValue,
            zxGponOntBatteryMissing              TruthValue,
            zxGponOntBatteryMissingMask          TruthValue,
            zxGponOntBatteryFailure              TruthValue,
            zxGponOntBatteryFailureMask          TruthValue,
            zxGponOntBatteryLow                  TruthValue,
            zxGponOntBatteryLowMask              TruthValue,
            zxGponOntPhysicalIntrusionAlarm      TruthValue,
            zxGponOntPhysicalIntrusionAlarmMask  TruthValue,
            zxGponOntONTSelfTestFailure          TruthValue,
            zxGponOntONTSelfTestFailureMask      TruthValue
        }

    zxGponOntEquipmentAlarm OBJECT-TYPE
        SYNTAX      TruthValue
        MAX-ACCESS  read-only
        STATUS      current
        DESCRIPTION
            "It is used to Indicate a functional failure on an internal interface.
             When this is true(1) the failure exists; When false(2), the failure is
             not exist."
        REFERENCE
            "G.984.4 Section 9.1.1"
        ::= { zxGponOntAlarmEntry 1}

    zxGponOntEquipmentAlarmMask OBJECT-TYPE
        SYNTAX      TruthValue
        MAX-ACCESS  read-write
        STATUS      current
        DESCRIPTION
            "Indicates whether the occurence of zxGponOntEquipmentAlarm alarm
             should result in NE generated by the agent layer. When this is false(2) 
             it should be generated; When true(1), not generated."
        REFERENCE
            "G.984.4 Section 9.1.1"
        DEFVAL  { false }
        ::= { zxGponOntAlarmEntry 2}

    zxGponOntPoweringAlarm OBJECT-TYPE
        SYNTAX      TruthValue
        MAX-ACCESS  read-only
        STATUS      current
        DESCRIPTION
            "It is used to Indicate Loss of external power.
             When this is true(1) the failure exists; When false(2), the failure is
             not exist."
        REFERENCE
            "G.984.4 Section 9.1.1"
        ::= { zxGponOntAlarmEntry 3}

    zxGponOntPoweringAlarmMask OBJECT-TYPE
        SYNTAX      TruthValue
        MAX-ACCESS  read-write
        STATUS      current
        DESCRIPTION
            "Indicates whether the occurence of zxGponOntPoweringAlarm alarm
             should result in NE generated by the agent layer. When this is false(2) 
             it should be generated; When true(1), not generated."
        REFERENCE
            "G.984.4 Section 9.1.1"
        DEFVAL  { false }
        ::= { zxGponOntAlarmEntry 4}

    zxGponOntBatteryMissing OBJECT-TYPE
        SYNTAX      TruthValue
        MAX-ACCESS  read-only
        STATUS      current
        DESCRIPTION
            "It is used to Indicate Battery is provisioned but missing.
             When this is true(1) the failure exists; When false(2), the failure is
             not exist."
        REFERENCE
            "G.984.4 Section 9.1.1"
        ::= { zxGponOntAlarmEntry 5}

    zxGponOntBatteryMissingMask OBJECT-TYPE
        SYNTAX      TruthValue
        MAX-ACCESS  read-write
        STATUS      current
        DESCRIPTION
            "Indicates whether the occurence of zxGponOntBatteryMissing alarm
             should result in NE generated by the agent layer. When this is false(2) 
             it should be generated; When true(1), not generated."
        REFERENCE
            "G.984.4 Section 9.1.1"
        DEFVAL  { false }
        ::= { zxGponOntAlarmEntry 6}

    zxGponOntBatteryFailure OBJECT-TYPE
        SYNTAX      TruthValue
        MAX-ACCESS  read-only
        STATUS      current
        DESCRIPTION
            "It is used to Indicate Battery is provisioned and present but cannot recharge.
             When this is true(1) the failure exists; When false(2), the failure is
             not exist."
        REFERENCE
            "G.984.4 Section 9.1.1"
        ::= { zxGponOntAlarmEntry 7}

    zxGponOntBatteryFailureMask OBJECT-TYPE
        SYNTAX      TruthValue
        MAX-ACCESS  read-write
        STATUS      current
        DESCRIPTION
            "Indicates whether the occurence of zxGponOntBatteryFailure alarm
             should result in NE generated by the agent layer. When this is false(2) 
             it should be generated; When true(1), not generated."
        REFERENCE
            "G.984.4 Section 9.1.1"
        DEFVAL  { false }
        ::= { zxGponOntAlarmEntry 8}

    zxGponOntBatteryLow OBJECT-TYPE
        SYNTAX      TruthValue
        MAX-ACCESS  read-only
        STATUS      current
        DESCRIPTION
            "It is used to Indicate battery is provisioned and present but its voltage is too low.
             When this is true(1) the failure exists; When false(2), the failure is
             not exist."
        REFERENCE
            "G.984.4 Section 9.1.1"
        ::= { zxGponOntAlarmEntry 9}

    zxGponOntBatteryLowMask OBJECT-TYPE
        SYNTAX      TruthValue
        MAX-ACCESS  read-write
        STATUS      current
        DESCRIPTION
            "Indicates whether the occurence of zxGponOntBatteryLow alarm
             should result in NE generated by the agent layer. When this is false(2) 
             it should be generated; When true(1), not generated."
        REFERENCE
            "G.984.4 Section 9.1.1"
        DEFVAL  { false }
        ::= { zxGponOntAlarmEntry 10}

    zxGponOntPhysicalIntrusionAlarm OBJECT-TYPE
        SYNTAX      TruthValue
        MAX-ACCESS  read-only
        STATUS      current
        DESCRIPTION
            "It is used to Indicate Applies if the ONT is supported with detection such as door or box open.
             When this is true(1) the failure exists; When false(2), the failure is
             not exist."
        REFERENCE
            "G.984.4 Section 9.1.1"
        ::= { zxGponOntAlarmEntry 11}

    zxGponOntPhysicalIntrusionAlarmMask OBJECT-TYPE
        SYNTAX      TruthValue
        MAX-ACCESS  read-write
        STATUS      current
        DESCRIPTION
            "Indicates whether the occurence of zxGponOntPhysicalIntrusionAlarm alarm
             should result in NE generated by the agent layer. When this is false(2) 
             it should be generated; When true(1), not generated."
        REFERENCE
            "G.984.4 Section 9.1.1"
        DEFVAL  { false }
        ::= { zxGponOntAlarmEntry 12}

    zxGponOntONTSelfTestFailure OBJECT-TYPE
        SYNTAX      TruthValue
        MAX-ACCESS  read-only
        STATUS      current
        DESCRIPTION
            "It is used to Indicate ONT has failed autonomous self test.
             When this is true(1) the failure exists; When false(2), the failure is
             not exist."
        REFERENCE
            "G.984.4 Section 9.1.1"
        ::= { zxGponOntAlarmEntry 13}

    zxGponOntONTSelfTestFailureMask OBJECT-TYPE
        SYNTAX      TruthValue
        MAX-ACCESS  read-write
        STATUS      current
        DESCRIPTION
            "Indicates whether the occurence of zxGponOntONTSelfTestFailure alarm
             should result in NE generated by the agent layer. When this is false(2) 
             it should be generated; When true(1), not generated."
        REFERENCE
            "G.984.4 Section 9.1.1"
        DEFVAL  { false }
        ::= { zxGponOntAlarmEntry 14}

    zxGponOntActionsTable OBJECT-TYPE
        SYNTAX      SEQUENCE OF ZxGponOntActionsEntry
        MAX-ACCESS  not-accessible
        STATUS      current
        DESCRIPTION
            "Acts the ONT table."
        REFERENCE
            "G.984.4 Section 9.1.1"
        ::= { zxGponOntEquipMgmt 3 }

    zxGponOntActionsEntry OBJECT-TYPE
        SYNTAX      ZxGponOntActionsEntry
        MAX-ACCESS  not-accessible
        STATUS      current
        DESCRIPTION
            "An entry in the ONT equipment Actions table."
        INDEX   { zxGponMgmtPonOltId, zxGponMgmtPonOnuId }
        ::= { zxGponOntActionsTable 1 }

    ZxGponOntActionsEntry ::=
        SEQUENCE {
            zxGponOntReboot     INTEGER,
            zxGponOntTest       INTEGER,
            zxGponOntSyncTime   INTEGER,
            zxGponOntMibReset   INTEGER,
            zxGponOntTestResult INTEGER
        }

    zxGponOntReboot OBJECT-TYPE
        SYNTAX      INTEGER{
                    reboot(1)
                    }
        MAX-ACCESS  read-write
        STATUS      current
        DESCRIPTION
            "It is used to Reboot the ONT."
        REFERENCE
            "G.984.4 Section 9.1.1"
        ::= { zxGponOntActionsEntry 1}

    zxGponOntTest OBJECT-TYPE
        SYNTAX      INTEGER{
                    test(1)
                    }
        MAX-ACCESS  read-write
        STATUS      current
        DESCRIPTION
            "It is used to initiate an ONT self test. Test outcome is 'Pass' or 'Fail'."
        REFERENCE
            "G.984.4 Section 9.1.1"
        ::= { zxGponOntActionsEntry 2}

    zxGponOntSyncTime OBJECT-TYPE
        SYNTAX      INTEGER{
                    synctime(1)
                    }
        MAX-ACCESS  read-write
        STATUS      current
        DESCRIPTION
            "It is used to synchronize the start time of all Monitoring managed entities
             of the ONT with the reference time of the OLT and to reset the registers of 
             the Monitoring managed entities. The effect of this action is that all counters 
             of all Monitoring managed entities are set to 0x00 and restart counting. 
             Also, the value of the Interval End Time attribute of the Monitoring managed 
             entities is set to 0x00 and restarts counting."
        REFERENCE
            "G.984.4 Section 9.1.1"
        ::= { zxGponOntActionsEntry 3}

    zxGponOntMibReset OBJECT-TYPE
        SYNTAX      INTEGER{
                    mibRest(1)
                    }
        MAX-ACCESS  read-write
        STATUS      current
        DESCRIPTION
            "Reset the MIB data sync attributes to 0x00 and reset the MIB of the ONT to its default
             state. This default MIB consists of one instance of the ONT(ONTB)-PON managed entity, one 
             instance of the ONT Data managed entity, two instances of the Software Image managed 
             entity, zero or more instances of the Subscriber Line Cardholder managed entity, zero 
             or more instances of the PON IF Line Cardholder, and zero or more instances of the 
             Priority QueueG-PON(B-PON) managed entity (for the priority queues that reside in the ONT)."
        REFERENCE
            "G.983.2 Section 7.1.2"
        ::= { zxGponOntActionsEntry 4}
        
    zxGponOntTestResult OBJECT-TYPE
        SYNTAX      INTEGER
        MAX-ACCESS  read-only
        STATUS      current
        DESCRIPTION
            "Test outcome is 'Pass' or 'Fail'."
        REFERENCE
            "G.984.4 Section 9.1.1"
        ::= { zxGponOntActionsEntry 5}


    zxGponOnt2StatusInfoTable OBJECT-TYPE
        SYNTAX      SEQUENCE OF ZxGponOnt2StatusInfoEntry
        MAX-ACCESS  not-accessible
        STATUS      current
        DESCRIPTION
            "An instance of this managed entity is automatically created by the ONT after
             initialization. After the creation of this managed entity, the associated 
             attributes are updated according to the data within the ONT itself;It 
             provides additional attributes that are associated with the G-PON ONT."
        REFERENCE
            "G.984.4 Section 9.1.2"
        ::= { zxGponOntEquipMgmt 4 }

    zxGponOnt2StatusInfoEntry OBJECT-TYPE
        SYNTAX      ZxGponOnt2StatusInfoEntry
        MAX-ACCESS  not-accessible
        STATUS      current
        DESCRIPTION
            "An entry in the ONT2 equipment config information table, 
             This managed entity represents the ONT additional attributes."
        INDEX   { zxGponMgmtPonOltId, zxGponMgmtPonOnuId, zxGponOnt2Index }
        ::= { zxGponOnt2StatusInfoTable 1 }

    ZxGponOnt2StatusInfoEntry ::=
        SEQUENCE {
            zxGponOnt2Index             INTEGER,
            zxGponOnt2MeId              INTEGER,
            zxGponOnt2EquipmentId       OntEquipmentId,
            zxGponOnt2OMCCVersion       INTEGER,
            zxGponOnt2VendorProdCode    INTEGER,
            zxGponOnt2SecurityCapab     INTEGER,
            zxGponOnt2SecurityMode      INTEGER,
            zxGponOnt2TotalPriQueNum    INTEGER,
            zxGponOnt2TotalTrafSchedNum INTEGER,
            zxGponOnt2Mode              INTEGER
        }

    zxGponOnt2Index OBJECT-TYPE
        SYNTAX      INTEGER
        MAX-ACCESS  not-accessible
        STATUS      current
        DESCRIPTION
            "An arbitrary(unique) integer for identifiying an entry
             in the ONT equipment, from 1 to M."
        ::= { zxGponOnt2StatusInfoEntry 1}

    zxGponOnt2MeId OBJECT-TYPE
        SYNTAX      INTEGER
        MAX-ACCESS  read-only
        STATUS      current
        DESCRIPTION
            "It provides a unique number for each instance of this managed entity."
        REFERENCE
            "G.984.4 Section 9.1.2"
        ::= { zxGponOnt2StatusInfoEntry 2}

    zxGponOnt2EquipmentId OBJECT-TYPE
        SYNTAX      OntEquipmentId(SIZE (20))
        MAX-ACCESS  read-only
        STATUS      current
        DESCRIPTION
            "It may be used to identify the specific type of ONT."
        REFERENCE
            "G.984.4 Section 9.1.2"
        ::= { zxGponOnt2StatusInfoEntry 3}

    zxGponOnt2OMCCVersion OBJECT-TYPE
        SYNTAX      INTEGER
        MAX-ACCESS  read-only
        STATUS      current
        DESCRIPTION
            "It is used to identify the specific version of the OMCC protocol
             being used by the ONT. This is used to allow the OLT to manage a 
             network with ONTs that support different OMCC versions. The only 
             valid value at this time is 0x80."
        REFERENCE
            "G.984.4 Section 9.1.2"
        ::= { zxGponOnt2StatusInfoEntry 4}

    zxGponOnt2VendorProdCode OBJECT-TYPE
        SYNTAX      INTEGER
        MAX-ACCESS  read-only
        STATUS      current
        DESCRIPTION
            "It is used to provide a vendor-specific product code for the ONT."
        REFERENCE
            "G.984.4 Section 9.1.2"
        ::= { zxGponOnt2StatusInfoEntry 5}

    zxGponOnt2SecurityCapab OBJECT-TYPE
        SYNTAX      INTEGER(0..255)
        MAX-ACCESS  read-only
        STATUS      current
        DESCRIPTION
            "It is used to advertise the advanced security modes of the ONT. 
             The following codepoints are defined:
          0: Reserved for future use; 
          1: AES encryption of the downstream payload is supported; 
          2..255: Reserved for future use."
        REFERENCE
            "G.984.4 Section 9.1.2"
        ::= { zxGponOnt2StatusInfoEntry 6}

    zxGponOnt2SecurityMode OBJECT-TYPE
        SYNTAX      INTEGER(0..255)
        MAX-ACCESS  read-write
        STATUS      current
        DESCRIPTION
            "It is used to select the advanced security mode for the ONT. 
             The following codepoints are defined:
          0: Reserved for future use; 
          1: AES algorithm for unicast traffic will be used; 
          2..255: Reserved for future use."
        REFERENCE
            "G.984.4 Section 9.1.2"
        ::= { zxGponOnt2StatusInfoEntry 7}

    zxGponOnt2TotalPriQueNum OBJECT-TYPE
        SYNTAX      INTEGER(0..4095)
        MAX-ACCESS  read-only
        STATUS      current
        DESCRIPTION
            "It provides a total number of priority queues which are not 
             associated with the PON IF line card."
        REFERENCE
            "G.984.4 Section 9.1.2"
        ::= { zxGponOnt2StatusInfoEntry 8}

    zxGponOnt2TotalTrafSchedNum OBJECT-TYPE
        SYNTAX      INTEGER(0..255)
        MAX-ACCESS  read-only
        STATUS      current
        DESCRIPTION
            "It provides a total number of Traffic Schedulers which are 
             not associated with the PON IF line card. The ONT supports 
             NULL function, HOL scheduling and WRR from the priority control 
             and guarantee of minimum rate control points of view, respectively. 
             If the ONT does not have any Traffic Scheduler, this attribute should be 0."
        REFERENCE
            "G.984.4 Section 9.1.2"
        ::= { zxGponOnt2StatusInfoEntry 9}

    zxGponOnt2Mode OBJECT-TYPE
        SYNTAX      INTEGER{
                    atm(1),
                    gem(2),
                    dual(3)
                    }
        MAX-ACCESS  read-only
        STATUS      current
        DESCRIPTION
            "It identifies whether the ONT can operate in ATM-only mode (1), 
             GEM-only mode (2), or dual (both ATM and GEM) mode (3)."
        REFERENCE
            "G.984.4 Section 9.1.2"
        ::= { zxGponOnt2StatusInfoEntry 10}


    zxGponThresholdDataTable OBJECT-TYPE
        SYNTAX      SEQUENCE OF ZxGponThresholdDataEntry
        MAX-ACCESS  not-accessible
        STATUS      current
        DESCRIPTION
            "Contains threshold values for the performance monitoring parameters
             maintained in one or more instances of other managed entities."
        REFERENCE
            "G.984.4 Section 9.1.8"
        ::= { zxGponOntEquipMgmt 11 }

    zxGponThresholdDataEntry OBJECT-TYPE
        SYNTAX      ZxGponThresholdDataEntry
        MAX-ACCESS  not-accessible
        STATUS      current
        DESCRIPTION
            "An entry in the Threshold Data 1 table."
        INDEX   { zxGponMgmtPonOltId, zxGponMgmtPonOnuId, zxGponThresholdDataIndex }
        ::= { zxGponThresholdDataTable 1 }

    ZxGponThresholdDataEntry ::=
        SEQUENCE {
            zxGponThresholdDataIndex          INTEGER,
            zxGponThresholdDataMeId           INTEGER,
            zxGponThresholdDataValue1         Unsigned32,
            zxGponThresholdDataValue2         Unsigned32,
            zxGponThresholdDataValue3         Unsigned32,
            zxGponThresholdDataValue4         Unsigned32,
            zxGponThresholdDataValue5         Unsigned32,
            zxGponThresholdDataValue6         Unsigned32,
            zxGponThresholdDataValue7         Unsigned32,
            zxGponThresholdDataValue8         Unsigned32,
            zxGponThresholdDataValue9         Unsigned32,
            zxGponThresholdDataValue10        Unsigned32,
            zxGponThresholdDataValue11        Unsigned32,
            zxGponThresholdDataValue12        Unsigned32,
            zxGponThresholdDataValue13        Unsigned32,
            zxGponThresholdDataValue14        Unsigned32,
            zxGponThresholdDataCreateUsedIdx  INTEGER,
            zxGponThresholdDataModifyMatchIdx INTEGER,
            zxGponThresholdDataModifyFlag     INTEGER,
            zxGponThresholdDataEntryStatus    RowStatus
        }

    zxGponThresholdDataIndex OBJECT-TYPE
        SYNTAX      INTEGER
        MAX-ACCESS  not-accessible
        STATUS      current
        DESCRIPTION
            "An arbitrary(unique) integer for identifiying an entry
             in the table, from 1 to M."
        ::= { zxGponThresholdDataEntry 1}

    zxGponThresholdDataMeId OBJECT-TYPE
        SYNTAX      INTEGER
        MAX-ACCESS  read-only
        STATUS      current
        DESCRIPTION
            "A unique number for each instance of this managed entity."
        REFERENCE
            "G.984.4 Section 9.1.8"
        ::= { zxGponThresholdDataEntry 2}

    zxGponThresholdDataValue1 OBJECT-TYPE
        SYNTAX      Unsigned32
        MAX-ACCESS  read-create
        STATUS      current
        DESCRIPTION
            "It provides the associated threshold value for the 1st thresholded counter in the
             History Data type managed entity. It may be created/read/written/modified.Writing or 
             modifing can be done when the entry SHOULD NOT be used by any other entry."
        REFERENCE
            "G.984.4 Section 9.1.8 Threshold Data 1"
        ::= { zxGponThresholdDataEntry 3}

    zxGponThresholdDataValue2 OBJECT-TYPE
        SYNTAX      Unsigned32
        MAX-ACCESS  read-create
        STATUS      current
        DESCRIPTION
            "It provides the associated threshold value for the 2nd thresholded counter in the
             History Data type managed entity. It may be created/read/written/modified.Writing or 
             modifing can be done when the entry SHOULD NOT be used by any other entry."
        REFERENCE
            "G.984.4 Section 9.1.8 Threshold Data 2"
        ::= { zxGponThresholdDataEntry 4}

    zxGponThresholdDataValue3 OBJECT-TYPE
        SYNTAX      Unsigned32
        MAX-ACCESS  read-create
        STATUS      current
        DESCRIPTION
            "It provides the associated threshold value for the 3rd/9th thresholded counter in the
             History Data type managed entity. It may be created/read/written/modified.Writing or 
             modifing can be done when the entry SHOULD NOT be used by any other entry."
        REFERENCE
            "G.984.4 Section 9.1.8 Threshold Data 3"
        ::= { zxGponThresholdDataEntry 5}

    zxGponThresholdDataValue4 OBJECT-TYPE
        SYNTAX      Unsigned32
        MAX-ACCESS  read-create
        STATUS      current
        DESCRIPTION
            "It provides the associated threshold value for the 4th thresholded counter in the
             History Data type managed entity. It may be created/read/written/modified.Writing or 
             modifing can be done when the entry SHOULD NOT be used by any other entry."
        REFERENCE
            "G.984.4 Section 9.1.8 Threshold Data 4"
        ::= { zxGponThresholdDataEntry 6}

    zxGponThresholdDataValue5 OBJECT-TYPE
        SYNTAX      Unsigned32
        MAX-ACCESS  read-create
        STATUS      current
        DESCRIPTION
            "It provides the associated threshold value for the 5th thresholded counter in the
             History Data type managed entity. It may be created/read/written/modified.Writing or 
             modifing can be done when the entry SHOULD NOT be used by any other entry."
        REFERENCE
            "G.984.4 Section 9.1.8 Threshold Data 5"
        ::= { zxGponThresholdDataEntry 7}

    zxGponThresholdDataValue6 OBJECT-TYPE
        SYNTAX      Unsigned32
        MAX-ACCESS  read-create
        STATUS      current
        DESCRIPTION
            "It provides the associated threshold value for the 6th thresholded counter in the
             History Data type managed entity. It may be created/read/written/modified.Writing or 
             modifing can be done when the entry SHOULD NOT be used by any other entry."
        REFERENCE
            "G.984.4 Section 9.1.8 Threshold Data 6"
        ::= { zxGponThresholdDataEntry 8}

    zxGponThresholdDataValue7 OBJECT-TYPE
        SYNTAX      Unsigned32
        MAX-ACCESS  read-create
        STATUS      current
        DESCRIPTION
            "It provides the associated threshold value for the 7st thresholded counter in the
             History Data type managed entity. It may be created/read/written/modified.Writing or 
             modifing can be done when the entry SHOULD NOT be used by any other entry."
        REFERENCE
            "G.984.4 Section 9.1.8 Threshold Data 7"
        ::= { zxGponThresholdDataEntry 9}

    zxGponThresholdDataValue8 OBJECT-TYPE
        SYNTAX      Unsigned32
        MAX-ACCESS  read-create
        STATUS      current
        DESCRIPTION
            "It provides the associated threshold value for the 8th thresholded counter in the
             History Data type managed entity. It may be created/read/written/modified.Writing or 
             modifing can be done when the entry SHOULD NOT be used by any other entry."
        REFERENCE
            "G.984.4 Section 9.1.9 Threshold Data 8"
        ::= { zxGponThresholdDataEntry 10}

    zxGponThresholdDataValue9 OBJECT-TYPE
        SYNTAX      Unsigned32
        MAX-ACCESS  read-create
        STATUS      current
        DESCRIPTION
            "It provides the associated threshold value for the 9th thresholded counter in the
             History Data type managed entity. It may be created/read/written/modified.Writing or 
             modifing can be done when the entry SHOULD NOT be used by any other entry."
        REFERENCE
            "G.984.4 Section 9.1.9 Threshold Data 9"
        ::= { zxGponThresholdDataEntry 11}

    zxGponThresholdDataValue10 OBJECT-TYPE
        SYNTAX      Unsigned32
        MAX-ACCESS  read-create
        STATUS      current
        DESCRIPTION
            "It provides the associated threshold value for the 10th thresholded counter in the
             History Data type managed entity. It may be created/read/written/modified.Writing or 
             modifing can be done when the entry SHOULD NOT be used by any other entry."
        REFERENCE
            "G.984.4 Section 9.1.9 Threshold Data 10"
        ::= { zxGponThresholdDataEntry 12}

    zxGponThresholdDataValue11 OBJECT-TYPE
        SYNTAX      Unsigned32
        MAX-ACCESS  read-create
        STATUS      current
        DESCRIPTION
            "It provides the associated threshold value for the 11th thresholded counter in the
             History Data type managed entity. It may be created/read/written/modified.Writing or 
             modifing can be done when the entry SHOULD NOT be used by any other entry."
        REFERENCE
            "G.984.4 Section 9.1.9 Threshold Data 11"
        ::= { zxGponThresholdDataEntry 13}

    zxGponThresholdDataValue12 OBJECT-TYPE
        SYNTAX      Unsigned32
        MAX-ACCESS  read-create
        STATUS      current
        DESCRIPTION
            "It provides the associated threshold value for the 12th thresholded counter in the
             History Data type managed entity. It may be created/read/written/modified.Writing or 
             modifing can be done when the entry SHOULD NOT be used by any other entry."
        REFERENCE
            "G.984.4 Section 9.1.9 Threshold Data 12"
        ::= { zxGponThresholdDataEntry 14}

    zxGponThresholdDataValue13 OBJECT-TYPE
        SYNTAX      Unsigned32
        MAX-ACCESS  read-create
        STATUS      current
        DESCRIPTION
            "It provides the associated threshold value for the 13th thresholded counter in the
             History Data type managed entity. It may be created/read/written/modified.Writing or 
             modifing can be done when the entry SHOULD NOT be used by any other entry."
        REFERENCE
            "G.984.4 Section 9.1.9 Threshold Data 13"
        ::= { zxGponThresholdDataEntry 15}

    zxGponThresholdDataValue14 OBJECT-TYPE
        SYNTAX      Unsigned32
        MAX-ACCESS  read-create
        STATUS      current
        DESCRIPTION
            "It provides the associated threshold value for the 14th thresholded counter in the
             History Data type managed entity. It may be created/read/written/modified.Writing or 
             modifing can be done when the entry SHOULD NOT be used by any other entry."
        REFERENCE
            "G.984.4 Section 9.1.9 Threshold Data 14"
        ::= { zxGponThresholdDataEntry 16}

   zxGponThresholdDataCreateUsedIdx OBJECT-TYPE
        SYNTAX      INTEGER
        MAX-ACCESS  read-create
        STATUS      current
        DESCRIPTION
            "This attribute represents the template index which created by zxGponE2eServicePathTable. If this
             object is not created by zxGponE2eServicePathTable, this attribute is set to 0. "
        ::= { zxGponThresholdDataEntry 17}

   zxGponThresholdDataModifyMatchIdx OBJECT-TYPE
        SYNTAX      INTEGER
        MAX-ACCESS  read-only
        STATUS      current
        DESCRIPTION
            "This attribute represents the template index of a matching template when this table is modified
             directly. If there is no mactching template after modified, this attribute is set to 0. "
        ::= { zxGponThresholdDataEntry 18}

   zxGponThresholdDataModifyFlag OBJECT-TYPE
        SYNTAX      INTEGER{
                    true(1),
                    false(2)
                    }
        MAX-ACCESS  read-only
        STATUS      current
        DESCRIPTION
            "If this object is created by zxGponE2eServicePathTable, this attribute represents the modifing 
             flag of template used by this object, it is set to true(1) if the template was modified, 
             otherwise, it is set to false(2). "
        ::= { zxGponThresholdDataEntry 19}

    zxGponThresholdDataEntryStatus OBJECT-TYPE
        SYNTAX      RowStatus
        MAX-ACCESS  read-create
        STATUS      current
        DESCRIPTION
            "The control that allows creation and deletion of entries."
        ::= { zxGponThresholdDataEntry 20}



    zxGponProtectionDataTable OBJECT-TYPE
        SYNTAX      SEQUENCE OF ZxGponProtectionDataEntry
        MAX-ACCESS  not-accessible
        STATUS      current
        DESCRIPTION
            "It is used for the ONT that supports the PON protection function.
             It represents the capability and parameters for protection function."
        REFERENCE
            "G.984.4 Section 9.1.10"
        ::= { zxGponOntEquipMgmt 13 }

    zxGponProtectionDataEntry OBJECT-TYPE
        SYNTAX      ZxGponProtectionDataEntry
        MAX-ACCESS  not-accessible
        STATUS      current
        DESCRIPTION
            "An entry in the Protection Data table."
        INDEX   { zxGponMgmtPonOltId, zxGponMgmtPonOnuId, zxGponProtectionDataIndex }
        ::= { zxGponProtectionDataTable 1 }

    ZxGponProtectionDataEntry ::=
        SEQUENCE {
            zxGponProtectionDataIndex           INTEGER,
            zxGponProtectionDataMeId            INTEGER,
            zxGponProtectionDataWorkingAni      INTEGER,
            zxGponProtectionDataProtectionAni   INTEGER,
            zxGponProtectionDataProtectionType  INTEGER,
            zxGponProtectionDataRevertive       TruthValue,
            zxGponProtectionDataWTT             INTEGER,
            zxGponProtectionDataSGT             INTEGER
        }

    zxGponProtectionDataIndex OBJECT-TYPE
        SYNTAX      INTEGER
        MAX-ACCESS  not-accessible
        STATUS      current
        DESCRIPTION
            "An arbitrary(unique) integer for identifiying an entry
             in the ONT equipment, from 1 to M."
        ::= { zxGponProtectionDataEntry 1}

    zxGponProtectionDataMeId OBJECT-TYPE
        SYNTAX      INTEGER
        MAX-ACCESS  read-only
        STATUS      current
        DESCRIPTION
            "A unique number for each instance of this managed entity."
        REFERENCE
            "G.984.4 Section 9.1.10"
        ::= { zxGponProtectionDataEntry 2}

    zxGponProtectionDataWorkingAni OBJECT-TYPE
        SYNTAX      INTEGER
        MAX-ACCESS  read-only
        STATUS      current
        DESCRIPTION
            "It indicates the index of the ANI-G managed table that represents a 
             working side of PON protection. I.e. it is the table XXXXX index."
        REFERENCE
            "G.984.4 Section 9.1.10"
        ::= { zxGponProtectionDataEntry 3}

    zxGponProtectionDataProtectionAni OBJECT-TYPE
        SYNTAX      INTEGER
        MAX-ACCESS  read-only
        STATUS      current
        DESCRIPTION
            "It indicates the index of the ANI-G managed table that represents a
             protection side of PON protection. I.e. it is the table XXXXX index."
        REFERENCE
            "G.984.4 Section 9.1.10"
        ::= { zxGponProtectionDataEntry 4}

    zxGponProtectionDataProtectionType OBJECT-TYPE
        SYNTAX      INTEGER{
                            oneplusone(1),
                            oneratioone1(2),
                            oneratioone2(3)
                            }
        MAX-ACCESS  read-only
        STATUS      current
        DESCRIPTION
            "It provides the behaviour of PON protection. The valid values are as follows:
             1: 1+1 Protection,
             2: 1:1 Protection without Extra traffic,
             3: 1:1 Protection with capability to support Extra traffic."
        REFERENCE
            "G.984.4 Section 9.1.10"
        ::= { zxGponProtectionDataEntry 5}

    zxGponProtectionDataRevertive OBJECT-TYPE
        SYNTAX      TruthValue
        MAX-ACCESS  read-only
        STATUS      current
        DESCRIPTION
            "It indicates whether the protection scheme uses revertive mode (true, value 1)
             or non-revertive mode (false, value 2)."
        REFERENCE
            "G.984.4 Section 9.1.10"
        ::= { zxGponProtectionDataEntry 6}

    zxGponProtectionDataWTT OBJECT-TYPE
        SYNTAX      INTEGER(0..65535)
        MAX-ACCESS  read-write
        STATUS      current
        DESCRIPTION
            "It specifies the amount of time, in units of seconds, to wait during the time from
             a fault clear to switching over the trail/connection/line to the working side."
        REFERENCE
            "G.984.4 Section 9.1.10"
        DEFVAL  { 3 }
        ::= { zxGponProtectionDataEntry 7}

    zxGponProtectionDataSGT OBJECT-TYPE
        SYNTAX      INTEGER(0..65535)
        MAX-ACCESS  read-write
        STATUS      current
        DESCRIPTION
            "It specifies the amount of time, in units of milliseconds, to wait during the interval
             from the detection of a fault to the time when a protection trail/connection/line can 
             be used to transport the normal traffic signal and/or to select the normal traffic signal."
        REFERENCE
            "G.984.4 Section 9.1.10"
        DEFVAL  { 50 }
        ::= { zxGponProtectionDataEntry 8}

--zxGponAniMgmt.mi2
    zxGponAniMgmt OBJECT IDENTIFIER ::= { zxGponRootMib 22 }  

    zxGponAniInfoTable OBJECT-TYPE
        SYNTAX      SEQUENCE OF ZxGponAniInfoEntry
        MAX-ACCESS  not-accessible
        STATUS      current
        DESCRIPTION
            "An instance of this managed entity is automatically created by 
             the ONT after initialization." 
        REFERENCE
            "G.984.4 Section 9.2.1"
        ::= { zxGponAniMgmt 1 }

    zxGponAniInfoEntry OBJECT-TYPE
        SYNTAX      ZxGponAniInfoEntry
        MAX-ACCESS  not-accessible
        STATUS      current
        DESCRIPTION
            "An entry in the ANI status information table, This managed entity
             is used to organize data associated with the Access Network 
             Interface supported by the ONT."
        INDEX   { zxGponMgmtPonOltId, zxGponMgmtPonOnuId, zxGponAniInfoIndex }
        ::= { zxGponAniInfoTable 1 }


    ZxGponAniInfoEntry ::=
        SEQUENCE {
            zxGponAniInfoIndex                 INTEGER,
            zxGponAniInfoMeId                  INTEGER,
            zxGponAniInfoSRIndication          TruthValue,
            zxGponAniInfoTotalTcontNumber      INTEGER,
            zxGponAniInfoGemBlockLength        INTEGER,
            zxGponAniInfoPiggybackDbaReporting INTEGER,
            zxGponAniInfoWholeOnuDbaReporting  INTEGER,
            zxGponAniInfoSFThreshold           INTEGER,
            zxGponAniInfoSDThreshold           INTEGER
        }

    zxGponAniInfoIndex OBJECT-TYPE
        SYNTAX      INTEGER
        MAX-ACCESS  not-accessible
        STATUS      current
        DESCRIPTION
            "An arbitrary(unique) integer for identifiying an entry
             in the Ani manangement, from 1 to M."
        ::= { zxGponAniInfoEntry 1}

    zxGponAniInfoMeId OBJECT-TYPE
        SYNTAX      INTEGER
        MAX-ACCESS  read-only
        STATUS      current
        DESCRIPTION
            "A unique number for each instance of this managed entity."
        REFERENCE
            "G.984.4 Section 9.2.1"
        ::= { zxGponAniInfoEntry 2}

    zxGponAniInfoSRIndication OBJECT-TYPE
        SYNTAX      TruthValue
        MAX-ACCESS  read-only
        STATUS      current
        DESCRIPTION
            "This Boolean attribute indicates the capability of status 
             reporting. The value TRUE means that the status reporting 
             is available for all T-CONTs which are associated with the 
             ANI."
        REFERENCE
            "G.984.4 Section 9.2.1"
        ::= { zxGponAniInfoEntry 3}

    zxGponAniInfoTotalTcontNumber OBJECT-TYPE
        SYNTAX      INTEGER
        MAX-ACCESS  read-only
        STATUS      current
        DESCRIPTION
            "This attribute provides the total number of T-CONTs that are 
             able to be supported in this ANI port."
        REFERENCE
            "G.984.4 Section 9.2.1"
        ::= { zxGponAniInfoEntry 4}

    zxGponAniInfoGemBlockLength OBJECT-TYPE
        SYNTAX      INTEGER
        MAX-ACCESS  read-write
        STATUS      current
        DESCRIPTION
            "This attribute indicates the reporting block size for GEM mode in 
             units of bytes."
        REFERENCE
            "G.984.4 Section 9.2.1"
        ::= { zxGponAniInfoEntry 5}

    zxGponAniInfoPiggybackDbaReporting OBJECT-TYPE
        SYNTAX      INTEGER{
                    mode0Only(1),
                    mode01(2),
                    mode02(3),
                    mode012(4),
                    modeNotSupport(5)
                    }
        MAX-ACCESS  read-only
        STATUS      current
        DESCRIPTION
            "This attribute provides a special code that indicates the piggyback 
             DBA reporting format capabilities of this ONT. ITU-T Rec."
        REFERENCE
            "G.984.4 Section 9.2.1"
        ::= { zxGponAniInfoEntry 6}

    zxGponAniInfoWholeOnuDbaReporting OBJECT-TYPE
        SYNTAX      INTEGER{
                    wholeDbaReportNotSupport(1),
                    wholeDbaReportSupport(2)
                    }
        MAX-ACCESS  read-only
        STATUS      current
        DESCRIPTION
            "This attribute indicates whether or not whole ONU DBA reporting as specified
             in ITU-T Rec. G.984.3 is supported by the ONU/ONT."
        REFERENCE
            "G.984.4 Section 9.2.1"
        ::= { zxGponAniInfoEntry 7}

    zxGponAniInfoSFThreshold OBJECT-TYPE
        SYNTAX      INTEGER
        MAX-ACCESS  read-write
        STATUS      current
        DESCRIPTION
            "This attribute represents the upstream/downstream BER threshold to detect SFi/SF alarm.
             When this value is y in decimal, the BER threshold for SFi/SF is 10^(-y).
             The valid values are from 3 to 8 inclusive."
        REFERENCE
            "G.984.4 Section 9.2.1"
        ::= { zxGponAniInfoEntry 8}
        
    zxGponAniInfoSDThreshold OBJECT-TYPE
        SYNTAX      INTEGER
        MAX-ACCESS  read-write
        STATUS      current
        DESCRIPTION
            "This attribute represents the upstream/downstream BER threshold to detect SDi/SD alarm.
             When this value is x in decimal, the BER threshold for SFi/SF is 10^(-x).
             The valid values are from 4 to 10 inclusive.
             Please note that the SD threshold shall be smaller than the SF threshold. This means that
             the value of x shall be larger than the value of y."
        REFERENCE
            "G.984.4 Section 9.2.1"
        ::= { zxGponAniInfoEntry 9}


    zxGponTcontInfoTable OBJECT-TYPE
        SYNTAX      SEQUENCE OF ZxGponTcontInfoEntry
        MAX-ACCESS  not-accessible
        STATUS      current
        DESCRIPTION
            "An instance of this managed entity represents a logical connection 
             group that is associated with the Alloc-id. A T-CONT can accommodate 
             ATM cells or GEM packets in priority queues or Traffic Schedulers 
             that exist in the ATM or GEM layer."
        REFERENCE
            "G.984.4 Section 9.2.3"
        ::= { zxGponAniMgmt 3 }

    zxGponTcontInfoEntry OBJECT-TYPE
        SYNTAX      ZxGponTcontInfoEntry
        MAX-ACCESS  not-accessible
        STATUS      current
        DESCRIPTION
            "An entry in the T-CONT status information table."
        INDEX   { zxGponMgmtPonOltId, zxGponMgmtPonOnuId, zxGponTcontInfoIndex }
        ::= { zxGponTcontInfoTable 1 }

    ZxGponTcontInfoEntry ::=
        SEQUENCE {
            zxGponTcontInfoIndex         INTEGER,
            zxGponTcontInfoMeId          INTEGER,
            zxGponTcontInfoAllocID       INTEGER,
            zxGponTcontInfoModeIndicator INTEGER,
            zxGponTcontInfoPolicy        INTEGER
        }

    zxGponTcontInfoIndex OBJECT-TYPE
        SYNTAX      INTEGER
        MAX-ACCESS  not-accessible
        STATUS      current
        DESCRIPTION
            "An arbitrary(unique) integer for identifiying an entry
             in the ANI management, from 1 to M."
        REFERENCE
            "G.984.4 Section 9.2.3"
        ::= { zxGponTcontInfoEntry 1 }

    zxGponTcontInfoMeId OBJECT-TYPE
        SYNTAX      INTEGER
        MAX-ACCESS  read-only
        STATUS      current
        DESCRIPTION
            "A unique number for each instance of this managed entity."
        REFERENCE
            "G.984.4 Section 9.2.3"
        ::= { zxGponTcontInfoEntry 2}

    zxGponTcontInfoAllocID OBJECT-TYPE
        SYNTAX      INTEGER
        MAX-ACCESS  read-write
        STATUS      current
        DESCRIPTION
            "Alloc ID."
        REFERENCE
            "G.984.4 Section 9.2.3"
        ::= { zxGponTcontInfoEntry 3 }

    zxGponTcontInfoModeIndicator OBJECT-TYPE
        SYNTAX      INTEGER{
                    modeAtm(1),
                    modeGem(2)
                    }
        MAX-ACCESS  read-only
        STATUS      current
        DESCRIPTION
            "Mode indicator."
        REFERENCE
            "G.984.4 Section 9.2.3"
        ::= { zxGponTcontInfoEntry 4 }

    zxGponTcontInfoPolicy OBJECT-TYPE
        SYNTAX      INTEGER{
                    hol(1),
                    wrr(2),
                    null(3)
                    }
        MAX-ACCESS  read-only
        STATUS      current
        DESCRIPTION
            "Strategy."
        REFERENCE
            "G.984.4 Section 9.2.3"
        DEFVAL  { hol }
        ::= { zxGponTcontInfoEntry 5 }

--zxGponUniMgmt.mi2
    zxGponUniMgmt OBJECT IDENTIFIER ::= { zxGponRootMib 23 }

    zxGpon8021pMapperTable OBJECT-TYPE
        SYNTAX      SEQUENCE OF ZxGpon8021pMapperEntry
        MAX-ACCESS  not-accessible
        STATUS      current
        DESCRIPTION
            "One or more instances is used to associate the priorities of 802.1P priority
             tagged frames with a specific connection." 
        REFERENCE
            "G.983.2 Rev Section 7.3.95"
        ::= { zxGponUniMgmt 1 }

    zxGpon8021pMapperEntry OBJECT-TYPE
        SYNTAX      ZxGpon8021pMapperEntry
        MAX-ACCESS  not-accessible
        STATUS      current
        DESCRIPTION
            "One or more instances of the 802.1p Mapper entity." 
        INDEX   { zxGponMgmtPonOltId, zxGponMgmtPonOnuId, zxGpon8021pMapperMeIdIdx }
        ::= { zxGpon8021pMapperTable 1 }

    ZxGpon8021pMapperEntry ::=
        SEQUENCE {
            zxGpon8021pMapperMeIdIdx        INTEGER,
            zxGpon8021pMapperPptpUniPtr     INTEGER,
            zxGpon8021pMapperPri0IwTpPtr    INTEGER,
            zxGpon8021pMapperPri1IwTpPtr    INTEGER,
            zxGpon8021pMapperPri2IwTpPtr    INTEGER,
            zxGpon8021pMapperPri3IwTpPtr    INTEGER,
            zxGpon8021pMapperPri4IwTpPtr    INTEGER,
            zxGpon8021pMapperPri5IwTpPtr    INTEGER,
            zxGpon8021pMapperPri6IwTpPtr    INTEGER,
            zxGpon8021pMapperPri7IwTpPtr    INTEGER,
            zxGpon8021pMapperUntagFrmInd    INTEGER,
            zxGpon8021pMapperDscpTo8021pPri OCTET STRING,
            zxGpon8021pMapperDefaultPri     INTEGER,
            zxGpon8021pMapperMgmtCtrlFlag   INTEGER,
            zxGpon8021pMapperEntryStatus    RowStatus
        }

    zxGpon8021pMapperMeIdIdx OBJECT-TYPE
        SYNTAX      INTEGER
        MAX-ACCESS  not-accessible
        STATUS      current
        DESCRIPTION
            "This attribute provides a unique number for each instance of this managed entity."
        REFERENCE
            "G.983.2 Rev Section 7.3.95"
        ::= { zxGpon8021pMapperEntry 1}

    zxGpon8021pMapperPptpUniPtr OBJECT-TYPE
        SYNTAX      INTEGER
        MAX-ACCESS  read-write
        STATUS      current
        DESCRIPTION
            "An instance identifier of the PPTP UNI that is associated with this 802.1p Priority
             Queue Mapper, in the case of direct 802.1p mapping. In the case of combined Bridging-
             mapping, this pointer is not used, and its value is set to 0xFFFF."
        REFERENCE
            "G.983.2 Rev Section 7.3.95"
        ::= { zxGpon8021pMapperEntry 2}

    zxGpon8021pMapperPri0IwTpPtr OBJECT-TYPE
        SYNTAX      INTEGER
        MAX-ACCESS  read-write
        STATUS      current
        DESCRIPTION
            "This attribute represents a pointer to the Interworking Termination Point that is
             associated with P-Bit = 000 tagged frames. The value 0xFFFF is a null pointer."
        REFERENCE
            "G.983.2 Rev Section 7.3.95"
        ::= { zxGpon8021pMapperEntry 3}

    zxGpon8021pMapperPri1IwTpPtr OBJECT-TYPE
        SYNTAX      INTEGER
        MAX-ACCESS  read-write
        STATUS      current
        DESCRIPTION
            "This attribute represents a pointer to the Interworking Termination Point that is
             associated with P-Bit = 001 tagged frames. The value 0xFFFF is a null pointer."
        REFERENCE
            "G.983.2 Rev Section 7.3.95"
        ::= { zxGpon8021pMapperEntry 4}

    zxGpon8021pMapperPri2IwTpPtr OBJECT-TYPE
        SYNTAX      INTEGER
        MAX-ACCESS  read-write
        STATUS      current
        DESCRIPTION
            "This attribute represents a pointer to the Interworking Termination Point that is
             associated with P-Bit = 010 tagged frames. The value 0xFFFF is a null pointer."
        REFERENCE
            "G.983.2 Rev Section 7.3.95"
        ::= { zxGpon8021pMapperEntry 5}

    zxGpon8021pMapperPri3IwTpPtr OBJECT-TYPE
        SYNTAX      INTEGER
        MAX-ACCESS  read-write
        STATUS      current
        DESCRIPTION
            "This attribute represents a pointer to the Interworking Termination Point that is
             associated with P-Bit = 011 tagged frames. The value 0xFFFF is a null pointer."
        REFERENCE
            "G.983.2 Rev Section 7.3.95"
        ::= { zxGpon8021pMapperEntry 6}

    zxGpon8021pMapperPri4IwTpPtr OBJECT-TYPE
        SYNTAX      INTEGER
        MAX-ACCESS  read-write
        STATUS      current
        DESCRIPTION
            "This attribute represents a pointer to the Interworking Termination Point that is
             associated with P-Bit = 100 tagged frames. The value 0xFFFF is a null pointer."
        REFERENCE
            "G.983.2 Rev Section 7.3.95"
        ::= { zxGpon8021pMapperEntry 7}

    zxGpon8021pMapperPri5IwTpPtr OBJECT-TYPE
        SYNTAX      INTEGER
        MAX-ACCESS  read-write
        STATUS      current
        DESCRIPTION
            "This attribute represents a pointer to the Interworking Termination Point that is
             associated with P-Bit = 101 tagged frames. The value 0xFFFF is a null pointer."
        REFERENCE
            "G.983.2 Rev Section 7.3.95"
        ::= { zxGpon8021pMapperEntry 8}

    zxGpon8021pMapperPri6IwTpPtr OBJECT-TYPE
        SYNTAX      INTEGER
        MAX-ACCESS  read-write
        STATUS      current
        DESCRIPTION
            "This attribute represents a pointer to the Interworking Termination Point that is
             associated with P-Bit = 110 tagged frames. The value 0xFFFF is a null pointer."
        REFERENCE
            "G.983.2 Rev Section 7.3.95"
        ::= { zxGpon8021pMapperEntry 9}

    zxGpon8021pMapperPri7IwTpPtr OBJECT-TYPE
        SYNTAX      INTEGER
        MAX-ACCESS  read-write
        STATUS      current
        DESCRIPTION
            "This attribute represents a pointer to the Interworking Termination Point that is
             associated with P-Bit = 111 tagged frames. The value 0xFFFF is a null pointer."
        REFERENCE
            "G.983.2 Rev Section 7.3.95"
        ::= { zxGpon8021pMapperEntry 10}

    zxGpon8021pMapperUntagFrmInd OBJECT-TYPE
        SYNTAX      INTEGER{
                    dscpTo8021p(1),
                    tagFrmToVal(2)
                    }
        MAX-ACCESS  read-write
        STATUS      current
        DESCRIPTION
            "This attribute indicates how the ONT should handle Untagged Ethernet frames received
             across the associated Ethernet interface.  Valid values include the following:
             1: Convert from DSCP to 802.1p
             2: Tag frame to a certain value."
        REFERENCE
            "G.983.2 Rev Section 7.3.95"
        ::= { zxGpon8021pMapperEntry 11}

    zxGpon8021pMapperDscpTo8021pPri OBJECT-TYPE
        SYNTAX      OCTET STRING(SIZE(8))
        MAX-ACCESS  read-write
        STATUS      current
        DESCRIPTION
            "This attribute is used in conjunction with the Unmarked Frame Option attribute. If unmarked
             frame option is 1('zxGpon8021pMapperUntagFrmInd' is dscpTo8021p), this attribute structure 
             can be considered a bitmap that represents a sequence of 64 '3-bit' groupings.  Each of the
             64 groupings represents the possible value of the 6-bit DSCP field.  Each of the '3-bit' 
             groupings represents the 'P-bit value' to which the associated DSCP value should be mapped.
             Once marked, the P-Bit marked frame will then be routed to the GEM Interwork Pointer as 
             indicated by the P-Bit to Interwork Pointer mappings above."
        REFERENCE
            "G.983.2 Rev Section 7.3.95"
        ::= { zxGpon8021pMapperEntry 12}

    zxGpon8021pMapperDefaultPri OBJECT-TYPE
        SYNTAX      INTEGER
        MAX-ACCESS  read-write
        STATUS      current
        DESCRIPTION
            "This attribute is used in conjunction with the Unmarked Frame Option attribute. If unmarked
             frame option is 2('zxGpon8021pMapperUntagFrmInd' is tagFrmToVal), this attribute contains 
             the default P-Bit priority setting that will be applied to the frame.  The P-Bit marked frame
             will then be routed to the GEM Interwork Pointer as indicated by the P-Bit to Interwork Pointer
             mappings above."
        REFERENCE
            "G.983.2 Rev Section 7.3.95"
        ::= { zxGpon8021pMapperEntry 13}

    zxGpon8021pMapperMgmtCtrlFlag OBJECT-TYPE
        SYNTAX      INTEGER{
                    nmsCreate(1),
                    neCreate(2)
                    }
        MAX-ACCESS  read-only
        STATUS      current
        DESCRIPTION
            "This attribute is used to indicate this record is created by NMS or NE. If it
             is neCreate(2), this record can not be deleted."
        REFERENCE
            "N/A"
        ::= { zxGpon8021pMapperEntry 14}

    zxGpon8021pMapperEntryStatus       OBJECT-TYPE
      SYNTAX      RowStatus
      MAX-ACCESS  read-create
      STATUS      current 
      DESCRIPTION 
        "This attribute can be create and delete."
      REFERENCE   "N/A"
      ::= { zxGpon8021pMapperEntry 15 }

    zxGponUniInfoTable OBJECT-TYPE
        SYNTAX      SEQUENCE OF ZxGponUniInfoEntry
        MAX-ACCESS  not-accessible
        STATUS      current
        DESCRIPTION
            "One or more instances of the UNI-G managed entity may be contained 
             in an instance of a Subscriber Line Card managed entity." 
        REFERENCE
            "G.984.4 Section 9.3.1"
        ::= { zxGponUniMgmt 2 }

    zxGponUniInfoEntry OBJECT-TYPE
        SYNTAX      ZxGponUniInfoEntry
        MAX-ACCESS  not-accessible
        STATUS      current
        DESCRIPTION
            "One or more instances of the UNI-G managed entity may be contained 
             in an instance of a Subscriber Line Card managed entity." 
        INDEX   { zxGponMgmtPonOltId, zxGponMgmtPonOnuId, zxGponUniInfoIndex }
        ::= { zxGponUniInfoTable 1 }

    ZxGponUniInfoEntry ::=
        SEQUENCE {
            zxGponUniInfoIndex      INTEGER,
            zxGponUniInfoMeId       INTEGER,
            zxGponUniInfoCfgOption  INTEGER,
            zxGponUniInfoAdminState INTEGER
        }

    zxGponUniInfoIndex OBJECT-TYPE
        SYNTAX      INTEGER
        MAX-ACCESS  not-accessible
        STATUS      current
        DESCRIPTION
            "An arbitrary(unique) integer for identifiying an entry
             in the UNI management, from 1 to M."
        ::= { zxGponUniInfoEntry 1}

    zxGponUniInfoMeId OBJECT-TYPE
        SYNTAX      INTEGER
        MAX-ACCESS  read-only
        STATUS      current
        DESCRIPTION
            "This attribute provides a unique number for each instance of this managed entity. 
             This number is directly associated with the physical position of the UNI."
        REFERENCE
            "G.984.4 Section 9.3.1"
        ::= { zxGponUniInfoEntry 2}

    zxGponUniInfoCfgOption OBJECT-TYPE
        SYNTAX      INTEGER
        MAX-ACCESS  read-write
        STATUS      current
        DESCRIPTION
            "This attribute holds the UNI Configuration Code field."
        REFERENCE
            "G.984.4 Section 9.3.1"
        ::= { zxGponUniInfoEntry 3}

    zxGponUniInfoAdminState OBJECT-TYPE
        SYNTAX      INTEGER{
                    enabled(1),
                    disabled(2)
                    }
        MAX-ACCESS  read-write
        STATUS      current
        DESCRIPTION
            "When the Administrative State attribute is set to disabled(2), all user traffic to and from 
             this UNI is blocked and alarms for this UNI and all associated managed entities are no 
             longer generated. "
        REFERENCE
            "G.984.4 Section 9.3.1"
        ::= { zxGponUniInfoEntry 4}

     Timeout ::= INTEGER -- an STP timer in units of 1/100 seconds

    ethernetUniMib OBJECT IDENTIFIER ::= { zxGponUniMgmt 8 }

    zxGponPPTPEthUniInfoTable OBJECT-TYPE
        SYNTAX      SEQUENCE OF ZxGponPPTPEthUniInfoEntry
        MAX-ACCESS  not-accessible
        STATUS      current
        DESCRIPTION
            "This managed entity represents the points at an Ethernet UNI in the ONT where 
             physical paths terminate and physical path level functions (e.g. Ethernet 
             function) are performed. An instance of this managed entity shall be automatically 
             created/deleted by the ONT upon the creation/deletion of a Subscriber Line Card of 
             Ethernet type" 
        REFERENCE
            "G.983.2 Section 7.3.2"
        ::= { ethernetUniMib 1 }

    zxGponPPTPEthUniInfoEntry OBJECT-TYPE
        SYNTAX      ZxGponPPTPEthUniInfoEntry
        MAX-ACCESS  not-accessible
        STATUS      current
        DESCRIPTION
            "One or more instances of this managed entity shall be contained in an instance of a 
             Subscriber Line Card managed entity classified as a native LAN type (e.g. Ethernet)."
        INDEX   { zxGponMgmtPonOltId, zxGponMgmtPonOnuId, zxGponPPTPEthInfoTPID }
        ::= { zxGponPPTPEthUniInfoTable 1 }

    ZxGponPPTPEthUniInfoEntry ::=
        SEQUENCE {
            zxGponPPTPEthInfoTPID              INTEGER,
            zxGponPPTPEthInfoMeId              INTEGER,
            zxGponPPTPEthInfoExpectedType      INTEGER,
            zxGponPPTPEthInfoSensedType        INTEGER,
            zxGponPPTPEthInfoAutoDetectCfg     INTEGER,
            zxGponPPTPEthInfoEthLoopback       INTEGER,
            zxGponPPTPEthInfoAdminState        INTEGER,
            zxGponPPTPEthInfoOperationalState  INTEGER,
            zxGponPPTPEthInfoDuplexSpeedInd    INTEGER,
            zxGponPPTPEthInfoMaxFrameSize      INTEGER,
            zxGponPPTPEthInfoDTEorDCEInd       INTEGER,
            zxGponPPTPEthInfoPauseTime         INTEGER,
            zxGponPPTPEthInfoBridgedorIPInd    INTEGER,
            zxGponPPTPEthInfoARC               INTEGER,
            zxGponPPTPEthInfoARCInterval       INTEGER,      
            zxGponPPTPEthInfoPppoeFilterEnable INTEGER
        }

   zxGponPPTPEthInfoTPID OBJECT-TYPE
        SYNTAX      INTEGER
        MAX-ACCESS  not-accessible
        STATUS      current
        DESCRIPTION
            "An arbitrary(unique) integer for identifiying an entry in the PPTP Ethernet 
             information Table."
        ::= { zxGponPPTPEthUniInfoEntry 1}
        
    zxGponPPTPEthInfoMeId OBJECT-TYPE
        SYNTAX      INTEGER
        MAX-ACCESS  read-only
        STATUS      current
        DESCRIPTION
            "This attribute provides a unique number for each instance of this managed entity. 
             This 2-byte number is directly associated with the physical position of the UNI. 
             The first byte is the slot id (defined in 7.1.3). The second byte is the port id 
             with value range from 0x01 to 0xFF (1 to 255): 0x01 is used for the leftmost/lowest 
             port on a subscriber line card, 0x02 is used for the next right/upper port, and so forth."
        ::= { zxGponPPTPEthUniInfoEntry 2}

    zxGponPPTPEthInfoExpectedType OBJECT-TYPE
        SYNTAX      INTEGER
        MAX-ACCESS  read-write
        STATUS      current
        DESCRIPTION
            "Coding    Contents              Description
             0         no LIM                Default value                                                         
             1         A1.5                  ATM 1.544 Mbit/s module                                               
             2         A2                    ATM 2.048 Mbit/s                                                      
             3         A6.3                  ATM 6.312 Mbit/s module                                               
             4         A6.3U                 ATM 6.312 Mbit/s module, Remote (U-interface)                         
             5         A8                    ATM 8.448 Mbit/s                                                      
             6         A25                   ATM 25.6 Mbit/s module                                                
             7         A34                   ATM 34.368 Mbit/s module                                              
             8         A45                   ATM 44.736 Mbit/s module                                              
             9         A45/34                Configurable ATM 44.736/34.368 Mbit/s module                          
             10        A150SMF SDH           ATM STM-1 SMF UNI                                                     
             11        A150MMF SDH           ATM STM-1 MMF UNI                                                     
             12        A150UTP SDH           ATM STM-1 UTP UNI                                                     
             13        C1.5 (DS1)            1.544 Mbit/s Local (T-interface) AAL 1 module                         
             14        C2.0 (E1)             2.048 Mbit/s Local (T-interface) AAL 1 module                         
             15        C6.3 (J2)             6.312 Mbit/s Local (T-interface) AAL 1 module                         
             16        C-DS1/E1              Configurable DS1/E1 AAL 1 module                                      
             17        C-DS1/E1/J1           Configurable DS1/E1/J1 AAL 1 module                                   
             18        C6.3U (J2)            6.312 Mbit/s Remote (U-interface) AAL 1 module                        
             19        C192k                 192 kbit/s Local (T-interface) AAL 1 module                           
             20        C44.7 (DS3)           44.736 Mbit/s Local (T-interface) AAL 1 module                        
             21        C34.3 (E3)            34.368 Mbit/s Local (T-interface) AAL 1 module                        
             22        10Base-T              10 Base-T Ethernet LAN IF                                             
             23        100Base-T             100 Base-T Ethernet LAN IF                                            
             24        10/100Base-T          10/100 Base-T Ethernet LAN IF                                         
             25        Token Ring            Token Ring LAN IF                                                     
             26        FDDI                  FDDI LAN IF                                                           
             27        FR                    Frame relay                                                           
             28        C1.5 (J1)             1.544 Mbit/s Local (T-interface) AAL 1 module                         
             29        A150SMF SONET         ATM OC-3 SMF UNI                                                      
             30        A150MMF SONET         ATM OC-3 MMF UNI                                                      
             31        A150UTP SONET         ATM OC-3 UTP UNI                                                      
             32        POTS                  Plain Old Telephony Service                                           
             33        ISDN-BRI              ISDN Basic Rate Interface                                             
             34        Gigabit Ethernet      Gigabit Ethernet IF                                                   
             35        ADSL                  ADSL IF                                                               
             36        SHDSL                 SHDSL IF                                                              
             37        VDSL                  VDSL IF                                                               
             38        Video Service         Video module                                                          
             39..251   Reserved                                                                                    
             252       PON622symm            Symmetric 622/622 Mbit/s PON IF                                       
             253       PON155                Symmetric 155/155 Mbit/s PON IF                                       
             254       PON622                Asymmetric 155/622 Mbit/s PON IF                                      
             255       Plug-and-play/Unknown Plug-and-play (for the Subscriber Line Cardholder managed entity only)
                                             Unrecognized module (for the Subscriber Line Card managed entity only)
             It may be 22,23,24,34 and so on. It may be created/read/written/modified.Writing or 
             modifing can be done when the entry SHOULD NOT be used by any other entry."
        REFERENCE
            "G.983.2 7.3.2 Physical path termination point ethernet UNI"
        DEFVAL  { 0 }
        ::= { zxGponPPTPEthUniInfoEntry 3}

   zxGponPPTPEthInfoSensedType OBJECT-TYPE
        SYNTAX      INTEGER
        MAX-ACCESS  read-only
        STATUS      current
        DESCRIPTION
            "If the value of 'Expected type' is not equal to 0x00, then the value of 'Sensed type' 
             equals the value of 'Expected type'. If the value of 'Expected type' equals 0x00, 
             then the value of 'Sensed type' = one of the values from Table 3 and by necessity is 
             compatible with the Type of Subscriber Line Card managed entity. Upon autonomous 
             instantiation, the value 0x00 is used. (R) (mandatory if the ONT supports LIMs with 
             configurable interface types, e.g. 10/100 Base-T card) "
        ::= { zxGponPPTPEthUniInfoEntry 4}
        
   zxGponPPTPEthInfoAutoDetectCfg OBJECT-TYPE
        SYNTAX      INTEGER
        MAX-ACCESS  read-write
        STATUS      current
        DESCRIPTION
            "For 10/100 Base-T Ethernet interfaces, this attribute is used to set the configuration options: 
             Auto-sensing: 0x00; 10Base-T: 0x01; 100Base-T: 0x02: Gigabit Ethernet: 0x03. "
        ::= { zxGponPPTPEthUniInfoEntry 5}
        
   zxGponPPTPEthInfoEthLoopback OBJECT-TYPE
        SYNTAX      INTEGER{
                    normal(1),
                    loop(2)
                    }
        MAX-ACCESS  read-write
        STATUS      current
        DESCRIPTION
            "This attribute is used to set the Ethernet loopback configuration: No loopback 
             (value normal), Loop3 (value loop, Loopback of downstream traffic after PHY 
             transceiver). Loop 3 is depicted in Figure 11a. Upon autonomous instantiation, 
             the value 0x00 is used."
        ::= { zxGponPPTPEthUniInfoEntry 6}

   zxGponPPTPEthInfoAdminState OBJECT-TYPE
        SYNTAX      INTEGER{
                    enabled(1),
                    disabled(2)
                    }
        MAX-ACCESS  read-write
        STATUS      current
        DESCRIPTION
            "This attribute is used to activate (unlock: value enabled) and deactivate 
             (lock: value disabled) the functions performed by instances of this managed entity. 
             Selection of a default value for this attribute is outside the scope of this 
             Recommendation as it is normally handled through supplier-operator negotiations. "
        ::= { zxGponPPTPEthUniInfoEntry 7}
        
   zxGponPPTPEthInfoOperationalState OBJECT-TYPE
        SYNTAX      INTEGER{
                    enabled(1),
                    disabled(2)
                    }
        MAX-ACCESS  read-only
        STATUS      current
        DESCRIPTION
            "This attribute indicates whether or not this managed entity is capable of performing 
             its task. The operational state reflects the perceived ability to receive or to 
             generate a valid signal. Valid values are enabled (enabled) and disabled (disabled)."
        ::= { zxGponPPTPEthUniInfoEntry 8}

    zxGponPPTPEthInfoDuplexSpeedInd OBJECT-TYPE
        SYNTAX      INTEGER{
                    autonegotiate(1),
                    half-10(2),
                    full-10(3),
                    half-100(4),
                    full-100(5),             
                    full-1000(6)
                    }
        MAX-ACCESS  read-only
        STATUS      current
        DESCRIPTION
            "For 10/100 Base-T Ethernet interfaces, it is used to set the configuration options:
             Auto-sensing(incluing speed and duplex): 1; It comprises 'Auto detection configuration'
             and 'DuplexInd' in G.983.2.It may be created/read/written/modified.Writing or 
             modifing can be done when the entry SHOULD NOT be used by any other entry."
        REFERENCE
            "G.983.2 7.3.2 Physical path termination point ethernet UNI"
        DEFVAL  { autonegotiate }
        ::= { zxGponPPTPEthUniInfoEntry 9}

    zxGponPPTPEthInfoMaxFrameSize OBJECT-TYPE
        SYNTAX      INTEGER
        MAX-ACCESS  read-write
        STATUS      current
        DESCRIPTION
            "It denotes the maximum allowed frame size to be transmitted across this interface.
             It may be created/read/written/modified.Writing or modifing can be done when the 
             entry SHOULD NOT be used by any other entry."
        REFERENCE
            "G.983.2 7.3.2 Physical path termination point ethernet UNI"
        DEFVAL  { 1518 }
        ::= { zxGponPPTPEthUniInfoEntry 10}

    zxGponPPTPEthInfoDTEorDCEInd OBJECT-TYPE
        SYNTAX      INTEGER{
                    dce(1),
                    dte(2)
                    }
        MAX-ACCESS  read-write
        STATUS      current
        DESCRIPTION
            "It indicates whether the Ethernet interface wiring is DTE(2) or DCE(1). It may be
             created/read/written/modified.Writing or modifing can be done when the entry SHOULD
             NOT be used by any other entry."
        REFERENCE
            "G.983.2 7.3.2 Physical path termination point ethernet UNI"
        DEFVAL  { dce }
        ::= { zxGponPPTPEthUniInfoEntry 11}

    zxGponPPTPEthInfoPauseTime OBJECT-TYPE
        SYNTAX      INTEGER(0..65535)
        MAX-ACCESS  read-write
        STATUS      current
        DESCRIPTION
            "It allows the ONT line card to request that the customer terminal temporarily suspend sending
             data. Units are in 'pause_quanta' (1 pause_quantum equals 512 bits times of the particular 
             implementation).It may be created/read/written/modified.Writing or modifing can be done when
             the entry SHOULD NOT be used by any other entry."
        REFERENCE
            "G.983.2 7.3.2 Physical path termination point ethernet UNI"
        DEFVAL  { 0 }
        ::= { zxGponPPTPEthUniInfoEntry 12}

    zxGponPPTPEthInfoBridgedorIPInd OBJECT-TYPE
        SYNTAX      INTEGER{
                    bridged(1),
                    iprouter(2),
                    auto(3)
                    }
        MAX-ACCESS  read-write
        STATUS      current
        DESCRIPTION
            "It indicates whether the Ethernet interface is bridged or derived from an IP router function
             (Bridged: 1; IP router: 2; 3: depends on Subscriber Line Card.) 3 means that the SLC(Subscriber
             Line Card) will be either Bridged or IP router. It may be created/read/written/modified.Writing
             or modifing can be done when the entry SHOULD NOT be used by any other entry."
        REFERENCE
            "G.983.2 7.3.2 Physical path termination point ethernet UNI"
        DEFVAL  { auto }
        ::= { zxGponPPTPEthUniInfoEntry 13}

    zxGponPPTPEthInfoARC OBJECT-TYPE
        SYNTAX      INTEGER{
                    off(1),
                    on(2)
                    }
        MAX-ACCESS  read-write
        STATUS      current
        DESCRIPTION
            "It is used to control alarm reporting from this ONT(managed entity). off means alarm reporting
             allowed immediately and on means alarm reporting inhibited, until this ONT(managed entity) detects
             a valid signal for the time interval specified by 'zxGponPPTPEthUNITempletARCInterval'. It may
             be created/read/written/modified.Writing or modifing can be done when the entry SHOULD NOT
             be used by any other entry."
        REFERENCE
            "G.983.2 7.3.2 Physical path termination point ethernet UNI"
        DEFVAL  { on }
        ::= { zxGponPPTPEthUniInfoEntry 14}

    zxGponPPTPEthInfoARCInterval OBJECT-TYPE
        SYNTAX      INTEGER(1..255)
        MAX-ACCESS  read-write
        STATUS      current
        DESCRIPTION
            "It provides a provisionable length of time. Units are given in minutes. It may
             be created/read/written/modified.Writing or modifing can be done when the entry SHOULD NOT
             be used by any other entry."
        REFERENCE
            "G.983.2 7.3.2 Physical path termination point ethernet UNI"
        DEFVAL  { 1 }
        ::= { zxGponPPTPEthUniInfoEntry 15}

   zxGponPPTPEthInfoPppoeFilterEnable OBJECT-TYPE
        SYNTAX      INTEGER{
                    enabled(1),
                    disabled(2)
                    }
        MAX-ACCESS  read-write
        STATUS      current
        DESCRIPTION
            "It may be used to control filtering of PPPoE packets on this Ethernet port. The disabled is
             used to disable filtering. The enabled is used to enable filtering. When filtering is enabled,
             all packets other than PPPoE packets will be discarded."
        DEFVAL  { disabled }
        ::= { zxGponPPTPEthUniInfoEntry 16}
        
        
    zxGponMACBSPInfoTable OBJECT-TYPE
        SYNTAX      SEQUENCE OF ZxGponMACBSPInfoEntry
        MAX-ACCESS  not-accessible
        STATUS      current
        DESCRIPTION
            "This managed entity is used to organize data that affects all ports on a MAC Bridge 
             at a bridged LAN Ethernet UNI interface on the ONT. Instances of this managed 
             entity are created and deleted by request of the OLT.''" 
        REFERENCE
            "G.983.2 Rev 7.3.29 MAC Bridge Service Profile"
        ::= { ethernetUniMib 2 }
        
    zxGponMACBSPInfoEntry OBJECT-TYPE
        SYNTAX      ZxGponMACBSPInfoEntry
        MAX-ACCESS  not-accessible
        STATUS      current
        DESCRIPTION
            "This managed entity is used to organize data that affects all ports on a MAC Bridge 
             at a bridged LAN Ethernet UNI interface on the ONT."
        INDEX   { zxGponMgmtPonOltId, zxGponMgmtPonOnuId, zxGponMACBSPInfoMeIdIdx }
        ::= { zxGponMACBSPInfoTable 1 }

    ZxGponMACBSPInfoEntry ::=
        SEQUENCE {
            zxGponMACBSPInfoMeIdIdx      INTEGER,
            zxGponMACBSPInfoSTPInd       TruthValue,
            zxGponMACBSPInfoLearningInd  TruthValue,
            zxGponMACBSPInfoPortBInd     TruthValue,
            zxGponMACBSPInfoPriority     INTEGER,
            zxGponMACBSPInfoMaxAge       Timeout,
            zxGponMACBSPInfoHelloTime    Timeout,
            zxGponMACBSPInfoForwardDelay Timeout,
            zxGponMACBSPInfoMgmtCtrlFlag INTEGER,
            zxGponMACBSPInfoEntryStatus  RowStatus
        }

   zxGponMACBSPInfoMeIdIdx OBJECT-TYPE
        SYNTAX      INTEGER
        MAX-ACCESS  not-accessible
        STATUS      current
        DESCRIPTION
            "This attribute provides a unique number for each instance of this managed entity. 
             The first byte is the slot id (defined in 7.1.3). If the UNI is integrated, this 
             value is 0x00. The second byte is the bridge group id, it is MeId."
        ::= { zxGponMACBSPInfoEntry 1}
        
    zxGponMACBSPInfoSTPInd OBJECT-TYPE
        SYNTAX      TruthValue
        MAX-ACCESS  read-write
        STATUS      current
        DESCRIPTION
            "It indicates whether or not a spanning tree algorithm(protocol) is enabled.
             The value TRUE means enabled. It may be created/read/written/modified.Writing or 
             modifing can be done when the entry SHOULD NOT be used by any other entry."
        REFERENCE
            "G.983.2 7.3.29 MAC bridge service profile"
        ::= { zxGponMACBSPInfoEntry 2}

    zxGponMACBSPInfoLearningInd OBJECT-TYPE
        SYNTAX      TruthValue
        MAX-ACCESS  read-write
        STATUS      current
        DESCRIPTION
            "It indicates whether or not the learning functions of the bridge are enabled.
             The value TRUE means enabled. It may be created/read/written/modified.Writing or 
             modifing can be done when the entry SHOULD NOT be used by any other entry."
        REFERENCE
            "G.983.2 7.3.29 MAC bridge service profile"
        ::= { zxGponMACBSPInfoEntry 3}

    zxGponMACBSPInfoPortBInd OBJECT-TYPE
        SYNTAX      TruthValue
        MAX-ACCESS  read-write
        STATUS      current
        DESCRIPTION
            "It indicates whether or not bridging between FE ports is enabled. The value TRUE
             means enabled. It may be created/read/written/modified.Writing or modifing can be
             done when the entry SHOULD NOT be used by any other entry."
        REFERENCE
            "G.983.2 7.3.29 MAC bridge service profile"
        ::= { zxGponMACBSPInfoEntry 4}

    zxGponMACBSPInfoPriority OBJECT-TYPE
        SYNTAX      INTEGER(0..65535)
        MAX-ACCESS  read-write
        STATUS      current
        DESCRIPTION
            "It indicates the bridge priority set on the LAN card(or MAC bridge). The value of this
             object is reflected to the BridgePriority attribute of the MAC Bridge Configuration Data
             managed entity. It may be created/read/written/modified.Writing or modifing can be done
             when the entry SHOULD NOT be used by any other entry."
        REFERENCE
            "G.983.2 7.3.29 MAC bridge service profile"
        ::= { zxGponMACBSPInfoEntry 5}

    zxGponMACBSPInfoMaxAge OBJECT-TYPE
        SYNTAX      Timeout(600..4000)
        MAX-ACCESS  read-write
        STATUS      current
        DESCRIPTION
            "The maximum age of Spanning Tree Protocol information learned from the network on any
             port before it is discarded, in units of hundredths of a second. But G.983.2 in units
             of 256ths of a second, The range is 0x0600 to 0x2800. It may be created/read/written/
             modified.Writing or modifing can be done when the entry SHOULD NOT be used by any other entry."
        REFERENCE
            "G.983.2 7.3.29 MAC bridge service profile"
        ::= { zxGponMACBSPInfoEntry 6}

    zxGponMACBSPInfoHelloTime OBJECT-TYPE
        SYNTAX      Timeout(100..1000)
        MAX-ACCESS  read-write
        STATUS      current
        DESCRIPTION
            "It uses for HelloTime when this bridge is acting as the root or that a bridge advertises
             its presence while as a root or attempting to become a root, in units of hundredths of a
             second. But G.983.2 in units of 256ths of a second, The range is 0x0100 to 0x0a00. It may
             be created/read/written/modified.Writing or modifing can be done when the entry SHOULD NOT
             be used by any other entry."
        REFERENCE
            "G.983.2 7.3.29 MAC bridge service profile"
        ::= { zxGponMACBSPInfoEntry 7}

    zxGponMACBSPInfoForwardDelay OBJECT-TYPE
        SYNTAX      Timeout(400..3000)
        MAX-ACCESS  read-write
        STATUS      current
        DESCRIPTION
            "It uses for ForwardDelay when this bridge is acting as the root or that the bridge on the
             Ethernet card in the ONT retains a packet before forwarding it, in units of hundredths of a
             second. But G.983.2 in units of 256ths of a second, The range is 0x0400  to 0x1e00. It may
             be created/read/written/modified.Writing or modifing can be done when the entry SHOULD NOT
             be used by any other entry."
        REFERENCE
            "G.983.2 7.3.29 MAC bridge service profile"
        ::= { zxGponMACBSPInfoEntry 8}

    zxGponMACBSPInfoMgmtCtrlFlag OBJECT-TYPE
        SYNTAX      INTEGER{
                    nmsCreate(1),
                    neCreate(2)
                    }
        MAX-ACCESS  read-only
        STATUS      current
        DESCRIPTION
            "This attribute is used to indicate this record is created by NMS or NE. If it
             is neCreate(2), this record can not be deleted."
        REFERENCE
            "N/A"
        ::= { zxGponMACBSPInfoEntry 9}

    zxGponMACBSPInfoEntryStatus       OBJECT-TYPE
      SYNTAX      RowStatus
      MAX-ACCESS  read-create
      STATUS      current 
      DESCRIPTION 
        "This attribute can be create and delete."
      REFERENCE   "N/A"
      ::= { zxGponMACBSPInfoEntry 10 }

    zxGponMACBridgeCfgDataInfoTable OBJECT-TYPE
        SYNTAX      SEQUENCE OF ZxGponMACBridgeCfgDataInfoEntry
        MAX-ACCESS  not-accessible
        STATUS      current
        DESCRIPTION
            "This managed entity is used to organize and record data that is associated with 
             bridged LAN configurations. Some of the data is volatile. Instances of this 
             managed entity shall be automatically created/deleted by the ONT upon the 
             creation/deletion of a MACBridgeServiceProfile." 
        REFERENCE
            "G.983.2 Rev 7.3.30 MAC Bridge Configuration Data"
        ::= { ethernetUniMib 3 }

    zxGponMACBridgeCfgDataInfoEntry OBJECT-TYPE
        SYNTAX      ZxGponMACBridgeCfgDataInfoEntry
        MAX-ACCESS  not-accessible
        STATUS      current
        DESCRIPTION
            "This managed entity is associated with one instance of a MACBridgeServiceProfile."
        INDEX   { zxGponMgmtPonOltId, zxGponMgmtPonOnuId, zxGponMACBSPInfoMeIdIdx }
        ::= { zxGponMACBridgeCfgDataInfoTable 1 }

    ZxGponMACBridgeCfgDataInfoEntry ::=
        SEQUENCE {
            zxGponMACBCfgDataBridgeMACAddress MacAddress,
            zxGponMACBCfgDataBridgePriority   INTEGER,
            zxGponMACBCfgDataDesignatedRoot   INTEGER,
            zxGponMACBCfgDataRootPathCost     INTEGER,
            zxGponMACBCfgDataBridgePortCount  INTEGER,
            zxGponMACBCfgDataRootPortNum      INTEGER,
            zxGponMACBCfgDataHelloTime        INTEGER,
            zxGponMACBCfgDataForwardDelay     INTEGER
        }

   zxGponMACBCfgDataBridgeMACAddress OBJECT-TYPE
        SYNTAX      MacAddress
        MAX-ACCESS  read-only
        STATUS      current
        DESCRIPTION
            "This attribute indicates the MAC address used by the bridge. Upon autonomous 
             instantiation, this attribute consists of all 0x00."
        ::= { zxGponMACBridgeCfgDataInfoEntry 1}        

   zxGponMACBCfgDataBridgePriority OBJECT-TYPE
        SYNTAX      INTEGER
        MAX-ACCESS  read-only
        STATUS      current
        DESCRIPTION
            "This attribute denotes the priority of the bridge and is positive 
             integer-valued. Upon autonomous instantiation, the value 0x8000 is used."
        ::= { zxGponMACBridgeCfgDataInfoEntry 2}

   zxGponMACBCfgDataDesignatedRoot OBJECT-TYPE
        SYNTAX      INTEGER
        MAX-ACCESS  read-only
        STATUS      current
        DESCRIPTION
            "This attribute provides the bridge identifier for the root of the spanning 
             tree. This attribute consists of Bridge Priority (2 bytes) and MAC 
             address (6 bytes)."
        ::= { zxGponMACBridgeCfgDataInfoEntry 3}        

   zxGponMACBCfgDataRootPathCost OBJECT-TYPE
        SYNTAX      INTEGER
        MAX-ACCESS  read-only
        STATUS      current
        DESCRIPTION
            "This attribute provides the cost of the best path to the root as seen 
             from the bridge. Upon autonomous instantiation, the value 0x00 is used. "
        ::= { zxGponMACBridgeCfgDataInfoEntry 4}

   zxGponMACBCfgDataBridgePortCount OBJECT-TYPE
        SYNTAX      INTEGER
        MAX-ACCESS  read-only
        STATUS      current
        DESCRIPTION
            "This attribute provides the number of existing ports controlled by this bridge. "
        ::= { zxGponMACBridgeCfgDataInfoEntry 5}        

   zxGponMACBCfgDataRootPortNum OBJECT-TYPE
        SYNTAX      INTEGER
        MAX-ACCESS  read-only
        STATUS      current
        DESCRIPTION
            "This attribute provides the port number that has the lowest cost from the 
             bridge to the root bridge. The value 0x00 means that the port itself is the root. 
             Upon autonomous instantiation, the value 0x00 is used. "
        ::= { zxGponMACBridgeCfgDataInfoEntry 6}

   zxGponMACBCfgDataHelloTime OBJECT-TYPE
        SYNTAX      INTEGER
        MAX-ACCESS  read-only
        STATUS      current
        DESCRIPTION
            "This attribute provides the time interval (in 256ths of a second) between hello 
             packets. It is the 'HelloTime' received from the designated root. The range 
             is 0x0100 to 0x0a00 (1 s to 10 s) in accordance with IEEE 802.1D [14]."
        ::= { zxGponMACBridgeCfgDataInfoEntry 7}        

   zxGponMACBCfgDataForwardDelay OBJECT-TYPE
        SYNTAX      INTEGER
        MAX-ACCESS  read-only
        STATUS      current
        DESCRIPTION
            "This attribute gives the time (in 256ths of a second) that the bridge on the 
             Ethernet card in the ONT retains a packet before forwarding it. It is the 
             'ForwardDelay' time received from the designated root. The range is 0x0400 
             to 0x1e00 (4 s to 30 s) in accordance with IEEE 802.1D [14]."
        ::= { zxGponMACBridgeCfgDataInfoEntry 8}        


    zxGponMACBriPortCfgDataInfoTable OBJECT-TYPE
        SYNTAX      SEQUENCE OF ZxGponMACBriPortCfgDataInfoEntry
        MAX-ACCESS  not-accessible
        STATUS      current
        DESCRIPTION
            "This managed entity is used to organize and record data that is associated 
             with a bridge port. Some of the data is volatile. Instances of this managed 
             entity are created and deleted by request of the OLT." 
        REFERENCE
            "G.983.2 Rev 7.3.31 MAC Bridge Port Configuration Data"
        ::= { ethernetUniMib 4 }

    zxGponMACBriPortCfgDataInfoEntry OBJECT-TYPE
        SYNTAX      ZxGponMACBriPortCfgDataInfoEntry
        MAX-ACCESS  not-accessible
        STATUS      current
        DESCRIPTION
            "Zero or more instances of this managed entity shall be contained in an 
             instance of the MACBridgeServiceProfile."
        INDEX   { zxGponMgmtPonOltId, zxGponMgmtPonOnuId, zxGponMACBriPortCfgDataMeIdIdx }
        ::= { zxGponMACBriPortCfgDataInfoTable 1 }

    ZxGponMACBriPortCfgDataInfoEntry ::=
        SEQUENCE {
            zxGponMACBriPortCfgDataMeIdIdx         INTEGER,
            zxGponMACBriPortCfgDataBridgeIdPtr     INTEGER,
            zxGponMACBriPortCfgDataPortNum         INTEGER,
            zxGponMACBriPortCfgDataTPType          INTEGER,
            zxGponMACBriPortCfgDataTPPointer       INTEGER,
            zxGponMACBriPortCfgDataPortPriority    INTEGER,
            zxGponMACBriPortCfgDataPortPathCost    INTEGER,
            zxGponMACBriPortCfgDataPortSpanTreeInd TruthValue,
            zxGponMACBriPortCfgDataEncapMethod     INTEGER,
            zxGponMACBriPortCfgDataLANFCSInd       INTEGER,
            zxGponMACBriPortCfgDataMgmtCtrlFlag    INTEGER,
            zxGponMACBriPortCfgDataEntryStatus     RowStatus
        }
 
   zxGponMACBriPortCfgDataMeIdIdx OBJECT-TYPE
        SYNTAX      INTEGER
        MAX-ACCESS  not-accessible
        STATUS      current
        DESCRIPTION
            "This attribute provides a unique number for each instance of this managed entity."
        ::= { zxGponMACBriPortCfgDataInfoEntry 1}

   zxGponMACBriPortCfgDataBridgeIdPtr OBJECT-TYPE
        SYNTAX      INTEGER
        MAX-ACCESS  read-write
        STATUS      current
        DESCRIPTION
            "This attribute identifies the MAC bridge controlling the port. This attribute 
             points to the instance of the MACBridgeServiceProfile."
        ::= { zxGponMACBriPortCfgDataInfoEntry 2}

   zxGponMACBriPortCfgDataPortNum OBJECT-TYPE
        SYNTAX      INTEGER
        MAX-ACCESS  read-write
        STATUS      current
        DESCRIPTION
            "This attribute provides the port number."
        ::= { zxGponMACBriPortCfgDataInfoEntry 3}

   zxGponMACBriPortCfgDataTPType OBJECT-TYPE
        SYNTAX      INTEGER
        MAX-ACCESS  read-write
        STATUS      current
        DESCRIPTION
            "This attribute identifies the type of the termination point associated with 
             this MAC bridge port. The value is set to 0x01 if this bridge port is associated 
             with the LAN side's termination point. The value is set to 0x02 if this bridge 
             port is associated with the ATM side's termination point."
        ::= { zxGponMACBriPortCfgDataInfoEntry 4}
        
   zxGponMACBriPortCfgDataTPPointer OBJECT-TYPE
        SYNTAX      INTEGER
        MAX-ACCESS  read-write
        STATUS      current
        DESCRIPTION
            "This attribute points to the termination point associated with this MAC bridge 
             port. The value of this attribute is the same as the id of the Physical Path 
             Termination Point Ethernet UNI associated with this MAC bridge port."
        ::= { zxGponMACBriPortCfgDataInfoEntry 5}

   zxGponMACBriPortCfgDataPortPriority OBJECT-TYPE
        SYNTAX      INTEGER
        MAX-ACCESS  read-write
        STATUS      current
        DESCRIPTION
            "This attribute denotes the priority of the port. The range is 0x00 to 0x00FF (0 to 255)."
        ::= { zxGponMACBriPortCfgDataInfoEntry 6}

   zxGponMACBriPortCfgDataPortPathCost OBJECT-TYPE
        SYNTAX      INTEGER
        MAX-ACCESS  read-write
        STATUS      current
        DESCRIPTION
            "This attribute provides the cost contribution of the port to the path cost towards 
             the spanning tree root bridge. The range is 0x0001 to 0xFFFF (1 to 65 535). "
        ::= { zxGponMACBriPortCfgDataInfoEntry 7}

   zxGponMACBriPortCfgDataPortSpanTreeInd OBJECT-TYPE
        SYNTAX      TruthValue
        MAX-ACCESS  read-write
        STATUS      current
        DESCRIPTION
            "This Boolean attribute indicates whether or not STP is enabled at this port. 
             The value TRUE means enabled. "
        ::= { zxGponMACBriPortCfgDataInfoEntry 8}
        
   zxGponMACBriPortCfgDataEncapMethod OBJECT-TYPE
        SYNTAX      INTEGER
        MAX-ACCESS  read-write
        STATUS      current
        DESCRIPTION
            "This attribute identifies the frame encapsulation method that is used. Value 
             0x00: identification by ATM VC; value 0x01: LLC encapsulation. Upon autonomous 
             instantiation, the value 0x00 is used."
        ::= { zxGponMACBriPortCfgDataInfoEntry 9}

   zxGponMACBriPortCfgDataLANFCSInd OBJECT-TYPE
        SYNTAX      INTEGER{
                    forward(1),
                    discarded(2)
                    }
        MAX-ACCESS  read-write
        STATUS      current
        DESCRIPTION
            "This attribute indicates whether LAN FCS (Frame Check Sequence) bytes are forwarded 
             (value 0x01) or discarded (value 0x02) towards the OLT. Upon autonomous instantiation, 
             the value 0x00 is used."
        ::= { zxGponMACBriPortCfgDataInfoEntry 10}

    zxGponMACBriPortCfgDataMgmtCtrlFlag OBJECT-TYPE
        SYNTAX      INTEGER{
                    nmsCreate(1),
                    neCreate(2)
                    }
        MAX-ACCESS  read-only
        STATUS      current
        DESCRIPTION
            "This attribute is used to indicate this record is created by NMS or NE. If it
             is neCreate(2), this record can not be deleted."
        REFERENCE
            "N/A"
        ::= { zxGponMACBriPortCfgDataInfoEntry 11}

    zxGponMACBriPortCfgDataEntryStatus       OBJECT-TYPE
      SYNTAX      RowStatus
      MAX-ACCESS  read-create
      STATUS      current 
      DESCRIPTION 
        "This attribute can be create and delete."
      REFERENCE   "N/A"
      ::= { zxGponMACBriPortCfgDataInfoEntry 12 }


    zxGponMACBriPortFilterTableInfoTable OBJECT-TYPE
        SYNTAX      SEQUENCE OF ZxGponMACBriPortFilterTableInfoEntry
        MAX-ACCESS  not-accessible
        STATUS      current
        DESCRIPTION
            "This managed entity is used to organize and record data that is associated with a 
             bridge port. Some of the data is volatile. Instances of this managed entity shall 
             be automatically created/deleted by the ONT upon the creation/deletion of a 
             MACBridgePortConfigurationData managed entity." 
        REFERENCE
            "G.983.2 7.3.33"
        ::= { ethernetUniMib 5 }

    zxGponMACBriPortFilterTableInfoEntry OBJECT-TYPE
        SYNTAX      ZxGponMACBriPortFilterTableInfoEntry
        MAX-ACCESS  not-accessible
        STATUS      current
        DESCRIPTION
            " Alternative schemes for this managed entity may be included in future Recommendations."
        INDEX   { zxGponMgmtPonOltId, zxGponMgmtPonOnuId, zxGponMACBriPortCfgDataMeIdIdx, zxGponMACBriPortFilterTableMacAddr }
        ::= { zxGponMACBriPortFilterTableInfoTable 1 }

    ZxGponMACBriPortFilterTableInfoEntry ::=
        SEQUENCE {
            zxGponMACBriPortFilterTableMacAddr     MacAddress,
            zxGponMACBriPortFilterTableAction      INTEGER,
            zxGponMACBriPortFilterTableEntryStatus RowStatus
        }

   zxGponMACBriPortFilterTableMacAddr OBJECT-TYPE
        SYNTAX      MacAddress
        MAX-ACCESS  not-accessible
        STATUS      current
        DESCRIPTION
            "This attribute lists destination MAC Addresses associated with the bridge port."
        ::= { zxGponMACBriPortFilterTableInfoEntry 1}

   zxGponMACBriPortFilterTableAction OBJECT-TYPE
        SYNTAX      INTEGER{
                    forward(1),
                    filter(2)
                    }
        MAX-ACCESS  read-write
        STATUS      current
        DESCRIPTION
            ""
        ::= { zxGponMACBriPortFilterTableInfoEntry 2}

   zxGponMACBriPortFilterTableEntryStatus OBJECT-TYPE
        SYNTAX      RowStatus
        MAX-ACCESS  read-create
        STATUS      current
        DESCRIPTION
            ""
        ::= { zxGponMACBriPortFilterTableInfoEntry 3}

    --G.983.2 Rev 7.3.32    MAC Bridge Port Designation Data
    zxGponMACBriPortDesignationDataTable OBJECT-TYPE
        SYNTAX      SEQUENCE OF ZxGponMACBriPortDesignationDataEntry
        MAX-ACCESS  not-accessible
        STATUS      current
        DESCRIPTION
            "This managed entity is used to organize and record data that is associated with a bridge port.
             Some of the data is volatile.  Instances of this managed entity shall be automatically created/
             deleted by the ONT upon the creation/deletion of a MACBridgePortConfigurationData." 
        REFERENCE
            "G.983.2 7.3.32"
        ::= { ethernetUniMib 6 }

    zxGponMACBriPortDesignationDataEntry OBJECT-TYPE
        SYNTAX      ZxGponMACBriPortDesignationDataEntry
        MAX-ACCESS  not-accessible
        STATUS      current
        DESCRIPTION
            ""
        INDEX   { zxGponMgmtPonOltId, zxGponMgmtPonOnuId, zxGponMACBSPInfoMeIdIdx }
        ::= { zxGponMACBriPortDesignationDataTable 1 }

    ZxGponMACBriPortDesignationDataEntry ::=
        SEQUENCE {
            zxGponMACBriPortDesignationDataRootCostPort OCTET STRING,
            zxGponMACBriPortDesignationDataPortState    INTEGER
        }

   zxGponMACBriPortDesignationDataRootCostPort OBJECT-TYPE
        SYNTAX      OCTET STRING(SIZE(24))
        MAX-ACCESS  read-only
        STATUS      current
        DESCRIPTION
            "This attribute provides the Designated Root, Designated Cost, Designated Bridge,
             and Designated Port outputs of the 'Read port parameters' operation defined in 14.
             8.2.1 of IEEE 802.1D [14], i.e.,
             -bridge identifier of the designated bridge for the port's segment (8 bytes)
             -bridge identifier of the root transmitted by the designated bridge for the segment (8 bytes)
             -port number of the designated port on the designated bridge considered to be part of this port's segment (4 bytes)
             -path cost contribution of the designated port to this port's segment (4 bytes) 
             Upon autonomous instantiation, this attribute consists of all 0x00."
        ::= { zxGponMACBriPortDesignationDataEntry 1}

   zxGponMACBriPortDesignationDataPortState OBJECT-TYPE
        SYNTAX      INTEGER
        MAX-ACCESS  read-only
        STATUS      current
        DESCRIPTION
            "This attribute provides status information on the port. Valid values include 'disabled'(value 0x00),
             'listening' (value 0x01), 'learning' (value 0x02), 'forwarding' (0x03), 'blocking' (value 0x04),
             'linkdown' (value 0x05), and 'stp_off' (value 0x06) in accordance with IEEE 802.1D [14]. 
             (Note:  The value 'linkdown' is introduced to denote the port status where the Ethernet link state
             is down. This value is necessary to distinguish the case where Ethernet is physically down and
             the case where Ethernet is administratively down, which can be denoted by 'disabled.'  The value 
             'stp_off' is introduced to denote the port status where Spanning Tree Protocol is disabled, by
             setting 'PortSpanningTreeInd' of 'MAC Bridge Port Configuration Data' to FALSE, and Ethernet link
             state is up. This value is used to distinguish whether or not a bridge port forwarding frames is
             under control of STP.)  Upon autonomous instantiation, the value 0x00 is used."
        ::= { zxGponMACBriPortDesignationDataEntry 2}

    -- G.983.2 Rev 7.3.34 MAC Bridge Port Bridge Table Data
    zxGponMACBriPortAddrInfoTable OBJECT-TYPE
        SYNTAX      SEQUENCE OF ZxGponMACBriPortAddrInfoEntry
        MAX-ACCESS  not-accessible
        STATUS      current
        DESCRIPTION
            "This managed entity is used to organize and record data that is associated with a bridge port.
             Some of the data is volatile.  Instances of this managed entity shall be automatically created/
             deleted by the ONT upon the creation/deletion of a MACBridgePortConfigurationData." 
        REFERENCE
            "G.983.2 7.3.34"
        ::= { ethernetUniMib 7 }

    zxGponMACBriPortAddrInfoEntry OBJECT-TYPE
        SYNTAX      ZxGponMACBriPortAddrInfoEntry
        MAX-ACCESS  not-accessible
        STATUS      current
        DESCRIPTION
            " Alternative schemes for this managed entity may be included in future Recommendations."
        INDEX   { zxGponMgmtPonOltId, zxGponMgmtPonOnuId, zxGponMACBriPortCfgDataMeIdIdx, zxGponMACBriPortAddrMacAddr }
        ::= { zxGponMACBriPortAddrInfoTable 1 }

    ZxGponMACBriPortAddrInfoEntry ::=
        SEQUENCE {
            zxGponMACBriPortAddrMacAddr     MacAddress,
            zxGponMACBriPortAddrAction      INTEGER,
            zxGponMACBriPortAddrDynStatic   INTEGER,
            zxGponMACBriPortAddrAgingTime   INTEGER
        }

   zxGponMACBriPortAddrMacAddr OBJECT-TYPE
        SYNTAX      MacAddress
        MAX-ACCESS  not-accessible
        STATUS      current
        DESCRIPTION
            "This attribute lists destination MAC Addresses associated with the bridge port."
        ::= { zxGponMACBriPortAddrInfoEntry 1}

   zxGponMACBriPortAddrAction OBJECT-TYPE
        SYNTAX      INTEGER{
                    forward(1),
                    filter(2)
                    }
        MAX-ACCESS  read-only
        STATUS      current
        DESCRIPTION
            ""
        ::= { zxGponMACBriPortAddrInfoEntry 2}

   zxGponMACBriPortAddrDynStatic OBJECT-TYPE
        SYNTAX      INTEGER{
                    static(1),
                    dynamic(2)
                    }
        MAX-ACCESS  read-only
        STATUS      current
        DESCRIPTION
            ""
        ::= { zxGponMACBriPortAddrInfoEntry 3}

   zxGponMACBriPortAddrAgingTime OBJECT-TYPE
        SYNTAX      INTEGER
        MAX-ACCESS  read-only
        STATUS      current
        DESCRIPTION
            "Age in seconds (1s to 4095s)"
        ::= { zxGponMACBriPortAddrInfoEntry 4}


    zxGponIpRouterSPInfoTable OBJECT-TYPE
        SYNTAX      SEQUENCE OF ZxGponIpRouterSPInfoEntry
        MAX-ACCESS  not-accessible
        STATUS      current
        DESCRIPTION
            "This managed entity is used to organize data that affects all ports on an IP router 
        on a routed LAN UNI interface on the ONT. Instances of this managed entity are created 
        and deleted by request of the OLT.''" 
        REFERENCE
            "G.983.2 Rev 7.3.38 IP router service profile"
        ::= { ethernetUniMib 8 }
        
    zxGponIpRouterSPInfoEntry OBJECT-TYPE
        SYNTAX      ZxGponIpRouterSPInfoEntry
        MAX-ACCESS  not-accessible
        STATUS      current
        DESCRIPTION
            "This managed entity is used to organize data that affects all ports on an IP router 
        on a routed LAN UNI interface on the ONT."
        INDEX   { zxGponMgmtPonOltId, zxGponMgmtPonOnuId, zxGponIpRouterSPInfoMeIdIdx }
        ::= { zxGponIpRouterSPInfoTable 1 }

    ZxGponIpRouterSPInfoEntry ::=
        SEQUENCE {
            zxGponIpRouterSPInfoMeIdIdx      INTEGER,
        zxGponIpRouterSPInfoForwardingInd   TruthValue,
            zxGponIpRouterSPInfoProxyARPInd     TruthValue,
        zxGponIpRouterSPInfoDirectedBroadcastInd       TruthValue,
        zxGponIpRouterSPInfoUpstreamMulticastFiltering       INTEGER,
        zxGponIpRouterSPInfoDownstreamMulticastFiltering       INTEGER,
            zxGponIpRouterSPInfoMgmtCtrlFlag INTEGER,
            zxGponIpRouterSPInfoEntryStatus  RowStatus
        }

   zxGponIpRouterSPInfoMeIdIdx OBJECT-TYPE
        SYNTAX      INTEGER
        MAX-ACCESS  not-accessible
        STATUS      current
        DESCRIPTION
            "This attribute provides a unique number for each instance of this managed entity."
        REFERENCE
            "G.983.2 Rev Section 7.3.38"
        ::= { zxGponIpRouterSPInfoEntry 1}
        
    zxGponIpRouterSPInfoForwardingInd OBJECT-TYPE
        SYNTAX      TruthValue
        MAX-ACCESS  read-write
        STATUS      current
        DESCRIPTION
            " This boolean attribute indicates whether or not forwarding of IP packets as 
        a whole is enabled. The value TRUE means enabled. The initial value is enabled. "
        REFERENCE
            "G.983.2 Rev Section 7.3.38"
        ::= { zxGponIpRouterSPInfoEntry 2}

    zxGponIpRouterSPInfoProxyARPInd OBJECT-TYPE
        SYNTAX      TruthValue
        MAX-ACCESS  read-write
        STATUS      current
        DESCRIPTION
            " This boolean attribute indicates whether or not proxy ARP is enabled. 
        The value TRUE means enabled. The initial value is enabled. "
        REFERENCE
            "G.983.2 Rev Section 7.3.38"
        ::= { zxGponIpRouterSPInfoEntry 3}

    zxGponIpRouterSPInfoDirectedBroadcastInd OBJECT-TYPE
        SYNTAX      TruthValue
        MAX-ACCESS  read-write
        STATUS      current
        DESCRIPTION
            " This boolean attribute indicates whether or not relaying of directed broadcast 
        packets is enabled. The value TRUE means enabled. The initial value is disabled. "
        REFERENCE
            "G.983.2 Rev Section 7.3.38"
        ::= { zxGponIpRouterSPInfoEntry 4}

    zxGponIpRouterSPInfoUpstreamMulticastFiltering OBJECT-TYPE
        SYNTAX      INTEGER{
                    forwarded(1),
                    filtered(2)
                    }
        MAX-ACCESS  read-write
        STATUS      current
        DESCRIPTION
            "This attribute indicates whether upstream IP multicast packets are 
        forwarded (value 0x01) or filtered (value 0x01). The initial value is 0x02."
        REFERENCE
            "G.983.2 Rev Section 7.3.38"
        ::= { zxGponIpRouterSPInfoEntry 5}

    zxGponIpRouterSPInfoDownstreamMulticastFiltering OBJECT-TYPE
        SYNTAX      INTEGER{
                    forwarded(1),
                    filtered(2)
                    }
        MAX-ACCESS  read-write
        STATUS      current
        DESCRIPTION
            "This attribute indicates whether upstream IP multicast packets are 
        forwarded (value 0x01) or filtered (value 0x01). The initial value is 0x02."
        REFERENCE
            "G.983.2 Rev Section 7.3.38"
        ::= { zxGponIpRouterSPInfoEntry 6}

    zxGponIpRouterSPInfoMgmtCtrlFlag OBJECT-TYPE
        SYNTAX      INTEGER{
                    nmsCreate(1),
                    neCreate(2)
                    }
        MAX-ACCESS  read-only
        STATUS      current
        DESCRIPTION
            "This attribute is used to indicate this record is created by NMS or NE. If it
             is neCreate(2), this record can not be deleted."
        REFERENCE
            "N/A"
        ::= { zxGponIpRouterSPInfoEntry 7}

    zxGponIpRouterSPInfoEntryStatus       OBJECT-TYPE
      SYNTAX      RowStatus
      MAX-ACCESS  read-create
      STATUS      current 
      DESCRIPTION 
        "This attribute can be create and delete."
      REFERENCE   "N/A"
      ::= { zxGponIpRouterSPInfoEntry 8 }


    zxGponIpPortCfgDataInfoTable OBJECT-TYPE
        SYNTAX      SEQUENCE OF ZxGponIpPortCfgDataInfoEntry
        MAX-ACCESS  not-accessible
        STATUS      current
        DESCRIPTION
            "This managed entity is used to organize data that is associated with IP address 
        and IP port provisioning. Instances of this managed entity are created and 
        deleted by request of the OLT." 
        REFERENCE
            "G.983.2 Rev 7.3.37 IP Port configuration data"
        ::= { ethernetUniMib 9 }

    zxGponIpPortCfgDataInfoEntry OBJECT-TYPE
        SYNTAX      ZxGponIpPortCfgDataInfoEntry
        MAX-ACCESS  not-accessible
        STATUS      current
        DESCRIPTION
            "Zero or more instances of this managed entity shall be contained in an 
             instance of the IP Port configuration data."
        INDEX   { zxGponMgmtPonOltId, zxGponMgmtPonOnuId, zxGponIpPortCfgDataMeIdIdx }
        ::= { zxGponIpPortCfgDataInfoTable 1 }

    ZxGponIpPortCfgDataInfoEntry ::=
        SEQUENCE {
            zxGponIpPortCfgDataMeIdIdx         INTEGER,
            zxGponIpPortCfgDataPortNum         INTEGER,
            zxGponIpPortCfgDataTPType          INTEGER,
        zxGponIpPortCfgDataTPPointer          INTEGER,
            zxGponIpPortCfgDataPortAddress     IpAddress,
            zxGponIpPortCfgDataPortMask        IpAddress,
        zxGponIpPortCfgDataUnnumbered      TruthValue,
        zxGponIpPortCfgDataAdministrativeState  INTEGER,
            zxGponIpPortCfgDataPortState            INTEGER,
            zxGponIpPortCfgDataAllowRemoteAccess    TruthValue,
            zxGponIpPortCfgDataRouterIdPointer     INTEGER,
        zxGponIpPortCfgDataARPPointer     INTEGER,
        zxGponIpPortCfgDataEncapsulationMethod INTEGER,
            zxGponIpPortCfgDataMgmtCtrlFlag    INTEGER,
            zxGponIpPortCfgDataEntryStatus     RowStatus
        }
 
   zxGponIpPortCfgDataMeIdIdx OBJECT-TYPE
        SYNTAX      INTEGER
        MAX-ACCESS  not-accessible
        STATUS      current
        DESCRIPTION
            "This attribute provides a unique number for each instance of this managed entity."
        ::= { zxGponIpPortCfgDataInfoEntry 1}

    zxGponIpPortCfgDataPortNum OBJECT-TYPE
        SYNTAX      INTEGER
        MAX-ACCESS  read-write
        STATUS      current
        DESCRIPTION
            "This attribute identifies the port at which IP provisioning takes place."
        REFERENCE
            "G.983.2 Rev Section 7.3.37"
        ::= { zxGponIpPortCfgDataInfoEntry 2}

     zxGponIpPortCfgDataTPType OBJECT-TYPE
        SYNTAX      INTEGER{
                    lan(1),
                    atm(2)
                    }
        MAX-ACCESS  read-write
        STATUS      current
        DESCRIPTION
            "This attribute identifies the type of the termination point associated with this IP port. 
        The value is set to 0x01 if this IP port is associated with the LAN side's TP. 
        The value is set to 0x02 if this IP port is associated with the ATM side's TP."
        REFERENCE
            "G.983.2 Rev Section 7.3.37"
        ::= { zxGponIpPortCfgDataInfoEntry 3}

     zxGponIpPortCfgDataTPPointer OBJECT-TYPE
        SYNTAX      INTEGER
        MAX-ACCESS  read-write
        STATUS      current
        DESCRIPTION
            "This attribute points to the instance of the TP associated with this port. When this IP 
        port is associated with the LAN side's TP, this attribute points to the instance of the 
        PPTP Ethernet UNI. When this IP port is associated with the ATM side's TP, this attribute 
        points to the instance of the Interworking VCC Termination Point."
        REFERENCE
            "G.983.2 Rev Section 7.3.37"
        ::= { zxGponIpPortCfgDataInfoEntry 4}

     zxGponIpPortCfgDataPortAddress OBJECT-TYPE
        SYNTAX      IpAddress
        MAX-ACCESS  read-write
        STATUS      current
        DESCRIPTION
            "This attribute identifies the provisioned IP address. 
        When an IP address is not assigned, this attribute consists of all 0x00."
        REFERENCE
            "G.983.2 Rev Section 7.3.37"
        ::= { zxGponIpPortCfgDataInfoEntry 5}

     zxGponIpPortCfgDataPortMask OBJECT-TYPE
        SYNTAX      IpAddress
        MAX-ACCESS  read-write
        STATUS      current
        DESCRIPTION
            "This attribute identifies the address mask associated with the provisioned IP address.
        When an IP address mask is not assigned, this attribute consists of all 0x00."
        REFERENCE
            "G.983.2 Rev Section 7.3.37"
        ::= { zxGponIpPortCfgDataInfoEntry 6}

     zxGponIpPortCfgDataUnnumbered OBJECT-TYPE
        SYNTAX      TruthValue
        MAX-ACCESS  read-write
        STATUS      current
        DESCRIPTION
            "This boolean attribute indicates whether or not this IP port has an IP address. 
        The value TRUE means unnumbered. (For future use by IP router function.)."
        REFERENCE
            "G.983.2 Rev Section 7.3.37"
        ::= { zxGponIpPortCfgDataInfoEntry 7}


     zxGponIpPortCfgDataAdministrativeState OBJECT-TYPE
        SYNTAX      INTEGER{
                    activate(1),
                    deactivate(2)
                    }
        MAX-ACCESS  read-write
        STATUS      current
        DESCRIPTION
        "This boolean attribute is used to activate (unlock, value 0x01) and 
        deactivate (lock, value 0x02) the functions performed by instances of this managed entity."
        REFERENCE
            "G.983.2 Rev Section 7.3.37"
        ::= { zxGponIpPortCfgDataInfoEntry 8}

      zxGponIpPortCfgDataPortState OBJECT-TYPE
        SYNTAX      INTEGER{
                up(1),
                    down(2)
                    }
        MAX-ACCESS  read-only
        STATUS      current
        DESCRIPTION
         "This boolean attribute provides status information on the port,
         Valid values include 'up' (value 0x01) and 'down' (value 0x02)."
        REFERENCE
            "G.983.2 Rev Section 7.3.37"
        ::= { zxGponIpPortCfgDataInfoEntry 9}


       zxGponIpPortCfgDataAllowRemoteAccess OBJECT-TYPE
        SYNTAX      TruthValue
        MAX-ACCESS  read-write
        STATUS      current
        DESCRIPTION
            "This boolean attribute indicates whether or not this IP port may be accessed remotely. 
        The value TRUE means remote access is enabled."
        REFERENCE
            "G.983.2 Rev Section 7.3.37"
        ::= { zxGponIpPortCfgDataInfoEntry 10}

       zxGponIpPortCfgDataRouterIdPointer OBJECT-TYPE
        SYNTAX      INTEGER
        MAX-ACCESS  read-write
        STATUS      current
        DESCRIPTION
            "This attribute identifies the IP router controlling the port, if it exists. 
        This attribute points to the instance of the IP Router Service Profile. 
        If no IP router controls the port, this attribute consists of a null pointer (0xFFFF)."
        REFERENCE
            "G.983.2 Rev Section 7.3.37"
        ::= { zxGponIpPortCfgDataInfoEntry 11}

       zxGponIpPortCfgDataARPPointer OBJECT-TYPE
        SYNTAX      INTEGER
        MAX-ACCESS  read-write
        STATUS      current
        DESCRIPTION
            "This attribute identifies the instance of ARP Service Profile associated with the IP port."
        REFERENCE
            "G.983.2 Rev Section 7.3.37"
        ::= { zxGponIpPortCfgDataInfoEntry 12}

      zxGponIpPortCfgDataEncapsulationMethod OBJECT-TYPE
        SYNTAX      INTEGER{
                    atmvc(1),
                    llc(2)
                    }
        MAX-ACCESS  read-write
        STATUS      current
        DESCRIPTION
            "This attribute identifies the frame encapsulation method that is used,
        Value 0x01: identification by ATM VC;
        value 0x02: LLC encapsulation, 
        Upon autonomous instantiation, the value 0x00 is used."
        REFERENCE
            "G.983.2 Rev Section 7.3.37"
        ::= { zxGponIpPortCfgDataInfoEntry 13}

    zxGponIpPortCfgDataMgmtCtrlFlag OBJECT-TYPE
        SYNTAX      INTEGER{
                    nmsCreate(1),
                    neCreate(2)
                    }
        MAX-ACCESS  read-only
        STATUS      current
        DESCRIPTION
            "This attribute is used to indicate this record is created by NMS or NE. If it
             is neCreate(2), this record can not be deleted."
        REFERENCE
            "N/A"
        ::= { zxGponIpPortCfgDataInfoEntry 14}

    zxGponIpPortCfgDataEntryStatus       OBJECT-TYPE
      SYNTAX      RowStatus
      MAX-ACCESS  read-create
      STATUS      current 
      DESCRIPTION 
        "This attribute can be create and delete."
      REFERENCE   "N/A"
      ::= { zxGponIpPortCfgDataInfoEntry 15 }


    cesUniMib OBJECT IDENTIFIER ::= { zxGponUniMgmt 9 }

    zxGponPPTPCesUniTable OBJECT-TYPE
        SYNTAX      SEQUENCE OF ZxGponPPTPCesUniEntry
        MAX-ACCESS  not-accessible
        STATUS      current
        DESCRIPTION
            "This managed entity represents the points at a CES UNI in the ONT where physical
             paths terminate and physical path level functions are performed." 
        REFERENCE
            "G.983.2 Rev Section 7.3.3"
        ::= { cesUniMib 1 }

    zxGponPPTPCesUniEntry OBJECT-TYPE
        SYNTAX      ZxGponPPTPCesUniEntry
        MAX-ACCESS  not-accessible
        STATUS      current
        DESCRIPTION
            ""
        INDEX   { zxGponMgmtPonOltId, zxGponMgmtPonOnuId, zxGponPPTPCesUniTPID }
        ::= { zxGponPPTPCesUniTable 1 }

    ZxGponPPTPCesUniEntry ::=
        SEQUENCE {
            zxGponPPTPCesUniTPID              INTEGER,
            zxGponPPTPCesUniMeId              INTEGER,
            zxGponPPTPCesUniExpectedType      INTEGER,
            zxGponPPTPCesUniSensedType        INTEGER,
            zxGponPPTPCesUniEesLoopback       INTEGER,
            zxGponPPTPCesUniAdminState        INTEGER,
            zxGponPPTPCesUniOperationalState  INTEGER,
            zxGponPPTPCesUniDS1Framing        INTEGER,
            zxGponPPTPCesUniEncoding          INTEGER,
            zxGponPPTPCesUniLineLength        INTEGER,
            zxGponPPTPCesUniDS1Mode           INTEGER,
            zxGponPPTPCesUniARC               INTEGER,
            zxGponPPTPCesUniARCInterval       INTEGER,      
            zxGponPPTPCesUniLineType          INTEGER
        }

   zxGponPPTPCesUniTPID OBJECT-TYPE
        SYNTAX      INTEGER
        MAX-ACCESS  not-accessible
        STATUS      current
        DESCRIPTION
            "An arbitrary(unique) integer for identifiying an entry in the PPTP ces 
             information Table."
        ::= { zxGponPPTPCesUniEntry 1}

    zxGponPPTPCesUniMeId OBJECT-TYPE
        SYNTAX      INTEGER
        MAX-ACCESS  read-only
        STATUS      current
        DESCRIPTION
            "This attribute provides a unique number for each instance of this managed entity. 
             This 2-byte number is directly associated with the physical position of the UNI. 
             The first byte is the slot id (defined in 7.1.3). The second byte is the port id 
             with value range from 0x01 to 0xFF (1 to 255): 0x01 is used for the leftmost/lowest 
             port on a subscriber line card, 0x02 is used for the next right/upper port, and so forth."
        ::= { zxGponPPTPCesUniEntry 2}

    zxGponPPTPCesUniExpectedType OBJECT-TYPE
        SYNTAX      INTEGER
        MAX-ACCESS  read-write
        STATUS      current
        DESCRIPTION
            "Coding    Contents              Description
             0         no LIM                Default value                                                         
             1         A1.5                  ATM 1.544 Mbit/s module                                               
             2         A2                    ATM 2.048 Mbit/s                                                      
             3         A6.3                  ATM 6.312 Mbit/s module                                               
             4         A6.3U                 ATM 6.312 Mbit/s module, Remote (U-interface)                         
             5         A8                    ATM 8.448 Mbit/s                                                      
             6         A25                   ATM 25.6 Mbit/s module                                                
             7         A34                   ATM 34.368 Mbit/s module                                              
             8         A45                   ATM 44.736 Mbit/s module                                              
             9         A45/34                Configurable ATM 44.736/34.368 Mbit/s module                          
             10        A150SMF SDH           ATM STM-1 SMF UNI                                                     
             11        A150MMF SDH           ATM STM-1 MMF UNI                                                     
             12        A150UTP SDH           ATM STM-1 UTP UNI                                                     
             13        C1.5 (DS1)            1.544 Mbit/s Local (T-interface) AAL 1 module                         
             14        C2.0 (E1)             2.048 Mbit/s Local (T-interface) AAL 1 module                         
             15        C6.3 (J2)             6.312 Mbit/s Local (T-interface) AAL 1 module                         
             16        C-DS1/E1              Configurable DS1/E1 AAL 1 module                                      
             17        C-DS1/E1/J1           Configurable DS1/E1/J1 AAL 1 module                                   
             18        C6.3U (J2)            6.312 Mbit/s Remote (U-interface) AAL 1 module                        
             19        C192k                 192 kbit/s Local (T-interface) AAL 1 module                           
             20        C44.7 (DS3)           44.736 Mbit/s Local (T-interface) AAL 1 module                        
             21        C34.3 (E3)            34.368 Mbit/s Local (T-interface) AAL 1 module                        
             22        10Base-T              10 Base-T ces LAN IF                                             
             23        100Base-T             100 Base-T ces LAN IF                                            
             24        10/100Base-T          10/100 Base-T ces LAN IF                                         
             25        Token Ring            Token Ring LAN IF                                                     
             26        FDDI                  FDDI LAN IF                                                           
             27        FR                    Frame relay                                                           
             28        C1.5 (J1)             1.544 Mbit/s Local (T-interface) AAL 1 module                         
             29        A150SMF SONET         ATM OC-3 SMF UNI                                                      
             30        A150MMF SONET         ATM OC-3 MMF UNI                                                      
             31        A150UTP SONET         ATM OC-3 UTP UNI                                                      
             32        POTS                  Plain Old Telephony Service                                           
             33        ISDN-BRI              ISDN Basic Rate Interface                                             
             34        Gigabit ces      Gigabit ces IF                                                   
             35        ADSL                  ADSL IF                                                               
             36        SHDSL                 SHDSL IF                                                              
             37        VDSL                  VDSL IF                                                               
             38        Video Service         Video module                                                          
             39..251   Reserved                                                                                    
             252       PON622symm            Symmetric 622/622 Mbit/s PON IF                                       
             253       PON155                Symmetric 155/155 Mbit/s PON IF                                       
             254       PON622                Asymmetric 155/622 Mbit/s PON IF                                      
             255       Plug-and-play/Unknown Plug-and-play (for the Subscriber Line Cardholder managed entity only)
                                             Unrecognized module (for the Subscriber Line Card managed entity only)
             It may be 22,23,24,34 and so on. It may be created/read/written/modified.Writing or 
             modifing can be done when the entry SHOULD NOT be used by any other entry."
        REFERENCE
            "G.983.2 Rev 7.3.3 Physical path termination point ces UNI"
        DEFVAL  { 0 }
        ::= { zxGponPPTPCesUniEntry 3}

   zxGponPPTPCesUniSensedType OBJECT-TYPE
        SYNTAX      INTEGER
        MAX-ACCESS  read-only
        STATUS      current
        DESCRIPTION
            "If the value of 'Expected type' is not equal to 0x00, then the value of 'Sensed type' equals
             the value of 'Expected type'. If the value of 'Expected type' equals 0x00, then the value of
             'Sensed type' = one of the values from Table 3 and by necessity is compatible with the Type 
             of the Subscriber Line Card managed entity. Upon autonomous instantiation, the value 0x00 
             is used. (R) (mandatory for the case of ONT supports LIMs with configurable interface types,
             e.g. C1.5/2/6.3)."
        ::= { zxGponPPTPCesUniEntry 4}
        
   zxGponPPTPCesUniEesLoopback OBJECT-TYPE
        SYNTAX      INTEGER
        MAX-ACCESS  read-write
        STATUS      current
        DESCRIPTION
            "This attribute represents the loopback configuration of the physical interface. 
                Value 0x00: no loopback; 
                value 0x01: payload loopback; 
                value 0x02: line loopback; 
                value 0x03: OpS-directed loopback1 (loopback from/to ATM network side); 
                value 0x04: OpS-directed loopback2 (loopback from/to CES UNI side); 
                value 0x05: OpS-directed loopback3 (loopback of both ATM network side and CES UNI side); 
                value 0x06: Manual button-directed loopback (Read only);
                value 0x07: Network-side Code inband-directed loopback (Read only); 
                value 0x08: SmartJack-directed loopback (Read only); 
                value 0x09: Network-side Code inband-directed loopback. (ARMED) (Read only).
                Upon autonomous instantiation, the value 0x00 is used."
        ::= { zxGponPPTPCesUniEntry 5}

   zxGponPPTPCesUniAdminState OBJECT-TYPE
        SYNTAX      INTEGER{
                    enabled(1),
                    disabled(2)
                    }
        MAX-ACCESS  read-write
        STATUS      current
        DESCRIPTION
            "This attribute is used to activate (unlock: value enabled) and deactivate (lock: value disabled)
             the functions performed by instances of this managed entity. Selection of a default value for 
             this attribute is outside the scope of this document as it is normally handled through supplier-
             operator negotiations. "
        ::= { zxGponPPTPCesUniEntry 6}
        
   zxGponPPTPCesUniOperationalState OBJECT-TYPE
        SYNTAX      INTEGER{
                    enabled(1),
                    disabled(2)
                    }
        MAX-ACCESS  read-only
        STATUS      current
        DESCRIPTION
            "This attribute indicates whether or not this managed entity is capable of performing its task.
             The operational state reflects the perceived ability to receive or to generate a valid signal.
             Valid values are enabled (0x01) and disabled (0x02)."
        ::= { zxGponPPTPCesUniEntry 7}

    zxGponPPTPCesUniDS1Framing OBJECT-TYPE
        SYNTAX      INTEGER{
                    extendedSuperFrame(1),
                    superFrame(2),
                    unFrame(3),
                    g704(4),
                    jt-g704(5)
                    }
        MAX-ACCESS  read-only
        STATUS      current
        DESCRIPTION
            "This attribute indicates the framing structure used.  Valid values are 'ExtendedSuperFrame,(0x01),
             'SuperFrame' (0x02), 'UnFrame' (0x03), 'G.704' (0x04) and 'JT-G.704' (0x05).  Upon autonomous 
             instantiation, the value 0x01 is used."
        REFERENCE
            "G.983.2 Rev 7.3.3 Physical path termination point ces UNI"
        DEFVAL  { extendedSuperFrame }
        ::= { zxGponPPTPCesUniEntry 8}

    zxGponPPTPCesUniEncoding OBJECT-TYPE
        SYNTAX      INTEGER{
                    b8zs(1),
                    ami(2),
                    hdb3(3),
                    b3zs(4)
                    }
        MAX-ACCESS  read-write
        STATUS      current
        DESCRIPTION
            "This attribute denotes the encoding scheme required. Valid values are 'B8ZS'(value 0x01),
             'AMI' (value 0x02), 'HDB3' (0x03), and 'B3ZS' (0x04). Upon autonomous instantiation, the
             value 0x01 is used."
        REFERENCE
            "G.983.2 Rev 7.3.3 Physical path termination point ces UNI"
        DEFVAL  { b8zs }
        ::= { zxGponPPTPCesUniEntry 9}

    zxGponPPTPCesUniLineLength OBJECT-TYPE
        SYNTAX      INTEGER
        MAX-ACCESS  read-write
        STATUS      current
        DESCRIPTION
            "This attribute provides the length of the twisted pair cable from the physicalPathTTP of
             type 'DS1' interface to the DSX1 cross-connect point or the length of the DS3 cable from
             the physicalPathTTP of type 'DS3' to the DSX3 cross-connect point.  Valid values are given
             in Table 6-e.  Upon autonomous instantiation for DS1 interfaces, the value 0x00 is used for
             non-power feed type DS1, and the value 0x06 is used for power feed type DS1.Upon autonomous
             instantiation for DS3 interfaces, the value 0x0F is used.
              Table 6-e/G.983.2 -- Valid values for LineLength attribute
              Value    Power Feed    Line Length
              0x00    Non-power feed type DS1    0-33.5 m (0-110 ft)
              0x01    Non-power feed type DS1    33.5-67.1 m (110-220 ft)
              0x02    Non-power feed type DS1    67.1 -100.6 m (220-330 ft)
              0x03    Non-power feed type DS1    100.6-134.1 m (330-440 ft)
              0x04    Non-power feed type DS1    132.1-167.6 m (440-550 ft)
              0x05    Non-power feed type DS1    167.6-201.2 m (550-660 ft)
              0x06    Power feed type DS1 (Wet-T1), short haul    0-40.5 m (0-133 ft)
              0x07    Power feed type DS1 (Wet-T1), short haul    40.5-81.1 m (133-266 ft)
              0x08    Power feed type DS1 (Wet-T1), short haul    81.1-121.6 m (266-399 ft)
              0x09    Power feed type DS1 (Wet-T1), short haul    121.6-162.5 m (399-533 ft)
              0x0A    Power feed type DS1 (Wet-T1), short haul    162.5-199.6 m (533-655 ft)
              0x0B    Power feed type DS1 (Wet-T1), long haul    0db
              0x0C    Power feed type DS1 (Wet-T1), long haul    7.5db
              0x0D    Power feed type DS1 (Wet-T1), long haul    15db
              0x0E    Power feed type DS1 (Wet-T1), long haul    22.5db
              0x0F    DS3 power feed    0-68.5 m (0-225 ft)
              0x10    DS3 power feed    68.5-137.1 m (226-450 ft)"
        REFERENCE
            "G.983.2 Rev 7.3.3 Physical path termination point ces UNI"
        DEFVAL  { 15 }
        ::= { zxGponPPTPCesUniEntry 10}

    zxGponPPTPCesUniDS1Mode OBJECT-TYPE
        SYNTAX      INTEGER
        MAX-ACCESS  read-write
        STATUS      current
        DESCRIPTION
            "This attribute indicates the mode of DS1 used.  The valid values are 'Mode#1'(value 0x00),
             'Mode#2' (value 0x01), 'Mode#3' (value 0x02), and 'Mode#4' (value 0x03). Moreover, each 
             Mode is defined as described in Table 6-f. Upon autonomous instantiation, the value 0x00
             is used.
                Table 6-f/G.983.2 -- Coding of DS1Mode attribute
                Mode    Connect    Line Length    Power Feed    Loop Back
                #1    DS1-CPE    Short Haul    Without power feed    Smart Jack
                #2    DS1-CPE    Long Haul    Without power feed    Smart Jack
                #3    DS1-NIU-CPE    Long Haul    Without power feed    Intelligent Office Repeater
                #4    DS1-NIU-CPE    Long Haul    With power feed    Intelligent Office Repeater
            "
        REFERENCE
            "G.983.2 Rev 7.3.3 Physical path termination point ces UNI"
        DEFVAL  { 0 }
        ::= { zxGponPPTPCesUniEntry 11}

    zxGponPPTPCesUniARC OBJECT-TYPE
        SYNTAX      INTEGER{
                    off(1),
                    on(2)
                    }
        MAX-ACCESS  read-write
        STATUS      current
        DESCRIPTION
            "It is used to control alarm reporting from this ONT(managed entity). off means alarm reporting
             allowed immediately and on means alarm reporting inhibited, until this ONT(managed entity) detects
             a valid signal for the time interval specified by 'zxGponPPTPEthUNITempletARCInterval'. It may
             be created/read/written/modified.Writing or modifing can be done when the entry SHOULD NOT
             be used by any other entry."
        REFERENCE
            "G.983.2 Rev 7.3.3 Physical path termination point ces UNI"
        DEFVAL  { on }
        ::= { zxGponPPTPCesUniEntry 12}

    zxGponPPTPCesUniARCInterval OBJECT-TYPE
        SYNTAX      INTEGER(1..255)
        MAX-ACCESS  read-write
        STATUS      current
        DESCRIPTION
            "It provides a provisionable length of time. Units are given in minutes. It may
             be created/read/written/modified.Writing or modifing can be done when the entry SHOULD NOT
             be used by any other entry."
        REFERENCE
            "G.983.2 Rev 7.3.3 Physical path termination point ces UNI"
        DEFVAL  { 1 }
        ::= { zxGponPPTPCesUniEntry 13}

    zxGponPPTPCesUniLineType OBJECT-TYPE
        SYNTAX      INTEGER
        MAX-ACCESS  read-write
        STATUS      current
        DESCRIPTION
            "This attribute denotes the line type used in the application for DS3 or E3 interfaces.
             Valid values are:
                              0x00, Other;
                              0x01, ds3m23;
                              0x02, ds3syntran;
                              0x03, ds3CbitParity;
                              0x04, ds3ClearChannel;
                              0x05, e3Framed;
                              0x06, e3plcp.
            (mandatory for DS3 and E3 interfaces, not applicable to other interfaces)."
        REFERENCE
            "G.983.2 Rev 7.3.3 Physical path termination point ces UNI"
        ::= { zxGponPPTPCesUniEntry 14}


    zxGponCESSPInfoTable OBJECT-TYPE
        SYNTAX      SEQUENCE OF ZxGponCESSPInfoEntry
        MAX-ACCESS  not-accessible
        STATUS      current
        DESCRIPTION
            "An instance of this managed entity is used to organize data that describe the CES Service 
        functions of the ONT. An instance of this managed entity shall be created and deleted by the OLT." 
        REFERENCE
            "G.983.2 Rev 7.3.12 CES Service Profile B-PON"
        ::= { cesUniMib 2 }

    zxGponCESSPInfoEntry OBJECT-TYPE
        SYNTAX      ZxGponCESSPInfoEntry
        MAX-ACCESS  not-accessible
        STATUS      current
        DESCRIPTION
            ""
        INDEX   { zxGponMgmtPonOltId, zxGponMgmtPonOnuId, zxGponCESSPInfoMeIdIdx }
        ::= { zxGponCESSPInfoTable 1 }

    ZxGponCESSPInfoEntry ::=
        SEQUENCE {
            zxGponCESSPInfoMeIdIdx                         INTEGER,
            zxGponCESSPInfoMBufferedCDVTolerance           INTEGER,
            zxGponCESSPInfoChannelAssociatedSignalling     INTEGER,
            zxGponCESSPInfoMgmtCtrlFlag                    INTEGER,
            zxGponCESSPInfoEntryStatus                     RowStatus
        }

   zxGponCESSPInfoMeIdIdx OBJECT-TYPE
        SYNTAX      INTEGER
        MAX-ACCESS  not-accessible
        STATUS      current
        DESCRIPTION
            "This attribute provides a unique number for the instance of this managed entity."
        REFERENCE
            "G.983.2 Rev Section 7.3.12"
        ::= { zxGponCESSPInfoEntry 1}

   zxGponCESSPInfoMBufferedCDVTolerance OBJECT-TYPE
        SYNTAX      INTEGER
        MAX-ACCESS  read-write
        STATUS      current
        DESCRIPTION
            "This attribute represents the duration of user data that must be buffered 
        by the CES interworking entity to offset the Cell Delay Variation. 
        This timing will be in 10 microseconds increment. The default value for DS1 CES is 750 microseconds 
        and 1000 microseconds for DS3 CES."
        REFERENCE
            "G.983.2 Rev Section 7.3.12"
        ::= { zxGponCESSPInfoEntry 2}

    zxGponCESSPInfoChannelAssociatedSignalling OBJECT-TYPE
        SYNTAX      INTEGER{
                    basic(1),
                    e1Cas(2),
                    sfCas(3),
            ds1EsfCas(4),
            j2Cas(5)
                    }
        MAX-ACCESS  read-only
        STATUS      current
        DESCRIPTION
            "This attribute selects which AAL 1 format should be used. It applies to structured 
        interfaces only. For unstructured interfaces, this value, if present, must be set to 
        the default of 0x00. The valid values are basic (0x01), e1Cas (0x02), sfCas (0x03), 
        ds1EsfCas (0x04), and j2Cas (0x05)."
        REFERENCE
            "G.983.2 Rev Section 7.3.12"
        ::= { zxGponCESSPInfoEntry 3}

    zxGponCESSPInfoMgmtCtrlFlag OBJECT-TYPE
        SYNTAX      INTEGER{
                    nmsCreate(1),
                    neCreate(2)
                    }
        MAX-ACCESS  read-only
        STATUS      current
        DESCRIPTION
            "This attribute is used to indicate this record is created by NMS or NE. If it
             is neCreate(2), this record can not be deleted."
        REFERENCE
            "N/A"
        ::= { zxGponCESSPInfoEntry 4}

    zxGponCESSPInfoEntryStatus       OBJECT-TYPE
      SYNTAX      RowStatus
      MAX-ACCESS  read-create
      STATUS      current 
      DESCRIPTION 
        "This attribute can be create,modify and delete."
      REFERENCE   "N/A"
      ::= { zxGponCESSPInfoEntry 5 }

    zxGponGemIWTPInfoTable OBJECT-TYPE
        SYNTAX      SEQUENCE OF ZxGponGemIWTPInfoEntry
        MAX-ACCESS  not-accessible
        STATUS      current
        DESCRIPTION
            "An instance of this managed entity represents a point in the ONT where the 
             interworking of a service (e.g., CES, IP) or underlying physical infrastructure 
             (e.g., nxDS0/DS1/DS3/E3/Ethernet) to GEM layer takes place." 
        REFERENCE
            "G.984.4 Section 9.3.3"
        ::= { zxGponUniMgmt 12 }

    zxGponGemIWTPInfoEntry OBJECT-TYPE
        SYNTAX      ZxGponGemIWTPInfoEntry
        MAX-ACCESS  not-accessible
        STATUS      current
        DESCRIPTION
            "Instances of this managed entity are created and deleted by the ONT on request 
             of the OLT."
        INDEX   { zxGponMgmtPonOltId, zxGponMgmtPonOnuId, zxGponGemIWTPInfoMeIdIdx }
        ::= { zxGponGemIWTPInfoTable 1 }

    ZxGponGemIWTPInfoEntry ::=
        SEQUENCE {
            zxGponGemIWTPInfoMeIdIdx              INTEGER,
            zxGponGemIWTPInfoPNCTPConnectivityPtr INTEGER,
            zxGponGemIWTPInfoIwOption             INTEGER,
            zxGponGemIWTPInfoServiceProPtr        INTEGER,
            zxGponGemIWTPInfoITPPtr               INTEGER,
            zxGponGemIWTPInfoPPTPCounter          INTEGER,
            zxGponGemIWTPInfoOpState              INTEGER,
            zxGponGemIWTPInfoGALProPtr            INTEGER,
            zxGponGemIWTPInfoGEMLoopbackCfg       INTEGER,
            zxGponGemIWTPInfoMgmtCtrlFlag         INTEGER,
            zxGponGemIWTPInfoEntryStatus          RowStatus
        }

    zxGponGemIWTPInfoMeIdIdx OBJECT-TYPE
        SYNTAX      INTEGER
        MAX-ACCESS  not-accessible
        STATUS      current
        DESCRIPTION
            "An arbitrary(unique) integer for identifiying an entry in the UNI management,
             from 1 to M. his attribute provides a unique number for each instance of this
             managed entity. This number is directly associated with the physical position
             of the UNI, it is MeId."
        ::= { zxGponGemIWTPInfoEntry 1}
        
    zxGponGemIWTPInfoPNCTPConnectivityPtr OBJECT-TYPE
        SYNTAX      INTEGER
        MAX-ACCESS  read-write
        STATUS      current
        DESCRIPTION
            "This attribute provides an instance identifier of the GEM Port 
             Network CTP that is associated with this GEM Interworking Termination Point."
        REFERENCE
            "G.984.4 Section 9.3.3"
        ::= { zxGponGemIWTPInfoEntry 2}
        
    zxGponGemIWTPInfoIwOption OBJECT-TYPE
        SYNTAX      INTEGER{
                    ces(1),
                    bridge(2)
                    }
        MAX-ACCESS  read-write
        STATUS      current
        DESCRIPTION
            "It identifies the type of non-GEM function that is being interworked; the option
             can be CES (1) or MAC Bridge LAN (2).It may be created/read/written/modified.
             Writing or modifing can be done when the entry SHOULD NOT be used by any other entry."
        ::= { zxGponGemIWTPInfoEntry 3}

    zxGponGemIWTPInfoServiceProPtr OBJECT-TYPE
        SYNTAX      INTEGER
        MAX-ACCESS  read-write
        STATUS      current
        DESCRIPTION
            "It provides the service profile type and a pointer to the instance of a service profile,
             such as the CES Service ProfileB-PON (if the zxGponGemIwTPTempletIwOption = 0) or MAC
             Bridge Service Profile (if the zxGponGemIwTPTempletIwOption = 1).It may be created/read/
             written/modified.Writing or modifing can be done when the entry SHOULD NOT be used by any
             other entry."
        ::= { zxGponGemIWTPInfoEntry 4}
        
    zxGponGemIWTPInfoITPPtr OBJECT-TYPE
        SYNTAX      INTEGER
        MAX-ACCESS  read-write
        STATUS      current
        DESCRIPTION
            "This attribute provides a pointer to the associated instance(s) of 
             the following managed entities (depending on the service provided)."
        REFERENCE
            "G.984.4 Section 9.3.3"
        ::= { zxGponGemIWTPInfoEntry 5}

    zxGponGemIWTPInfoPPTPCounter OBJECT-TYPE
        SYNTAX      INTEGER
        MAX-ACCESS  read-only
        STATUS      current
        DESCRIPTION
            "This attribute represents the number of instances of PPTP managed entities 
             associated with this instance of the GEM Interworking Termination Point 
             managed entity."
        REFERENCE
            "G.984.4 Section 9.3.3"
        ::= { zxGponGemIWTPInfoEntry 6}

    zxGponGemIWTPInfoOpState OBJECT-TYPE
        SYNTAX      INTEGER{
                    enabled(1),
                    disabled(2)
                    }
        MAX-ACCESS  read-only
        STATUS      current
        DESCRIPTION
            "This attribute indicates whether or not this managed entity is capable of 
             performing its task. The operational state reflects the perceived ability to 
             receive or to generate a valid signal. This value is set to enabled(1) if the 
             managed entity have this capacity, otherwise, this value is disabled(2)."
        REFERENCE
            "G.984.4 Section 9.3.3"
        ::= { zxGponGemIWTPInfoEntry 7}
        
    zxGponGemIWTPInfoGALProPtr OBJECT-TYPE
        SYNTAX      INTEGER
        MAX-ACCESS  read-write
        STATUS      current
        DESCRIPTION
            "For GEM mode, it provides the GAL profile type and a pointer to an instance of a GAL
             Profile such as GAL TDM Profile if the zxGponGemIwTPTempletIwOption = 0 or GAL Ethernet
             Profile if the zxGponGemIwTPTempletIwOption = 0x01."
        ::= { zxGponGemIWTPInfoEntry 8}
        
    zxGponGemIWTPInfoGEMLoopbackCfg OBJECT-TYPE
        SYNTAX      INTEGER{
                    normal(1),
                    loopback(2)
                    }
        MAX-ACCESS  read-write
        STATUS      current
        DESCRIPTION
            "This attribute is used to set the loopback configuration when using GEM mode."
        REFERENCE
            "G.984.4 Section 9.3.3"
        ::= { zxGponGemIWTPInfoEntry 9}

    zxGponGemIWTPInfoMgmtCtrlFlag OBJECT-TYPE
        SYNTAX      INTEGER{
                    nmsCreate(1),
                    neCreate(2)
                    }
        MAX-ACCESS  read-only
        STATUS      current
        DESCRIPTION
            "This attribute is used to indicate this record is created by NMS or NE. If it
             is neCreate(2), this record can not be deleted."
        REFERENCE
            "N/A"
        ::= { zxGponGemIWTPInfoEntry 10}

    zxGponGemIWTPInfoEntryStatus       OBJECT-TYPE
      SYNTAX      RowStatus
      MAX-ACCESS  read-create
      STATUS      current 
      DESCRIPTION 
        "This attribute can be create and delete."
      REFERENCE   "N/A"
      ::= { zxGponGemIWTPInfoEntry 11 }

    zxGponGemIWTPAlarmTable OBJECT-TYPE
        SYNTAX      SEQUENCE OF ZxGponGemIWTPAlarmEntry
        MAX-ACCESS  not-accessible
        STATUS      current
        DESCRIPTION
            "An instance of this managed entity represents a point in the ONT where the 
             interworking of a service (e.g., CES, IP) or underlying physical infrastructure 
             (e.g., nxDS0/DS1/DS3/E3/Ethernet) to GEM layer takes place." 
        REFERENCE
            "G.984.4 Section 9.3.3"
        ::= { zxGponUniMgmt 13 }

    zxGponGemIWTPAlarmEntry OBJECT-TYPE
        SYNTAX      ZxGponGemIWTPAlarmEntry
        MAX-ACCESS  not-accessible
        STATUS      current
        DESCRIPTION
            "Instances of this managed entity are created and deleted by the ONT on request 
             of the OLT."
        INDEX   { zxGponMgmtPonOltId, zxGponMgmtPonOnuId, zxGponGemIWTPAlarmIndex }
        ::= { zxGponGemIWTPAlarmTable 1 }

    ZxGponGemIWTPAlarmEntry ::=
        SEQUENCE {
            zxGponGemIWTPAlarmIndex     INTEGER,
            zxGponGemIWTPAlarmMeId      INTEGER,
            zxGponGemIWTPGFSAAlarm      TruthValue,
            zxGponGemIWTPGFSAAlarmMask  TruthValue
        }

    zxGponGemIWTPAlarmIndex OBJECT-TYPE
        SYNTAX      INTEGER
        MAX-ACCESS  not-accessible
        STATUS      current
        DESCRIPTION
            "An arbitrary(unique) integer for identifiying an entry
             in the UNI management, from 1 to M."
        ::= { zxGponGemIWTPAlarmEntry 1}

    zxGponGemIWTPAlarmMeId OBJECT-TYPE
        SYNTAX      INTEGER
        MAX-ACCESS  read-only
        STATUS      current
        DESCRIPTION
            "This attribute provides a unique number for each instance of this managed entity. 
             This number is directly associated with the physical position of the UNI."
        REFERENCE
            "G.984.4 Section 9.3.3"
        ::= { zxGponGemIWTPAlarmEntry 2}

    zxGponGemIWTPGFSAAlarm OBJECT-TYPE
        SYNTAX      TruthValue
        MAX-ACCESS  read-only
        STATUS      current
        DESCRIPTION 
            "It is used to Indicate that GEM Frame Starve Alarm. When this is true(1) meadn that the Alarm 
             is presented, when false(2), mean there is no this alarm."
        REFERENCE
            "G.984.4 Section 9.3.3"
        ::= { zxGponGemIWTPAlarmEntry 3}

    zxGponGemIWTPGFSAAlarmMask OBJECT-TYPE
        SYNTAX      TruthValue
        MAX-ACCESS  read-write
        STATUS      current
        DESCRIPTION 
            "Indicates whether the occurence of zxGponGemITPGFSAAlarm alarm
             should result in NE generated by the agent layer. When this is false(2) 
             it should be generated; When true(1), not generated."
        REFERENCE
            "G.984.4 Section 9.3.3"
        ::= { zxGponGemIWTPAlarmEntry 4}

--zxGponConnMgmt.mi2
    zxGponConnMgmt OBJECT IDENTIFIER ::= { zxGponRootMib 24 }   

    zxGponGemPNCTPInfoTable OBJECT-TYPE
        SYNTAX      SEQUENCE OF ZxGponGemPNCTPInfoEntry
        MAX-ACCESS  not-accessible
        STATUS      current
        DESCRIPTION
            "This managed entity is used to represent the termination of GEM ports on an ONT." 
        REFERENCE
            "G.984.4 Section 9.4.1"
        ::= { zxGponConnMgmt 1 }

    zxGponGemPNCTPInfoEntry OBJECT-TYPE
        SYNTAX      ZxGponGemPNCTPInfoEntry
        MAX-ACCESS  not-accessible
        STATUS      current
        DESCRIPTION
            "Instances of the GEM Port Network CTP managed entity will be created on demand 
             of the OLT as a consequence of action 'create' on the GEM Port Network CTP 
             managed entity."
        INDEX   { zxGponMgmtPonOltId, zxGponMgmtPonOnuId, zxGponGemPNCTPInfoMeIdIdx }
        ::= { zxGponGemPNCTPInfoTable 1 }

    ZxGponGemPNCTPInfoEntry ::=
        SEQUENCE {
            zxGponGemPNCTPInfoMeIdIdx            INTEGER,
            zxGponGemPNCTPInfoPortId             INTEGER,
            zxGponGemPNCTPInfoPONTCAdapterGPtr   INTEGER,
            zxGponGemPNCTPInfoDirection          INTEGER,
            zxGponGemPNCTPInfoPriorityUpstream   INTEGER,
            zxGponGemPNCTPInfoPriorityDownstream INTEGER,
            zxGponGemPNCTPInfoTDescProfPtr       INTEGER,
            zxGponGemPNCTPInfoUniCounter         INTEGER,
            zxGponGemPNCTPInfoMgmtCtrlFlag       INTEGER,
            zxGponGemPNCTPInfoEntryStatus        RowStatus
        }

     zxGponGemPNCTPInfoMeIdIdx OBJECT-TYPE
        SYNTAX      INTEGER
        MAX-ACCESS  not-accessible
        STATUS      current
        DESCRIPTION
            "An arbitrary(unique) integer for identifiying an entry in the ONT equipment,
             from 1 to M, it is MeId."
        ::= { zxGponGemPNCTPInfoEntry 1}

   zxGponGemPNCTPInfoPortId OBJECT-TYPE
        SYNTAX      INTEGER
        MAX-ACCESS  read-write
        STATUS      current
        DESCRIPTION
            "This attribute identifies the PortID associated with the GEM port being terminated."
        ::= { zxGponGemPNCTPInfoEntry 2}

   zxGponGemPNCTPInfoPONTCAdapterGPtr OBJECT-TYPE
        SYNTAX      INTEGER
        MAX-ACCESS  read-write
        STATUS      current
        DESCRIPTION
            "This attribute associates the GEM Port Network CTP ME with the PON TC Adapter-G ME. It 
             points to the connected PON TC Adapter-G instance id. If use template, the value of this 
             attribute is not a pointer, it just a template number"
        ::= { zxGponGemPNCTPInfoEntry 3}

   zxGponGemPNCTPInfoDirection OBJECT-TYPE
        SYNTAX      INTEGER{
                    uni2ani(1),
                    ani2uni(2),
                    bidirectional(3)
                    }
        MAX-ACCESS  read-write
        STATUS      current
        DESCRIPTION
            "It specifies whether the GEM port is used for UNI-to-ANI (uni2uni(1)), ANI-to-UNI(
             ani2uni(2)), or bidirectional (bidirectional(3)) connection. It may be created/read/
             written/modified.Writing or modifing can be done when the entry SHOULD NOT be used 
             by any other entry."
        REFERENCE
            "G.984.4 Section 9.4.1 GEM Port Network CTP"
        ::= { zxGponGemPNCTPInfoEntry 4}
        
   zxGponGemPNCTPInfoPriorityUpstream OBJECT-TYPE
        SYNTAX      INTEGER
        MAX-ACCESS  read-write
        STATUS      current
        DESCRIPTION
            "This attribute points to the instance of the Priority Queue-G ME used for this GEM Port 
             Network CTP ME in the upstream direction. It is used when the Traffic Management Option 
             attribute in ONT-G ME is 0x00; this pointer is null otherwise. "
        ::= { zxGponGemPNCTPInfoEntry 5}

   zxGponGemPNCTPInfoPriorityDownstream OBJECT-TYPE
        SYNTAX      INTEGER
        MAX-ACCESS  read-write
        STATUS      current
        DESCRIPTION
            "This attribute points to the instance of the Priority Queue-G used for this GEM Port Network
             CTP in the downstream direction. It is used when the Traffic Management Option attribute in 
             ONT-G is 0x00; this pointer is null otherwise. "
        ::= { zxGponGemPNCTPInfoEntry 6}

   zxGponGemPNCTPInfoTDescProfPtr OBJECT-TYPE
        SYNTAX      INTEGER
        MAX-ACCESS  read-write
        STATUS      current
        DESCRIPTION
            "It serves as a pointer to the instance of the Traffic Descriptor Profile managed entity
             that contains the traffic parameters used for this GEM Port Network CTP entry. This 
             attribute is used when the Traffic Management Option attribute in ONT-G ME is 0x01. When
             traffic shaping is used, it applies to the ANI side GEM Port Network CTP entry. In this 
             case, this pointer points to a Traffic Descriptor Profile managed entity and the Priority
             Queue Pointer for the upstream attribute is null. I.e. it is the index of the table 
             zxGponGemTraffDescTempletTable, zxGponTDTempletIndex. It may be created/read/written/
             modified.Writing or modifing can be done when the entry SHOULD NOT be used by any other entry."
        REFERENCE
            "G.984.4 Section 9.4.1 GEM Port Network CTP"
        ::= { zxGponGemPNCTPInfoEntry 7}

   zxGponGemPNCTPInfoUniCounter OBJECT-TYPE
        SYNTAX      INTEGER
        MAX-ACCESS  read-only
        STATUS      current
        DESCRIPTION
            "This attribute represents the number of instances of UNI-G managed entity associated with an 
             instance of the GEM Port Network CTP managed entity. If only one instance of a UNI-G managed 
             entity is associated with an instance of the GEM Port Network CTP managed entity, this 
             attribute is set to 0x01. If multiple instances of UNI-G managed entity are associated with an 
             instance of the GEM Port Network CTP managed entity, this attribute is set to 0xZZ, where ZZ 
             represents the number of associated UNI-G instances. "
        ::= { zxGponGemPNCTPInfoEntry 8}

    zxGponGemPNCTPInfoMgmtCtrlFlag OBJECT-TYPE
        SYNTAX      INTEGER{
                    nmsCreate(1),
                    neCreate(2)
                    }
        MAX-ACCESS  read-only
        STATUS      current
        DESCRIPTION
            "This attribute is used to indicate this record is created by NMS or NE. If it
             is neCreate(2), this record can not be deleted."
        REFERENCE
            "N/A"
        ::= { zxGponGemPNCTPInfoEntry 9}

    zxGponGemPNCTPInfoEntryStatus       OBJECT-TYPE
      SYNTAX      RowStatus
      MAX-ACCESS  read-create
      STATUS      current 
      DESCRIPTION 
        "This attribute can be create and delete."
      REFERENCE   "N/A"
      ::= { zxGponGemPNCTPInfoEntry 10 }

    zxGponGemPNCTPAlarmCfgTable OBJECT-TYPE
        SYNTAX      SEQUENCE OF ZxGponGemPNCTPAlarmCfgEntry
        MAX-ACCESS  not-accessible
        STATUS      current
        DESCRIPTION
            "This managed entity is used to represent the termination of GEM ports on an ONT." 
        REFERENCE
            "G.984.4 Section 9.4.1"
        ::= { zxGponConnMgmt 2 }

    zxGponGemPNCTPAlarmCfgEntry OBJECT-TYPE
        SYNTAX      ZxGponGemPNCTPAlarmCfgEntry
        MAX-ACCESS  not-accessible
        STATUS      current
        DESCRIPTION
            "Instances of the GEM Port Network CTP managed entity will be created on demand 
             of the OLT as a consequence of action 'create' on the GEM Port Network CTP 
             managed entity."
        INDEX   { zxGponMgmtPonOltId, zxGponMgmtPonOnuId, zxGponGemPNCTPInfoMeIdIdx }
        ::= { zxGponGemPNCTPAlarmCfgTable 1 }

    ZxGponGemPNCTPAlarmCfgEntry ::=
        SEQUENCE {
            zxGponGemPNCTPAlarmCfgMeId                  INTEGER,
            zxGponGemPNCTPAlarmCfgE2eLossContinuity     TruthValue,
            zxGponGemPNCTPAlarmCfgE2eLossContinuityMask TruthValue
        }

    zxGponGemPNCTPAlarmCfgMeId OBJECT-TYPE
        SYNTAX      INTEGER
        MAX-ACCESS  read-only
        STATUS      current
        DESCRIPTION
            "A unique number for each instance of this managed entity."
        REFERENCE
            "G.984.4 Section 9.4.1"
        ::= { zxGponGemPNCTPAlarmCfgEntry 1}

    zxGponGemPNCTPAlarmCfgE2eLossContinuity OBJECT-TYPE
        SYNTAX      TruthValue
        MAX-ACCESS  read-only
        STATUS      current
        DESCRIPTION
            "Loss of continuity can be detected when the GEM Port Network CTP supports a GEM 
             Interworking Termination Point. set this attribute is true(1) if End to end loss continuity occured, 
             otherwise, this attribute is false(2)."
        REFERENCE
            "G.984.4 Section 9.4.1"
        ::= { zxGponGemPNCTPAlarmCfgEntry 2}

    zxGponGemPNCTPAlarmCfgE2eLossContinuityMask OBJECT-TYPE
        SYNTAX      TruthValue
        MAX-ACCESS  read-write
        STATUS      current
        DESCRIPTION
            "Indicates whether the occurence of zxGponGemPNCTPAlarmCfgE2eLossContinuity alarm
             should result in NE generated by the agent layer. When this is false(2) 
             it is generated; When true(1), it is not generated."
        REFERENCE
            "G.984.4 Section 9.4.1"
        ::= { zxGponGemPNCTPAlarmCfgEntry 3}


    zxGponGemPPPMHDInfoTable OBJECT-TYPE
        SYNTAX      SEQUENCE OF ZxGponGemPPPMHDInfoEntry
        MAX-ACCESS  not-accessible
        STATUS      current
        DESCRIPTION
            "This managed entity is used to collect and report performance monitoring data 
             associated with a GEM Port Network CTP for the last completed 15-minute interval. " 
        REFERENCE
            "G.984.4 Section 9.4.2"
        ::= { zxGponConnMgmt 3 }

    zxGponGemPPPMHDInfoEntry OBJECT-TYPE
        SYNTAX      ZxGponGemPPPMHDInfoEntry
        MAX-ACCESS  not-accessible
        STATUS      current
        DESCRIPTION
            "This managed entity is used to collect and report performance monitoring data 
             associated with a GEM Port Network CTP for the last completed 15-minute interval. " 
        INDEX   { zxGponMgmtPonOltId, zxGponMgmtPonOnuId, zxGponGemPPPMHDInfoMeIdIdx }
        ::= { zxGponGemPPPMHDInfoTable 1 }

    ZxGponGemPPPMHDInfoEntry ::=
        SEQUENCE {
            zxGponGemPPPMHDInfoMeIdIdx                     INTEGER,
            zxGponGemPPPMHDInfoIntervalEndTime             INTEGER,
            zxGponGemPPPMHDInfoThresholdDataID             INTEGER,
            zxGponGemPPPMHDInfoLostPackets                 INTEGER,
            zxGponGemPPPMHDInfoMisinsertedPackets          INTEGER,
            zxGponGemPPPMHDInfoReceivedPackets             INTEGER,
            zxGponGemPPPMHDInfoReceivedBlocks              INTEGER,
            zxGponGemPPPMHDInfoTransmittedBlocks           INTEGER,
            zxGponGemPPPMHDInfoImpairedBlocks              INTEGER
        }

    zxGponGemPPPMHDInfoMeIdIdx OBJECT-TYPE
        SYNTAX      INTEGER
        MAX-ACCESS  not-accessible
        STATUS      current
        DESCRIPTION
            "An arbitrary(unique) integer for identifiying an entry in the performance monitoring data
             reporting, from 1 to M. This attribute provides a unique number for each instance of this 
             managed entity. The assigned number is the same as the Managed Entity id of the corresponding
             GEM Port Network CTP."
        ::= { zxGponGemPPPMHDInfoEntry 1}
        
    zxGponGemPPPMHDInfoIntervalEndTime OBJECT-TYPE
        SYNTAX      INTEGER
        MAX-ACCESS  read-only
        STATUS      current
        DESCRIPTION
            "This attribute identifies the most recently finished 15-minute interval. It is a cyclic 
             counter (modulo 0x100 (256)) that is incremented each time a new interval is finished 
             and the actual counters are updated. The value of this attribute is 0x00 during the first 
             15-minute interval that starts with the reception of the 'synchronize time' action. The 
             value is 0x01 during the first period after this, and so on. If this managed entity is 
             created after the reception of the 'synchronize time' action, the value of this attribute 
             is set equal to the number of the last completed interval. The actual counters of this 
             managed entity start counting directly. "
        REFERENCE
            "G.984.4 Section 9.4.2"
        ::= { zxGponGemPPPMHDInfoEntry 2}

    zxGponGemPPPMHDInfoThresholdDataID OBJECT-TYPE
        SYNTAX      INTEGER
        MAX-ACCESS  read-write
        STATUS      current
        DESCRIPTION
            "This attribute provides a pointer to instances of the Threshold Data 1 and 2 
             managed entities that contain the threshold values for the performance monitoring 
             data collected by this managed entity."
        REFERENCE
            "G.984.4 Section 9.4.2"
        ::= { zxGponGemPPPMHDInfoEntry 3}

    zxGponGemPPPMHDInfoLostPackets OBJECT-TYPE
        SYNTAX      INTEGER
        MAX-ACCESS  read-only
        STATUS      current
        DESCRIPTION
            "This attribute measures background packet loss. It cannot distinguish between 
             packets lost because of header bit errors or buffer overflows. It records only 
             loss of information. The unit of this counter is GEM frame. If the actual counter 
             saturates, it remains on its maximum value. "
        REFERENCE
            "G.984.4 Section 9.4.2"
        ::= { zxGponGemPPPMHDInfoEntry 4}

    zxGponGemPPPMHDInfoMisinsertedPackets OBJECT-TYPE
        SYNTAX      INTEGER
        MAX-ACCESS  read-only
        STATUS      current
        DESCRIPTION
            "This attribute is used to measure occurrences of when a packet is misrouted to an 
             active GEM port that is being monitored. The unit of this counter is GEM frame. If 
             the actual counter saturates, it remains on its maximum value."
        REFERENCE
            "G.984.4 Section 9.4.2"
        ::= { zxGponGemPPPMHDInfoEntry 5}

    zxGponGemPPPMHDInfoReceivedPackets OBJECT-TYPE
        SYNTAX      INTEGER
        MAX-ACCESS  read-only
        STATUS      current
        DESCRIPTION
            "This attribute provides a count of all packets that are correctly received at the 
             monitored GEM port. The unit of this counter is GEM frame."
        REFERENCE
            "G.984.4 Section 9.4.2"
        ::= { zxGponGemPPPMHDInfoEntry 6}

    zxGponGemPPPMHDInfoReceivedBlocks OBJECT-TYPE
        SYNTAX      INTEGER
        MAX-ACCESS  read-only
        STATUS      current
        DESCRIPTION
            "This attribute provides a count of all blocks that are correctly received at the 
             monitored GEM port. The unit of this counter is GEM block length."
        REFERENCE
            "G.984.4 Section 9.4.2"
        ::= { zxGponGemPPPMHDInfoEntry 7}

    zxGponGemPPPMHDInfoTransmittedBlocks OBJECT-TYPE
        SYNTAX      INTEGER
        MAX-ACCESS  read-only
        STATUS      current
        DESCRIPTION
            "This attribute provides a count of all blocks that are originated at a monitored 
             connection by the transmitting end point (i.e., backward reporting is assumed). 
             The unit of this counter is GEM block length."
        REFERENCE
            "G.984.4 Section 9.4.2"
        ::= { zxGponGemPPPMHDInfoEntry 8}

    zxGponGemPPPMHDInfoImpairedBlocks OBJECT-TYPE
        SYNTAX      INTEGER
        MAX-ACCESS  read-only
        STATUS      current
        DESCRIPTION
            "This severely errored data block counter will be incremented whenever one of the 
             following events takes place: the number of misinserted packets exceeds M(misinserted), 
             the number of bipolar violations exceeds M(errored), or the number of lost packets 
             exceeds M(lost). The values for M(misinserted), M(errored), and M(lost) are set based on 
             vendor operator negotiation."
        REFERENCE
            "G.984.4 Section 9.4.2"
        ::= { zxGponGemPPPMHDInfoEntry 9}


    zxGponGemPPPMHDAlarmCfgTable OBJECT-TYPE
        SYNTAX      SEQUENCE OF ZxGponGemPPPMHDAlarmCfgEntry
        MAX-ACCESS  not-accessible
        STATUS      current
        DESCRIPTION
            "This notification is used to notify the management system when a threshold 
             crossing alert (TCA) is detected or cleared. The TCA change notification 
             'on' will be sent at the crossing of the threshold; the TCA change notification 
             'off' will be sent at the end of the 15-minute period since that is when the 
             counters are reset to 0x00. " 
        REFERENCE
            "G.984.4 Section 9.4.2"
        ::= { zxGponConnMgmt 4 }

    zxGponGemPPPMHDAlarmCfgEntry OBJECT-TYPE
        SYNTAX      ZxGponGemPPPMHDAlarmCfgEntry
        MAX-ACCESS  not-accessible
        STATUS      current
        DESCRIPTION
            "This notification is used to notify the management system when a threshold 
             crossing alert (TCA) is detected or cleared. The TCA change notification 
             'on' will be sent at the crossing of the threshold; the TCA change notification 
             'off' will be sent at the end of the 15-minute period since that is when the 
             counters are reset to 0x00. " 
        INDEX   { zxGponMgmtPonOltId, zxGponMgmtPonOnuId, zxGponGemPPPMHDInfoMeIdIdx }
        ::= { zxGponGemPPPMHDAlarmCfgTable 1 }

    ZxGponGemPPPMHDAlarmCfgEntry ::=
        SEQUENCE {
            zxGponGemPPPMHDAlarmCfgMeId              INTEGER,
            zxGponGemPPPMHDAlarmCfgLosPkgs           TruthValue,
            zxGponGemPPPMHDAlarmCfgLosPkgsMask       TruthValue,
            zxGponGemPPPMHDAlarmCfgMisInsertPkgs     TruthValue,
            zxGponGemPPPMHDAlarmCfgMisInsertPkgsMask TruthValue,
            zxGponGemPPPMHDAlarmCfgImpairBlks        TruthValue,
            zxGponGemPPPMHDAlarmCfgImpairBlksMask    TruthValue            
        }

    zxGponGemPPPMHDAlarmCfgMeId OBJECT-TYPE
        SYNTAX      INTEGER
        MAX-ACCESS  read-only
        STATUS      current
        DESCRIPTION
            "An arbitrary(unique) integer for identifiying an entry
             in the ONT equipment, from 1 to M."
        ::= { zxGponGemPPPMHDAlarmCfgEntry 1}

    zxGponGemPPPMHDAlarmCfgLosPkgs OBJECT-TYPE
        SYNTAX      TruthValue
        MAX-ACCESS  read-only
        STATUS      current
        DESCRIPTION
            "Lost packets exceeds threshold alarm. If the lost packets exceeds threshold event occured, this 
             value is true(1), otherwise, this value is false(2)."
        REFERENCE
            "G.984.4 Section 9.4.2"
        ::= { zxGponGemPPPMHDAlarmCfgEntry 2}

    zxGponGemPPPMHDAlarmCfgLosPkgsMask OBJECT-TYPE
        SYNTAX      TruthValue
        MAX-ACCESS  read-write
        STATUS      current
        DESCRIPTION
            "The mask bit for lost packets exceeds threshold alarm. "
        REFERENCE
            "G.984.4 Section 9.4.2"
        ::= { zxGponGemPPPMHDAlarmCfgEntry 3}

    zxGponGemPPPMHDAlarmCfgMisInsertPkgs OBJECT-TYPE
        SYNTAX      TruthValue
        MAX-ACCESS  read-only
        STATUS      current
        DESCRIPTION
            "Misinserted packets exceeds threshold alarm. If the misinserted packets exceeds threshold event 
             occured, this value is true(1), otherwise, this value is false(2)."
        REFERENCE
            "G.984.4 Section 9.4.2"
        ::= { zxGponGemPPPMHDAlarmCfgEntry 4}

    zxGponGemPPPMHDAlarmCfgMisInsertPkgsMask OBJECT-TYPE
        SYNTAX      TruthValue
        MAX-ACCESS  read-write
        STATUS      current
        DESCRIPTION
            "The mask birt for misinserted packets exceeds threshold alarm. "
        REFERENCE
            "G.984.4 Section 9.4.2"
        ::= { zxGponGemPPPMHDAlarmCfgEntry 5}

    zxGponGemPPPMHDAlarmCfgImpairBlks OBJECT-TYPE
        SYNTAX      TruthValue
        MAX-ACCESS  read-only
        STATUS      current
        DESCRIPTION
            "Impaired blocks exceeds threshold alarm. If the impaired blocks exceeds threshold event 
             occured, this value is true(1), otherwise, this value is false(2)."
        REFERENCE
            "G.984.4 Section 9.4.2"
        ::= { zxGponGemPPPMHDAlarmCfgEntry 6}

    zxGponGemPPPMHDAlarmCfgImpairBlksMask OBJECT-TYPE
        SYNTAX      TruthValue
        MAX-ACCESS  read-write
        STATUS      current
        DESCRIPTION
            "The mask birt for impaired blocks exceeds threshold alarm. "
        REFERENCE
            "G.984.4 Section 9.4.2"
        ::= { zxGponGemPPPMHDAlarmCfgEntry 7}

--zxGponTrafficMgmt.mi2
    zxGponTrafficMgmt OBJECT IDENTIFIER ::= { zxGponRootMib 25 }

    zxGponPriorityQueueTable OBJECT-TYPE
        SYNTAX      SEQUENCE OF ZxGponPriorityQueueEntry
        MAX-ACCESS  not-accessible
        STATUS      current
        DESCRIPTION
            "This managed entity specifies the priority queue in the ONT that is used for the 
             VP Network CTP-G or GEM Port Network CTP.
             
             If N priority queues reside in the ONT, the Subscriber Line Card, ONT core or PON 
             IF Line Card, N instances of Priority Queue-G management entity will be automatically 
             created by the ONT following the creation of the Subscriber Line Card or T-CONT ME. 
             In ANI side, the Priority Queue-G ME is related to T-CONT ME. After instances of 
             T-CONT ME are created, instances of Priority Queue-G ME should be created autonomously.
             
             Note that the OLT will find all the queues by reading the Priority Queue-G managed entity 
             instances. If the OLT tries to retrieve a non-existing priority queue, this will be 
             indicated in the response from the ONT to the OLT.
             
             See also Appendix IV/G.983.2.
             
             Upstream priority queues can be added to the ONT. Moreover, priority queues can exist in 
             the ONT core and subscriber line cards as well as PON IF Line Cards. 
             
             In order to configure the optional Traffic Scheduler, the Weight attribute is included.
             Several attributes are included that support back pressure operation. Back pressure is 
             defined as a mechanism for backward flow control. The back pressure signal is sent backward 
             and causes the customer terminal to temporarily suspend sending data." 
        REFERENCE
            "G.984.4 Section 9.5.1"
        ::= { zxGponTrafficMgmt 1 }

    zxGponPriorityQueueEntry OBJECT-TYPE
        SYNTAX      ZxGponPriorityQueueEntry
        MAX-ACCESS  not-accessible
        STATUS      current
        DESCRIPTION
            "One or more instances of this managed entity are contained in the ONT-G managed 
             entity to model the upstream priority queues if the Traffic Management Option 
             attribute in ONT G ME is 0x00. One or more instances of this managed entity are 
             associated with the Subscriber Line Card managed entity as downstream priority 
             queues. For the ONT that has one or more fixed user interfaces, one or more 
             instances are contained in the ONT-G managed entity for the downstream priority 
             queues."
        INDEX   { zxGponMgmtPonOltId, zxGponMgmtPonOnuId, zxGponPriorQueueIndex }
        ::= { zxGponPriorityQueueTable 1 }

    ZxGponPriorityQueueEntry ::=
        SEQUENCE {
            zxGponPriorQueueIndex                           INTEGER,
            zxGponPriorQueueMeId                            INTEGER,
            zxGponPriorQueueCfgOption                       INTEGER,
            zxGponPriorQueueMaxQueueSize                    INTEGER,
            zxGponPriorQueueAllocSize                       INTEGER,
            zxGponPriorQueueInterval                        INTEGER,
            zxGponPriorQueueBufOverflowThreshold            INTEGER,
            zxGponPriorQueueRelatedPort                     INTEGER,
            zxGponPriorQueueTrafficSchedulerGPtr            INTEGER,
            zxGponPriorQueueWeight                          INTEGER,
            zxGponPriorQueueBackPressureAdmin               INTEGER,
            zxGponPriorQueueBackPressureTime                Unsigned32,
            zxGponPriorQueueBackPressAssertThresh           INTEGER,
            zxGponPriorQueueBackPressClearThresh            INTEGER
        }

     zxGponPriorQueueIndex OBJECT-TYPE
        SYNTAX      INTEGER
        MAX-ACCESS  not-accessible
        STATUS      current
        DESCRIPTION
            "An arbitrary(unique) integer for identifiying an entry
             in the Ani manangement, from 1 to M."
        ::= { zxGponPriorityQueueEntry 1}

     zxGponPriorQueueMeId OBJECT-TYPE
        SYNTAX      INTEGER
        MAX-ACCESS  read-only
        STATUS      current
        DESCRIPTION
            "This attribute provides a unique number for each instance of this managed entity. The 
             most significant bit represents the direction (0b1: Upstream, 0b0: Downstream). The 15 
             least significant bits represent a queue id. The queue id is numbered in ascending order 
             by the ONT itself. The range of the downstream queue id is 0x0000 to 0x7FFF and the 
             range of upstream queue id is 0x8000 to 0xFFFF in an ONT."
        ::= { zxGponPriorityQueueEntry 2}

     zxGponPriorQueueCfgOption OBJECT-TYPE
        SYNTAX      INTEGER
        MAX-ACCESS  read-only
        STATUS      current
        DESCRIPTION
            "This attribute identifies the buffer-partitioning policy. The value of 0x01 means that 
             all the queues share one buffer size of Maximum Queue Size and the value 0x00 means that 
             each queue uses its individual buffer size of Maximum Queue Size."
        ::= { zxGponPriorityQueueEntry 3}

     zxGponPriorQueueMaxQueueSize OBJECT-TYPE
        SYNTAX      INTEGER
        MAX-ACCESS  read-only
        STATUS      current
        DESCRIPTION
            "This attribute specifies the maximum size of the queue. Units are cells for ATM mode 
             and 'GEM block lengths' for GEM mode. "
        ::= { zxGponPriorityQueueEntry 4}
        
    zxGponPriorQueueAllocSize OBJECT-TYPE
        SYNTAX      INTEGER(0..65535)
        MAX-ACCESS  read-write
        STATUS      current
        DESCRIPTION
            "It identifies the allocated size of this queue. Units are cells for ATM
             mode and 'GEM block lengths' for GEM mode.It may be created/read/written/
             modified.Writing or modifing can be done when the entry SHOULD NOT be used
             by any other entry."
        REFERENCE
            "G.984.4 Section 9.5.1 Priority Queue-G"
        DEFVAL  { 48 }
        ::= { zxGponPriorityQueueEntry 5}

    zxGponPriorQueueInterval OBJECT-TYPE
        SYNTAX      INTEGER(0..65535)
        MAX-ACCESS  read-write
        STATUS      current
        DESCRIPTION
            "It represents the interval in milliseconds at which the counter resets itself.
             It may be created/read/written/modified.Writing or modifing can be done when 
             the entry SHOULD NOT be used by any other entry."
        REFERENCE
            "G.984.4 Section 9.5.1 Priority Queue-G"
        ::= { zxGponPriorityQueueEntry 6}

    zxGponPriorQueueBufOverflowThreshold OBJECT-TYPE
        SYNTAX      INTEGER(0..65535)
        MAX-ACCESS  read-write
        STATUS      current
        DESCRIPTION
            "The threshold for the number of cells or GEM block lengths discarded on this
             queue due to buffer overflow.It may be created/read/written/modified.Writing 
             or modifing can be done when the entry SHOULD NOT be used by any other entry."
        REFERENCE
            "G.984.4 Section 9.5.1 Priority Queue-G"
        ::= { zxGponPriorityQueueEntry 7}

     zxGponPriorQueueRelatedPort OBJECT-TYPE
        SYNTAX      INTEGER
        MAX-ACCESS  read-only
        STATUS      current
        DESCRIPTION
            "This attribute represents the slot, port/T-CONT and priority information that is associated 
             with the instance of Priority Queue-G ME. This attribute consists of four bytes. The first 
             byte represents the slot id where the traffic that is stored in the queue is outgoing. 
             The second byte represents the ME id of T-CONT ME (in the case of upstream) or port id (in the 
             case of downstream) where the traffic that is stored in the queue is outgoing. The last two 
             bytes represent the priority of this queue. The range of the priority is 0x0000 to 0x0FFF. 
             The value 0x0000 indicates the highest priority and the value 0x0FFF indicates the lowest 
             priority."
        ::= { zxGponPriorityQueueEntry 8}

     zxGponPriorQueueTrafficSchedulerGPtr OBJECT-TYPE
        SYNTAX      INTEGER
        MAX-ACCESS  read-write
        STATUS      current
        DESCRIPTION
            "This attribute represents the Traffic Scheduler-G ME instance that is directly associated with 
             this priority queue. Upon autonomous instantiation, this attribute is null (0x0000). This 
             pointer is used when this priority queue is connected with a Traffic Scheduler. Default 
             value is 0x0000."
        ::= { zxGponPriorityQueueEntry 9}

    zxGponPriorQueueWeight OBJECT-TYPE
        SYNTAX      INTEGER
        MAX-ACCESS  read-write
        STATUS      current
        DESCRIPTION
            "It represents weight for WRR. This weight is used by the Traffic Scheduler or T-CONT
             (whose Policy is WRR) indicated by the Traffic Scheduler-G pointer attribute or Related
             Port attribute.It may be created/read/written/modified.Writing or modifing can be done
             when the entry SHOULD NOT be used by any other entry."
        REFERENCE
            "G.984.4 Section 9.5.1 Priority Queue-G"
        DEFVAL  { 1 }
        ::= { zxGponPriorityQueueEntry 10}

    zxGponPriorQueueBackPressureAdmin OBJECT-TYPE
        SYNTAX      INTEGER{
                    enable(1),
                    disable(2)
                    }
        MAX-ACCESS  read-write
        STATUS      current
        DESCRIPTION
            "It is used to activate (true: value 1) or deactivate (false: value 2) the functions of
             Back Pressure operation.It may be created/read/written/modified.Writing or modifing can
             be done when the entry SHOULD NOT be used by any other entry."
        REFERENCE
            "G.984.4 Section 9.5.1 Priority Queue-G"
        DEFVAL  { disable }
        ::= { zxGponPriorityQueueEntry 11}

    zxGponPriorQueueBackPressureTime OBJECT-TYPE
        SYNTAX      Unsigned32
        MAX-ACCESS  read-write
        STATUS      current
        DESCRIPTION
            "It indicates the time duration in which the customer terminal temporarily suspends
             sending data. This instance presents the duration in microseconds. It can be used 
             as a pause time for Ethernet UNI.It may be created/read/written/modified.Writing or
             modifing can be done when the entry SHOULD NOT be used by any other entry."
        REFERENCE
            "G.984.4 Section 9.5.1 Priority Queue-G"
        DEFVAL  { 0 }
        ::= { zxGponPriorityQueueEntry 12}

    zxGponPriorQueueBackPressAssertThresh OBJECT-TYPE
        SYNTAX      INTEGER
        MAX-ACCESS  read-write
        STATUS      current
        DESCRIPTION
            "It  identifies the threshold size of this queue to start sending Back Pressure
             signal.It may be created/read/written/modified.Writing or modifing can be done
             when the entry SHOULD NOT be used by any other entry."
        REFERENCE
            "G.984.4 Section 9.5.1 Priority Queue-G"
        ::= { zxGponPriorityQueueEntry 13}

    zxGponPriorQueueBackPressClearThresh OBJECT-TYPE
        SYNTAX      INTEGER
        MAX-ACCESS  read-write
        STATUS      current
        DESCRIPTION
            "It  identifies the threshold size of this queue to stop sending Back Pressure
             signal.It may be created/read/written/modified.Writing or modifing can be done
             when the entry SHOULD NOT be used by any other entry."
        REFERENCE
            "G.984.4 Section 9.5.1 Priority Queue-G"
        ::= { zxGponPriorityQueueEntry 14}


    zxGponPriorityQueueAlarmCfgTable OBJECT-TYPE
        SYNTAX      SEQUENCE OF ZxGponPriorityQueueAlarmCfgEntry
        MAX-ACCESS  not-accessible
        STATUS      current
        DESCRIPTION
            "" 
        REFERENCE
            "G.984.4 Section 9.5.1"
        ::= { zxGponTrafficMgmt 2 }

    zxGponPriorityQueueAlarmCfgEntry OBJECT-TYPE
        SYNTAX      ZxGponPriorityQueueAlarmCfgEntry
        MAX-ACCESS  not-accessible
        STATUS      current
        DESCRIPTION
            ""
        INDEX   { zxGponMgmtPonOltId, zxGponMgmtPonOnuId, zxGponPriorQueueAlarmIndex }
        ::= { zxGponPriorityQueueAlarmCfgTable 1 }

    ZxGponPriorityQueueAlarmCfgEntry ::=
        SEQUENCE {
            zxGponPriorQueueAlarmIndex             INTEGER,
            zxGponPriorQueueAlarmMeId              INTEGER,
            zxGponPriorQueueAlarmCellLosThresh     TruthValue,
            zxGponPriorQueueAlarmCellLosThreshMask TruthValue
        }

     zxGponPriorQueueAlarmIndex OBJECT-TYPE
        SYNTAX      INTEGER
        MAX-ACCESS  not-accessible
        STATUS      current
        DESCRIPTION
            ""
        ::= { zxGponPriorityQueueAlarmCfgEntry 1}    
    
     zxGponPriorQueueAlarmMeId OBJECT-TYPE
        SYNTAX      INTEGER
        MAX-ACCESS  read-only
        STATUS      current
        DESCRIPTION
            ""
        ::= { zxGponPriorityQueueAlarmCfgEntry 2}

     zxGponPriorQueueAlarmCellLosThresh OBJECT-TYPE
        SYNTAX      TruthValue
        MAX-ACCESS  read-only
        STATUS      current
        DESCRIPTION
            ""
        ::= { zxGponPriorityQueueAlarmCfgEntry 3}

     zxGponPriorQueueAlarmCellLosThreshMask OBJECT-TYPE
        SYNTAX      TruthValue
        MAX-ACCESS  read-write
        STATUS      current
        DESCRIPTION
            ""
        ::= { zxGponPriorityQueueAlarmCfgEntry 4}


    zxGponTrafficScheduleTable OBJECT-TYPE
        SYNTAX      SEQUENCE OF ZxGponTrafficScheduleEntry
        MAX-ACCESS  not-accessible
        STATUS      current
        DESCRIPTION
            "An instance of this managed entity represents a logical object of some Traffic Scheduler to 
             control upstream ATM cells or GEM packets. A Traffic Scheduler can accommodate ATM cells or 
             GEM packets after priority queue or other Traffic Scheduler and transfer ATM cells or GEM 
             packets toward the next Traffic Scheduler or T-CONT." 
        REFERENCE
            "G.984.4 Section 9.5.2"
        ::= { zxGponTrafficMgmt 3 }

    zxGponTrafficScheduleEntry OBJECT-TYPE
        SYNTAX      ZxGponTrafficScheduleEntry
        MAX-ACCESS  not-accessible
        STATUS      current
        DESCRIPTION
            "G.984.4 Section 9.5.2"
        INDEX   { zxGponMgmtPonOltId, zxGponMgmtPonOnuId, zxGponTrafficScheduleIndex }
        ::= { zxGponTrafficScheduleTable 1 }

    ZxGponTrafficScheduleEntry ::=
        SEQUENCE {
            zxGponTrafficScheduleIndex     INTEGER,
            zxGponTrafficScheduleMeId      INTEGER,
            zxGponTrafficScheduleTCountPtr INTEGER,
            zxGponTrafficScheduleOtherPtr  INTEGER,
            zxGponTrafficSchedulePolicy    INTEGER,
            zxGponTrafficSchedulePriWeight INTEGER
        }

     zxGponTrafficScheduleIndex OBJECT-TYPE
        SYNTAX      INTEGER
        MAX-ACCESS  not-accessible
        STATUS      current
        DESCRIPTION
            "An arbitrary(unique) integer for identifiying an entry
             in the Ani manangement, from 1 to M."
        ::= { zxGponTrafficScheduleEntry 1}    

     zxGponTrafficScheduleMeId OBJECT-TYPE
        SYNTAX      INTEGER
        MAX-ACCESS  read-only
        STATUS      current
        DESCRIPTION
            "This attribute provides a unique number for each instance of this managed entity. 
             This 2-byte number is associated with the physical capability that realizes the 
             Traffic Scheduler. The first byte is the slot id of the PON IF card with which this 
             Traffic Scheduler is associated. For integrated PON IF interfaces, this byte can be 
             associated with 'pseudo' slot id 0x80 (128). If the ONT has Traffic Schedulers that 
             are not associated with the PON IF card at the creation of this instance, the first 
             byte of this Traffic Scheduler is 0xFF. The second byte is the Traffic Scheduler id 
             that is numbered by the ONT itself. The Traffic Scheduler id is numbered in ascending 
             order with the range of 0x00 to 0xFF."
        ::= { zxGponTrafficScheduleEntry 2}    

     zxGponTrafficScheduleTCountPtr OBJECT-TYPE
        SYNTAX      INTEGER
        MAX-ACCESS  read-only
        STATUS      current
        DESCRIPTION
            "This attribute represents the T-CONT ME instance that is directly associated with this 
             Traffic Scheduler. This pointer is used when this Traffic Scheduler is connected to the 
             T-CONT directly, it is null (0x0000) otherwise. "
        ::= { zxGponTrafficScheduleEntry 3}    

     zxGponTrafficScheduleOtherPtr OBJECT-TYPE
        SYNTAX      INTEGER
        MAX-ACCESS  read-only
        STATUS      current
        DESCRIPTION
            "This attribute represents the Traffic Scheduler-G ME instance that serves this Traffic 
             Scheduler. Upon autonomous instantiation this attribute is null (0x0000). This pointer 
             is used when this Traffic Scheduler is connected to another Traffic Scheduler, it is null 
             otherwise. The default value is 0x0000."
        ::= { zxGponTrafficScheduleEntry 4}    

     zxGponTrafficSchedulePolicy OBJECT-TYPE
        SYNTAX      INTEGER{
                    hol(1),
                    wrr(2),
                    null(3)
                    }
        MAX-ACCESS  read-only
        STATUS      current
        DESCRIPTION
            "This attribute represents scheduling policy. Valid values include but are not limited 
             to 'Null' (value 0x03), 'HOL' (value 0x01) or 'WRR' (value 0x02). Upon autonomous 
             instantiation, this attribute consists of the value 0x00. "
        DEFVAL { null }
        ::= { zxGponTrafficScheduleEntry 5}    

    zxGponTrafficSchedulePriWeight OBJECT-TYPE
        SYNTAX      INTEGER(0..255)
        MAX-ACCESS  read-write
        STATUS      current
        DESCRIPTION
            "It represents priority for HOL scheduling or the weight for WRR scheduling.
             This value is used by the T-CONT or Traffic Scheduler indicated by the T-CONT 
             Pointer attribute or Traffic Scheduler Pointer attribute. If the indicated 
             pointer has Policy = HOL, then this value is interpreted as a priority (0 
             indicates the highest priority, and 0xFF (255) the lowest). If the indicated 
             pointer has Policy = WRR, then this value is interpreted as a weight.It may be
             created/read/written/modified.Writing or modifing can be done when the entry 
             SHOULD NOT be used by any other entry."
        REFERENCE
            "G.984.4 Section 9.5.2 Traffic Scheduler-G"
        ::= { zxGponTrafficScheduleEntry 6}

    zxGponGemTrafficDescriptorsTable OBJECT-TYPE
        SYNTAX      SEQUENCE OF ZxGponGemTrafficDescriptorsEntry
        MAX-ACCESS  not-accessible
        STATUS      current
        DESCRIPTION
            "" 
        REFERENCE
            "G.984.4 Section 9.5.3"
        ::= { zxGponTrafficMgmt 4 }

    zxGponGemTrafficDescriptorsEntry OBJECT-TYPE
        SYNTAX      ZxGponGemTrafficDescriptorsEntry
        MAX-ACCESS  not-accessible
        STATUS      current
        DESCRIPTION
            ""
        INDEX   { zxGponMgmtPonOltId, zxGponMgmtPonOnuId, zxGponGemTrafficDescriptorsMeIdIdx }
        ::= { zxGponGemTrafficDescriptorsTable 1 }

    ZxGponGemTrafficDescriptorsEntry ::=
        SEQUENCE {
            zxGponGemTrafficDescriptorsMeIdIdx      INTEGER,
            zxGponGemTrafficDescriptorsSIR          INTEGER,
            zxGponGemTrafficDescriptorsPIR          INTEGER,
            zxGponGemTrafficDescriptorsMgmtCtrlFlag INTEGER,
            zxGponGemTrafficDescriptorsEntryStatus  RowStatus
        }

     zxGponGemTrafficDescriptorsMeIdIdx OBJECT-TYPE
        SYNTAX      INTEGER
        MAX-ACCESS  not-accessible
        STATUS      current
        DESCRIPTION
            ""
        ::= { zxGponGemTrafficDescriptorsEntry 1}    
    
    zxGponGemTrafficDescriptorsSIR OBJECT-TYPE
        SYNTAX      INTEGER
        MAX-ACCESS  read-write
        STATUS      current
        DESCRIPTION
            "It is SIR (Sustained Information Rate). The unit of Kbps. It may be created/read/
             written/modified.Writing or modifing can be done when the entry SHOULD NOT be used
             by any other entry."
        REFERENCE
            "G.984.4 Section 9.5.3 GEM Traffic Descriptor"
        ::= { zxGponGemTrafficDescriptorsEntry 2}

    zxGponGemTrafficDescriptorsPIR OBJECT-TYPE
        SYNTAX      INTEGER
        MAX-ACCESS  read-write
        STATUS      current
        DESCRIPTION
            "It is PIR (Peak Information Rate). The unit of Kbps. It may be created/read/written/
             modified.Writing or modifing can be done when the entry SHOULD NOT be used by any 
             other entry."
        REFERENCE
            "G.984.4 Section 9.5.3 GEM Traffic Descriptor"
        ::= { zxGponGemTrafficDescriptorsEntry 3}

    zxGponGemTrafficDescriptorsMgmtCtrlFlag OBJECT-TYPE
        SYNTAX      INTEGER{
                    nmsCreate(1),
                    neCreate(2)
                    }
        MAX-ACCESS  read-only
        STATUS      current
        DESCRIPTION
            "This attribute is used to indicate this record is created by NMS or NE. If it
             is neCreate(2), this record can not be deleted."
        REFERENCE
            "N/A"
        ::= { zxGponGemTrafficDescriptorsEntry 4}

   zxGponGemTrafficDescriptorsEntryStatus OBJECT-TYPE
        SYNTAX      RowStatus
        MAX-ACCESS  read-create
        STATUS      current
        DESCRIPTION
            ""
        ::= { zxGponGemTrafficDescriptorsEntry 5}

--zxGponProfileMgmt.mi2
    zxGponProfileMgmt OBJECT IDENTIFIER ::= { zxGponRootMib 26 }

    zxGponBandwidthProfileTable OBJECT-TYPE
        SYNTAX      SEQUENCE OF ZxGponBandwidthProfileEntry
        MAX-ACCESS  not-accessible
        STATUS      current
        DESCRIPTION
            "Bandwidth allocation for one T-CONT in some ONT.
             these bandwidths as following:
             fixed bandwidth        ab. FBW
             assured bandwidth      ab. ABW
             non-assured bandwidth  ab. NABW
             best effort bandwidth  ab. BEBW
             additional bandwidth   ab. AddBW
             guaranteed bandwidth   ab. GBW
             maximum bandwidth      ab. MaxBW
             minimum bandwidth      ab. MinBW
             AddBW = NABW + BEBW
             GBW   = FBW  + ABW
             MaxBW = GBW  + AddBW
             MinBW = FBW?
             NABW, BEBW, FBW and ABWare able to participate in DBA
             "
        ::= { zxGponProfileMgmt 1 }

    zxGponBandwidthProfileEntry OBJECT-TYPE
        SYNTAX      ZxGponBandwidthProfileEntry
        MAX-ACCESS  not-accessible
        STATUS      current
        DESCRIPTION
            "An entry in the Bandwidth profile table."
        INDEX   { zxGponBWProfileIndex }
        ::= { zxGponBandwidthProfileTable 1 }

    ZxGponBandwidthProfileEntry ::=
        SEQUENCE {
            zxGponBWProfileIndex       INTEGER,
            zxGponBWProfileName        ZxGponRecordName,
            zxGponBWProfileFixed       INTEGER,
            zxGponBWProfileAssured     INTEGER,
            zxGponBWProfileMaximum     INTEGER,
            zxGponBWProfileType        INTEGER,
            zxGponBWProfileRefCnt      INTEGER,
            zxGponBWProfileEntryStatus RowStatus
        }

    zxGponBWProfileIndex OBJECT-TYPE
        SYNTAX      INTEGER
        MAX-ACCESS  not-accessible
        STATUS      current
        DESCRIPTION
            "An arbitrary(unique) integer for identifiying an entry
             in the line card, from 1 to M, M is equal to 512."
        ::= { zxGponBandwidthProfileEntry 1}

    zxGponBWProfileName OBJECT-TYPE
        SYNTAX      ZxGponRecordName(SIZE (0..64))
        MAX-ACCESS  read-write
        STATUS      current
        DESCRIPTION
            "The Bandwidth Profile Name.It may be created/read/written/modified.
             Writing or modifing can be done all the time."
        ::= { zxGponBandwidthProfileEntry 2}

    zxGponBWProfileFixed OBJECT-TYPE
        SYNTAX      INTEGER
        MAX-ACCESS  read-write
        STATUS      current
        DESCRIPTION
            "The Fixed Bandwidth is entirely reserved and cyclically allocated in order
             to achieve a low traffic transfer delay.The unit of kbps.It may be created
             /read/written/modified. Guaranteed Bandwidth is the summation of Assured 
             Bandwidth and Fixed Bandwidth. Writing or modifing can be done when the 
             entry SHOULD NOT be used by any other entry."
        ::= { zxGponBandwidthProfileEntry 3}

    zxGponBWProfileAssured OBJECT-TYPE
        SYNTAX      INTEGER
        MAX-ACCESS  read-write
        STATUS      current
        DESCRIPTION
            "The Assured Bandwidth is bandwidth that is always available to the ONU/ONT if
             the T-CONT buffer is expected to have traffic to transmit. If the T-CONT buffer 
             does not have traffic to transmit, this bandwidth may be used by other T-CONTs.
             The unit of kbps. It may be created/read/written/modified. Guaranteed Bandwidth
             is the summation of Assured Bandwidth and Fixed Bandwidth. Writing or modifing 
             can be done when the entry SHOULD NOT be used by any other entry."
        ::= { zxGponBandwidthProfileEntry 4}

    zxGponBWProfileMaximum OBJECT-TYPE
        SYNTAX      INTEGER
        MAX-ACCESS  read-write
        STATUS      current
        DESCRIPTION
            "The Maximum Bandwidth.The unit of kbps.It may be created/read/written/modified. 
             Writing or modifing can be done when the entry SHOULD NOT be used by any other entry."
        ::= { zxGponBandwidthProfileEntry 5}

    zxGponBWProfileType OBJECT-TYPE
        SYNTAX      INTEGER{
                    type1(1),
                    type2(2),
                    type3(3),
                    type4(4),
                    type5(5)
                    }
        MAX-ACCESS  read-write
        STATUS      current
        DESCRIPTION
            "Type 1 is characterized by Fixed bandwidth only;
             Type 2 is characterized by Assured bandwidth only;
             Type 3 has Assured bandwidth and Non-assured bandwidth;
             Type 4 has Best-effort bandwidth only and does not have any Guaranteed bandwidth;
             Type 5 is the super set of all of types."
        ::= { zxGponBandwidthProfileEntry 6}
        
    zxGponBWProfileRefCnt OBJECT-TYPE
        SYNTAX      INTEGER
        MAX-ACCESS  read-only
        STATUS      current
        DESCRIPTION
            "Indicate the reference count of this BW profile."
        ::= { zxGponBandwidthProfileEntry 7}

    zxGponBWProfileEntryStatus OBJECT-TYPE
        SYNTAX      RowStatus
        MAX-ACCESS  read-create
        STATUS      current
        DESCRIPTION
            "The control that allows creation and deletion of entries. Deleting can be done
             when the entry SHOULD NOT be used by any other entry."
        ::= { zxGponBandwidthProfileEntry 8}

    zxGponTrafficProfileTable OBJECT-TYPE
        SYNTAX      SEQUENCE OF ZxGponTrafficProfileEntry
        MAX-ACCESS  not-accessible
        STATUS      current
        DESCRIPTION
            "Rate configuration for one traffic.
             As following:
             sustainable information rate      ab. SIR
             peak information rate             ab. PIR
             "
        ::= { zxGponProfileMgmt 2 }

    zxGponTrafficProfileEntry OBJECT-TYPE
        SYNTAX      ZxGponTrafficProfileEntry
        MAX-ACCESS  not-accessible
        STATUS      current
        DESCRIPTION
            "An entry in the Traffic profile table."
        INDEX   { zxGponTrafficProfileIndex }
        ::= { zxGponTrafficProfileTable 1 }

    ZxGponTrafficProfileEntry ::=
        SEQUENCE {
            zxGponTrafficProfileIndex       INTEGER,
            zxGponTrafficProfileName        ZxGponRecordName,
            zxGponTrafficProfileSir         INTEGER,
            zxGponTrafficProfilePir         INTEGER,
            zxGponTrafficProfileRefCnt      INTEGER,
            zxGponTrafficProfileEntryStatus RowStatus
        }

    zxGponTrafficProfileIndex OBJECT-TYPE
        SYNTAX      INTEGER
        MAX-ACCESS  not-accessible
        STATUS      current
        DESCRIPTION
            "An arbitrary(unique) integer for identifiying an entry
             in the line card, from 1 to M, M is equal to 512."
        ::= { zxGponTrafficProfileEntry 1}

    zxGponTrafficProfileName OBJECT-TYPE
        SYNTAX      ZxGponRecordName(SIZE (0..64))
        MAX-ACCESS  read-write
        STATUS      current
        DESCRIPTION
            "The Traffic Profile Name.It may be created/read/written/modified.
             Writing or modifing can be done all the time."
        ::= { zxGponTrafficProfileEntry 2}

    zxGponTrafficProfileSir OBJECT-TYPE
        SYNTAX      INTEGER
        MAX-ACCESS  read-write
        STATUS      current
        DESCRIPTION
            "The SIR is sustainable rate of the traffic. Writing or modifing can be done when the 
             entry SHOULD NOT be used by any other entry."
        ::= { zxGponTrafficProfileEntry 3}

    zxGponTrafficProfilePir OBJECT-TYPE
        SYNTAX      INTEGER
        MAX-ACCESS  read-write
        STATUS      current
        DESCRIPTION
            "The PIR is peak rate of the traffic. Writing or modifing can be done when the 
             entry SHOULD NOT be used by any other entry."
        ::= { zxGponTrafficProfileEntry 4}
        
    zxGponTrafficProfileRefCnt OBJECT-TYPE
        SYNTAX      INTEGER
        MAX-ACCESS  read-only
        STATUS      current
        DESCRIPTION
            "The reference count of this profile."
        ::= { zxGponTrafficProfileEntry 5}

    zxGponTrafficProfileEntryStatus OBJECT-TYPE
        SYNTAX      RowStatus
        MAX-ACCESS  read-create
        STATUS      current
        DESCRIPTION
            "The control that allows creation and deletion of entries. Deleting can be done
             when the entry SHOULD NOT be used by any other entry."
        ::= { zxGponTrafficProfileEntry 6}
    
    zxGponThresholdDataProfileTable OBJECT-TYPE
        SYNTAX      SEQUENCE OF ZxGponThresholdDataProfileEntry
        MAX-ACCESS  not-accessible
        STATUS      current
        DESCRIPTION
            "It represents threshold values for the performance monitoring parameters."
        REFERENCE
            "G.984.4 Section 9.1.8 Threshold Data 1 and Section 9.1.9 Threshold Data 2"
        ::= { zxGponProfileMgmt 3 }

    zxGponThresholdDataProfileEntry OBJECT-TYPE
        SYNTAX      ZxGponThresholdDataProfileEntry
        MAX-ACCESS  not-accessible
        STATUS      current
        DESCRIPTION
            "It provide a Threshold Data pointer."
        REFERENCE
            "G.984.4 Section 9.1.8 Threshold Data 1 and Section 9.1.9 Threshold Data 2"
        INDEX   { zxGponThresholdDataProfileIndex }
        ::= { zxGponThresholdDataProfileTable 1 }

    ZxGponThresholdDataProfileEntry ::=
        SEQUENCE {
            zxGponThresholdDataProfileIndex       INTEGER,
            zxGponThresholdDataProfileName        ZxGponRecordName,
            zxGponThresholdDataProfileVal1        Unsigned32,
            zxGponThresholdDataProfileVal2        Unsigned32,
            zxGponThresholdDataProfileVal3        Unsigned32,
            zxGponThresholdDataProfileVal4        Unsigned32,
            zxGponThresholdDataProfileVal5        Unsigned32,
            zxGponThresholdDataProfileVal6        Unsigned32,
            zxGponThresholdDataProfileVal7        Unsigned32,
            zxGponThresholdDataProfileVal8        Unsigned32,
            zxGponThresholdDataProfileVal9        Unsigned32,
            zxGponThresholdDataProfileVal10       Unsigned32,
            zxGponThresholdDataProfileVal11       Unsigned32,
            zxGponThresholdDataProfileVal12       Unsigned32,
            zxGponThresholdDataProfileVal13       Unsigned32,
            zxGponThresholdDataProfileVal14       Unsigned32,
            zxGponThresholdDataProfileRefCnt       INTEGER,
            zxGponThresholdDataProfileEntryStatus RowStatus
        }

    zxGponThresholdDataProfileIndex OBJECT-TYPE
        SYNTAX      INTEGER
        MAX-ACCESS  not-accessible
        STATUS      current
        DESCRIPTION
            "An arbitrary(unique) integer for identifiying an entry in the Threshold Data,
             from 1 to M, M is equal to 128."
        ::= { zxGponThresholdDataProfileEntry 1}

    zxGponThresholdDataProfileName OBJECT-TYPE
        SYNTAX      ZxGponRecordName(SIZE (0..64))
        MAX-ACCESS  read-write
        STATUS      current
        DESCRIPTION
            "The Threshold Data Templet Name.It may be created/read/written/modified.
             Writing or modifing can be done all the time."
        ::= { zxGponThresholdDataProfileEntry 2}

    zxGponThresholdDataProfileVal1 OBJECT-TYPE
        SYNTAX      Unsigned32
        MAX-ACCESS  read-write
        STATUS      current
        DESCRIPTION
            "It provides the associated threshold value for the 1st thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 3}

    zxGponThresholdDataProfileVal2 OBJECT-TYPE
        SYNTAX      Unsigned32
        MAX-ACCESS  read-write
        STATUS      current
        DESCRIPTION
            "It provides the associated threshold value for the 2nd thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 4}

    zxGponThresholdDataProfileVal3 OBJECT-TYPE
        SYNTAX      Unsigned32
        MAX-ACCESS  read-write
        STATUS      current
        DESCRIPTION
            "It provides the associated threshold value for the 3rd thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 5}

    zxGponThresholdDataProfileVal4 OBJECT-TYPE
        SYNTAX      Unsigned32
        MAX-ACCESS  read-write
        STATUS      current
        DESCRIPTION
            "It provides the associated threshold value for the 4th thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 6}

    zxGponThresholdDataProfileVal5 OBJECT-TYPE
        SYNTAX      Unsigned32
        MAX-ACCESS  read-write
        STATUS      current
        DESCRIPTION
            "It provides the associated threshold value for the 5th thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 7}

    zxGponThresholdDataProfileVal6 OBJECT-TYPE
        SYNTAX      Unsigned32
        MAX-ACCESS  read-write
        STATUS      current
        DESCRIPTION
            "It provides the associated threshold value for the 6th thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 8}

    zxGponThresholdDataProfileVal7 OBJECT-TYPE
        SYNTAX      Unsigned32
        MAX-ACCESS  read-write
        STATUS      current
        DESCRIPTION
            "It provides the associated threshold value for the 7st thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 9}

    zxGponThresholdDataProfileVal8 OBJECT-TYPE
        SYNTAX      Unsigned32
        MAX-ACCESS  read-write
        STATUS      current
        DESCRIPTION
            "It provides the associated threshold value for the 8th thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 10}

    zxGponThresholdDataProfileVal9 OBJECT-TYPE
        SYNTAX      Unsigned32
        MAX-ACCESS  read-write
        STATUS      current
        DESCRIPTION
            "It provides the associated threshold value for the 9th thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 11}

    zxGponThresholdDataProfileVal10 OBJECT-TYPE
        SYNTAX      Unsigned32
        MAX-ACCESS  read-write
        STATUS      current
        DESCRIPTION
            "It provides the associated threshold value for the 10th thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 12}

    zxGponThresholdDataProfileVal11 OBJECT-TYPE
        SYNTAX      Unsigned32
        MAX-ACCESS  read-write
        STATUS      current
        DESCRIPTION
            "It provides the associated threshold value for the 11th thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 13}

    zxGponThresholdDataProfileVal12 OBJECT-TYPE
        SYNTAX      Unsigned32
        MAX-ACCESS  read-write
        STATUS      current
        DESCRIPTION
            "It provides the associated threshold value for the 12th thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 14}

    zxGponThresholdDataProfileVal13 OBJECT-TYPE
        SYNTAX      Unsigned32
        MAX-ACCESS  read-write
        STATUS      current
        DESCRIPTION
            "It provides the associated threshold value for the 13th thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 15}

    zxGponThresholdDataProfileVal14 OBJECT-TYPE
        SYNTAX      Unsigned32
        MAX-ACCESS  read-write
        STATUS      current
        DESCRIPTION
            "It provides the associated threshold value for the 14th thresholded counter in the
             History Data type managed entity. It may be created/read/written/modified.Writing or 
             modifing can be done when the entry SHOULD NOT be used by any other entry."
        REFERENCE
            "G.984.4 Section 9.1.8 Threshold Data 1 and Section 9.1.9 Threshold Data 2"
        ::= { zxGponThresholdDataProfileEntry 16}
        
    zxGponThresholdDataProfileRefCnt OBJECT-TYPE
        SYNTAX      INTEGER
        MAX-ACCESS  read-only
        STATUS      current
        DESCRIPTION
            "The reference count of this profile."
        REFERENCE
            ""
        ::= { zxGponThresholdDataProfileEntry 17}

    zxGponThresholdDataProfileEntryStatus OBJECT-TYPE
        SYNTAX      RowStatus
        MAX-ACCESS  read-create
        STATUS      current
        DESCRIPTION
            "The control that allows creation and deletion of entries. Deleting can be done
             when the entry SHOULD NOT be used by any other entry."
        ::= { zxGponThresholdDataProfileEntry 18}

---
--- DA(48 bits) SA(48 bits) TYPE/LEN(16 bits) RSVD(1bit) PRI(3 bits) VLAN(12 bits) ... ...
--- multicast and VLAN from 10 - 100, the rule as flow:
--- 1st bit = 7,   1st len = 1,  min val = 1,  max val = 1
--- 2nd bit = 116, 2nd len = 12, min val = 10, max val = 100
---

--zxGponStandardOnu.mi2
    zxGponStandardOnu OBJECT IDENTIFIER ::= { zxGponRootMib 27 }
    zxGponOnuEncryptTable OBJECT-TYPE
        SYNTAX      SEQUENCE OF ZxGponOnuEncryptEntry
        MAX-ACCESS  not-accessible
        STATUS      current
        DESCRIPTION
            "" 
        REFERENCE
            "G.984.3"
        ::= { zxGponStandardOnu 3 }

    zxGponOnuEncryptEntry OBJECT-TYPE
        SYNTAX      ZxGponOnuEncryptEntry
        MAX-ACCESS  not-accessible
        STATUS      current
        DESCRIPTION
            ""
        INDEX   { zxGponMgmtPonOltId, zxGponMgmtPonOnuId }
        ::= { zxGponOnuEncryptTable 1 }

    ZxGponOnuEncryptEntry ::=
        SEQUENCE {
            zxGponOnuEncryptDir    INTEGER,
            zxGponOnuEncryptEnable INTEGER,
            zxGponOnuEncryptMode   INTEGER
        }

     zxGponOnuEncryptDir OBJECT-TYPE
        SYNTAX      INTEGER{
                    us(1),
                    ds(2),
                    both(3)
                    }
        MAX-ACCESS  read-write
        STATUS      current
        DESCRIPTION
            ""
        ::= { zxGponOnuEncryptEntry 1}

     zxGponOnuEncryptEnable OBJECT-TYPE
        SYNTAX      INTEGER{
                    start(1),
                    stop(2)
                    }
        MAX-ACCESS  read-write
        STATUS      current
        DESCRIPTION
            ""
        ::= { zxGponOnuEncryptEntry 2}

     zxGponOnuEncryptMode OBJECT-TYPE
        SYNTAX      INTEGER{
                    aes(1),
                    other(2)
                    }
        MAX-ACCESS  read-write
        STATUS      current
        DESCRIPTION
            ""
        ::= { zxGponOnuEncryptEntry 3}


    zxGponPortIdEncryptTable OBJECT-TYPE
        SYNTAX      SEQUENCE OF ZxGponPortIdEncryptEntry
        MAX-ACCESS  not-accessible
        STATUS      current
        DESCRIPTION
            "" 
        REFERENCE
            "G.984.3"
        ::= { zxGponStandardOnu 4 }

    zxGponPortIdEncryptEntry OBJECT-TYPE
        SYNTAX      ZxGponPortIdEncryptEntry
        MAX-ACCESS  not-accessible
        STATUS      current
        DESCRIPTION
            ""
        INDEX   { zxGponMgmtPonOltId, zxGponMgmtPonOnuId, zxGponGemPortIdx }
        ::= { zxGponPortIdEncryptTable 1 }

    ZxGponPortIdEncryptEntry ::=
        SEQUENCE {
            zxGponPortIdEncryptEnable TruthValue
        }

     zxGponPortIdEncryptEnable OBJECT-TYPE
        SYNTAX      TruthValue
        MAX-ACCESS  read-write
        STATUS      current
        DESCRIPTION
            ""
        ::= { zxGponPortIdEncryptEntry 1}

    zxGponOnuAlarmStatusTable OBJECT-TYPE
        SYNTAX      SEQUENCE OF ZxGponOnuAlarmStatusEntry
        MAX-ACCESS  not-accessible
        STATUS      current
        DESCRIPTION
            "" 
        REFERENCE
            "G.984.3"
        ::= { zxGponStandardOnu 6 }

    zxGponOnuAlarmStatusEntry OBJECT-TYPE
        SYNTAX      ZxGponOnuAlarmStatusEntry
        MAX-ACCESS  not-accessible
        STATUS      current
        DESCRIPTION
            ""
        INDEX   { zxGponMgmtPonOltId, zxGponMgmtPonOnuId }
        ::= { zxGponOnuAlarmStatusTable 1 }

    ZxGponOnuAlarmStatusEntry ::=
        SEQUENCE {
            zxGponOnuAlarmLOSd      TruthValue,
            zxGponOnuAlarmLOSdMask  TruthValue,
            zxGponOnuAlarmLOFd      TruthValue,
            zxGponOnuAlarmLOFdMask  TruthValue,
            zxGponOnuAlarmSFd       TruthValue,
            zxGponOnuAlarmSFdMask   TruthValue,
            zxGponOnuAlarmSDd       TruthValue,
            zxGponOnuAlarmSDdMask   TruthValue,
            zxGponOnuAlarmLCDAd     TruthValue,
            zxGponOnuAlarmLCDAdMask TruthValue,
            zxGponOnuAlarmLCDGd     TruthValue,
            zxGponOnuAlarmLCDGdMask TruthValue,
            zxGponOnuAlarmTFd       TruthValue,
            zxGponOnuAlarmTFdMask   TruthValue,
            zxGponOnuAlarmSUFd      TruthValue,
            zxGponOnuAlarmSUFdMask  TruthValue,
            zxGponOnuAlarmMEMd      TruthValue,
            zxGponOnuAlarmMEMdMask  TruthValue,
            zxGponOnuAlarmDACTd     TruthValue,
            zxGponOnuAlarmDACTdMask TruthValue,
            zxGponOnuAlarmDISd      TruthValue,
            zxGponOnuAlarmDISdMask  TruthValue,
            zxGponOnuAlarmMISd      TruthValue,
            zxGponOnuAlarmMISdMask  TruthValue,
            zxGponOnuAlarmPEEd      TruthValue,
            zxGponOnuAlarmPEEdMask  TruthValue,
            zxGponOnuAlarmRDId      TruthValue,
            zxGponOnuAlarmRDIdMask  TruthValue
        }

     zxGponOnuAlarmLOSd OBJECT-TYPE
        SYNTAX      TruthValue
        MAX-ACCESS  read-only
        STATUS      current
        DESCRIPTION
            ""
        ::= { zxGponOnuAlarmStatusEntry 1}
        
      zxGponOnuAlarmLOSdMask OBJECT-TYPE
        SYNTAX      TruthValue
        MAX-ACCESS  read-write
        STATUS      current
        DESCRIPTION
            ""
        ::= { zxGponOnuAlarmStatusEntry 2}       

     zxGponOnuAlarmLOFd OBJECT-TYPE
        SYNTAX      TruthValue
        MAX-ACCESS  read-only
        STATUS      current
        DESCRIPTION
            ""
        ::= { zxGponOnuAlarmStatusEntry 3}
        
      zxGponOnuAlarmLOFdMask OBJECT-TYPE
        SYNTAX      TruthValue
        MAX-ACCESS  read-write
        STATUS      current
        DESCRIPTION
            ""
        ::= { zxGponOnuAlarmStatusEntry 4}       

     zxGponOnuAlarmSFd OBJECT-TYPE
        SYNTAX      TruthValue
        MAX-ACCESS  read-only
        STATUS      current
        DESCRIPTION
            ""
        ::= { zxGponOnuAlarmStatusEntry 5}
        
      zxGponOnuAlarmSFdMask OBJECT-TYPE
        SYNTAX      TruthValue
        MAX-ACCESS  read-write
        STATUS      current
        DESCRIPTION
            ""
        ::= { zxGponOnuAlarmStatusEntry 6}       

     zxGponOnuAlarmSDd OBJECT-TYPE
        SYNTAX      TruthValue
        MAX-ACCESS  read-only
        STATUS      current
        DESCRIPTION
            ""
        ::= { zxGponOnuAlarmStatusEntry 7}
        
      zxGponOnuAlarmSDdMask OBJECT-TYPE
        SYNTAX      TruthValue
        MAX-ACCESS  read-write
        STATUS      current
        DESCRIPTION
            ""
        ::= { zxGponOnuAlarmStatusEntry 8}       

     zxGponOnuAlarmLCDAd OBJECT-TYPE
        SYNTAX      TruthValue
        MAX-ACCESS  read-only
        STATUS      current
        DESCRIPTION
            ""
        ::= { zxGponOnuAlarmStatusEntry 9}
        
      zxGponOnuAlarmLCDAdMask OBJECT-TYPE
        SYNTAX      TruthValue
        MAX-ACCESS  read-write
        STATUS      current
        DESCRIPTION
            ""
        ::= { zxGponOnuAlarmStatusEntry 10}       

     zxGponOnuAlarmLCDGd OBJECT-TYPE
        SYNTAX      TruthValue
        MAX-ACCESS  read-only
        STATUS      current
        DESCRIPTION
            ""
        ::= { zxGponOnuAlarmStatusEntry 11}
        
      zxGponOnuAlarmLCDGdMask OBJECT-TYPE
        SYNTAX      TruthValue
        MAX-ACCESS  read-write
        STATUS      current
        DESCRIPTION
            ""
        ::= { zxGponOnuAlarmStatusEntry 12}       

     zxGponOnuAlarmTFd OBJECT-TYPE
        SYNTAX      TruthValue
        MAX-ACCESS  read-only
        STATUS      current
        DESCRIPTION
            ""
        ::= { zxGponOnuAlarmStatusEntry 13}
        
      zxGponOnuAlarmTFdMask OBJECT-TYPE
        SYNTAX      TruthValue
        MAX-ACCESS  read-write
        STATUS      current
        DESCRIPTION
            ""
        ::= { zxGponOnuAlarmStatusEntry 14}       

     zxGponOnuAlarmSUFd OBJECT-TYPE
        SYNTAX      TruthValue
        MAX-ACCESS  read-only
        STATUS      current
        DESCRIPTION
            ""
        ::= { zxGponOnuAlarmStatusEntry 15}
        
      zxGponOnuAlarmSUFdMask OBJECT-TYPE
        SYNTAX      TruthValue
        MAX-ACCESS  read-write
        STATUS      current
        DESCRIPTION
            ""
        ::= { zxGponOnuAlarmStatusEntry 16}       

     zxGponOnuAlarmMEMd OBJECT-TYPE
        SYNTAX      TruthValue
        MAX-ACCESS  read-only
        STATUS      current
        DESCRIPTION
            ""
        ::= { zxGponOnuAlarmStatusEntry 17}
        
      zxGponOnuAlarmMEMdMask OBJECT-TYPE
        SYNTAX      TruthValue
        MAX-ACCESS  read-write
        STATUS      current
        DESCRIPTION
            ""
        ::= { zxGponOnuAlarmStatusEntry 18}       

     zxGponOnuAlarmDACTd OBJECT-TYPE
        SYNTAX      TruthValue
        MAX-ACCESS  read-only
        STATUS      current
        DESCRIPTION
            ""
        ::= { zxGponOnuAlarmStatusEntry 19}
        
      zxGponOnuAlarmDACTdMask OBJECT-TYPE
        SYNTAX      TruthValue
        MAX-ACCESS  read-write
        STATUS      current
        DESCRIPTION
            ""
        ::= { zxGponOnuAlarmStatusEntry 20}       

     zxGponOnuAlarmDISd OBJECT-TYPE
        SYNTAX      TruthValue
        MAX-ACCESS  read-only
        STATUS      current
        DESCRIPTION
            ""
        ::= { zxGponOnuAlarmStatusEntry 21}
        
      zxGponOnuAlarmDISdMask OBJECT-TYPE
        SYNTAX      TruthValue
        MAX-ACCESS  read-write
        STATUS      current
        DESCRIPTION
            ""
        ::= { zxGponOnuAlarmStatusEntry 22}       

     zxGponOnuAlarmMISd OBJECT-TYPE
        SYNTAX      TruthValue
        MAX-ACCESS  read-only
        STATUS      current
        DESCRIPTION
            ""
        ::= { zxGponOnuAlarmStatusEntry 23}
        
      zxGponOnuAlarmMISdMask OBJECT-TYPE
        SYNTAX      TruthValue
        MAX-ACCESS  read-write
        STATUS      current
        DESCRIPTION
            ""
        ::= { zxGponOnuAlarmStatusEntry 24}       

     zxGponOnuAlarmPEEd OBJECT-TYPE
        SYNTAX      TruthValue
        MAX-ACCESS  read-only
        STATUS      current
        DESCRIPTION
            ""
        ::= { zxGponOnuAlarmStatusEntry 25}
        
      zxGponOnuAlarmPEEdMask OBJECT-TYPE
        SYNTAX      TruthValue
        MAX-ACCESS  read-write
        STATUS      current
        DESCRIPTION
            ""
        ::= { zxGponOnuAlarmStatusEntry 26}       

     zxGponOnuAlarmRDId OBJECT-TYPE
        SYNTAX      TruthValue
        MAX-ACCESS  read-only
        STATUS      current
        DESCRIPTION
            ""
        ::= { zxGponOnuAlarmStatusEntry 27}
        
      zxGponOnuAlarmRDIdMask OBJECT-TYPE
        SYNTAX      TruthValue
        MAX-ACCESS  read-write
        STATUS      current
        DESCRIPTION
            ""
        ::= { zxGponOnuAlarmStatusEntry 28}       


    zxGponSignalThresholdTable OBJECT-TYPE
        SYNTAX      SEQUENCE OF ZxGponSignalThresholdEntry
        MAX-ACCESS  not-accessible
        STATUS      current
        DESCRIPTION
            "" 
        REFERENCE
            "G.984.3"
        ::= { zxGponStandardOnu 7 }

    zxGponSignalThresholdEntry OBJECT-TYPE
        SYNTAX      ZxGponSignalThresholdEntry
        MAX-ACCESS  not-accessible
        STATUS      current
        DESCRIPTION
            ""
        INDEX   { zxGponMgmtPonOltId, zxGponMgmtPonOnuId }
        ::= { zxGponSignalThresholdTable 1 }

    ZxGponSignalThresholdEntry ::=
        SEQUENCE {
            zxGponSignalThresholdSDd  INTEGER,
            zxGponSignalThresholdSFd  INTEGER
        }

     zxGponSignalThresholdSDd OBJECT-TYPE
        SYNTAX      INTEGER
        MAX-ACCESS  read-write
        STATUS      current
        DESCRIPTION
            ""
        ::= { zxGponSignalThresholdEntry 1}

     zxGponSignalThresholdSFd OBJECT-TYPE
        SYNTAX      INTEGER
        MAX-ACCESS  read-write
        STATUS      current
        DESCRIPTION
            ""
        ::= { zxGponSignalThresholdEntry 2}


    zxGponOnuPerfStatisticTable OBJECT-TYPE
        SYNTAX      SEQUENCE OF ZxGponOnuPerfStatisticEntry
        MAX-ACCESS  not-accessible
        STATUS      current
        DESCRIPTION
            "" 
        REFERENCE
            "G.984.3"
        ::= { zxGponStandardOnu 8 }

    zxGponOnuPerfStatisticEntry OBJECT-TYPE
        SYNTAX      ZxGponOnuPerfStatisticEntry
        MAX-ACCESS  not-accessible
        STATUS      current
        DESCRIPTION
            ""
        INDEX   { zxGponMgmtPonOltId, zxGponMgmtPonOnuId }
        ::= { zxGponOnuPerfStatisticTable 1 }

    ZxGponOnuPerfStatisticEntry ::=
        SEQUENCE {
            zxGponOnuPerfStatERRdCounter   Counter64,
            zxGponOnuPerfStatBIPErrCounter Counter64
        }

     zxGponOnuPerfStatERRdCounter OBJECT-TYPE
        SYNTAX      Counter64
        MAX-ACCESS  read-only
        STATUS      current
        DESCRIPTION
            ""
        ::= { zxGponOnuPerfStatisticEntry 1}

     zxGponOnuPerfStatBIPErrCounter OBJECT-TYPE
        SYNTAX      Counter64
        MAX-ACCESS  read-only
        STATUS      current
        DESCRIPTION
            ""
        ::= { zxGponOnuPerfStatisticEntry 2}
        
    zxGponOnuWeightTable OBJECT-TYPE
        SYNTAX      SEQUENCE OF ZxGponOnuWeightEntry
        MAX-ACCESS  not-accessible
        STATUS      current
        DESCRIPTION
            "This table represents ONU side  configuration."
        ::= { zxGponStandardOnu 9 }

    zxGponOnuWeightEntry OBJECT-TYPE
        SYNTAX      ZxGponOnuWeightEntry
        MAX-ACCESS  not-accessible
        STATUS      current
        DESCRIPTION
            "It is entry in the table zxGponOnuWeightTable."
        INDEX   { zxGponMgmtPonOltId, zxGponMgmtPonOnuId}
        ::= { zxGponOnuWeightTable 1 }

    ZxGponOnuWeightEntry ::=
        SEQUENCE {
            zxGponOnuSchedulemode             INTEGER,
            zxGponOnuCos1Weight               INTEGER,
            zxGponOnuCos2Weight               INTEGER,
            zxGponOnuCos3Weight               INTEGER,
            zxGponOnuCos4Weight               INTEGER,
            zxGponOnuDownTrafficPtr           INTEGER
        }
   
    zxGponOnuSchedulemode OBJECT-TYPE
        SYNTAX      INTEGER{
                     none(0),
                     sp(1),
                     wrr(2)
                     }
        MAX-ACCESS  read-write
        STATUS      current
        DESCRIPTION
            "COS Schedule mode."
        ::= { zxGponOnuWeightEntry 1}
        
    zxGponOnuCos1Weight     OBJECT-TYPE
      SYNTAX      INTEGER
      MAX-ACCESS  read-write
      STATUS      current 
      DESCRIPTION 
        "Weight of COS1(0-100)."
      ::= { zxGponOnuWeightEntry 2 }
    
    zxGponOnuCos2Weight     OBJECT-TYPE
      SYNTAX      INTEGER
      MAX-ACCESS  read-write
      STATUS      current 
      DESCRIPTION 
        "Weight of COS2(0-100)."
      ::= { zxGponOnuWeightEntry 3 }
      
    zxGponOnuCos3Weight     OBJECT-TYPE
      SYNTAX      INTEGER
      MAX-ACCESS  read-write
      STATUS      current 
      DESCRIPTION 
        "Weight of COS3(0-100)."
      ::= { zxGponOnuWeightEntry 4 }
    
    zxGponOnuCos4Weight     OBJECT-TYPE
      SYNTAX      INTEGER
      MAX-ACCESS  read-write
      STATUS      current 
      DESCRIPTION 
        "Weight of COS4(0-100)."
      ::= { zxGponOnuWeightEntry 5 }
      
    zxGponOnuDownTrafficPtr OBJECT-TYPE
        SYNTAX      INTEGER
        MAX-ACCESS  read-write
        STATUS      current
        DESCRIPTION
            "The ONU downstream traffic descriptor profile."
        ::= { zxGponOnuWeightEntry 6}

--zxGponPrivateOnu.mi2
    zxGponPrivateOnu OBJECT IDENTIFIER ::= { zxGponRootMib 28 }

    zxGponOntDevMgmtTable OBJECT-TYPE
        SYNTAX      SEQUENCE OF ZxGponOntDevMgmtEntry
        MAX-ACCESS  not-accessible
        STATUS      current
        DESCRIPTION
            "" 
        REFERENCE
            "G.984.3"
        ::= { zxGponPrivateOnu 1 }

    zxGponOntDevMgmtEntry OBJECT-TYPE
        SYNTAX      ZxGponOntDevMgmtEntry
        MAX-ACCESS  not-accessible
        STATUS      current
        DESCRIPTION
            ""
        INDEX   { zxGponMgmtPonOltId, zxGponMgmtPonOnuId }
        ::= { zxGponOntDevMgmtTable 1 }

    ZxGponOntDevMgmtEntry ::=
        SEQUENCE {
            zxGponOntDevMgmtTypeName            OCTET STRING,
            zxGponOntDevMgmtName                OCTET STRING,
            zxGponOntDevMgmtDescription         OCTET STRING,
            zxGponOntDevMgmtRegisterId          OCTET STRING,
            zxGponOntDevMgmtProvisionSn         OntSerialNumber,
            zxGponOntDevMgmtPwMode              INTEGER,
            zxGponOntDevMgmtPassword            OCTET STRING,
            zxGponOntTargetState                INTEGER,
            zxGponOntDevMgmtEntryStatus         RowStatus,
          zxGponOntIsAutoUpdate                TruthValue,
          zxGponOntRegMode                    INTEGER,
          zxGponOntRegId                      OCTET STRING
        }

   zxGponOntDevMgmtTypeName OBJECT-TYPE
        SYNTAX      OCTET STRING(SIZE(0..64))
        MAX-ACCESS  read-write
        STATUS      current
        DESCRIPTION
            ""
        ::= { zxGponOntDevMgmtEntry 1}

   zxGponOntDevMgmtName OBJECT-TYPE
        SYNTAX      OCTET STRING(SIZE(0..128))
        MAX-ACCESS  read-write
        STATUS      current
        DESCRIPTION
            ""
        ::= { zxGponOntDevMgmtEntry 2}

   zxGponOntDevMgmtDescription OBJECT-TYPE
        SYNTAX      OCTET STRING(SIZE(127))
        MAX-ACCESS  read-write
        STATUS      current
        DESCRIPTION
            "The definition size of description does not include the termination."
        ::= { zxGponOntDevMgmtEntry 3}

   zxGponOntDevMgmtRegisterId OBJECT-TYPE
        SYNTAX      OCTET STRING(SIZE(4))
        MAX-ACCESS  read-write
        STATUS      current
        DESCRIPTION
            "Reserved. use in the future."
        ::= { zxGponOntDevMgmtEntry 4}

     zxGponOntDevMgmtProvisionSn OBJECT-TYPE
        SYNTAX      OntSerialNumber(SIZE (8))
        MAX-ACCESS  read-write
        STATUS      current
        DESCRIPTION
            "SN configed by Olt for the purpose of register"
        ::= { zxGponOntDevMgmtEntry 5}

   zxGponOntDevMgmtPwMode OBJECT-TYPE
        SYNTAX      INTEGER{
                    nonePw(1),
                    force(2)
                    }
        MAX-ACCESS  read-write
        STATUS      current
        DESCRIPTION
            ""
        ::= { zxGponOntDevMgmtEntry 6}

   zxGponOntDevMgmtPassword OBJECT-TYPE
        SYNTAX      OCTET STRING(SIZE(10))
        MAX-ACCESS  read-write
        STATUS      current
        DESCRIPTION
            "password configed by Olt for the purpose of register"
        ::= { zxGponOntDevMgmtEntry 7}
        
    zxGponOntTargetState OBJECT-TYPE
        SYNTAX      INTEGER{
                    deactive(1),
                    omciready(2)
                    }
        MAX-ACCESS  read-write
        STATUS      current
        DESCRIPTION
            ""
        ::= { zxGponOntDevMgmtEntry 8}

   zxGponOntDevMgmtEntryStatus OBJECT-TYPE
        SYNTAX      RowStatus
        MAX-ACCESS  read-create
        STATUS      current
        DESCRIPTION
            ""
        ::= { zxGponOntDevMgmtEntry 9}

   zxGponOntIsAutoUpdate OBJECT-TYPE
        SYNTAX      TruthValue
        MAX-ACCESS  read-write
        STATUS      current
        DESCRIPTION
            ""
        ::= { zxGponOntDevMgmtEntry 10}
   
  zxGponOntRegMode OBJECT-TYPE
        SYNTAX      INTEGER{
                     regModeSn(1),
                     regModePw(2),
                     regModeSnPlusPw(3),
                     regModeId(4)
                    }
        MAX-ACCESS  read-write
        STATUS      current
        DESCRIPTION
            ""
        ::= { zxGponOntDevMgmtEntry 11}
        
   zxGponOntRegId OBJECT-TYPE
        SYNTAX      OCTET STRING(SIZE(64))
        MAX-ACCESS  read-write
        STATUS      current
        DESCRIPTION
            "ID configed by Olt for the purpose of register"
        ::= { zxGponOntDevMgmtEntry 12}   

    zxGponOntStateTable OBJECT-TYPE
        SYNTAX      SEQUENCE OF ZxGponOntStateEntry
        MAX-ACCESS  not-accessible
        STATUS      current
        DESCRIPTION
            "" 
        REFERENCE
            "G.984.3"
        ::= { zxGponPrivateOnu 2 }

    zxGponOntStateEntry OBJECT-TYPE
        SYNTAX      ZxGponOntStateEntry
        MAX-ACCESS  not-accessible
        STATUS      current
        DESCRIPTION
            ""
        INDEX   { zxGponMgmtPonOltId, zxGponMgmtPonOnuId }
        ::= { zxGponOntStateTable 1 }

    ZxGponOntStateEntry ::=
        SEQUENCE {
            zxGponOntAdminState          INTEGER,
            zxGponOntOmccState           TruthValue,
            zxGponOntO1O7State           INTEGER,
            zxGponOntPhaseState          INTEGER
        }

   zxGponOntAdminState OBJECT-TYPE
        SYNTAX      INTEGER{
                    enable(1),
                    disable(2)
                    }
        MAX-ACCESS  read-write
        STATUS      current
        DESCRIPTION
            ""
        ::= { zxGponOntStateEntry 1}

   zxGponOntOmccState OBJECT-TYPE
        SYNTAX      TruthValue
        MAX-ACCESS  read-only
        STATUS      current
        DESCRIPTION
            ""
        ::= { zxGponOntStateEntry 2}

   zxGponOntO1O7State OBJECT-TYPE
        SYNTAX      INTEGER{
                    unknown(0),
                    o1-initial(1),
                    o2-standby(2),
                    o3-powersetup(3),
                    o4-serialnumber(4),
                    o5-ranging(5),
                    o6-operation(6),
                    o7-popup(7)
                    }
        MAX-ACCESS  read-only
        STATUS      current
        DESCRIPTION
            "
            Unknown(DyingGasp),
            Initial-state(O1),
            Standby-state(O2),
            Power-Setup-state(O3),
            Serial-Number-state(O4),
            Ranging-state(O5),
            Operation-state(O6),
            POPUP-state(O7)
            "
        ::= { zxGponOntStateEntry 3}

   zxGponOntPhaseState OBJECT-TYPE
        SYNTAX      INTEGER{
                    logging(0),
                    los(1),
                    syncMib(2),
                    working(3),
                    dyinggasp(4),
                    authFailed(5),
                    offline(6)
                    }
        MAX-ACCESS  read-only
        STATUS      current
        DESCRIPTION
            ""
        ::= { zxGponOntStateEntry 4}

    zxGponOntDevInfoTable OBJECT-TYPE
        SYNTAX      SEQUENCE OF ZxGponOntDevInfoEntry
        MAX-ACCESS  not-accessible
        STATUS      current
        DESCRIPTION
            "" 
        REFERENCE
            "G.984.3"
        ::= { zxGponPrivateOnu 3 }

    zxGponOntDevInfoEntry OBJECT-TYPE
        SYNTAX      ZxGponOntDevInfoEntry
        MAX-ACCESS  not-accessible
        STATUS      current
        DESCRIPTION
            ""
        INDEX   { zxGponMgmtPonOltId, zxGponMgmtPonOnuId }
        ::= { zxGponOntDevInfoTable 1 }

    ZxGponOntDevInfoEntry ::=
        SEQUENCE {
            zxGponOntDevInfoSupportTcontNum  INTEGER,
            zxGponOntDevInfoCurUsedTcontNum  INTEGER,
            zxGponOntDevInfoSupportPortIdNum INTEGER,
            zxGponOntDevInfoCurUsedPortIdNum INTEGER,
            zxGponOntDevInfoPqNum            INTEGER,
            zxGponOntDevInfoTsNum            INTEGER,
            zxGponOntDevInfoServiceType      INTEGER,
            zxGponOntDevInfoRealOnuId        INTEGER
        }

   zxGponOntDevInfoSupportTcontNum OBJECT-TYPE
        SYNTAX      INTEGER
        MAX-ACCESS  read-only
        STATUS      current
        DESCRIPTION
            ""
        ::= { zxGponOntDevInfoEntry 1}

   zxGponOntDevInfoCurUsedTcontNum OBJECT-TYPE
        SYNTAX      INTEGER
        MAX-ACCESS  read-only
        STATUS      current
        DESCRIPTION
            ""
        ::= { zxGponOntDevInfoEntry 2}

   zxGponOntDevInfoSupportPortIdNum OBJECT-TYPE
        SYNTAX      INTEGER
        MAX-ACCESS  read-only
        STATUS      current
        DESCRIPTION
            "Reserved. used in the future."
        ::= { zxGponOntDevInfoEntry 3}

   zxGponOntDevInfoCurUsedPortIdNum OBJECT-TYPE
        SYNTAX      INTEGER
        MAX-ACCESS  read-only
        STATUS      current
        DESCRIPTION
            ""
        ::= { zxGponOntDevInfoEntry 4}

   zxGponOntDevInfoPqNum OBJECT-TYPE
        SYNTAX      INTEGER
        MAX-ACCESS  read-only
        STATUS      current
        DESCRIPTION
            ""
        ::= { zxGponOntDevInfoEntry 5}
        
   zxGponOntDevInfoTsNum OBJECT-TYPE
        SYNTAX      INTEGER
        MAX-ACCESS  read-only
        STATUS      current
        DESCRIPTION
            ""
        ::= { zxGponOntDevInfoEntry 6}

   zxGponOntDevInfoServiceType OBJECT-TYPE
        SYNTAX      INTEGER
        MAX-ACCESS  read-only
        STATUS      current
        DESCRIPTION
            "Reserved. used in the future."
        ::= { zxGponOntDevInfoEntry 7}
        
   zxGponOntDevInfoRealOnuId OBJECT-TYPE
        SYNTAX      INTEGER
        MAX-ACCESS  read-only
        STATUS      current
        DESCRIPTION
            ""
        ::= { zxGponOntDevInfoEntry 8}

    zxGponOntUniPortInfoTable OBJECT-TYPE
        SYNTAX      SEQUENCE OF ZxGponOntUniPortInfoEntry
        MAX-ACCESS  not-accessible
        STATUS      current
        DESCRIPTION
            "" 
        REFERENCE
            "G.984.3"
        ::= { zxGponPrivateOnu 4 }

    zxGponOntUniPortInfoEntry OBJECT-TYPE
        SYNTAX      ZxGponOntUniPortInfoEntry
        MAX-ACCESS  not-accessible
        STATUS      current
        DESCRIPTION
            ""
        INDEX   { zxGponMgmtPonOltId, zxGponMgmtPonOnuId }
        ::= { zxGponOntUniPortInfoTable 1 }

    ZxGponOntUniPortInfoEntry ::=
        SEQUENCE {
            zxGponOntUniPortInfoTotalUniPorts INTEGER,
            zxGponOntUniPortInfoE1Ports       INTEGER,
            zxGponOntUniPortInfoT1Ports       INTEGER,
            zxGponOntUniPortInfoSTMPorts      INTEGER,
            zxGponOntUniPortInfoPOTSPorts     INTEGER,
            zxGponOntUniPortInfoEthPorts      INTEGER,
            zxGponOntUniPortInfoRFPorts       INTEGER,
            zxGponOntUniPortInfoMoCAPorts     INTEGER,
            zxGponOntUniPortInfoWiFiPorts     INTEGER,
            zxGponOntUniPortInfoAdslPorts     INTEGER,
            zxGponOntUniPortInfoVdslPorts     INTEGER
        }

   zxGponOntUniPortInfoTotalUniPorts OBJECT-TYPE
        SYNTAX      INTEGER
        MAX-ACCESS  read-only
        STATUS      current
        DESCRIPTION
            "It is total UNI ports number in the ONT/ONU."
        ::= { zxGponOntUniPortInfoEntry 1}

   zxGponOntUniPortInfoE1Ports OBJECT-TYPE
        SYNTAX      INTEGER
        MAX-ACCESS  read-only
        STATUS      current
        DESCRIPTION
            "It is total those UNI ports number, that it is E1."
        ::= { zxGponOntUniPortInfoEntry 2}

   zxGponOntUniPortInfoT1Ports OBJECT-TYPE
        SYNTAX      INTEGER
        MAX-ACCESS  read-only
        STATUS      current
        DESCRIPTION
            "It is total those UNI ports number, that it is T1."
        ::= { zxGponOntUniPortInfoEntry 3}

   zxGponOntUniPortInfoSTMPorts OBJECT-TYPE
        SYNTAX      INTEGER
        MAX-ACCESS  read-only
        STATUS      current
        DESCRIPTION
            "It is total those UNI ports number, that it is STM-1/STM-4 and so on."
        ::= { zxGponOntUniPortInfoEntry 4}

   zxGponOntUniPortInfoPOTSPorts OBJECT-TYPE
        SYNTAX      INTEGER
        MAX-ACCESS  read-only
        STATUS      current
        DESCRIPTION
            "It is total those UNI ports number, that it is used telephone, such as n * 64K, or VOIP."
        ::= { zxGponOntUniPortInfoEntry 5}

   zxGponOntUniPortInfoEthPorts OBJECT-TYPE
        SYNTAX      INTEGER
        MAX-ACCESS  read-only
        STATUS      current
        DESCRIPTION
            "It is total those UNI ports number, that it is used ethernet, such as FE/GE."
        ::= { zxGponOntUniPortInfoEntry 6}

   zxGponOntUniPortInfoRFPorts OBJECT-TYPE
        SYNTAX      INTEGER
        MAX-ACCESS  read-only
        STATUS      current
        DESCRIPTION
            "It is total those UNI ports number, that it is used Radio Freqency(RF)."
        ::= { zxGponOntUniPortInfoEntry 7}

   zxGponOntUniPortInfoMoCAPorts OBJECT-TYPE
        SYNTAX      INTEGER
        MAX-ACCESS  read-only
        STATUS      current
        DESCRIPTION
            "It is total those UNI ports number, that it is used MoCA."
        ::= { zxGponOntUniPortInfoEntry 8}

   zxGponOntUniPortInfoWiFiPorts OBJECT-TYPE
        SYNTAX      INTEGER
        MAX-ACCESS  read-only
        STATUS      current
        DESCRIPTION
            "It is total those UNI ports number, that it is used WiFI."
        ::= { zxGponOntUniPortInfoEntry 9}

   zxGponOntUniPortInfoAdslPorts OBJECT-TYPE
        SYNTAX      INTEGER
        MAX-ACCESS  read-only
        STATUS      current
        DESCRIPTION
            "It is total those UNI ports number, that it is used ADSL."
        ::= { zxGponOntUniPortInfoEntry 10}

   zxGponOntUniPortInfoVdslPorts OBJECT-TYPE
        SYNTAX      INTEGER
        MAX-ACCESS  read-only
        STATUS      current
        DESCRIPTION
            "It is total those UNI ports number, that it is used VDSL."
        ::= { zxGponOntUniPortInfoEntry 11}
        
        
   zxGponOntPmStatisInfoTable OBJECT-TYPE
        SYNTAX      SEQUENCE OF ZxGponOntPmStatisInfoEntry
        MAX-ACCESS  not-accessible
        STATUS      current
        DESCRIPTION
            "" 
        REFERENCE
            "G.984.3"
        ::= { zxGponPrivateOnu 5 }

    zxGponOntPmStatisInfoEntry OBJECT-TYPE
        SYNTAX      ZxGponOntPmStatisInfoEntry
        MAX-ACCESS  not-accessible
        STATUS      current
        DESCRIPTION
            ""
        INDEX   { zxGponMgmtPonOltId, zxGponMgmtPonOnuId }
        ::= { zxGponOntPmStatisInfoTable 1 }

    ZxGponOntPmStatisInfoEntry ::=
        SEQUENCE {
            zxGponOntPmStatisInfoGemPacketTxLo                INTEGER,
            zxGponOntPmStatisInfoGemPacketRxCorIdleLo         INTEGER,
            zxGponOntPmStatisInfoGemPacketRxCorNoIdleLo       INTEGER,
            zxGponOntPmStatisInfoGemPacketRxErrLo             INTEGER,
            zxGponOntPmStatisInfoGemPayloadBytesRxLo          INTEGER,
            zxGponOntPmStatisInfoEthPacketTxLo                INTEGER,
            zxGponOntPmStatisInfoEthPacketRxCorLo             INTEGER,
            zxGponOntPmStatisInfoEthPacketRxErrLo             INTEGER,
            zxGponOntPmStatisInfoOmciPacketTxLo               INTEGER,
            zxGponOntPmStatisInfoOmciPacketRxLo               INTEGER,
            zxGponOntPmStatisInfoOmciPacketRxCorLo            INTEGER,
            zxGponOntPmStatisInfoOmciPacketRxErrLo            INTEGER,
            zxGponOntPmStatisInfoPloamTxLo                    INTEGER,
            zxGponOntPmStatisInfoPloamRxCorLo                 INTEGER,
            zxGponOntPmStatisInfoPloamRxErrLo                 INTEGER,
            zxGponOntPmStatisInfoBipErrorRxLo                 INTEGER,
            zxGponOntPmStatisInfoERRLo                        INTEGER,
            zxGponOntPmStatisInfoREILo                        INTEGER
        }

   zxGponOntPmStatisInfoGemPacketTxLo OBJECT-TYPE
        SYNTAX      INTEGER
        MAX-ACCESS  read-only
        STATUS      current
        DESCRIPTION
            ""
        ::= { zxGponOntPmStatisInfoEntry 1}

   zxGponOntPmStatisInfoGemPacketRxCorIdleLo OBJECT-TYPE
        SYNTAX      INTEGER
        MAX-ACCESS  read-only
        STATUS      current
        DESCRIPTION
            ""
        ::= { zxGponOntPmStatisInfoEntry 2}

   zxGponOntPmStatisInfoGemPacketRxCorNoIdleLo OBJECT-TYPE
        SYNTAX      INTEGER
        MAX-ACCESS  read-only
        STATUS      current
        DESCRIPTION
            ""
        ::= { zxGponOntPmStatisInfoEntry 3}

   zxGponOntPmStatisInfoGemPacketRxErrLo OBJECT-TYPE
        SYNTAX      INTEGER
        MAX-ACCESS  read-only
        STATUS      current
        DESCRIPTION
            ""
        ::= { zxGponOntPmStatisInfoEntry 4}

   zxGponOntPmStatisInfoGemPayloadBytesRxLo OBJECT-TYPE
        SYNTAX      INTEGER
        MAX-ACCESS  read-only
        STATUS      current
        DESCRIPTION
            ""
        ::= { zxGponOntPmStatisInfoEntry 5}
        
   zxGponOntPmStatisInfoEthPacketTxLo OBJECT-TYPE
        SYNTAX      INTEGER
        MAX-ACCESS  read-only
        STATUS      current
        DESCRIPTION
            ""
        ::= { zxGponOntPmStatisInfoEntry 6}

   zxGponOntPmStatisInfoEthPacketRxCorLo OBJECT-TYPE
        SYNTAX      INTEGER
        MAX-ACCESS  read-only
        STATUS      current
        DESCRIPTION
            "Reserved. used in the future."
        ::= { zxGponOntPmStatisInfoEntry 7}
        
   zxGponOntPmStatisInfoEthPacketRxErrLo OBJECT-TYPE
        SYNTAX      INTEGER
        MAX-ACCESS  read-only
        STATUS      current
        DESCRIPTION
            ""
        ::= { zxGponOntPmStatisInfoEntry 8}
        
   zxGponOntPmStatisInfoOmciPacketTxLo OBJECT-TYPE
        SYNTAX      INTEGER
        MAX-ACCESS  read-only
        STATUS      current
        DESCRIPTION
            ""
        ::= { zxGponOntPmStatisInfoEntry 9}
        
   zxGponOntPmStatisInfoOmciPacketRxLo OBJECT-TYPE
        SYNTAX      INTEGER
        MAX-ACCESS  read-only
        STATUS      current
        DESCRIPTION
            ""
        ::= { zxGponOntPmStatisInfoEntry 10}
        
   zxGponOntPmStatisInfoOmciPacketRxCorLo OBJECT-TYPE
        SYNTAX      INTEGER
        MAX-ACCESS  read-only
        STATUS      current
        DESCRIPTION
            ""
        ::= { zxGponOntPmStatisInfoEntry 11}
        
   zxGponOntPmStatisInfoOmciPacketRxErrLo OBJECT-TYPE
        SYNTAX      INTEGER
        MAX-ACCESS  read-only
        STATUS      current
        DESCRIPTION
            ""
        ::= { zxGponOntPmStatisInfoEntry 12}
      
   zxGponOntPmStatisInfoPloamTxLo OBJECT-TYPE
        SYNTAX      INTEGER
        MAX-ACCESS  read-only
        STATUS      current
        DESCRIPTION
            ""
        ::= { zxGponOntPmStatisInfoEntry 13}
        
   zxGponOntPmStatisInfoPloamRxCorLo OBJECT-TYPE
        SYNTAX      INTEGER
        MAX-ACCESS  read-only
        STATUS      current
        DESCRIPTION
            ""
        ::= { zxGponOntPmStatisInfoEntry 14}
        
   zxGponOntPmStatisInfoPloamRxErrLo OBJECT-TYPE
        SYNTAX      INTEGER
        MAX-ACCESS  read-only
        STATUS      current
        DESCRIPTION
            ""
        ::= { zxGponOntPmStatisInfoEntry 15}
        
   zxGponOntPmStatisInfoBipErrorRxLo OBJECT-TYPE
        SYNTAX      INTEGER
        MAX-ACCESS  read-only
        STATUS      current
        DESCRIPTION
            ""
        ::= { zxGponOntPmStatisInfoEntry 16}
        
   zxGponOntPmStatisInfoERRLo OBJECT-TYPE
        SYNTAX      INTEGER
        MAX-ACCESS  read-only
        STATUS      current
        DESCRIPTION
            ""
        ::= { zxGponOntPmStatisInfoEntry 17}
        
   zxGponOntPmStatisInfoREILo OBJECT-TYPE
        SYNTAX      INTEGER
        MAX-ACCESS  read-only
        STATUS      current
        DESCRIPTION
            ""
        ::= { zxGponOntPmStatisInfoEntry 18}
        
   zxGponOntPmStatisRealtimeInfoTable OBJECT-TYPE
        SYNTAX      SEQUENCE OF ZxGponOntPmStatisRealtimeInfoEntry
        MAX-ACCESS  not-accessible
        STATUS      current
        DESCRIPTION
            "" 
        REFERENCE
            "G.984.3"
        ::= { zxGponPrivateOnu 6 }

    zxGponOntPmStatisRealtimeInfoEntry OBJECT-TYPE
        SYNTAX      ZxGponOntPmStatisRealtimeInfoEntry
        MAX-ACCESS  not-accessible
        STATUS      current
        DESCRIPTION
            ""
        INDEX   { zxGponMgmtPonOltId, zxGponMgmtPonOnuId }
        ::= { zxGponOntPmStatisRealtimeInfoTable 1 }

    ZxGponOntPmStatisRealtimeInfoEntry ::=
        SEQUENCE {
            zxGponOntPmStatisInfoCorrectNonIdleGemFramesUpstream                Unsigned32,
            zxGponOntPmStatisInfoCorrectIdleGemFramesUpstream         Unsigned32,
            zxGponOntPmStatisInfoErroredGemFramesUpstream       Unsigned32,
            zxGponOntPmStatisInfoGemPayloadBytesUpstream             Unsigned32,
            zxGponOntPmStatisInfoCorrectEthernetFramesUpstream          Unsigned32,
            zxGponOntPmStatisInfoErroredEthernetFramesUpstream                Unsigned32,
            zxGponOntPmStatisInfoTotalOmciFramesUpstream             Unsigned32,
            zxGponOntPmStatisInfoERRi             Unsigned32,
            zxGponOntPmStatisInfoREIi               Unsigned32,
            zxGponOntPmStatisInfoUnreceivedBurstsUpstream               Unsigned32,
            zxGponOntPmStatisInfoBipErrorUpstream            Unsigned32,
            zxGponOntPmStatisInfoCorrectedBitsUpstream            Unsigned32,
            zxGponOntPmStatisInfoNotCorrectedWordsUpstream                    Unsigned32
        }

   zxGponOntPmStatisInfoCorrectNonIdleGemFramesUpstream OBJECT-TYPE
        SYNTAX      Unsigned32
        MAX-ACCESS  read-only
        STATUS      current
        DESCRIPTION
            ""
        ::= { zxGponOntPmStatisRealtimeInfoEntry 1}

   zxGponOntPmStatisInfoCorrectIdleGemFramesUpstream OBJECT-TYPE
        SYNTAX      Unsigned32
        MAX-ACCESS  read-only
        STATUS      current
        DESCRIPTION
            ""
        ::= { zxGponOntPmStatisRealtimeInfoEntry 2}

   zxGponOntPmStatisInfoErroredGemFramesUpstream OBJECT-TYPE
        SYNTAX      Unsigned32
        MAX-ACCESS  read-only
        STATUS      current
        DESCRIPTION
            ""
        ::= { zxGponOntPmStatisRealtimeInfoEntry 3}

   zxGponOntPmStatisInfoGemPayloadBytesUpstream OBJECT-TYPE
        SYNTAX      Unsigned32
        MAX-ACCESS  read-only
        STATUS      current
        DESCRIPTION
            ""
        ::= { zxGponOntPmStatisRealtimeInfoEntry 4}

   zxGponOntPmStatisInfoCorrectEthernetFramesUpstream OBJECT-TYPE
        SYNTAX      Unsigned32
        MAX-ACCESS  read-only
        STATUS      current
        DESCRIPTION
            ""
        ::= { zxGponOntPmStatisRealtimeInfoEntry 5}

   zxGponOntPmStatisInfoErroredEthernetFramesUpstream OBJECT-TYPE
        SYNTAX      Unsigned32
        MAX-ACCESS  read-only
        STATUS      current
        DESCRIPTION
            ""
        ::= { zxGponOntPmStatisRealtimeInfoEntry 6}

   zxGponOntPmStatisInfoTotalOmciFramesUpstream OBJECT-TYPE
        SYNTAX      Unsigned32
        MAX-ACCESS  read-only
        STATUS      current
        DESCRIPTION
            ""
        ::= { zxGponOntPmStatisRealtimeInfoEntry 7}

   zxGponOntPmStatisInfoERRi OBJECT-TYPE
        SYNTAX      Unsigned32
        MAX-ACCESS  read-only
        STATUS      current
        DESCRIPTION
            ""
        ::= { zxGponOntPmStatisRealtimeInfoEntry 8}

   zxGponOntPmStatisInfoREIi OBJECT-TYPE
        SYNTAX      Unsigned32
        MAX-ACCESS  read-only
        STATUS      current
        DESCRIPTION
            ""
        ::= { zxGponOntPmStatisRealtimeInfoEntry 9}

   zxGponOntPmStatisInfoUnreceivedBurstsUpstream OBJECT-TYPE
        SYNTAX      Unsigned32
        MAX-ACCESS  read-only
        STATUS      current
        DESCRIPTION
            ""
        ::= { zxGponOntPmStatisRealtimeInfoEntry 10}

   zxGponOntPmStatisInfoBipErrorUpstream OBJECT-TYPE
        SYNTAX      Unsigned32
        MAX-ACCESS  read-only
        STATUS      current
        DESCRIPTION
            ""
        ::= { zxGponOntPmStatisRealtimeInfoEntry 11}

   zxGponOntPmStatisInfoCorrectedBitsUpstream OBJECT-TYPE
        SYNTAX      Unsigned32
        MAX-ACCESS  read-only
        STATUS      current
        DESCRIPTION
            ""
        ::= { zxGponOntPmStatisRealtimeInfoEntry 12}

   zxGponOntPmStatisInfoNotCorrectedWordsUpstream OBJECT-TYPE
        SYNTAX      Unsigned32
        MAX-ACCESS  read-only
        STATUS      current
        DESCRIPTION
            ""
        ::= { zxGponOntPmStatisRealtimeInfoEntry 13}

   zxGponOntPmStatisHistoryInfoTable OBJECT-TYPE
        SYNTAX      SEQUENCE OF ZxGponOntPmStatisHistoryInfoEntry
        MAX-ACCESS  not-accessible
        STATUS      current
        DESCRIPTION
            "" 
        REFERENCE
            "G.984.3"
        ::= { zxGponPrivateOnu 7 }

    zxGponOntPmStatisHistoryInfoEntry OBJECT-TYPE
        SYNTAX      ZxGponOntPmStatisHistoryInfoEntry
        MAX-ACCESS  not-accessible
        STATUS      current
        DESCRIPTION
            ""
        INDEX   { zxGponMgmtPonOltId, zxGponMgmtPonOnuId }
        ::= { zxGponOntPmStatisHistoryInfoTable 1 }

    ZxGponOntPmStatisHistoryInfoEntry ::=
        SEQUENCE {
            zxGponOntPmStatisHistoryInfoCorrectNonIdleGemFramesUpstream                Unsigned32,
            zxGponOntPmStatisHistoryInfoCorrectIdleGemFramesUpstream         Unsigned32,
            zxGponOntPmStatisHistoryInfoErroredGemFramesUpstream       Unsigned32,
            zxGponOntPmStatisHistoryInfoGemPayloadBytesUpstream             Unsigned32,
            zxGponOntPmStatisHistoryInfoCorrectEthernetFramesUpstream          Unsigned32,
            zxGponOntPmStatisHistoryInfoErroredEthernetFramesUpstream                Unsigned32,
            zxGponOntPmStatisHistoryInfoTotalOmciFramesUpstream             Unsigned32,
            zxGponOntPmStatisHistoryInfoERRi             Unsigned32,
            zxGponOntPmStatisHistoryInfoREIi               Unsigned32,
            zxGponOntPmStatisHistoryInfoUnreceivedBurstsUpstream               Unsigned32,
            zxGponOntPmStatisHistoryInfoBipErrorUpstream            Unsigned32,
            zxGponOntPmStatisHistoryInfoCorrectedBitsUpstream            Unsigned32,
            zxGponOntPmStatisHistoryInfoNotCorrectedWordsUpstream                    Unsigned32
        }

   zxGponOntPmStatisHistoryInfoCorrectNonIdleGemFramesUpstream OBJECT-TYPE
        SYNTAX      Unsigned32
        MAX-ACCESS  read-only
        STATUS      current
        DESCRIPTION
            ""
        ::= { zxGponOntPmStatisHistoryInfoEntry 1}

   zxGponOntPmStatisHistoryInfoCorrectIdleGemFramesUpstream OBJECT-TYPE
        SYNTAX      Unsigned32
        MAX-ACCESS  read-only
        STATUS      current
        DESCRIPTION
            ""
        ::= { zxGponOntPmStatisHistoryInfoEntry 2}

   zxGponOntPmStatisHistoryInfoErroredGemFramesUpstream OBJECT-TYPE
        SYNTAX      Unsigned32
        MAX-ACCESS  read-only
        STATUS      current
        DESCRIPTION
            ""
        ::= { zxGponOntPmStatisHistoryInfoEntry 3}

   zxGponOntPmStatisHistoryInfoGemPayloadBytesUpstream OBJECT-TYPE
        SYNTAX      Unsigned32
        MAX-ACCESS  read-only
        STATUS      current
        DESCRIPTION
            ""
        ::= { zxGponOntPmStatisHistoryInfoEntry 4}

   zxGponOntPmStatisHistoryInfoCorrectEthernetFramesUpstream OBJECT-TYPE
        SYNTAX      Unsigned32
        MAX-ACCESS  read-only
        STATUS      current
        DESCRIPTION
            ""
        ::= { zxGponOntPmStatisHistoryInfoEntry 5}

   zxGponOntPmStatisHistoryInfoErroredEthernetFramesUpstream OBJECT-TYPE
        SYNTAX      Unsigned32
        MAX-ACCESS  read-only
        STATUS      current
        DESCRIPTION
            ""
        ::= { zxGponOntPmStatisHistoryInfoEntry 6}

   zxGponOntPmStatisHistoryInfoTotalOmciFramesUpstream OBJECT-TYPE
        SYNTAX      Unsigned32
        MAX-ACCESS  read-only
        STATUS      current
        DESCRIPTION
            ""
        ::= { zxGponOntPmStatisHistoryInfoEntry 7}

   zxGponOntPmStatisHistoryInfoERRi OBJECT-TYPE
        SYNTAX      Unsigned32
        MAX-ACCESS  read-only
        STATUS      current
        DESCRIPTION
            ""
        ::= { zxGponOntPmStatisHistoryInfoEntry 8}

   zxGponOntPmStatisHistoryInfoREIi OBJECT-TYPE
        SYNTAX      Unsigned32
        MAX-ACCESS  read-only
        STATUS      current
        DESCRIPTION
            ""
        ::= { zxGponOntPmStatisHistoryInfoEntry 9}

   zxGponOntPmStatisHistoryInfoUnreceivedBurstsUpstream OBJECT-TYPE
        SYNTAX      Unsigned32
        MAX-ACCESS  read-only
        STATUS      current
        DESCRIPTION
            ""
        ::= { zxGponOntPmStatisHistoryInfoEntry 10}

   zxGponOntPmStatisHistoryInfoBipErrorUpstream OBJECT-TYPE
        SYNTAX      Unsigned32
        MAX-ACCESS  read-only
        STATUS      current
        DESCRIPTION
            ""
        ::= { zxGponOntPmStatisHistoryInfoEntry 11}

   zxGponOntPmStatisHistoryInfoCorrectedBitsUpstream OBJECT-TYPE
        SYNTAX      Unsigned32
        MAX-ACCESS  read-only
        STATUS      current
        DESCRIPTION
            ""
        ::= { zxGponOntPmStatisHistoryInfoEntry 12}

   zxGponOntPmStatisHistoryInfoNotCorrectedWordsUpstream OBJECT-TYPE
        SYNTAX      Unsigned32
        MAX-ACCESS  read-only
        STATUS      current
        DESCRIPTION
            ""
        ::= { zxGponOntPmStatisHistoryInfoEntry 13}



    zxGponOntLoopbackTestInfoTable OBJECT-TYPE
        SYNTAX      SEQUENCE OF ZxGponOntLoopbackTestInfoEntry
        MAX-ACCESS  not-accessible
        STATUS      current
        DESCRIPTION
            "" 
        ::= { zxGponPrivateOnu 8 }

    zxGponOntLoopbackTestInfoEntry OBJECT-TYPE
        SYNTAX      ZxGponOntLoopbackTestInfoEntry
        MAX-ACCESS  not-accessible
        STATUS      current
        DESCRIPTION
            ""
        INDEX   { zxGponMgmtPonOltId, zxGponMgmtPonOnuId }
        ::= { zxGponOntLoopbackTestInfoTable 1 }

    ZxGponOntLoopbackTestInfoEntry ::=
        SEQUENCE {
            zxGponOntLoopbackTestStart                INTEGER
            }

   zxGponOntLoopbackTestStart OBJECT-TYPE
        SYNTAX      INTEGER
        MAX-ACCESS  read-write
        STATUS      current
        DESCRIPTION
            "1:start loopback test 2:stop loopback test"
        ::= { zxGponOntLoopbackTestInfoEntry 1}

--zxGponServiceMgmt.mi2
    zxGponServiceMgmt OBJECT IDENTIFIER ::= { zxGponRootMib 30 }

    zxOnuTrafficMgmtUnitTable OBJECT-TYPE
        SYNTAX      SEQUENCE OF ZxOnuTrafficMgmtUnitEntry
        MAX-ACCESS  not-accessible
        STATUS      current
        DESCRIPTION
            "This table represents ONU's traffic management unit information including T-CONT and
            user bandwidth management unit."
        ::= { zxGponServiceMgmt 1 }

    zxOnuTrafficMgmtUnitEntry OBJECT-TYPE
        SYNTAX      ZxOnuTrafficMgmtUnitEntry
        MAX-ACCESS  not-accessible
        STATUS      current
        DESCRIPTION
            "It is entry in the zxOnuTrafficMgmtUnitTable."
        INDEX   { zxGponMgmtPonOltId, zxGponMgmtPonOnuId, zxOnuTrafficMgmtUnitTcontIdx }
        ::= { zxOnuTrafficMgmtUnitTable 1 }

    ZxOnuTrafficMgmtUnitEntry ::=
        SEQUENCE {
            zxOnuTrafficMgmtUnitTcontIdx          INTEGER,
            zxOnuTrafficMgmtUnitName              ZxGponRecordName,
            zxOnuTrafficMgmtUnitTcontUpBWIdxPtr   INTEGER,
            zxOnuTrafficMgmtUnitAllocId            INTEGER,
            zxOnuTrafficMgmtUnitUsedPortIdNum     INTEGER,
            zxOnuTrafficMgmtUnitUsedFlowNum       INTEGER,
            zxOnuTrafficMgmtUnitUsedCos           INTEGER,
            zxOnuTrafficMgmtUnitEntryStatus       RowStatus
        }

    zxOnuTrafficMgmtUnitTcontIdx OBJECT-TYPE
        SYNTAX      INTEGER
        MAX-ACCESS  not-accessible
        STATUS      current
        DESCRIPTION
            "An arbitrary(unique) integer for identifiying an entry
             in the table, from 1 to N."
        ::= { zxOnuTrafficMgmtUnitEntry 1}

    zxOnuTrafficMgmtUnitName       OBJECT-TYPE
      SYNTAX      ZxGponRecordName(SIZE (0..64))
      MAX-ACCESS  read-write
      STATUS      current 
      DESCRIPTION 
        ""
      REFERENCE   "N/A"
      ::= { zxOnuTrafficMgmtUnitEntry 2 }

    zxOnuTrafficMgmtUnitTcontUpBWIdxPtr       OBJECT-TYPE
      SYNTAX      INTEGER
      MAX-ACCESS  read-write
      STATUS      current 
      DESCRIPTION 
        "This attribute is the index of templet used by T-CONT BW configuration."
      REFERENCE   "N/A"
      ::= { zxOnuTrafficMgmtUnitEntry 3 }

    zxOnuTrafficMgmtUnitAllocId       OBJECT-TYPE
      SYNTAX      INTEGER
      MAX-ACCESS  read-write
      STATUS      current 
      DESCRIPTION 
        "This attribute is the allocid of tcont,value range is [256..4095]."
      REFERENCE   "N/A"
      ::= { zxOnuTrafficMgmtUnitEntry 4 }
      
    zxOnuTrafficMgmtUnitUsedPortIdNum     OBJECT-TYPE
      SYNTAX      INTEGER
      MAX-ACCESS  read-only
      STATUS      current 
      DESCRIPTION 
        "The number of portId using this BW management unit."
      REFERENCE   "N/A"
      ::= { zxOnuTrafficMgmtUnitEntry 5 }
      
    zxOnuTrafficMgmtUnitUsedFlowNum     OBJECT-TYPE
      SYNTAX      INTEGER
      MAX-ACCESS  read-only
      STATUS      current 
      DESCRIPTION 
        "The number of flow using this BW management unit."
      REFERENCE   "N/A"
      ::= { zxOnuTrafficMgmtUnitEntry 6 }

    zxOnuTrafficMgmtUnitUsedCos     OBJECT-TYPE
      SYNTAX      INTEGER
      MAX-ACCESS  read-only
      STATUS      current 
      DESCRIPTION 
        "The integer in binary mode indicates the used COS(0-3)."
      REFERENCE   "N/A"
      ::= { zxOnuTrafficMgmtUnitEntry 7 }
      
    zxOnuTrafficMgmtUnitEntryStatus       OBJECT-TYPE
      SYNTAX      RowStatus
      MAX-ACCESS  read-create
      STATUS      current 
      DESCRIPTION 
        "This entry can be create modified and delete."
      REFERENCE   "N/A"
      ::= { zxOnuTrafficMgmtUnitEntry 8 }
      

    zxGponGemPortTable OBJECT-TYPE
        SYNTAX      SEQUENCE OF ZxGponGemPortEntry
        MAX-ACCESS  not-accessible
        STATUS      current
        DESCRIPTION
            "This table represents ONU side  configuration."
        ::= { zxGponServiceMgmt 2 }

    zxGponGemPortEntry OBJECT-TYPE
        SYNTAX      ZxGponGemPortEntry
        MAX-ACCESS  not-accessible
        STATUS      current
        DESCRIPTION
            "It is entry in the table zxGponGemPortTable."
        INDEX   { zxGponMgmtPonOltId, zxGponMgmtPonOnuId, zxGponGemPortIdx }
        ::= { zxGponGemPortTable 1 }

    ZxGponGemPortEntry ::=
        SEQUENCE {
            zxGponGemPortIdx               INTEGER,
            zxGponGemPortName              ZxGponRecordName,
            zxGponGemPortType              INTEGER,
            zxGponGemPortTcontIdx          INTEGER,
            zxGponGemPortDirection         INTEGER,
            zxGponGemPortUpTrafficPtr      INTEGER,
            zxGponGemPortDownTrafficPtr    INTEGER,
            zxGponGemPortPortId            INTEGER,
            zxGponGemPortDefaultCosType    INTEGER,
            zxGponGemPortEntryStatus       RowStatus,
            zxGponGemPortUpQueue           INTEGER
        }

    zxGponGemPortIdx OBJECT-TYPE
        SYNTAX      INTEGER
        MAX-ACCESS  not-accessible
        STATUS      current
        DESCRIPTION
            "An arbitrary(unique) integer for identifiying an entry
             in the table. It is the virtual portid index"
        ::= { zxGponGemPortEntry 1}

    zxGponGemPortName       OBJECT-TYPE
      SYNTAX      ZxGponRecordName(SIZE (0..64))
      MAX-ACCESS  read-write
      STATUS      current 
      DESCRIPTION 
        "This attribute specifies the name of the GEM port."
      REFERENCE   ""
      ::= { zxGponGemPortEntry 2 }

    zxGponGemPortType OBJECT-TYPE
        SYNTAX      INTEGER{
                    unicast(1),
                    multicast(2)
                    }
        MAX-ACCESS  read-write
        STATUS      current
        DESCRIPTION
            "This attribute specifies the type of the GEM port. Only 'unicast' is supported at present."
        ::= { zxGponGemPortEntry 3}

    zxGponGemPortTcontIdx OBJECT-TYPE
        SYNTAX      INTEGER
        MAX-ACCESS  read-write
        STATUS      current
        DESCRIPTION
            "It is equal to the 'zxOnuTrafficMgmtUnitTcontIdx' of 'zxOnuTrafficMgmtUnitTable'."
        ::= { zxGponGemPortEntry 4}

    zxGponGemPortDirection OBJECT-TYPE
        SYNTAX      INTEGER{
                    up(1),
                    down(2),
                    bidirection(3)
                    }
        MAX-ACCESS  read-write
        STATUS      current
        DESCRIPTION
            "This attribute specifies the type of the direction of GEM port. Default value is 'bidirection'."
        ::= { zxGponGemPortEntry 5}

    zxGponGemPortUpTrafficPtr OBJECT-TYPE
        SYNTAX      INTEGER
        MAX-ACCESS  read-write
        STATUS      current
        DESCRIPTION
            "The GEM PORT upstream traffic descriptor profile."
        ::= { zxGponGemPortEntry 6}

    zxGponGemPortDownTrafficPtr OBJECT-TYPE
        SYNTAX      INTEGER
        MAX-ACCESS  read-write
        STATUS      current
        DESCRIPTION
            "The GEM PORT downstream traffic descriptor profile."
        ::= { zxGponGemPortEntry 7}

    zxGponGemPortPortId OBJECT-TYPE
        SYNTAX      INTEGER
        MAX-ACCESS  read-write
        STATUS      current
        DESCRIPTION
            "portid of gemport([65..1023])."
        ::= { zxGponGemPortEntry 8}

    zxGponGemPortDefaultCosType OBJECT-TYPE
        SYNTAX      INTEGER{
                     cos0(1),
                     cos1(2),
                     cos2(3),
                     cos3(4)
                     }
        MAX-ACCESS  read-write
        STATUS      current
        DESCRIPTION
            "The default COS."
        ::= { zxGponGemPortEntry 9}
        

    zxGponGemPortEntryStatus       OBJECT-TYPE
      SYNTAX      RowStatus
      MAX-ACCESS  read-create
      STATUS      current 
      DESCRIPTION 
        "This entry can be create modified and delete."
      REFERENCE   "N/A"
      ::= { zxGponGemPortEntry 10 }

    zxGponGemPortUpQueue OBJECT-TYPE
        SYNTAX      INTEGER
        MAX-ACCESS  read-write
        STATUS      current
        DESCRIPTION
            "The GEM PORT up queue,value scope for 0 to 7 and default is 0."
        ::= { zxGponGemPortEntry 11}


    zxGponGemPortBasicTable OBJECT-TYPE
        SYNTAX      SEQUENCE OF ZxGponGemPortBasicEntry
        MAX-ACCESS  not-accessible
        STATUS      current
        DESCRIPTION
            "This table represents basic information of GEM Port, mainly CTP and IWTP which are the same 
         regardless of connection of type."
        ::= { zxGponServiceMgmt 5 }

    zxGponGemPortBasicEntry OBJECT-TYPE
        SYNTAX      ZxGponGemPortBasicEntry
        MAX-ACCESS  not-accessible
        STATUS      current
        DESCRIPTION
            "It is entry in the table zxGponGemPortBasicTable."
        INDEX   { zxGponMgmtPonOltId, zxGponMgmtPonOnuId, zxGponGemPortIdx}
        ::= { zxGponGemPortBasicTable 1 }

    ZxGponGemPortBasicEntry ::=
        SEQUENCE {
            zxGponGemBasicPNCTPInfoDirection           INTEGER,
            zxGponGemBasicPNCTPInfoPriorityUpstreamID    INTEGER,
            zxGponGemBasicPNCTPInfoPriorityDownstreamID  INTEGER,
            zxGponGemBasicPNCTPInfoUniCounter          INTEGER,
            zxGponGemBasicIWTPInfoIwOption             INTEGER,
        zxGponGemBasicIWTPInfoServiceProPtr             INTEGER,
            zxGponGemBasicIWTPInfoPPTPCounter          INTEGER,
            zxGponGemBasicIWTPInfoOpState              INTEGER,
            zxGponBasicGALTDMProfileInfoFrameLossIntPeriod INTEGER,
        zxGponBasicGALEthProfileInfoMaxPayloadSize INTEGER,
            zxGponGemBasicMgmtCtrlFlag                 INTEGER,
            zxGponGemBasicEntryStatus                  RowStatus
        }

   zxGponGemBasicPNCTPInfoDirection OBJECT-TYPE
        SYNTAX      INTEGER{
                    uni2ani(1),
                    ani2uni(2),
                    bidirectional(3)
                    }
        MAX-ACCESS  read-write
        STATUS      current
        DESCRIPTION
            "It specifies whether the GEM port is used for UNI-to-ANI (uni2uni(1)), ANI-to-UNI(
             ani2uni(2)), or bidirectional (bidirectional(3)) connection. It may be created/read/
             written/modified.Writing or modifing can be done when the entry SHOULD NOT be used 
             by any other entry."
        REFERENCE
            "G.984.4 Section 9.4.1 GEM Port Network CTP"
        ::= { zxGponGemPortBasicEntry 1}
        
   zxGponGemBasicPNCTPInfoPriorityUpstreamID OBJECT-TYPE
        SYNTAX      INTEGER
        MAX-ACCESS  read-write
        STATUS      current
        DESCRIPTION
            "This attribute points to the instance of the Priority Queue-G ME used for this GEM Port 
             Network CTP ME in the upstream direction. It is used when the Traffic Management Option 
             attribute in ONT-G ME is 0x00; this pointer is null otherwise. "
        ::= { zxGponGemPortBasicEntry 2}

   zxGponGemBasicPNCTPInfoPriorityDownstreamID OBJECT-TYPE
        SYNTAX      INTEGER
        MAX-ACCESS  read-write
        STATUS      current
        DESCRIPTION
            "This attribute points to the instance of the Priority Queue-G used for this GEM Port Network
             CTP in the downstream direction. It is used when the Traffic Management Option attribute in 
             ONT-G is 0x00; this pointer is null otherwise. "
        ::= { zxGponGemPortBasicEntry 3}


   zxGponGemBasicPNCTPInfoUniCounter OBJECT-TYPE
        SYNTAX      INTEGER
        MAX-ACCESS  read-only
        STATUS      current
        DESCRIPTION
            "This attribute represents the number of instances of UNI-G managed entity associated with an 
             instance of the GEM Port Network CTP managed entity. If only one instance of a UNI-G managed 
             entity is associated with an instance of the GEM Port Network CTP managed entity, this 
             attribute is set to 0x01. If multiple instances of UNI-G managed entity are associated with an 
             instance of the GEM Port Network CTP managed entity, this attribute is set to 0xZZ, where ZZ 
             represents the number of associated UNI-G instances, which will not be shown in NMS"
        ::= { zxGponGemPortBasicEntry 4}

    zxGponGemBasicIWTPInfoIwOption OBJECT-TYPE
        SYNTAX      INTEGER{
                    ces(1),
                    bridge(2),
            mapper(6)
                    }
        MAX-ACCESS  read-only
        STATUS      current
        DESCRIPTION
            "It identifies the type of non-GEM function that is being interworked; the option
             can be CES (1) or MAC Bridge LAN (2) or 802.1p Mapper (6)."
        ::= { zxGponGemPortBasicEntry 5}

    zxGponGemBasicIWTPInfoServiceProPtr OBJECT-TYPE
        SYNTAX      INTEGER
        MAX-ACCESS  read-write
        STATUS      current
        DESCRIPTION
            "It provides the service profile type and a pointer to the instance of a service profile,
             such as the CES Service ProfileB-PON (if the zxGponGemIwTPTempletIwOption = 0) or MAC
             Bridge Service Profile (if the zxGponGemIwTPTempletIwOption = 1).It may be created/read/
             written/modified.Writing or modifing can be done when the entry SHOULD NOT be used by any
             other entry."
        ::= { zxGponGemPortBasicEntry 6}
      
    zxGponGemBasicIWTPInfoPPTPCounter OBJECT-TYPE
        SYNTAX      INTEGER
        MAX-ACCESS  read-only
        STATUS      current
        DESCRIPTION
            "This attribute represents the number of instances of PPTP managed entities 
             associated with this instance of the GEM Interworking Termination Point 
             managed entity."
        REFERENCE
            "G.984.4 Section 9.3.3"
        ::= { zxGponGemPortBasicEntry 7}

    zxGponGemBasicIWTPInfoOpState OBJECT-TYPE
        SYNTAX      INTEGER{
                    enabled(1),
                    disabled(2)
                    }
        MAX-ACCESS  read-only
        STATUS      current
        DESCRIPTION
            "This attribute indicates whether or not this managed entity is capable of 
             performing its task. The operational state reflects the perceived ability to 
             receive or to generate a valid signal. This value is set to enabled(1) if the 
             managed entity have this capacity, otherwise, this value is disabled(2)."
        REFERENCE
            "G.984.4 Section 9.3.3"
        ::= { zxGponGemPortBasicEntry 8}
        
   zxGponBasicGALTDMProfileInfoFrameLossIntPeriod OBJECT-TYPE
        SYNTAX      INTEGER(0..65535)
        MAX-ACCESS  read-write
        STATUS      current
        DESCRIPTION
            "I.e GEM Frame Loss Integration Period, It represents the duration in milliseconds
             of the GEM frame loss integration period. If the GEM frame loss persists for such
             a period, the GEM Interworking Termination Point managed entity associated with this 
             entity will generate a GEM frame starvation alarm. It is modified, when the OLT or 
             ONU is restarted , this value will be valid.when zxGponGemBasicIWTPInfoIwOption is 
         ces(1), this value is valid."
        ::= { zxGponGemPortBasicEntry 9}

    zxGponBasicGALEthProfileInfoMaxPayloadSize OBJECT-TYPE
        SYNTAX      INTEGER(0..65535)
        MAX-ACCESS  read-write
        STATUS      current
        DESCRIPTION
            "I.e Maximum GEM Payload Size, it represents a maximum payload size that is generated
             in the associated GEM Interworking Termination Point managed entity. It is modified,
             when the OLT or ONU is restarted , this value will be valid.when zxGponGemBasicIWTPInfoIwOption 
         is bridge(2) or 802.1pMapper(6), this value is valid."
        REFERENCE
            "G.984.4 Section 9.3.5 GAL Ethernet profile"
        ::= { zxGponGemPortBasicEntry 10}

    zxGponGemBasicMgmtCtrlFlag OBJECT-TYPE
        SYNTAX      INTEGER{
                    nmsCreate(1),
                    neCreate(2)
                    }
        MAX-ACCESS  read-only
        STATUS      current
        DESCRIPTION
            "This attribute is used to indicate this record is created by NMS or NE. If it
             is neCreate(2), this record can not be deleted."
        REFERENCE
            "N/A"
        ::= { zxGponGemPortBasicEntry 11}

    zxGponGemBasicEntryStatus       OBJECT-TYPE
      SYNTAX      RowStatus
      MAX-ACCESS  read-create
      STATUS      current 
      DESCRIPTION 
        "This attribute can be create,modify and delete."
      REFERENCE   "N/A"
      ::= { zxGponGemPortBasicEntry 12 }

    zxGponGemPortMACBridgeIWTPTable OBJECT-TYPE
        SYNTAX      SEQUENCE OF ZxGponGemPortMACBridgeIWTPEntry
        MAX-ACCESS  not-accessible
        STATUS      current
        DESCRIPTION
            "This table represents MAC Bridge lan Information."
        ::= { zxGponServiceMgmt 6}

    zxGponGemPortMACBridgeIWTPEntry OBJECT-TYPE
        SYNTAX      ZxGponGemPortMACBridgeIWTPEntry
        MAX-ACCESS  not-accessible
        STATUS      current
        DESCRIPTION
            "It is entry in the table zxGponGemPortMACBridgeTable."
        INDEX   { zxGponMgmtPonOltId, zxGponMgmtPonOnuId, zxGponGemPortIdx}
        ::= { zxGponGemPortMACBridgeIWTPTable 1 }

    ZxGponGemPortMACBridgeIWTPEntry ::=
        SEQUENCE {
        zxGponMACBriPortCfgDataIWTPMeIdIdx         INTEGER,
            zxGponMACBriPortCfgDataIWTPPortNum         INTEGER,
            zxGponMACBriPortCfgDataIWTPTPType          INTEGER,
            zxGponMACBriPortCfgDataIWTPPortPriority    INTEGER,
            zxGponMACBriPortCfgDataIWTPPortPathCost    INTEGER,
            zxGponMACBriPortCfgDataIWTPPortSpanTreeInd TruthValue,
            zxGponMACBriPortCfgDataIWTPEncapMethod     INTEGER,
            zxGponMACBriPortCfgDataIWTPLANFCSInd       INTEGER,
            zxGponMACBriPortCfgDataIWTPMgmtCtrlFlag    INTEGER,
            zxGponMACBriPortCfgDataIWTPEntryStatus     RowStatus
        }

   zxGponMACBriPortCfgDataIWTPMeIdIdx OBJECT-TYPE
        SYNTAX      INTEGER
        MAX-ACCESS  read-only
        STATUS      current
        DESCRIPTION
            "This attribute provides a unique number for each instance of this managed entity."
        ::= { zxGponGemPortMACBridgeIWTPEntry 1}

   zxGponMACBriPortCfgDataIWTPPortNum OBJECT-TYPE
        SYNTAX      INTEGER
        MAX-ACCESS  read-write
        STATUS      current
        DESCRIPTION
            "This attribute provides the port number."
        ::= { zxGponGemPortMACBridgeIWTPEntry 2}

   zxGponMACBriPortCfgDataIWTPTPType OBJECT-TYPE
        SYNTAX      INTEGER{
                    atm(2),
                    pri8021p(3),
                    gemiw(5)
                    }
        MAX-ACCESS  read-only
        STATUS      current
        DESCRIPTION
            "This attribute identifies the type of the termination point associated with 
             this MAC bridge port. The value is set to 0x01 if this bridge port is associated 
             with the LAN side's termination point. The value is set to 0x02 if this bridge 
             port is associated with the ATM side's termination point."
        ::= { zxGponGemPortMACBridgeIWTPEntry 3}
        
   zxGponMACBriPortCfgDataIWTPPortPriority OBJECT-TYPE
        SYNTAX      INTEGER(0..255)
        MAX-ACCESS  read-write
        STATUS      current
        DESCRIPTION
            "This attribute denotes the priority of the port. The range is 0x00 to 0x00FF (0 to 255)."
        ::= { zxGponGemPortMACBridgeIWTPEntry 4}

   zxGponMACBriPortCfgDataIWTPPortPathCost OBJECT-TYPE
        SYNTAX      INTEGER(1..65535)
        MAX-ACCESS  read-write
        STATUS      current
        DESCRIPTION
            "This attribute provides the cost contribution of the port to the path cost towards 
             the spanning tree root bridge. The range is 0x0001 to 0xFFFF (1 to 65 535). "
        ::= { zxGponGemPortMACBridgeIWTPEntry 5}

   zxGponMACBriPortCfgDataIWTPPortSpanTreeInd OBJECT-TYPE
        SYNTAX      TruthValue
        MAX-ACCESS  read-write
        STATUS      current
        DESCRIPTION
            "This Boolean attribute indicates whether or not STP is enabled at this port. 
             The value TRUE means enabled. "
        ::= { zxGponGemPortMACBridgeIWTPEntry 6}
        
   zxGponMACBriPortCfgDataIWTPEncapMethod OBJECT-TYPE
        SYNTAX      INTEGER
        MAX-ACCESS  read-write
        STATUS      current
        DESCRIPTION
            "This attribute identifies the frame encapsulation method that is used. Value 
             0x00: identification by ATM VC; value 0x01: LLC encapsulation. Upon autonomous 
             instantiation, the value 0x00 is used."
        ::= { zxGponGemPortMACBridgeIWTPEntry 7}

   zxGponMACBriPortCfgDataIWTPLANFCSInd OBJECT-TYPE
        SYNTAX      INTEGER{
                    forward(1),
                    discarded(2)
                    }
        MAX-ACCESS  read-write
        STATUS      current
        DESCRIPTION
            "This attribute indicates whether LAN FCS (Frame Check Sequence) bytes are forwarded 
             (value 0x01) or discarded (value 0x02) towards the OLT. Upon autonomous instantiation, 
             the value 0x00 is used."
        ::= { zxGponGemPortMACBridgeIWTPEntry 8}

    zxGponMACBriPortCfgDataIWTPMgmtCtrlFlag OBJECT-TYPE
        SYNTAX      INTEGER{
                    nmsCreate(1),
                    neCreate(2)
                    }
        MAX-ACCESS  read-only
        STATUS      current
        DESCRIPTION
            "This attribute is used to indicate this record is created by NMS or NE. If it
             is neCreate(2), this record can not be deleted."
        REFERENCE
            "N/A"
        ::= { zxGponGemPortMACBridgeIWTPEntry 9}

    zxGponMACBriPortCfgDataIWTPEntryStatus       OBJECT-TYPE
      SYNTAX      RowStatus
      MAX-ACCESS  read-create
      STATUS      current 
      DESCRIPTION 
        "This attribute can be create,modify and delete."
      REFERENCE   "N/A"
      ::= { zxGponGemPortMACBridgeIWTPEntry 10 }

    zxGponGemPortMACBridgeUNITable OBJECT-TYPE
        SYNTAX      SEQUENCE OF ZxGponGemPortMACBridgeUNIEntry
        MAX-ACCESS  not-accessible
        STATUS      current
        DESCRIPTION
            "This table represents MAC Bridge lan Information."
        ::= { zxGponServiceMgmt 7}

    zxGponGemPortMACBridgeUNIEntry OBJECT-TYPE
        SYNTAX      ZxGponGemPortMACBridgeUNIEntry
        MAX-ACCESS  not-accessible
        STATUS      current
        DESCRIPTION
            "It is entry in the table zxGponGemPortMACBridgeUNITable."
        INDEX   { zxGponMgmtPonOltId, zxGponMgmtPonOnuId, zxGponPPTPEthInfoTPID}
        ::= { zxGponGemPortMACBridgeUNITable 1 }

    ZxGponGemPortMACBridgeUNIEntry ::=
        SEQUENCE {
        zxGponMACBriPortCfgDataUNIMeIdIdx          INTEGER,
            zxGponMACBriPortCfgDataUNIPortNum          INTEGER,
            zxGponMACBriPortCfgDataUNITPType           INTEGER,
            zxGponMACBriPortCfgDataUNIPortPriority     INTEGER,
            zxGponMACBriPortCfgDataUNIPortPathCost     INTEGER,
            zxGponMACBriPortCfgDataUNIPortSpanTreeInd  TruthValue,
            zxGponMACBriPortCfgDataUNIEncapMethod      INTEGER,
            zxGponMACBriPortCfgDataUNILANFCSInd        INTEGER
        }

   zxGponMACBriPortCfgDataUNIMeIdIdx OBJECT-TYPE
        SYNTAX      INTEGER
        MAX-ACCESS  read-only
        STATUS      current
        DESCRIPTION
            "This attribute provides a unique number for each instance of this managed entity."
        ::= { zxGponGemPortMACBridgeUNIEntry 1}

   zxGponMACBriPortCfgDataUNIPortNum OBJECT-TYPE
        SYNTAX      INTEGER
        MAX-ACCESS  read-write
        STATUS      current
        DESCRIPTION
            "This attribute provides the port number."
        ::= { zxGponGemPortMACBridgeUNIEntry 2}

   zxGponMACBriPortCfgDataUNITPType OBJECT-TYPE
        SYNTAX      INTEGER{
                    lan(1)
                    }
        MAX-ACCESS  read-only
        STATUS      current
        DESCRIPTION
            "This attribute identifies the type of the termination point associated with 
             this MAC bridge port. The value is set to 0x01 if this bridge port is associated 
             with the LAN side's termination point. The value is set to 0x02 if this bridge 
             port is associated with the ATM side's termination point."
        ::= { zxGponGemPortMACBridgeUNIEntry 3}
        
   zxGponMACBriPortCfgDataUNIPortPriority OBJECT-TYPE
        SYNTAX      INTEGER(0..255)
        MAX-ACCESS  read-write
        STATUS      current
        DESCRIPTION
            "This attribute denotes the priority of the port. The range is 0x00 to 0x00FF (0 to 255)."
        ::= { zxGponGemPortMACBridgeUNIEntry 4}

   zxGponMACBriPortCfgDataUNIPortPathCost OBJECT-TYPE
        SYNTAX      INTEGER(1..65535)
        MAX-ACCESS  read-write
        STATUS      current
        DESCRIPTION
            "This attribute provides the cost contribution of the port to the path cost towards 
             the spanning tree root bridge. The range is 0x0001 to 0xFFFF (1 to 65 535). "
        ::= { zxGponGemPortMACBridgeUNIEntry 5}

   zxGponMACBriPortCfgDataUNIPortSpanTreeInd OBJECT-TYPE
        SYNTAX      TruthValue
        MAX-ACCESS  read-write
        STATUS      current
        DESCRIPTION
            "This Boolean attribute indicates whether or not STP is enabled at this port. 
             The value TRUE means enabled. "
        ::= { zxGponGemPortMACBridgeUNIEntry 6}
        
   zxGponMACBriPortCfgDataUNIEncapMethod OBJECT-TYPE
        SYNTAX      INTEGER
        MAX-ACCESS  read-write
        STATUS      current
        DESCRIPTION
            "This attribute identifies the frame encapsulation method that is used. Value 
             0x00: identification by ATM VC; value 0x01: LLC encapsulation. Upon autonomous 
             instantiation, the value 0x00 is used."
        ::= { zxGponGemPortMACBridgeUNIEntry 7}

   zxGponMACBriPortCfgDataUNILANFCSInd OBJECT-TYPE
        SYNTAX      INTEGER{
                    forward(1),
                    discarded(2)
                    }
        MAX-ACCESS  read-write
        STATUS      current
        DESCRIPTION
            "This attribute indicates whether LAN FCS (Frame Check Sequence) bytes are forwarded 
             (value 0x01) or discarded (value 0x02) towards the OLT. Upon autonomous instantiation, 
             the value 0x00 is used."
        ::= { zxGponGemPortMACBridgeUNIEntry 8}


    zxGponGemPort8021pTable OBJECT-TYPE
        SYNTAX      SEQUENCE OF ZxGponGemPort8021pEntry
        MAX-ACCESS  not-accessible
        STATUS      current
        DESCRIPTION
            "This table represents 802.1p priority mapper Information."
        ::= { zxGponServiceMgmt 8}

    zxGponGemPort8021pEntry OBJECT-TYPE
        SYNTAX      ZxGponGemPort8021pEntry
        MAX-ACCESS  not-accessible
        STATUS      current
        DESCRIPTION
            "It is entry in the table zxGponGemPort8021pTable."
        INDEX   { zxGponMgmtPonOltId, zxGponMgmtPonOnuId, zxGponPPTPEthInfoTPID}
        ::= { zxGponGemPort8021pTable 1 }

    ZxGponGemPort8021pEntry ::=
        SEQUENCE {
        zxGponGemPort8021pMapperUntagFrmInd               INTEGER,
            zxGponGemPort8021pMapperDscpTo8021pPri            OCTET STRING,
            zxGponGemPort8021pMapperDefaultPri                INTEGER,
            zxGponGemPort8021pMapperTPType                    INTEGER
        }

    zxGponGemPort8021pMapperUntagFrmInd OBJECT-TYPE
        SYNTAX      INTEGER{
                    dscpTo8021p(1),
                    tagFrmToVal(2)
                    }
        MAX-ACCESS  read-write
        STATUS      current
        DESCRIPTION
            "This attribute indicates how the ONT should handle Untagged Ethernet frames received
             across the associated Ethernet interface.  Valid values include the following:
             1: Convert from DSCP to 802.1p
             2: Tag frame to a certain value."
        REFERENCE
            "G.983.2 Rev Section 7.3.95"
        ::= { zxGponGemPort8021pEntry 1}

    zxGponGemPort8021pMapperDscpTo8021pPri OBJECT-TYPE
        SYNTAX      OCTET STRING(SIZE(24))
        MAX-ACCESS  read-write
        STATUS      current
        DESCRIPTION
            "This attribute is used in conjunction with the Unmarked Frame Option attribute. If unmarked
             frame option is 1('zxGpon8021pMapperUntagFrmInd' is dscpTo8021p), this attribute structure 
             can be considered a bitmap that represents a sequence of 64 '3-bit' groupings.  Each of the
             64 groupings represents the possible value of the 6-bit DSCP field.  Each of the '3-bit' 
             groupings represents the 'P-bit value' to which the associated DSCP value should be mapped.
             Once marked, the P-Bit marked frame will then be routed to the GEM Interwork Pointer as 
             indicated by the P-Bit to Interwork Pointer mappings above."
        REFERENCE
            "G.983.2 Rev Section 7.3.95"
        ::= { zxGponGemPort8021pEntry 2}

    zxGponGemPort8021pMapperDefaultPri OBJECT-TYPE
        SYNTAX      INTEGER
        MAX-ACCESS  read-write
        STATUS      current
        DESCRIPTION
            "This attribute is used in conjunction with the Unmarked Frame Option attribute. If unmarked
             frame option is 2('zxGpon8021pMapperUntagFrmInd' is tagFrmToVal), this attribute contains 
             the default P-Bit priority setting that will be applied to the frame.  The P-Bit marked frame
             will then be routed to the GEM Interwork Pointer as indicated by the P-Bit to Interwork Pointer
             mappings above."
        REFERENCE
            "G.983.2 Rev Section 7.3.95"
        ::= { zxGponGemPort8021pEntry 3}

    zxGponGemPort8021pMapperTPType OBJECT-TYPE
        SYNTAX      INTEGER{
                    bridging-mapping(1),
                    ethernet(2),
                    ip-host-service(3)
                    }
        MAX-ACCESS  read-only
        STATUS      current
        DESCRIPTION
            "This attribute identifies the type of termination point associated with the mapper. 
        The value is set to 0x01 if the mapper is used for Bridging-mapping. 
        The value is set to 0x02 if the mapper is directly associated with a PPTP Ethernet UNI. 
        The value is set to 0x03 if the mapper is directly associated with an IP Host Service. 
        The value 0x03 is reserved for future standardization, which will not be shown in NMS."
        REFERENCE
            "G.983.2 Rev Section 7.3.95"
        ::= { zxGponGemPort8021pEntry 4}

    zxGponGemPortStructuredCESTable OBJECT-TYPE
        SYNTAX      SEQUENCE OF ZxGponGemPortStructuredCESEntry
        MAX-ACCESS  not-accessible
        STATUS      current
        DESCRIPTION
            "This table represents Logical N X 64 kbit/s sub-port CTP Information."
        ::= { zxGponServiceMgmt 9}

    zxGponGemPortStructuredCESEntry OBJECT-TYPE
        SYNTAX      ZxGponGemPortStructuredCESEntry
        MAX-ACCESS  not-accessible
        STATUS      current
        DESCRIPTION
            "It is entry in the table zxGponGemPortCESTable."
        INDEX   { zxGponMgmtPonOltId, zxGponMgmtPonOnuId, zxGponGemPortIdx}
        ::= { zxGponGemPortStructuredCESTable 1 }

    ZxGponGemPortStructuredCESEntry ::=
        SEQUENCE {
            zxGponLogicalSubportCTPMeIdIdx             INTEGER,
            zxGponLogicalSubportCTPTimeSlots           OCTET STRING
        }

    zxGponLogicalSubportCTPMeIdIdx OBJECT-TYPE
        SYNTAX      INTEGER
        MAX-ACCESS  read-only
        STATUS      current
        DESCRIPTION
            "This attribute provides a unique number for each instance of this managed entity."
        REFERENCE
            "G.983.2 Rev Section 7.3.4"
        ::= { zxGponGemPortStructuredCESEntry 1}

    zxGponLogicalSubportCTPTimeSlots OBJECT-TYPE
        SYNTAX      OCTET STRING(SIZE(12))
        MAX-ACCESS  read-only
        STATUS      current
        DESCRIPTION
            " This attribute provides a bitmap, which indicates the time slots. 
        Each bit indicates whether the corresponding time slot is included in the connection or not. 
        The correspondence is as indicated in Table 8. "
        REFERENCE
            "G.983.2 Rev Section 7.3.4"
        ::= { zxGponGemPortStructuredCESEntry 2}


    zxGponGemPortIpRouterIWTPTable OBJECT-TYPE
        SYNTAX      SEQUENCE OF ZxGponGemPortIpRouterIWTPEntry
        MAX-ACCESS  not-accessible
        STATUS      current
        DESCRIPTION
            "This table represents IP router Information."
        ::= { zxGponServiceMgmt 10}

    zxGponGemPortIpRouterIWTPEntry OBJECT-TYPE
        SYNTAX      ZxGponGemPortIpRouterIWTPEntry
        MAX-ACCESS  not-accessible
        STATUS      current
        DESCRIPTION
            "It is entry in the table zxGponGemPortIpRouterIWTPTable."
        INDEX   { zxGponMgmtPonOltId, zxGponMgmtPonOnuId, zxGponGemPortIdx}
        ::= { zxGponGemPortIpRouterIWTPTable 1 }

    ZxGponGemPortIpRouterIWTPEntry ::=
        SEQUENCE {
        zxGponGemPortIpPortCfgDataIWTPMeIdIdx          INTEGER,
            zxGponGemPortIpPortCfgDataIWTPPortNum         INTEGER,
            zxGponGemPortIpPortCfgDataIWTPTPType          INTEGER,
            zxGponGemPortIpPortCfgDataIWTPPortAddress            IpAddress,
            zxGponGemPortIpPortCfgDataIWTPPortMask               IpAddress,
        zxGponGemPortIpPortCfgDataIWTPUnnumbered           TruthValue,
        zxGponGemPortIpPortCfgDataIWTPAdministrativeState  INTEGER,
            zxGponGemPortIpPortCfgDataIWTPPortState            INTEGER,
            zxGponGemPortIpPortCfgDataIWTPAllowRemoteAccess    TruthValue,
            zxGponGemPortIpPortCfgDataIWTPEncapsulationMethod INTEGER
        }
 

    zxGponGemPortIpPortCfgDataIWTPMeIdIdx OBJECT-TYPE
        SYNTAX      INTEGER
        MAX-ACCESS  read-only
        STATUS      current
        DESCRIPTION
            "This attribute provides a unique number for each instance of this managed entity."
        REFERENCE
            "G.983.2 Rev Section 7.3.37"
        ::= { zxGponGemPortIpRouterIWTPEntry 1}

    zxGponGemPortIpPortCfgDataIWTPPortNum OBJECT-TYPE
        SYNTAX      INTEGER
        MAX-ACCESS  read-write
        STATUS      current
        DESCRIPTION
            "This attribute identifies the port at which IP provisioning takes place."
        REFERENCE
            "G.983.2 Rev Section 7.3.37"
        ::= { zxGponGemPortIpRouterIWTPEntry 2}

     zxGponGemPortIpPortCfgDataIWTPTPType OBJECT-TYPE
        SYNTAX      INTEGER{
                    lan(1),
                    atm(2)
                    }
        MAX-ACCESS  read-only
        STATUS      current
        DESCRIPTION
            "This attribute identifies the type of the termination point associated with this IP port. 
        The value is set to 0x01 if this IP port is associated with the LAN side's TP. 
        The value is set to 0x02 if this IP port is associated with the ATM side's TP."
        REFERENCE
            "G.983.2 Rev Section 7.3.37"
        ::= { zxGponGemPortIpRouterIWTPEntry 3}


     zxGponGemPortIpPortCfgDataIWTPPortAddress OBJECT-TYPE
        SYNTAX      IpAddress
        MAX-ACCESS  read-write
        STATUS      current
        DESCRIPTION
            "This attribute identifies the provisioned IP address. 
        When an IP address is not assigned, this attribute consists of all 0x00."
        REFERENCE
            "G.983.2 Rev Section 7.3.37"
        ::= { zxGponGemPortIpRouterIWTPEntry 4}

     zxGponGemPortIpPortCfgDataIWTPPortMask OBJECT-TYPE
        SYNTAX      IpAddress
        MAX-ACCESS  read-write
        STATUS      current
        DESCRIPTION
            "This attribute identifies the address mask associated with the provisioned IP address.
        When an IP address mask is not assigned, this attribute consists of all 0x00."
        REFERENCE
            "G.983.2 Rev Section 7.3.37"
        ::= { zxGponGemPortIpRouterIWTPEntry 5}

     zxGponGemPortIpPortCfgDataIWTPUnnumbered OBJECT-TYPE
        SYNTAX      TruthValue
        MAX-ACCESS  read-write
        STATUS      current
        DESCRIPTION
            "This boolean attribute indicates whether or not this IP port has an IP address. 
        The value TRUE means unnumbered. (For future use by IP router function.)."
        REFERENCE
            "G.983.2 Rev Section 7.3.37"
        ::= { zxGponGemPortIpRouterIWTPEntry 6}

     zxGponGemPortIpPortCfgDataIWTPAdministrativeState OBJECT-TYPE
        SYNTAX      INTEGER{
                    activate(1),
                    deactivate(2)
                    }
        MAX-ACCESS  read-write
        STATUS      current
        DESCRIPTION
            "This boolean attribute is used to activate (unlock, value 0x00) and 
        deactivate (lock, value 0x01) the functions performed by instances of this managed entity."
        REFERENCE
            "G.983.2 Rev Section 7.3.37"
        ::= { zxGponGemPortIpRouterIWTPEntry 7}


      zxGponGemPortIpPortCfgDataIWTPPortState OBJECT-TYPE
        SYNTAX      INTEGER{
                    up(1),
                    down(2)
                    }
        MAX-ACCESS  read-only
        STATUS      current
        DESCRIPTION
            "This boolean attribute provides status information on the port. 
        Valid values include 'up' (value 0x00) and 'down' (value 0x01)."
        REFERENCE
            "G.983.2 Rev Section 7.3.37"
        ::= { zxGponGemPortIpRouterIWTPEntry 8}


       zxGponGemPortIpPortCfgDataIWTPAllowRemoteAccess OBJECT-TYPE
        SYNTAX      TruthValue
        MAX-ACCESS  read-only
        STATUS      current
        DESCRIPTION
            "This boolean attribute indicates whether or not this IP port may be accessed remotely. 
        The value TRUE means remote access is enabled."
        REFERENCE
            "G.983.2 Rev Section 7.3.37"
        ::= { zxGponGemPortIpRouterIWTPEntry 9}

      zxGponGemPortIpPortCfgDataIWTPEncapsulationMethod OBJECT-TYPE
        SYNTAX      INTEGER{
                    atmvc(1),
                    llc(2)
                    }
        MAX-ACCESS  read-write
        STATUS      current
        DESCRIPTION
            "This attribute identifies the frame encapsulation method that is used.
        Value 0x00: identification by ATM VC;
        value 0x01: LLC encapsulation. 
        Upon autonomous instantiation, the value 0x00 is used."
        REFERENCE
            "G.983.2 Rev Section 7.3.37"
        ::= { zxGponGemPortIpRouterIWTPEntry 10}

    zxGponGemPortIpRouterUNITable OBJECT-TYPE
        SYNTAX      SEQUENCE OF ZxGponGemPortIpRouterUNIEntry
        MAX-ACCESS  not-accessible
        STATUS      current
        DESCRIPTION
            "This table represents IP router Information."
        ::= { zxGponServiceMgmt 11}

    zxGponGemPortIpRouterUNIEntry OBJECT-TYPE
        SYNTAX      ZxGponGemPortIpRouterUNIEntry
        MAX-ACCESS  not-accessible
        STATUS      current
        DESCRIPTION
            "It is entry in the table zxGponGemPortIpRouterTable."
        INDEX   { zxGponMgmtPonOltId, zxGponMgmtPonOnuId, zxGponPPTPEthInfoTPID}
        ::= { zxGponGemPortIpRouterUNITable 1 }

    ZxGponGemPortIpRouterUNIEntry ::=
        SEQUENCE {
        zxGponGemPortIpPortCfgDataUNIMeIdIdx          INTEGER,
            zxGponGemPortIpPortCfgDataUNIPortNum         INTEGER,
            zxGponGemPortIpPortCfgDataUNITPType          INTEGER,
            zxGponGemPortIpPortCfgDataUNIPortAddress IpAddress,
            zxGponGemPortIpPortCfgDataUNIPortMask   IpAddress,
        zxGponGemPortIpPortCfgDataUNIUnnumbered TruthValue,
        zxGponGemPortIpPortCfgDataUNIAdministrativeState INTEGER,
            zxGponGemPortIpPortCfgDataUNIPortState    INTEGER,
            zxGponGemPortIpPortCfgDataUNIAllowRemoteAccess    TruthValue,
            zxGponGemPortIpPortCfgDataUNIEncapsulationMethod INTEGER
        }
 
    zxGponGemPortIpPortCfgDataUNIMeIdIdx OBJECT-TYPE
        SYNTAX      INTEGER
        MAX-ACCESS  read-only
        STATUS      current
        DESCRIPTION
            "This attribute provides a unique number for each instance of this managed entity."
        REFERENCE
            "G.983.2 Rev Section 7.3.37"
        ::= { zxGponGemPortIpRouterUNIEntry 1}

    zxGponGemPortIpPortCfgDataUNIPortNum OBJECT-TYPE
        SYNTAX      INTEGER
        MAX-ACCESS  read-write
        STATUS      current
        DESCRIPTION
            "This attribute identifies the port at which IP provisioning takes place."
        REFERENCE
            "G.983.2 Rev Section 7.3.37"
        ::= { zxGponGemPortIpRouterUNIEntry 2}

     zxGponGemPortIpPortCfgDataUNITPType OBJECT-TYPE
        SYNTAX      INTEGER{
                    lan(1),
                    atm(2)
                    }
        MAX-ACCESS  read-only
        STATUS      current
        DESCRIPTION
            "This attribute identifies the type of the termination point associated with this IP port. 
        The value is set to 0x01 if this IP port is associated with the LAN side's TP. 
        The value is set to 0x02 if this IP port is associated with the ATM side's TP."
        REFERENCE
            "G.983.2 Rev Section 7.3.37"
        ::= { zxGponGemPortIpRouterUNIEntry 3}


     zxGponGemPortIpPortCfgDataUNIPortAddress OBJECT-TYPE
        SYNTAX      IpAddress
        MAX-ACCESS  read-write
        STATUS      current
        DESCRIPTION
            "This attribute identifies the provisioned IP address. 
        When an IP address is not assigned, this attribute consists of all 0x00."
        REFERENCE
            "G.983.2 Rev Section 7.3.37"
        ::= { zxGponGemPortIpRouterUNIEntry 4}

     zxGponGemPortIpPortCfgDataUNIPortMask OBJECT-TYPE
        SYNTAX      IpAddress
        MAX-ACCESS  read-write
        STATUS      current
        DESCRIPTION
            "This attribute identifies the address mask associated with the provisioned IP address.
        When an IP address mask is not assigned, this attribute consists of all 0x00."
        REFERENCE
            "G.983.2 Rev Section 7.3.37"
        ::= { zxGponGemPortIpRouterUNIEntry 5}

     zxGponGemPortIpPortCfgDataUNIUnnumbered OBJECT-TYPE
        SYNTAX      TruthValue
        MAX-ACCESS  read-write
        STATUS      current
        DESCRIPTION
            "This boolean attribute indicates whether or not this IP port has an IP address. 
        The value TRUE means unnumbered. (For future use by IP router function.)."
        REFERENCE
            "G.983.2 Rev Section 7.3.37"
        ::= { zxGponGemPortIpRouterUNIEntry 6}


     zxGponGemPortIpPortCfgDataUNIAdministrativeState OBJECT-TYPE
        SYNTAX      INTEGER{
                    activate(1),
                    deactivate(2)
                    }
        MAX-ACCESS  read-write
        STATUS      current
        DESCRIPTION
            "This boolean attribute is used to activate (unlock, value 0x00) and 
        deactivate (lock, value 0x01) the functions performed by instances of this managed entity."
        REFERENCE
            "G.983.2 Rev Section 7.3.37"
        ::= { zxGponGemPortIpRouterUNIEntry 7}


      zxGponGemPortIpPortCfgDataUNIPortState OBJECT-TYPE
        SYNTAX      INTEGER{
                    up(1),
                    down(2)
                    }
        MAX-ACCESS  read-only
        STATUS      current
        DESCRIPTION
            "This boolean attribute provides status information on the port. 
        Valid values include 'up' (value 0x00) and 'down' (value 0x01)."
        REFERENCE
            "G.983.2 Rev Section 7.3.37"
        ::= { zxGponGemPortIpRouterUNIEntry 8}


       zxGponGemPortIpPortCfgDataUNIAllowRemoteAccess OBJECT-TYPE
        SYNTAX      TruthValue
        MAX-ACCESS  read-only
        STATUS      current
        DESCRIPTION
            "This boolean attribute indicates whether or not this IP port may be accessed remotely. 
        The value TRUE means remote access is enabled."
        REFERENCE
            "G.983.2 Rev Section 7.3.37"
        ::= { zxGponGemPortIpRouterUNIEntry 9}


      zxGponGemPortIpPortCfgDataUNIEncapsulationMethod OBJECT-TYPE
        SYNTAX      INTEGER{
                    atmvc(1),
                    llc(2)
                    }
        MAX-ACCESS  read-write
        STATUS      current
        DESCRIPTION
            "This attribute identifies the frame encapsulation method that is used.
        Value 0x00: identification by ATM VC;
        value 0x01: LLC encapsulation. 
        Upon autonomous instantiation, the value 0x00 is used."
        REFERENCE
            "G.983.2 Rev Section 7.3.37"
        ::= { zxGponGemPortIpRouterUNIEntry 10}

    zxGponGemPortIWTPMACBriPortFilterTableInfoTable OBJECT-TYPE
        SYNTAX      SEQUENCE OF ZxGponGemPortIWTPMACBriPortFilterTableInfoEntry
        MAX-ACCESS  not-accessible
        STATUS      current
        DESCRIPTION
            "This managed entity is used to organize and record data that is associated with a 
             bridge port. Some of the data is volatile. Instances of this managed entity shall 
             be automatically created/deleted by the ONT upon the creation/deletion of a 
             MACBridgePortConfigurationData managed entity." 
        REFERENCE
            "G.983.2 7.3.33"
        ::= { zxGponServiceMgmt 12 }  

    zxGponGemPortIWTPMACBriPortFilterTableInfoEntry OBJECT-TYPE
        SYNTAX      ZxGponGemPortIWTPMACBriPortFilterTableInfoEntry
        MAX-ACCESS  not-accessible
        STATUS      current
        DESCRIPTION
            " Alternative schemes for this managed entity may be included in future Recommendations."
        INDEX   { zxGponMgmtPonOltId, zxGponMgmtPonOnuId, zxGponGemPortIdx, zxGponGemPortIWTPMACBriPortFilterTableMacAddr }
        ::= { zxGponGemPortIWTPMACBriPortFilterTableInfoTable 1 }

    ZxGponGemPortIWTPMACBriPortFilterTableInfoEntry ::=
        SEQUENCE {
            zxGponGemPortIWTPMACBriPortFilterTableMacAddr     MacAddress,
            zxGponGemPortIWTPMACBriPortFilterTableAction      INTEGER,
            zxGponGemPortIWTPMACBriPortFilterTableEntryStatus RowStatus
        }

   zxGponGemPortIWTPMACBriPortFilterTableMacAddr OBJECT-TYPE
        SYNTAX      MacAddress
        MAX-ACCESS  not-accessible
        STATUS      current
        DESCRIPTION
            "This attribute lists destination MAC Addresses associated with the bridge port."
        ::= { zxGponGemPortIWTPMACBriPortFilterTableInfoEntry 1}

   zxGponGemPortIWTPMACBriPortFilterTableAction OBJECT-TYPE
        SYNTAX      INTEGER{
                    forward(1),
                    filter(2)
                    }
        MAX-ACCESS  read-write
        STATUS      current
        DESCRIPTION
            ""
        ::= { zxGponGemPortIWTPMACBriPortFilterTableInfoEntry 2}

   zxGponGemPortIWTPMACBriPortFilterTableEntryStatus OBJECT-TYPE
        SYNTAX      RowStatus
        MAX-ACCESS  read-create
        STATUS      current
        DESCRIPTION
            ""
        ::= { zxGponGemPortIWTPMACBriPortFilterTableInfoEntry 3}

    zxGponGemPortUNIMACBriPortFilterTableInfoTable OBJECT-TYPE
        SYNTAX      SEQUENCE OF ZxGponGemPortUNIMACBriPortFilterTableInfoEntry
        MAX-ACCESS  not-accessible
        STATUS      current
        DESCRIPTION
            "This managed entity is used to organize and record data that is associated with a 
             bridge port. Some of the data is volatile. Instances of this managed entity shall 
             be automatically created/deleted by the ONT upon the creation/deletion of a 
             MACBridgePortConfigurationData managed entity." 
        REFERENCE
            "G.983.2 7.3.33"
        ::= { zxGponServiceMgmt 13 }  

    zxGponGemPortUNIMACBriPortFilterTableInfoEntry OBJECT-TYPE
        SYNTAX      ZxGponGemPortUNIMACBriPortFilterTableInfoEntry
        MAX-ACCESS  not-accessible
        STATUS      current
        DESCRIPTION
            " Alternative schemes for this managed entity may be included in future Recommendations."
        INDEX   { zxGponMgmtPonOltId, zxGponMgmtPonOnuId, zxGponPPTPEthInfoTPID, zxGponGemPortUNIMACBriPortFilterTableMacAddr }
        ::= { zxGponGemPortUNIMACBriPortFilterTableInfoTable 1 }

    ZxGponGemPortUNIMACBriPortFilterTableInfoEntry ::=
        SEQUENCE {
            zxGponGemPortUNIMACBriPortFilterTableMacAddr     MacAddress,
            zxGponGemPortUNIMACBriPortFilterTableAction      INTEGER,
            zxGponGemPortUNIMACBriPortFilterTableEntryStatus RowStatus
        }

   zxGponGemPortUNIMACBriPortFilterTableMacAddr OBJECT-TYPE
        SYNTAX      MacAddress
        MAX-ACCESS  not-accessible
        STATUS      current
        DESCRIPTION
            "This attribute lists destination MAC Addresses associated with the bridge port."
        ::= { zxGponGemPortUNIMACBriPortFilterTableInfoEntry 1}

   zxGponGemPortUNIMACBriPortFilterTableAction OBJECT-TYPE
        SYNTAX      INTEGER{
                    forward(1),
                    filter(2)
                    }
        MAX-ACCESS  read-write
        STATUS      current
        DESCRIPTION
            ""
        ::= { zxGponGemPortUNIMACBriPortFilterTableInfoEntry 2}

   zxGponGemPortUNIMACBriPortFilterTableEntryStatus OBJECT-TYPE
        SYNTAX      RowStatus
        MAX-ACCESS  read-create
        STATUS      current
        DESCRIPTION
            ""
        ::= { zxGponGemPortUNIMACBriPortFilterTableInfoEntry 3}
        
      zxGponGemPortWeightTable OBJECT-TYPE
        SYNTAX      SEQUENCE OF ZxGponGemPortWeightEntry
        MAX-ACCESS  not-accessible
        STATUS      current
        DESCRIPTION
            "This table represents ONU side  configuration."
        ::= { zxGponServiceMgmt 14 }

    zxGponGemPortWeightEntry OBJECT-TYPE
        SYNTAX      ZxGponGemPortWeightEntry
        MAX-ACCESS  not-accessible
        STATUS      current
        DESCRIPTION
            "It is entry in the table zxGponGemPortWeightTable."
        INDEX   { zxGponMgmtPonOltId, zxGponMgmtPonOnuId, zxGponGemPortIdx }
        ::= { zxGponGemPortWeightTable 1 }

    ZxGponGemPortWeightEntry ::=
        SEQUENCE {
            zxGponGemPortSchedulemode             INTEGER,
            zxGponGemPortCos1Weight               INTEGER,
            zxGponGemPortCos2Weight               INTEGER,
            zxGponGemPortCos3Weight               INTEGER,
            zxGponGemPortCos4Weight               INTEGER
       }
   
    zxGponGemPortSchedulemode OBJECT-TYPE
        SYNTAX      INTEGER{
                     none(0),
                     sp(1),
                     wrr(2)
                     }
        MAX-ACCESS  read-write
        STATUS      current
        DESCRIPTION
            "COS Schedule mode."
        ::= { zxGponGemPortWeightEntry 1}
        
    zxGponGemPortCos1Weight     OBJECT-TYPE
      SYNTAX      INTEGER
      MAX-ACCESS  read-write
      STATUS      current 
      DESCRIPTION 
        "Weight of COS1(0-100)."
      ::= { zxGponGemPortWeightEntry 2 }
    
    zxGponGemPortCos2Weight     OBJECT-TYPE
      SYNTAX      INTEGER
      MAX-ACCESS  read-write
      STATUS      current 
      DESCRIPTION 
        "Weight of COS2(0-100)."
      ::= { zxGponGemPortWeightEntry 3 }
      
    zxGponGemPortCos3Weight     OBJECT-TYPE
      SYNTAX      INTEGER
      MAX-ACCESS  read-write
      STATUS      current 
      DESCRIPTION 
        "Weight of COS3(0-100)."
      ::= { zxGponGemPortWeightEntry 4 }
    
    zxGponGemPortCos4Weight     OBJECT-TYPE
      SYNTAX      INTEGER
      MAX-ACCESS  read-write
      STATUS      current 
      DESCRIPTION 
        "Weight of COS4(0-100)."
      ::= { zxGponGemPortWeightEntry 5 }
      
        
   zxGponGemPortPrioReGenTable OBJECT-TYPE
        SYNTAX      SEQUENCE OF ZxGponGemPortPrioReGenEntry
        MAX-ACCESS  not-accessible
        STATUS      current
        DESCRIPTION
            ""
        ::= { zxGponServiceMgmt 20 }

    zxGponGemPortPrioReGenEntry OBJECT-TYPE
        SYNTAX      ZxGponGemPortPrioReGenEntry
        MAX-ACCESS  not-accessible
        STATUS      current
        DESCRIPTION
            "It is entry in the table zxGponGemPortPrioReGenTable."
        INDEX   { zxGponMgmtPonOltId, zxGponMgmtPonOnuId, zxGponGemPortIdx }
        ::= { zxGponGemPortPrioReGenTable 1 }

    ZxGponGemPortPrioReGenEntry ::=
        SEQUENCE {
            zxGponGemPortPrioReGenMode              INTEGER,
            zxGponGemPortPrioReGenMap0              INTEGER,
            zxGponGemPortPrioReGenMap1              INTEGER,
            zxGponGemPortPrioReGenMap2              INTEGER,
            zxGponGemPortPrioReGenMap3              INTEGER,
            zxGponGemPortPrioReGenMap4              INTEGER,
            zxGponGemPortPrioReGenMap5              INTEGER,
            zxGponGemPortPrioReGenMap6              INTEGER,
            zxGponGemPortPrioReGenMap7              INTEGER
        }

    zxGponGemPortPrioReGenMode       OBJECT-TYPE
      SYNTAX      INTEGER{
                  svlan(1),
                  cvlan(2),
                  both(3)
                  }
      MAX-ACCESS  read-write
      STATUS      current 
      DESCRIPTION 
        "This attribute specifies the priority-regeneration mode of GEM port."
      REFERENCE   ""
      ::= { zxGponGemPortPrioReGenEntry 1 }

    zxGponGemPortPrioReGenMap0 OBJECT-TYPE
        SYNTAX      INTEGER(0..7)
        MAX-ACCESS  read-write
        STATUS      current
        DESCRIPTION
        "This attribute specifies the regenerated priority of priority 0."
        ::= { zxGponGemPortPrioReGenEntry 2}

    zxGponGemPortPrioReGenMap1 OBJECT-TYPE
        SYNTAX      INTEGER(0..7)
        MAX-ACCESS  read-write
        STATUS      current
        DESCRIPTION
        "This attribute specifies the regenerated priority of priority 1."
        ::= { zxGponGemPortPrioReGenEntry 3}

    zxGponGemPortPrioReGenMap2 OBJECT-TYPE
        SYNTAX      INTEGER(0..7)
        MAX-ACCESS  read-write
        STATUS      current
        DESCRIPTION
        "This attribute specifies the regenerated priority of priority 2."
        ::= { zxGponGemPortPrioReGenEntry 4}

    zxGponGemPortPrioReGenMap3 OBJECT-TYPE
        SYNTAX      INTEGER(0..7)
        MAX-ACCESS  read-write
        STATUS      current
        DESCRIPTION
        "This attribute specifies the regenerated priority of priority 3."
        ::= { zxGponGemPortPrioReGenEntry 5}

    zxGponGemPortPrioReGenMap4 OBJECT-TYPE
        SYNTAX      INTEGER(0..7)
        MAX-ACCESS  read-write
        STATUS      current
        DESCRIPTION
        "This attribute specifies the regenerated priority of priority 4."
        ::= { zxGponGemPortPrioReGenEntry 6}

    zxGponGemPortPrioReGenMap5 OBJECT-TYPE
        SYNTAX      INTEGER(0..7)
        MAX-ACCESS  read-write
        STATUS      current
        DESCRIPTION
        "This attribute specifies the regenerated priority of priority 5."
        ::= { zxGponGemPortPrioReGenEntry 7}

    zxGponGemPortPrioReGenMap6 OBJECT-TYPE
        SYNTAX      INTEGER(0..7)
        MAX-ACCESS  read-write
        STATUS      current
        DESCRIPTION
        "This attribute specifies the regenerated priority of priority 6."
        ::= { zxGponGemPortPrioReGenEntry 8}
        
    zxGponGemPortPrioReGenMap7 OBJECT-TYPE
        SYNTAX      INTEGER(0..7)
        MAX-ACCESS  read-write
        STATUS      current
        DESCRIPTION
        "This attribute specifies the regenerated priority of priority 7."
        ::= { zxGponGemPortPrioReGenEntry 9}
   zxGponGemPortStaticsTable OBJECT-TYPE
        SYNTAX      SEQUENCE OF ZxGponGemPortStaticsEntry
        MAX-ACCESS  not-accessible
        STATUS      current
        DESCRIPTION
            ""
        ::= { zxGponServiceMgmt 21 }

    zxGponGemPortStaticsEntry OBJECT-TYPE
        SYNTAX      ZxGponGemPortStaticsEntry
        MAX-ACCESS  not-accessible
        STATUS      current
        DESCRIPTION
            "It is entry in the table zxGponGemPortStaticsTable."
        INDEX   { zxGponMgmtPonOltId, zxGponMgmtPonOnuId, zxGponGemPortIdx }
        ::= { zxGponGemPortStaticsTable 1 }

    ZxGponGemPortStaticsEntry ::=
        SEQUENCE {
            zxGponGemPortUpUcastPkts              Unsigned32,
            zxGponGemPortUpMcastPkts              Unsigned32,
            zxGponGemPortUpBcastPkts              Unsigned32,
            zxGponGemPortUpPassedBytes            Unsigned32,
            zxGponGemPortUpDroppedPkts            Unsigned32,
            zxGponGemPortDownUcastPkts            Unsigned32,
            zxGponGemPortDownMcastPkts            Unsigned32,
            zxGponGemPortDownBcastPkts            Unsigned32,
            zxGponGemPortDownPassedBytes          Unsigned32,
        zxGponGemPortDownDroppedPkts          Unsigned32
        }

    zxGponGemPortUpUcastPkts       OBJECT-TYPE
      SYNTAX      Unsigned32
      MAX-ACCESS  read-only
      STATUS      current 
      DESCRIPTION 
        ""     
      ::= { zxGponGemPortStaticsEntry 1 }
    zxGponGemPortUpMcastPkts OBJECT-TYPE
      SYNTAX      Unsigned32
      MAX-ACCESS  read-only
      STATUS      current 
      DESCRIPTION 
        ""     
      ::= { zxGponGemPortStaticsEntry 2 }
    zxGponGemPortUpBcastPkts OBJECT-TYPE
      SYNTAX      Unsigned32
      MAX-ACCESS  read-only
      STATUS      current 
      DESCRIPTION 
        ""     
      ::= { zxGponGemPortStaticsEntry 3 }

    zxGponGemPortUpPassedBytes OBJECT-TYPE
      SYNTAX      Unsigned32
      MAX-ACCESS  read-only
      STATUS      current 
      DESCRIPTION 
        ""     
      ::= { zxGponGemPortStaticsEntry 4 }

    zxGponGemPortUpDroppedPkts OBJECT-TYPE
      SYNTAX      Unsigned32
      MAX-ACCESS  read-only
      STATUS      current 
      DESCRIPTION 
        ""     
      ::= { zxGponGemPortStaticsEntry 5 }

    zxGponGemPortDownUcastPkts OBJECT-TYPE
      SYNTAX      Unsigned32
      MAX-ACCESS  read-only
      STATUS      current 
      DESCRIPTION 
        ""     
      ::= { zxGponGemPortStaticsEntry 6 }

    zxGponGemPortDownMcastPkts OBJECT-TYPE
      SYNTAX      Unsigned32
      MAX-ACCESS  read-only
      STATUS      current 
      DESCRIPTION 
        ""     
      ::= { zxGponGemPortStaticsEntry 7 }
    zxGponGemPortDownBcastPkts OBJECT-TYPE
      SYNTAX      Unsigned32
      MAX-ACCESS  read-only
      STATUS      current 
      DESCRIPTION 
        ""     
      ::= { zxGponGemPortStaticsEntry 8 }        
    zxGponGemPortDownPassedBytes OBJECT-TYPE
      SYNTAX      Unsigned32
      MAX-ACCESS  read-only
      STATUS      current 
      DESCRIPTION 
        ""     
      ::= { zxGponGemPortStaticsEntry 9 }
    zxGponGemPortDownDroppedPkts OBJECT-TYPE
      SYNTAX      Unsigned32
      MAX-ACCESS  read-only
      STATUS      current 
      DESCRIPTION 
        ""     
      ::= { zxGponGemPortStaticsEntry 10 }


   zxGponGemPortStaticsHistoryInfoTable OBJECT-TYPE
        SYNTAX      SEQUENCE OF ZxGponGemPortStaticsHistoryInfoEntry
        MAX-ACCESS  not-accessible
        STATUS      current
        DESCRIPTION
            ""
        ::= { zxGponServiceMgmt 22 }

    zxGponGemPortStaticsHistoryInfoEntry OBJECT-TYPE
        SYNTAX      ZxGponGemPortStaticsHistoryInfoEntry
        MAX-ACCESS  not-accessible
        STATUS      current
        DESCRIPTION
            "It is entry in the table zxGponGemPortStaticsHistoryInfoTable."
        INDEX   { zxGponMgmtPonOltId, zxGponMgmtPonOnuId, zxGponGemPortIdx }
        ::= { zxGponGemPortStaticsHistoryInfoTable 1 }

    ZxGponGemPortStaticsHistoryInfoEntry ::=
        SEQUENCE {
            zxGponGemPortUpUcastPktsHistoryInfo              Unsigned32,
            zxGponGemPortUpMcastPktsHistoryInfo              Unsigned32,
            zxGponGemPortUpBcastPktsHistoryInfo              Unsigned32,
            zxGponGemPortUpPassedBytesHistoryInfo            Unsigned32,
            zxGponGemPortUpDroppedPktsHistoryInfo            Unsigned32,
            zxGponGemPortDownUcastPktsHistoryInfo            Unsigned32,
            zxGponGemPortDownMcastPktsHistoryInfo            Unsigned32,
            zxGponGemPortDownBcastPktsHistoryInfo            Unsigned32,
            zxGponGemPortDownPassedBytesHistoryInfo          Unsigned32,
        zxGponGemPortDownDroppedPktsHistoryInfo          Unsigned32
        }

    zxGponGemPortUpUcastPktsHistoryInfo       OBJECT-TYPE
      SYNTAX      Unsigned32
      MAX-ACCESS  read-only
      STATUS      current 
      DESCRIPTION 
        ""     
      ::= { zxGponGemPortStaticsHistoryInfoEntry 1 }
    zxGponGemPortUpMcastPktsHistoryInfo OBJECT-TYPE
      SYNTAX      Unsigned32
      MAX-ACCESS  read-only
      STATUS      current 
      DESCRIPTION 
        ""     
      ::= { zxGponGemPortStaticsHistoryInfoEntry 2 }
    zxGponGemPortUpBcastPktsHistoryInfo OBJECT-TYPE
      SYNTAX      Unsigned32
      MAX-ACCESS  read-only
      STATUS      current 
      DESCRIPTION 
        ""     
      ::= { zxGponGemPortStaticsHistoryInfoEntry 3 }

    zxGponGemPortUpPassedBytesHistoryInfo OBJECT-TYPE
      SYNTAX      Unsigned32
      MAX-ACCESS  read-only
      STATUS      current 
      DESCRIPTION 
        ""     
      ::= { zxGponGemPortStaticsHistoryInfoEntry 4 }

    zxGponGemPortUpDroppedPktsHistoryInfo OBJECT-TYPE
      SYNTAX      Unsigned32
      MAX-ACCESS  read-only
      STATUS      current 
      DESCRIPTION 
        ""     
      ::= { zxGponGemPortStaticsHistoryInfoEntry 5 }

    zxGponGemPortDownUcastPktsHistoryInfo OBJECT-TYPE
      SYNTAX      Unsigned32
      MAX-ACCESS  read-only
      STATUS      current 
      DESCRIPTION 
        ""     
      ::= { zxGponGemPortStaticsHistoryInfoEntry 6 }

    zxGponGemPortDownMcastPktsHistoryInfo OBJECT-TYPE
      SYNTAX      Unsigned32
      MAX-ACCESS  read-only
      STATUS      current 
      DESCRIPTION 
        ""     
      ::= { zxGponGemPortStaticsHistoryInfoEntry 7 }
    zxGponGemPortDownBcastPktsHistoryInfo OBJECT-TYPE
      SYNTAX      Unsigned32
      MAX-ACCESS  read-only
      STATUS      current 
      DESCRIPTION 
        ""     
      ::= { zxGponGemPortStaticsHistoryInfoEntry 8 }        
    zxGponGemPortDownPassedBytesHistoryInfo OBJECT-TYPE
      SYNTAX      Unsigned32
      MAX-ACCESS  read-only
      STATUS      current 
      DESCRIPTION 
        ""     
      ::= { zxGponGemPortStaticsHistoryInfoEntry 9 }
    zxGponGemPortDownDroppedPktsHistoryInfo OBJECT-TYPE
      SYNTAX      Unsigned32
      MAX-ACCESS  read-only
      STATUS      current 
      DESCRIPTION 
        ""     
      ::= { zxGponGemPortStaticsHistoryInfoEntry 10 }
        
--------------------------------------------------------------------------------
-- 40.MAC Drift Mgmt
--------------------------------------------------------------------------------   
    zxGponMacSpoofingObjects OBJECT IDENTIFIER  ::=  { zxGponRootMib 40 }
    
    zxGponSpoofingPort OBJECT-TYPE
        SYNTAX      INTEGER
        MAX-ACCESS  read-only
        STATUS      current
        DESCRIPTION
            "The Gem Port."
        ::= { zxGponMacSpoofingObjects 1 }
        
    zxGponSpoofingMac OBJECT-TYPE
        SYNTAX      MacAddress
        MAX-ACCESS  read-only
        STATUS      current
        DESCRIPTION
            "The MAC of packets,which spoofing."
        ::= { zxGponMacSpoofingObjects 2 }  
        
    zxGponSpoofingVlan OBJECT-TYPE
        SYNTAX      VlanId
        MAX-ACCESS  read-only
        STATUS      current
        DESCRIPTION
            "The port VLAN, which MAC Spoofing."
        ::= { zxGponMacSpoofingObjects 3 }  
        
    zxGponSpoofingConflictPort OBJECT-TYPE
        SYNTAX      INTEGER
        MAX-ACCESS  read-only
        STATUS      current
        DESCRIPTION
            "The conflict gem port."
        ::= { zxGponMacSpoofingObjects 4 }          
                
        
   zxGponTraps          OBJECT IDENTIFIER ::= { zxGponRootMib 45}    
      
  zxGponTrapsBindVar          OBJECT IDENTIFIER ::= { zxGponTraps 1}    

    zxGponOltRxPowerAlarmiReason OBJECT-TYPE
        SYNTAX      INTEGER
                        {
                        toohigh(1),
                        toolow(2)
                        }
        MAX-ACCESS  read-only
        STATUS      current
        DESCRIPTION
                ""
        ::= { zxGponTrapsBindVar 1 }   

    zxGponOltRxPowerAbnormalInformiReason OBJECT-TYPE
        SYNTAX      INTEGER
                        {
                        toohigh(1),
                        toolow(2)
                        }
        MAX-ACCESS  read-only
        STATUS      current
        DESCRIPTION
                ""
        ::= { zxGponTrapsBindVar 2 }   

    zxGponOltTxPowerAlarmReason OBJECT-TYPE
        SYNTAX      INTEGER
                        {
                        toohigh(1),
                        toolow(2)
                        }
        MAX-ACCESS  read-only
        STATUS      current
        DESCRIPTION
                ""
        ::= { zxGponTrapsBindVar 3 }   

    zxGponOltTxPowerAbnormalInformReason OBJECT-TYPE
        SYNTAX      INTEGER
                        {
                        toohigh(1),
                        toolow(2)
                        }
        MAX-ACCESS  read-only
        STATUS      current
        DESCRIPTION
                ""
        ::= { zxGponTrapsBindVar 4 }   

    zxGponTrapEventString OBJECT-TYPE
        SYNTAX      OCTET STRING(SIZE (0..255))
        MAX-ACCESS  read-only
        STATUS      current
        DESCRIPTION
                "Gpon trap event string."
        ::= { zxGponTrapsBindVar 5 }

    zxGponOltLOSi        NOTIFICATION-TYPE
        OBJECTS {
                ifIndex,zxGponOntDevMgmtName,zxGponOntDevMgmtTypeName,zxGponOntDevMgmtDescription
                }
        STATUS  current
        DESCRIPTION 
            "LOSi is Loss of signal for ONUi. Generate notification."
        ::={zxGponTraps 101}             
         
    zxGponOltLosiRestore  NOTIFICATION-TYPE
        OBJECTS {
                ifIndex,zxGponOntDevMgmtName,zxGponOntDevMgmtTypeName,zxGponOntDevMgmtDescription
                }
        STATUS  current
        DESCRIPTION 
            "LOSi is Loss of signal for ONUi.When the OLT receives 
            a valid optical signal from ONUi, Alarm is restored"
        ::={zxGponTraps 102} 
          
    zxGponOltLOFi        NOTIFICATION-TYPE
        OBJECTS {
                ifIndex,zxGponOntDevMgmtName,zxGponOntDevMgmtTypeName,zxGponOntDevMgmtDescription
                }
        STATUS  current
        DESCRIPTION 
            "LOFi is Loss of Frame of ONUi. Send 3 times 
            Deactivate_ONU-ID messages. Generate Loss_of_phy_layer_I 
            notification."
        ::={zxGponTraps 103}
        
    zxGponOltLOFiRestore        NOTIFICATION-TYPE
        OBJECTS {
                ifIndex,zxGponOntDevMgmtName,zxGponOntDevMgmtTypeName,zxGponOntDevMgmtDescription
                }
        STATUS  current
        DESCRIPTION 
            "LOFi is Loss of Frame of ONUi. When frame delineation 
            for ONUi is achieved in the operating state."
        ::={zxGponTraps 104}
                
    zxGponOltDOWi        NOTIFICATION-TYPE
        OBJECTS {
                ifIndex,zxGponOntDevMgmtName,zxGponOntDevMgmtTypeName,zxGponOntDevMgmtDescription
                }
        STATUS  current
        DESCRIPTION 
            "DOWi is Drift of Window of ONUi. Send modified EqD to the ONUi."
        ::={zxGponTraps 105}
                
    zxGponOltDOWiRestore   NOTIFICATION-TYPE
        OBJECTS {
                ifIndex,zxGponOntDevMgmtName,zxGponOntDevMgmtTypeName,zxGponOntDevMgmtDescription
                }
        STATUS current
        DESCRIPTION 
        "DOWi is Drift of Window of ONUi. When the OLT 
        receives the ONUi Transmission in the correct position."
        ::={zxGponTraps 106}
             
    zxGponOltSFi        NOTIFICATION-TYPE
        OBJECTS {
                ifIndex,zxGponOntDevMgmtName,zxGponOntDevMgmtTypeName,zxGponOntDevMgmtDescription
                }
        STATUS current
        DESCRIPTION 
            "SFi is Signal Fail of ONUi. Send 3 times 
            Deactivate_ONU-ID messages. Generate Loss_of_phy_layer_I 
            notification."
        ::={zxGponTraps 107}
                
    zxGponOltSFiRestore  NOTIFICATION-TYPE
        OBJECTS {
                ifIndex,zxGponOntDevMgmtName,zxGponOntDevMgmtTypeName,zxGponOntDevMgmtDescription
                }
        STATUS current
        DESCRIPTION 
            "SFi is Signal Fail of ONUi.When the upstream 
            BER of ONUi becomes <10?y+1, this state is cleared."
        ::={zxGponTraps 108}
        
    zxGponOltSDi       NOTIFICATION-TYPE
        OBJECTS {
                ifIndex,zxGponOntDevMgmtName,zxGponOntDevMgmtTypeName,zxGponOntDevMgmtDescription
                }
        STATUS current
        DESCRIPTION 
            "SDi is Signal Degraded of ONUi."
        ::={zxGponTraps 109}
        
    zxGponOltSDiRestore  NOTIFICATION-TYPE
        OBJECTS {
                ifIndex,zxGponOntDevMgmtName,zxGponOntDevMgmtTypeName,zxGponOntDevMgmtDescription
                }
        STATUS current
        DESCRIPTION 
        "SDi is Signal Degraded of ONUi. When the upstream 
        BER of ONUi becomes <10?X+1, this state is cleared."
        ::={zxGponTraps 110}
        
    zxGponOltLCDAi     NOTIFICATION-TYPE
        OBJECTS {
                ifIndex,zxGponOntDevMgmtName,zxGponOntDevMgmtTypeName,zxGponOntDevMgmtDescription
                }
        STATUS current
        DESCRIPTION 
            "LCDAi is Loss of ATM channel delineation. 
            Send 3 times Deactivate_ONU-ID messages Generate
            Loss_of_phy_layer_I notification."
        ::={zxGponTraps 111}
            
    zxGponOltLCDAiRestore  NOTIFICATION-TYPE
        OBJECTS {
                ifIndex,zxGponOntDevMgmtName,zxGponOntDevMgmtTypeName,zxGponOntDevMgmtDescription
                }
        STATUS current
        DESCRIPTION 
            "LCDAi is Loss of ATM channel delineation. When 
            cell delineation for ONUi is achieved."
        ::={zxGponTraps 112}
        
    zxGponOltLCDGi    NOTIFICATION-TYPE
        OBJECTS {
                ifIndex,zxGponOntDevMgmtName,zxGponOntDevMgmtTypeName,zxGponOntDevMgmtDescription
                }
        STATUS current
        DESCRIPTION 
            "LCDGi is Loss of GEM channel delineation. 
            Send 3 times Deactivate_ONU-ID messages Generate
            Loss_of_phy_layer_I notification."
        ::={zxGponTraps 113}
        
    zxGponOltLCDGiRestore    NOTIFICATION-TYPE
        OBJECTS {
                ifIndex,zxGponOntDevMgmtName,zxGponOntDevMgmtTypeName,zxGponOntDevMgmtDescription
                }
        STATUS current
        DESCRIPTION 
            "LCDGi is Loss of GEM channel delineation. When 
            GEM channel delineation for ONUi is achieved."
        ::={zxGponTraps 114}
              
    zxGponOltRDIi    NOTIFICATION-TYPE
        OBJECTS {
                ifIndex,zxGponOntDevMgmtName,zxGponOntDevMgmtTypeName,zxGponOntDevMgmtDescription
                }
        STATUS current
        DESCRIPTION 
            "RDIi is Remote Defect Indication of ONUi."
        ::={zxGponTraps 115}
            
    zxGponOltRDIiRestore   NOTIFICATION-TYPE
        OBJECTS {
                ifIndex,zxGponOntDevMgmtName,zxGponOntDevMgmtTypeName,zxGponOntDevMgmtDescription
                }
        STATUS current
        DESCRIPTION 
            "RDIi is Remote Defect Indication of ONUi. When the RDI field of 
            ONUi is de-asserted."
        ::={zxGponTraps 116}
             
    zxGponOltSUFi  NOTIFICATION-TYPE
        OBJECTS {
                ifIndex,zxGponOntDevMgmtName,zxGponOntDevMgmtTypeName,zxGponOntDevMgmtDescription
                }
        STATUS current
        DESCRIPTION 
            "SUFi is Start-up Failure of ONUi. Send 3 times Deactivate_ONU-ID messages."
        ::={zxGponTraps 117}
                
    zxGponOltSUFiRestore   NOTIFICATION-TYPE
        OBJECTS {
                ifIndex,zxGponOntDevMgmtName,zxGponOntDevMgmtTypeName,zxGponOntDevMgmtDescription
                }
        STATUS current
        DESCRIPTION 
            "SUFi is Start-up Failure of ONUi. The ONU is ranged successfully."
        ::={zxGponTraps 118}        
        
    zxGponOltDFi  NOTIFICATION-TYPE
        OBJECTS {
                ifIndex,zxGponOntDevMgmtName,zxGponOntDevMgmtTypeName,zxGponOntDevMgmtDescription
                }
        STATUS current
        DESCRIPTION 
            "DFi is Deactivate Failure of ONUi."
        ::={zxGponTraps 119}
                
    zxGponOltDFiRestore  NOTIFICATION-TYPE
        OBJECTS {
                ifIndex,zxGponOntDevMgmtName,zxGponOntDevMgmtTypeName,zxGponOntDevMgmtDescription
                }
        STATUS current
        DESCRIPTION 
            "DFi is Deactivate Failure of ONUi. Cancelled by the operator."
        ::={zxGponTraps 120}
                
    zxGponOltLOAi  NOTIFICATION-TYPE
        OBJECTS {
                ifIndex,zxGponOntDevMgmtName,zxGponOntDevMgmtTypeName,zxGponOntDevMgmtDescription
                }
        STATUS current
        DESCRIPTION 
            "LOAi is Loss of Acknowledge with ONUi. Send 3 times 
            Deactivate_ONU-ID messages. Generate Loss_of_phy_layer_I 
            notification."
        ::={zxGponTraps 121}
        
    zxGponOltLOAiRestore  NOTIFICATION-TYPE
        OBJECTS {
                ifIndex,zxGponOntDevMgmtName,zxGponOntDevMgmtTypeName,zxGponOntDevMgmtDescription
                }
        STATUS current
        DESCRIPTION 
            "LOAi is Loss of Acknowledge with ONUi. When the OLT 
            receives an acknowledgement from the ONU."
        ::={zxGponTraps 122}        
            
    zxGponOltDGi  NOTIFICATION-TYPE
        OBJECTS {
                ifIndex,zxGponOntDevMgmtName,zxGponOntDevMgmtTypeName,zxGponOntDevMgmtDescription
                }
        STATUS current
        DESCRIPTION 
            "DGi is Receive Dying-Gasp of ONUi. Ignore received 
            alarms from this ONU. Generate Loss_of_phy_layer_I 
            notification."
        ::={zxGponTraps 123}
                
    zxGponOltDGiRestore  NOTIFICATION-TYPE
        OBJECTS {
                ifIndex,zxGponOntDevMgmtName,zxGponOntDevMgmtTypeName,zxGponOntDevMgmtDescription
                }
        STATUS current
        DESCRIPTION 
            "DGi is Receive Dying-Gasp of ONUi. When the OLT receives
             a PLOAM message during ranging process."
        ::={zxGponTraps 124}
        
    zxGponOltLOAMi  NOTIFICATION-TYPE
        OBJECTS {
                ifIndex,zxGponOntDevMgmtName,zxGponOntDevMgmtTypeName,zxGponOntDevMgmtDescription
                }
        STATUS current
        DESCRIPTION 
            "LOAMi is Loss of PLOAM for ONUi. Send 3 times 
            Deactivate_ONU-ID messages. Generate Loss_of_phy_layer_I 
            notification."
        ::={zxGponTraps 125}
                
    zxGponOltLOAMiRestore  NOTIFICATION-TYPE
        OBJECTS {
                ifIndex,zxGponOntDevMgmtName,zxGponOntDevMgmtTypeName,zxGponOntDevMgmtDescription
                }
        STATUS current
        DESCRIPTION 
            "LOAMi is Loss of PLOAM for ONUi. When the OLT receives 
            a PLOAM message corresponding to its PLOAM flag in the 
            Operating state."
        ::={zxGponTraps 126}
                
    zxGponOltMEMi  NOTIFICATION-TYPE
        OBJECTS {
                ifIndex,zxGponOntDevMgmtName,zxGponOntDevMgmtTypeName,zxGponOntDevMgmtDescription
                }
        STATUS current
        DESCRIPTION 
            "MEMi is Message_Error Message from ONUi."
        ::={zxGponTraps 127}
                
    zxGponOltMEMiRestore  NOTIFICATION-TYPE
        OBJECTS {
                ifIndex,zxGponOntDevMgmtName,zxGponOntDevMgmtTypeName,zxGponOntDevMgmtDescription
                }
        STATUS current
        DESCRIPTION 
            "MEMi is Message_Error Message from ONUi. When 
            the operator is informed."
        ::={zxGponTraps 128}
                
    zxGponOltMISi  NOTIFICATION-TYPE
        OBJECTS {
                ifIndex,zxGponOntDevMgmtName,zxGponOntDevMgmtTypeName,zxGponOntDevMgmtDescription
                }
        STATUS current
        DESCRIPTION 
            "Misi is Link Mismatch of ONUi."
        ::={zxGponTraps 129}
                
    zxGponOltMISiRestore  NOTIFICATION-TYPE
        OBJECTS {
                ifIndex,zxGponOntDevMgmtName,zxGponOntDevMgmtTypeName,zxGponOntDevMgmtDescription
                }
        STATUS current
        DESCRIPTION 
            "MISi is Link Mismatch of ONUi. The OLT detects 
            that received PSTi and the transmitted PST are the same."
        ::={zxGponTraps 130}
                
    zxGponOltPEEi  NOTIFICATION-TYPE
        OBJECTS {
                ifIndex,zxGponOntDevMgmtName,zxGponOntDevMgmtTypeName,zxGponOntDevMgmtDescription
                }
        STATUS current
        DESCRIPTION 
            "PEEi is Physical Equipment Error of ONUi. 
            Generate Loss_of_physical_layer_I notification."
        ::={zxGponTraps 131}
              
    zxGponOltPEEiRestore  NOTIFICATION-TYPE
        OBJECTS {
                ifIndex,zxGponOntDevMgmtName,zxGponOntDevMgmtTypeName,zxGponOntDevMgmtDescription
                }
        STATUS current
        DESCRIPTION 
            "PEEi is Physical Equipment Error of ONUi. When 
            the OLT doesn't receive a PEE message from the ONUi in 3 s."
        ::={zxGponTraps 132}
                
    zxGponOntLOS    NOTIFICATION-TYPE
        OBJECTS {
                ifIndex
                }
        STATUS current
        DESCRIPTION 
            "LOS is Loss Of Signal. Switch off laser. Generate 
            Loss_of_phy_layer notification. Move to Initial- State."
        ::={zxGponTraps 133}
                
    zxGponOntLOSRestore    NOTIFICATION-TYPE
        OBJECTS {
                ifIndex
                }
        STATUS current
        DESCRIPTION 
            "LOS is Loss Of Signal. Valid optical signal."
        ::={zxGponTraps 134}
                
    zxGponOntLOF    NOTIFICATION-TYPE
        OBJECTS {
                ifIndex
                }
        STATUS current
        DESCRIPTION 
            "LOF is Loss of Frame. Switch off laser. Generate 
            Loss_of_phy_layer notification. Move to Initial- State."
        ::={zxGponTraps 135}
                
    zxGponOntLOFRestore    NOTIFICATION-TYPE
        OBJECTS {
                ifIndex
                }
        STATUS current
        DESCRIPTION 
            "LOF is Loss of Frame. When 2 consecutive frames 
            have correct PSYNC."
        ::={zxGponTraps 136}
                
    zxGponOntTF    NOTIFICATION-TYPE
        OBJECTS {
                ifIndex
                }
        STATUS current
        DESCRIPTION 
            "TF is Transmitter Failure."
        ::={zxGponTraps 137}
                
    zxGponOntTFRestore    NOTIFICATION-TYPE
        OBJECTS {
                ifIndex
                }
        STATUS current
        DESCRIPTION 
            "TF is Transmitter Failure."
        ::={zxGponTraps 138}
                
    zxGponOntSF    NOTIFICATION-TYPE
        OBJECTS {
                ifIndex
                }
        STATUS current
        DESCRIPTION 
            "SF is Signal Failed."
        ::={zxGponTraps 139}
                
    zxGponOntSFRestore    NOTIFICATION-TYPE
        OBJECTS {
                ifIndex
                }
        STATUS current
        DESCRIPTION 
            "SF is Signal Failed. Set inactive when 
            the downstream BER is <10?(y+1)."
        ::={zxGponTraps 140}
                
    zxGponOntSD    NOTIFICATION-TYPE
        OBJECTS {
                ifIndex
                }
        STATUS current
        DESCRIPTION 
            "SD is Signal Degraded."
        ::={zxGponTraps 141}
                
    zxGponOntSDRestore    NOTIFICATION-TYPE
        OBJECTS {
                ifIndex
                }
        STATUS current
        DESCRIPTION 
            "SD is Signal Degraded. Set inactive 
            when the downstream BER is <10?(x+1)."
        ::={zxGponTraps 142}
                
    zxGponOntLCDA    NOTIFICATION-TYPE
        OBJECTS {
                ifIndex
                }
        STATUS current
        DESCRIPTION 
            "LCDA is Loss of ATM channel delineation. 
            Switch off laser. Generate Loss_of_phy_layer 
            notification."
        ::={zxGponTraps 143}
                
    zxGponOntLCDARestore    NOTIFICATION-TYPE
        OBJECTS {
                ifIndex
                }
        STATUS current
        DESCRIPTION 
            "LCDA is Loss of ATM channel delineation. 
        When cell delineation is achieved."
        ::={zxGponTraps 144}
              
    zxGponOntLCDG    NOTIFICATION-TYPE
        OBJECTS {
                ifIndex
                }
        STATUS current
        DESCRIPTION 
            "LCDG is Loss of GEM channel delineation. 
        Switch off laser. Generate Loss_of_phy_layer 
        notification."
        ::={zxGponTraps 145}
                
    zxGponOntLCDGRestore    NOTIFICATION-TYPE
        OBJECTS {
                ifIndex
                }
        STATUS current
        DESCRIPTION 
            "LCDG is Loss of GEM channel delineation. 
        When GEM delineation is achieved."
        ::={zxGponTraps 146}
                
    zxGponOntRDI    NOTIFICATION-TYPE
        OBJECTS {
                ifIndex
                }
        STATUS current
        DESCRIPTION 
            "RDI is Remote Defect Indication in ONU. Set RDI status bit in PLOu."
        ::={zxGponTraps 147}
                
    zxGponOntRDIRestore    NOTIFICATION-TYPE
        OBJECTS {
                ifIndex
                }
        STATUS current
        DESCRIPTION 
            "RDI is Remote Defect Indication in ONU. When the OLT transmission defect is resolved."
        ::={zxGponTraps 148}           
        
    zxGponOntSUF    NOTIFICATION-TYPE
        OBJECTS {
                ifIndex
                }
        STATUS current
        DESCRIPTION 
            "SUF is Start-up Failure."
        ::={zxGponTraps 149}
                
    zxGponOntSUFRestore    NOTIFICATION-TYPE
        OBJECTS {
                ifIndex
                }
        STATUS current
        DESCRIPTION 
            "SUF is Start-up Failure. When ranging is successful."
        ::={zxGponTraps 150}
                
    zxGponOntMEM    NOTIFICATION-TYPE
        OBJECTS {
                ifIndex
                }
        STATUS current
        DESCRIPTION 
            "MEM is Message Error Message."
        ::={zxGponTraps 151}
                
    zxGponOntMEMRestore    NOTIFICATION-TYPE
        OBJECTS {
                ifIndex
                }
        STATUS current
        DESCRIPTION 
            "MEM is Message Error Message."
        ::={zxGponTraps 152}
               
    zxGponOntDACT    NOTIFICATION-TYPE
        OBJECTS {
                ifIndex
                }
        STATUS current
        DESCRIPTION 
            "DACT is Deactivate ONU-ID. Switch off the 
            laser and go to Standby-State. Generate 
            Loss_of_phy_layer notification."
        ::={zxGponTraps 153}
                
    zxGponOntDACTRestore    NOTIFICATION-TYPE
        OBJECTS {
                ifIndex
                }
        STATUS current
        DESCRIPTION 
            "DACT is Deactivate ONU-ID.Reception of Upstream_overhead message."
        ::={zxGponTraps 154}
                
    zxGponOntDIS    NOTIFICATION-TYPE
        OBJECTS {
                ifIndex
                }
        STATUS current
        DESCRIPTION 
            "DIS is Disabled ONU. Switch off laser. Go to 
            Emergency-Stop State Generate Loss_of_phy_layer 
            notification."
        ::={zxGponTraps 155}
        
    zxGponOntDISRestore    NOTIFICATION-TYPE
        OBJECTS {
                ifIndex
                }
        STATUS current
        DESCRIPTION 
            "DIS is Disabled ONU. When the ONU receives a Disable_Serial_Number
            message with Enable flag=0x0F or when it receives a Disable_Serial_Number 
            message with it's own serial number and the enable flag=0x00."
        ::={zxGponTraps 156}
                
    zxGponOntMIS    NOTIFICATION-TYPE
        OBJECTS {
                ifIndex
                }
        STATUS current
        DESCRIPTION 
            "MIS is Link Mismatching."
        ::={zxGponTraps 157}
        
    zxGponOntMISRestore    NOTIFICATION-TYPE
        OBJECTS {
                ifIndex
                }
        STATUS current
        DESCRIPTION 
            "MIS is Link Mismatching. The ONU detects that the received 
            PST and transmitted PST are the same."
        ::={zxGponTraps 158}
                
    zxGponOntPee    NOTIFICATION-TYPE
        OBJECTS {
                ifIndex
                }
        STATUS current
        DESCRIPTION 
            "Pee is Physical Equipment Error. Generate Loss_of_physical_layer notification."
        ::={zxGponTraps 159}
                
    zxGponOntPeeRestore    NOTIFICATION-TYPE
        OBJECTS {
                ifIndex
                }
        STATUS current
        DESCRIPTION 
            "Pee is Physical Equipment Error. When the ONU doesn't receive a PEE message in 3 s."
        ::={zxGponTraps 160}
        
    zxGponOltLOS    NOTIFICATION-TYPE
        OBJECTS {
                ifIndex
                }
        STATUS current
        DESCRIPTION 
            "LOS is Loss Of Signal. Switch off laser. Generate 
            Loss_of_phy_layer notification. Move to Initial- State."
        ::={zxGponTraps 161}
        
    zxGponOltLOSRestore    NOTIFICATION-TYPE
        OBJECTS {
                ifIndex
                }
        STATUS current
        DESCRIPTION 
            "LOS is Loss Of Signal. Valid optical signal."
        ::={zxGponTraps 162}
        
    zxGponOltLOF    NOTIFICATION-TYPE
        OBJECTS {
                ifIndex
                }
        STATUS current
        DESCRIPTION 
            "LOF is Loss of Frame. Switch off laser. Generate 
            Loss_of_phy_layer notification. Move to Initial- State."
        ::={zxGponTraps 163}
        
    zxGponOltLOFRestore    NOTIFICATION-TYPE
        OBJECTS {
                ifIndex
                }
        STATUS current
        DESCRIPTION 
            "LOF is Loss of Frame. When 2 consecutive frames"
        ::={zxGponTraps 164}
                
    zxGponOntRegister  NOTIFICATION-TYPE
        OBJECTS {
                ifIndex 
                }
        STATUS current
        DESCRIPTION 
            " "
        ::={zxGponTraps 165}
                
    zxGponOntUnregister  NOTIFICATION-TYPE
        OBJECTS {
                ifIndex
                }
        STATUS current
        DESCRIPTION 
            ""
        ::={zxGponTraps 166}
            
    zxGponOntAuthPass  NOTIFICATION-TYPE
        OBJECTS {
                ifIndex
                }
        STATUS current
        DESCRIPTION 
            ""
        ::={zxGponTraps 167}
        
    zxGponOntAuthFailed  NOTIFICATION-TYPE
        OBJECTS {
                ifIndex
                }
        STATUS current
        DESCRIPTION 
            ""
        ::={zxGponTraps 168} 

    zxPonFanOffLine    NOTIFICATION-TYPE
        OBJECTS {
                ifIndex
                }
        STATUS current
        DESCRIPTION 
            ""
        ::={zxGponTraps 171}
        
    zxPonFanOffLineRestore    NOTIFICATION-TYPE
        OBJECTS {
                ifIndex
                }
        STATUS current
        DESCRIPTION 
            ""
        ::={zxGponTraps 172}

    zxGponLinkOntDyingGasp    NOTIFICATION-TYPE
        OBJECTS {
                ifIndex
                }
        STATUS current
        DESCRIPTION 
            ""
        ::={zxGponTraps 173}
        
    zxGponLinkOntDyingGaspRestore    NOTIFICATION-TYPE
        OBJECTS {
                ifIndex
                }
        STATUS current
        DESCRIPTION 
            ""
        ::={zxGponTraps 174}

    zxGponOltRxPowerAlarmi    NOTIFICATION-TYPE
        OBJECTS {
                ifIndex,zxGponOltRxPowerAlarmiReason,zxGponOntDevMgmtName,zxGponOntDevMgmtTypeName,zxGponOntDevMgmtDescription
                }
        STATUS current
        DESCRIPTION 
            ""
        ::={zxGponTraps 175}
        
    zxGponOltRxPowerAlarmiRestore    NOTIFICATION-TYPE
        OBJECTS {
                ifIndex,zxGponOltRxPowerAlarmiReason,zxGponOntDevMgmtName,zxGponOntDevMgmtTypeName,zxGponOntDevMgmtDescription
                }
        STATUS current
        DESCRIPTION 
            ""
        ::={zxGponTraps 176}

    zxGponOltRxPowerAbnormalInformi    NOTIFICATION-TYPE
        OBJECTS {
                ifIndex,zxGponOltRxPowerAbnormalInformiReason,zxGponOntDevMgmtName,zxGponOntDevMgmtTypeName,zxGponOntDevMgmtDescription
                }
        STATUS current
        DESCRIPTION 
            ""
        ::={zxGponTraps 177}
        
    zxGponOltRxPowerNormalInformi    NOTIFICATION-TYPE
        OBJECTS {
                ifIndex,zxGponOntDevMgmtName,zxGponOntDevMgmtTypeName,zxGponOntDevMgmtName,zxGponOntDevMgmtTypeName,zxGponOntDevMgmtDescription
                }
        STATUS current
        DESCRIPTION 
            ""
        ::={zxGponTraps 178}

    zxGponOltTxPowerAlarm    NOTIFICATION-TYPE
        OBJECTS {
                ifIndex,zxGponOltTxPowerAlarmReason
                }
        STATUS current
        DESCRIPTION 
            ""
        ::={zxGponTraps 179}
        
    zxGponOltTxPowerAlarmRestore    NOTIFICATION-TYPE
        OBJECTS {
                ifIndex,zxGponOltTxPowerAlarmReason
                }
        STATUS current
        DESCRIPTION 
            ""
        ::={zxGponTraps 180}
    
    zxGponOltTxPowerAbnormalInform    NOTIFICATION-TYPE
        OBJECTS {
                ifIndex,zxGponOltTxPowerAbnormalInformReason
                }
        STATUS current
        DESCRIPTION 
            ""
        ::={zxGponTraps 181}
        
    zxGponOltTxPowerNormalInform    NOTIFICATION-TYPE
        OBJECTS {
                ifIndex,zxGponOntDevMgmtName,zxGponOntDevMgmtTypeName,zxGponOntDevMgmtDescription
                }
        STATUS current
        DESCRIPTION 
            ""
        ::={zxGponTraps 182}

    zxGponOltFakedSN    NOTIFICATION-TYPE
        OBJECTS {
                ifIndex,zxGponTrapEventString,zxGponOntDevMgmtName,zxGponOntDevMgmtTypeName,zxGponOntDevMgmtDescription
                }
        STATUS current
        DESCRIPTION 
            "OLT detects a faked SN event."
        ::={zxGponTraps 183}
        
    zxGponOnuConstantOptical    NOTIFICATION-TYPE
        OBJECTS {
                ifIndex,zxGponOntDevMgmtName,zxGponOntDevMgmtTypeName,zxGponOntDevMgmtDescription
                }
        STATUS current
        DESCRIPTION 
            "It  indicate ONU constant optical."
        ::={zxGponTraps 184}
        
    zxGponOnuConstantOpticalRestore    NOTIFICATION-TYPE
        OBJECTS {
                ifIndex,zxGponOntDevMgmtName,zxGponOntDevMgmtTypeName,zxGponOntDevMgmtDescription
                }
        STATUS current
        DESCRIPTION 
            "It  indicate ONU constant optical restore."
        ::={zxGponTraps 185}
        
    zxGponOnuFiberBending    NOTIFICATION-TYPE
        OBJECTS {
                ifIndex,zxGponOntDevMgmtName,zxGponOntDevMgmtTypeName,zxGponOntDevMgmtDescription
                }
        STATUS current
        DESCRIPTION 
            "It  indicate ONU constant optical."
        ::={zxGponTraps 186}
        
    zxGponOnuFiberBendingRestore    NOTIFICATION-TYPE
        OBJECTS {
                ifIndex,zxGponOntDevMgmtName,zxGponOntDevMgmtTypeName,zxGponOntDevMgmtDescription
                }
        STATUS current
        DESCRIPTION 
            "It  indicate ONU constant optical restore."
        ::={zxGponTraps 187}        

    zxGponOnuOpticalTransceiverLos  NOTIFICATION-TYPE
        OBJECTS {
                ifIndex,zxGponOntDevMgmtName,zxGponOntDevMgmtTypeName,zxGponOntDevMgmtDescription
                }
        STATUS current
        DESCRIPTION 
            "It  indicate ONU constant optical."
        ::={zxGponTraps 188}
        
    zxGponOnuOpticalTransceiverLosRestore    NOTIFICATION-TYPE
        OBJECTS {
                ifIndex,zxGponOntDevMgmtName,zxGponOntDevMgmtTypeName,zxGponOntDevMgmtDescription
                }
        STATUS current
        DESCRIPTION 
            "It  indicate ONU constant optical restore."
        ::={zxGponTraps 189}
        
    zxGponMacSpoofing    NOTIFICATION-TYPE
        OBJECTS {
                ifIndex,zxGponSpoofingPort,zxGponSpoofingMac,zxGponSpoofingVlan,zxGponSpoofingConflictPort,zxGponOntDevMgmtName,zxGponOntDevMgmtTypeName,zxGponOntDevMgmtDescription
                }
        STATUS current
        DESCRIPTION 
            "It  indicate Gpon port mac spoolfing."
        ::={zxGponTraps 190}
        
    zxGponUnauthOnuOnline  NOTIFICATION-TYPE
        OBJECTS {
                ifIndex,zxGponOntDevMgmtTypeName,zxGponUnCfgSnOntSN,zxGponUnCfgSnOntRID,zxGponUnCfgSnOntPsw,zxGponUnCfgSnOntRtd
                }
        STATUS current
        DESCRIPTION 
            "It  indicate ONU constant optical."
        ::={zxGponTraps 191}
 
     zxGponOltTF    NOTIFICATION-TYPE
        OBJECTS {
                ifIndex
                }
        STATUS current
        DESCRIPTION 
            "TF is Transmitter Failure."
        ::={zxGponTraps 192}
                
    zxGponOltTFRestore    NOTIFICATION-TYPE
        OBJECTS {
                ifIndex
                }
        STATUS current
        DESCRIPTION 
            "TF is Transmitter Failure."
        ::={zxGponTraps 193}
    zxGponOltFakedPassword    NOTIFICATION-TYPE
        OBJECTS {
                ifIndex,zxGponTrapEventString
                }
        STATUS current
        DESCRIPTION 
            "OLT detects a faked passwrod event."
        ::={zxGponTraps 194}
END

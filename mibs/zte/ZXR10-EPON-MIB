-- *****************************************************************
-- ZTE EPON MIB
--
-- 05-30-2008 ,liuliang
--
-- Copyright(c) 2008 by ZTE Corporation
-- All rights reserved.
-- *****************************************************************  

ZXR10-EPON-MIB DEFINITIONS ::= BEGIN
                
   IMPORTS                           
       RowStatus,                   	  
       DisplayString,MacAddress      FROM SNMPv2-TC   
       OBJECT-TYPE,
       Integer32,
       enterprises,
       Counter64		          FROM SNMPv2-SMI
       ifIndex                       FROM RFC1213-MIB
       IpAddress                     FROM RFC1155-SMI;
       --zxr10EponObjects              FROM ZXR10-SMI; 
       
      --         Counter, TimeTicks     FROM RFC1155-SMI
      -- IpAddress,DisplayString, mib-2   FROM RFC1213-MIB
      --            OBJECT-TYPE            FROM RFC-1212     
       zte                          OBJECT IDENTIFIER ::= { enterprises 3902 }
       zxr10                        OBJECT IDENTIFIER ::= { zte 3}     
       zxr10EponObjects             OBJECT IDENTIFIER ::= { zxr10 309}   
      
       zxr10EponLocal               OBJECT IDENTIFIER ::= { zxr10EponObjects 1}
       zxr10EponRemoteOnu           OBJECT IDENTIFIER ::= { zxr10EponObjects 2}
       zxr10EponTopologyCollect     OBJECT IDENTIFIER ::= { zxr10EponObjects 3}

      
------------------------------------------------------------------------------
--  zxr10EponObjects                
------------------------------------------------------------------------------  
------------------------------------------------------------------------------
--  Local manage
------------------------------------------------------------------------------ 
    
    zxr10EponOnuAuthTable OBJECT-TYPE 
            SYNTAX         SEQUENCE OF Zxr10EponOnuAuthEntry
            MAX-ACCESS     not-accessible 
            STATUS         current 
            DESCRIPTION 
                ""
            ::= {zxr10EponLocal 1}  
            
   zxr10EponOnuAuthEntry OBJECT-TYPE
            SYNTAX         Zxr10EponOnuAuthEntry
            MAX-ACCESS     not-accessible 
            STATUS         current 
            DESCRIPTION 
                ""
            INDEX    { eponSlotId } 
            ::= { zxr10EponOnuAuthTable 1}        
            
    Zxr10EponOnuAuthEntry ::=
           SEQUENCE { 
        		eponSlotId              Integer32,
        		onuSoftwareAuth         INTEGER,
        		onuHardwareSwitch       INTEGER,
        		onuAutoAuthSwtich       INTEGER
    			}  
     
    eponSlotId  OBJECT-TYPE
        	SYNTAX      Integer32(1..12)
        	MAX-ACCESS  read-only
       		STATUS      current
        	DESCRIPTION
           	 	"index"
        	::= { zxr10EponOnuAuthEntry 1}
    
    onuSoftwareAuth OBJECT-TYPE
        	SYNTAX      INTEGER{sn(0),mac(1)}
        	MAX-ACCESS  read-write
       		STATUS      current
        	DESCRIPTION
           	 	""
        	::= { zxr10EponOnuAuthEntry 2}
    
    onuHardwareSwitch  OBJECT-TYPE
        	SYNTAX      INTEGER{disable(0),enable(1)}
        	MAX-ACCESS  read-write
       		STATUS      current
        	DESCRIPTION
           	 	""
        	::= { zxr10EponOnuAuthEntry 3}
        	
    onuAutoAuthSwtich OBJECT-TYPE
        	SYNTAX      INTEGER{disable(0),enable(1)}
        	MAX-ACCESS  read-write
       		STATUS      current
        	DESCRIPTION
           	 	""
        	::= { zxr10EponOnuAuthEntry 4}   	
    
    zxr10EponOltOptiInfoTable OBJECT-TYPE 
            SYNTAX         SEQUENCE OF Zxr10EponOltOptiInfoEntry
            MAX-ACCESS     not-accessible 
            STATUS         current 
            DESCRIPTION 
                "" 
            ::= {zxr10EponLocal 2}

    zxr10EponOltOptiInfoEntry OBJECT-TYPE
            SYNTAX         Zxr10EponOltOptiInfoEntry
            MAX-ACCESS     not-accessible 
            STATUS         current 
            DESCRIPTION 
                "the index,for example:epon-olt_1/1"
            INDEX    { ifIndex } 
            ::= { zxr10EponOltOptiInfoTable 1}
            
    Zxr10EponOltOptiInfoEntry::= 
        SEQUENCE { 
        		eponOltPortName         	 DisplayString,      
     			optiInfoSFPID           	  Integer32,
    			optiInfoVendor               DisplayString,
    			optiInfoWavelength      	  Integer32,
    			optiInfoVendorPN        	  DisplayString,
    			oltPortSupportedLlidNum      Integer32,
    			oltPortSoftwareVersion       DisplayString,
    			oltPortAGCLockTime       	 Integer32,
   			    oltPortCDRLockTime           Integer32
    			}
        
    eponOltPortName  OBJECT-TYPE
            SYNTAX         DisplayString
            MAX-ACCESS     read-only 
            STATUS         current 
            DESCRIPTION 
                ""              
            ::= {zxr10EponOltOptiInfoEntry 1}
            				
    optiInfoSFPID OBJECT-TYPE
            SYNTAX         Integer32
            MAX-ACCESS     read-only 
            STATUS         current 
            DESCRIPTION 
                ""              
            ::= {zxr10EponOltOptiInfoEntry 2}				
    	
    optiInfoVendor  OBJECT-TYPE
            SYNTAX         DisplayString
            MAX-ACCESS     read-only 
            STATUS         current 
            DESCRIPTION 
                ""              
            ::= {zxr10EponOltOptiInfoEntry 3} 	
    	
  	optiInfoWavelength  OBJECT-TYPE
            SYNTAX         Integer32
            MAX-ACCESS     read-only 
            STATUS         current 
            DESCRIPTION 
                ""              
            ::= {zxr10EponOltOptiInfoEntry 4} 	
  
    optiInfoVendorPN  OBJECT-TYPE
            SYNTAX         DisplayString
            MAX-ACCESS     read-only 
            STATUS         current 
            DESCRIPTION 
                ""              
            ::= {zxr10EponOltOptiInfoEntry 5}
            
    oltPortSupportedLlidNum OBJECT-TYPE      	    
            SYNTAX        Integer32 
            MAX-ACCESS    read-only
            STATUS        current 
            DESCRIPTION 
				""
			::= {zxr10EponOltOptiInfoEntry 6}				
    				
    oltPortSoftwareVersion 	OBJECT-TYPE      	    
            SYNTAX        DisplayString 
            MAX-ACCESS    read-only
            STATUS        current 
            DESCRIPTION 
				""
			::= {zxr10EponOltOptiInfoEntry 7}			
    			
     oltPortAGCLockTime  OBJECT-TYPE      	    
            SYNTAX        Integer32            
            MAX-ACCESS    read-only
            STATUS        current 
            DESCRIPTION 
				""
			::= {zxr10EponOltOptiInfoEntry 8}
    
    oltPortCDRLockTime  OBJECT-TYPE      	    
            SYNTAX        Integer32            
            MAX-ACCESS    read-only
            STATUS        current 
            DESCRIPTION 
				""
			::= {zxr10EponOltOptiInfoEntry 9}
            
    zxr10EponOltEncryptTable OBJECT-TYPE 
            SYNTAX         SEQUENCE OF Zxr10EponOltEncryptEntry
            MAX-ACCESS     not-accessible 
            STATUS         current 
            DESCRIPTION 
                "configure OLT encryption arithmetic"
            ::= {zxr10EponLocal 3}   
     
    zxr10EponOltEncryptEntry OBJECT-TYPE
            SYNTAX         Zxr10EponOltEncryptEntry
            MAX-ACCESS     not-accessible 
            STATUS         current 
            DESCRIPTION 
                "the index,for example:epon-olt_1/1"
            INDEX    {ifIndex } 
            ::= { zxr10EponOltEncryptTable 1}   
            
   	Zxr10EponOltEncryptEntry::= 
    	    SEQUENCE {   	    		 
    	            oltEncryptAlgorithm    	INTEGER,
    	            oltKeyUpdatePeriod      Integer32,    
    	            oltChurningTimer        Integer32,
    	            oltMaxRtt               Integer32,   		     	
    		     	oltLaserSwitch          INTEGER,
    		        opticsMeasureLow        Integer32,
    		        opticsMeasureHigh		Integer32,
    		        packetLimitType         DisplayString,		        
    		        packetLimitSwitch       INTEGER,
    		        protocolProtectMode     DisplayString ,
    		        protocolProtectSwitch   INTEGER,
    		        optiDiagInterval        Integer32,			
    		        oltEncryptRowStatus     RowStatus,
                     oltPortDBAType               INTEGER
            	    }
     
    oltEncryptAlgorithm  OBJECT-TYPE
	       	SYNTAX        INTEGER{triple-churning(1),aes(2)}
            MAX-ACCESS    read-write
            STATUS        current 
            DESCRIPTION 
				""
			::= {zxr10EponOltEncryptEntry 1}
     
    oltKeyUpdatePeriod  OBJECT-TYPE
	       	SYNTAX        Integer32(1..255)
            MAX-ACCESS    read-write
            STATUS        current 
            DESCRIPTION 
				"the default vlaue is 10"
			::= {zxr10EponOltEncryptEntry 2}
     
    oltChurningTimer OBJECT-TYPE
	       	SYNTAX        Integer32(1..255)
            MAX-ACCESS    read-write
            STATUS        current 
            DESCRIPTION 
				""
			::= {zxr10EponOltEncryptEntry 3}
			
	oltMaxRtt  OBJECT-TYPE 
            SYNTAX         Integer32(1000..25000)
            MAX-ACCESS     read-write 
            STATUS         current 
            DESCRIPTION 
                ""
            ::= {zxr10EponOltEncryptEntry 4} 
			
	oltLaserSwitch 	OBJECT-TYPE
	       	SYNTAX        INTEGER{enable(0),disable(1)}
            MAX-ACCESS    read-write
            STATUS        current 
            DESCRIPTION 
				""
			::= {zxr10EponOltEncryptEntry 5}
			
	opticsMeasureLow OBJECT-TYPE
	       	SYNTAX        Integer32
            MAX-ACCESS    read-write
            STATUS        current 
            DESCRIPTION 
				""
			::= {zxr10EponOltEncryptEntry 6}
			
	opticsMeasureHigh OBJECT-TYPE
	       	SYNTAX        Integer32
            MAX-ACCESS    read-write
            STATUS        current 
            DESCRIPTION 
				""
			::= {zxr10EponOltEncryptEntry 7}
			
	packetLimitType OBJECT-TYPE
	       	SYNTAX       DisplayString
            MAX-ACCESS    read-write
            STATUS        current 
            DESCRIPTION 
				""
			::= {zxr10EponOltEncryptEntry 8}									
    
    packetLimitSwitch OBJECT-TYPE
	       	SYNTAX        INTEGER{disable(0),enable(1)}
            MAX-ACCESS    read-write
            STATUS        current 
            DESCRIPTION 
				""
			::= {zxr10EponOltEncryptEntry 9} 
			
	protocolProtectMode OBJECT-TYPE
	       	SYNTAX        DisplayString 
            MAX-ACCESS    read-write
            STATUS        current 
            DESCRIPTION 
				""
			::= {zxr10EponOltEncryptEntry 10}
			
	protocolProtectSwitch OBJECT-TYPE
	       	SYNTAX        INTEGER{disable(0),enable(1)}
            MAX-ACCESS    read-write
            STATUS        current 
            DESCRIPTION 
				""
			::= {zxr10EponOltEncryptEntry 11}
			
	optiDiagInterval OBJECT-TYPE
	       	SYNTAX        Integer32
            MAX-ACCESS    read-write
            STATUS        current 
            DESCRIPTION 
				""
			::= {zxr10EponOltEncryptEntry 12}						
     
    oltEncryptRowStatus  OBJECT-TYPE
	       	SYNTAX        RowStatus
            MAX-ACCESS    read-write
            STATUS        current 
            DESCRIPTION 
				""
			::= {zxr10EponOltEncryptEntry 13}	             	     
    oltPortDBAType  OBJECT-TYPE      	    
            SYNTAX        INTEGER{
            			  	archimedes(0),
            			  	thales(1),
            			  	plato(2)
            			  } 
            MAX-ACCESS    read-write
            STATUS        current 
            DESCRIPTION 
				""
			::= {zxr10EponOltEncryptEntry 14}	  
            	    
    zxr10EponOnuAuthInfoTable OBJECT-TYPE 
            SYNTAX         SEQUENCE OF Zxr10EponOnuAuthInfoEntry
            MAX-ACCESS     not-accessible 
            STATUS         current 
            DESCRIPTION 
                ""
            ::= {zxr10EponLocal 4}   
            
    zxr10EponOnuAuthInfoEntry OBJECT-TYPE
            SYNTAX         Zxr10EponOnuAuthInfoEntry
            MAX-ACCESS     not-accessible 
            STATUS         current 
            DESCRIPTION 
                "ifIndex,for example epon-olt_1/1;onuId is the number of yhe onu"
            INDEX    { ifIndex,onuId} 
            ::= { zxr10EponOnuAuthInfoTable 1}     
            
    Zxr10EponOnuAuthInfoEntry::=   
    		SEQUENCE { 
    				onuId                     Integer32,
    				onuAuthState     		  INTEGER, 
    				onuType          		  INTEGER, 
    				onuAuthPCBVer    		  DisplayString, 
    				onuAuthSoftVer   		  DisplayString, 
					onuEEPROMVer    		  DisplayString, 
					onuHostType      		  DisplayString, 
					onuOpticalLen   		  Integer32,
					onuHardVer				  DisplayString,
					onuRTT                    Integer32,
    	        	onuMacPortName        	  DisplayString,      
     				onuBindTypeName           DisplayString,
    				onuBindMacAddr            MacAddress, 
    				onuBindSN                 Integer32,
    				onuMacMaxNum       	      Integer32,
    				onuBindRowStatus          RowStatus
					}
    
    onuId   OBJECT-TYPE      	    
            SYNTAX        Integer32(1..32)       	    
            MAX-ACCESS    read-only
            STATUS        current 
            DESCRIPTION 
				""
			::= {zxr10EponOnuAuthInfoEntry 1}
    	 
    onuAuthState OBJECT-TYPE      	    
            SYNTAX        INTEGER{
            			  offline(0),
            			  up(1),
            			  down(2)            			  
            			  }       	    
            MAX-ACCESS    read-only
            STATUS        current 
            DESCRIPTION 
				""
			::= {zxr10EponOnuAuthInfoEntry 2}				
    				
    onuType OBJECT-TYPE      	    
            SYNTAX        INTEGER{mac(0),sn(1)}
            MAX-ACCESS    read-only
            STATUS        current 
            DESCRIPTION 
				""
			::= {zxr10EponOnuAuthInfoEntry 3}				
    				
    onuAuthPCBVer OBJECT-TYPE      	    
            SYNTAX        DisplayString 
            MAX-ACCESS    read-only
            STATUS        current 
            DESCRIPTION 
				""
			::= {zxr10EponOnuAuthInfoEntry 4}				
    				
    onuAuthSoftVer 	OBJECT-TYPE      	    
            SYNTAX        DisplayString
            MAX-ACCESS    read-only
            STATUS        current 
            DESCRIPTION 
				""
			::= {zxr10EponOnuAuthInfoEntry 5}			
    				
    onuEEPROMVer  OBJECT-TYPE      	    
            SYNTAX        DisplayString 
            MAX-ACCESS    read-only
            STATUS        current 
            DESCRIPTION 
				""
			::= {zxr10EponOnuAuthInfoEntry 6}
    
    onuHostType  OBJECT-TYPE      	    
            SYNTAX        DisplayString 
            MAX-ACCESS    read-only
            STATUS        current 
            DESCRIPTION 
				""
			::= {zxr10EponOnuAuthInfoEntry 7} 		
			
	onuOpticalLen OBJECT-TYPE      	    
            SYNTAX        Integer32 
            MAX-ACCESS    read-only
            STATUS        current 
            DESCRIPTION 
				""
			::= {zxr10EponOnuAuthInfoEntry 8}
			
	onuHardVer  OBJECT-TYPE      	    
            SYNTAX        DisplayString 
            MAX-ACCESS    read-only
            STATUS        current 
            DESCRIPTION 
				""
			::= {zxr10EponOnuAuthInfoEntry 9}
			
	onuRTT 	OBJECT-TYPE      	    
            SYNTAX        Integer32
            MAX-ACCESS    read-only
            STATUS        current 
            DESCRIPTION 
				""
			::= {zxr10EponOnuAuthInfoEntry 10}
			
	onuMacPortName   OBJECT-TYPE
            SYNTAX        DisplayString
            MAX-ACCESS    read-only
            STATUS        current 
            DESCRIPTION 
				""
			::= {zxr10EponOnuAuthInfoEntry 11}
						         
    onuBindTypeName OBJECT-TYPE 
            SYNTAX         DisplayString
            MAX-ACCESS     read-write 
            STATUS         current 
            DESCRIPTION 
                ""
            ::= {zxr10EponOnuAuthInfoEntry 12}        
            
    onuBindMacAddr  OBJECT-TYPE 
            SYNTAX         MacAddress
            MAX-ACCESS     read-write 
            STATUS         current 
            DESCRIPTION 
                "mpcp protocol"
            ::= {zxr10EponOnuAuthInfoEntry 13}
            
    onuBindSN    OBJECT-TYPE 
            SYNTAX         Integer32
            MAX-ACCESS     read-write 
            STATUS         current 
            DESCRIPTION 
                ""
            ::= {zxr10EponOnuAuthInfoEntry 14}     
            
    onuMacMaxNum  OBJECT-TYPE 
            SYNTAX         Integer32(0..8192)
            MAX-ACCESS     read-write 
            STATUS         current 
            DESCRIPTION 
                "default value is 256"
            ::= {zxr10EponOnuAuthInfoEntry 15}        
               
    onuBindRowStatus  OBJECT-TYPE 
            SYNTAX         RowStatus
            MAX-ACCESS     read-write 
            STATUS         current 
            DESCRIPTION 
                ""
            ::= {zxr10EponOnuAuthInfoEntry 16}									
							
   	zxr10EponOltPortStatTable OBJECT-TYPE 
            SYNTAX         SEQUENCE OF Zxr10EponOltPortStatEntry
            MAX-ACCESS     not-accessible 
            STATUS         current 
            DESCRIPTION 
                ""
            ::= {zxr10EponLocal 5} 
            
    zxr10EponOltPortStatEntry OBJECT-TYPE
            SYNTAX         Zxr10EponOltPortStatEntry
            MAX-ACCESS     not-accessible 
            STATUS         current 
            DESCRIPTION 
                "index,for example:epon-olt_1/1"   
            INDEX    {ifIndex }
            ::= {zxr10EponOltPortStatTable 1}
    
    Zxr10EponOltPortStatEntry ::=
    		SEQUENCE { 		
    				oltStatisBer                 Counter64,
    				oltStatisFer                 Counter64,
					oltStatisPortBer             Counter64,
					oltStatisInPkts              Counter64,  
					oltStatisInOctes             Counter64,
					oltStatisInUniPkts           Counter64, 
					oltStatisInMultiPkts         Counter64,
					oltStatisInBroadPkts         Counter64,  
					oltStatisOutPkts             Counter64,
					oltStatisOutOctes            Counter64,  
					oltStatisOutUniPkts          Counter64,
					oltStatisOutMultiPkts        Counter64, 
					oltStatisOutBroadPkts        Counter64,
					oamFramesCounters            Counter64,  
					standardOamStatistics        Counter64,
					standardOamMpcpStatistic     Counter64,
					cpuPortsOctets               Counter64, 
					cpuPortsFrames               Counter64,
					transmittedFramesPerLLID     Counter64,
					droppedFramesPerLLID         Counter64,
					transmittedOctetsPerLLID     Counter64,
					inRangeLengthErrorsPerLLID   Counter64,  					
					frameTooLongErrorsPerLLID    Counter64
    				}       
          				    
    oltStatisBer   OBJECT-TYPE      	    
            SYNTAX        Counter64            
            MAX-ACCESS    read-only
            STATUS        current 
            DESCRIPTION 
				""
			::= {zxr10EponOltPortStatEntry 1}
    
    oltStatisFer   OBJECT-TYPE      	    
            SYNTAX        Counter64             
            MAX-ACCESS    read-only
            STATUS        current 
            DESCRIPTION 
				""
			::= {zxr10EponOltPortStatEntry 2}             					

	oltStatisPortBer  OBJECT-TYPE      	    
            SYNTAX        Counter64            
            MAX-ACCESS    read-only
            STATUS        current 
            DESCRIPTION 
				""
			::= {zxr10EponOltPortStatEntry 3}          					
			
	oltStatisInPkts   OBJECT-TYPE      	    
            SYNTAX        Counter64             
            MAX-ACCESS    read-only
            STATUS        current 
            DESCRIPTION 
				""
			::= {zxr10EponOltPortStatEntry 4}        
					
	oltStatisInOctes   OBJECT-TYPE      	    
            SYNTAX        Counter64            
            MAX-ACCESS    read-only
            STATUS        current 
            DESCRIPTION 
				""
			::= {zxr10EponOltPortStatEntry 5}         
				
	oltStatisInUniPkts   OBJECT-TYPE      	    
            SYNTAX        Counter64             
            MAX-ACCESS    read-only
            STATUS        current 
            DESCRIPTION 
				""
			::= {zxr10EponOltPortStatEntry 6}    
					
	oltStatisInMultiPkts  OBJECT-TYPE      	    
            SYNTAX        Counter64            
            MAX-ACCESS    read-only
            STATUS        current 
            DESCRIPTION 
				""
			::= {zxr10EponOltPortStatEntry 7}     					
			
	oltStatisInBroadPkts  OBJECT-TYPE      	    
            SYNTAX        Counter64            
            MAX-ACCESS    read-only
            STATUS        current 
            DESCRIPTION 
				""
			::= {zxr10EponOltPortStatEntry 8}     
					
	oltStatisOutPkts   OBJECT-TYPE      	    
            SYNTAX        Counter64            
            MAX-ACCESS    read-only
            STATUS        current 
            DESCRIPTION 
				""
			::= {zxr10EponOltPortStatEntry 9}       					
			
	oltStatisOutOctes  OBJECT-TYPE      	    
            SYNTAX        Counter64             
            MAX-ACCESS    read-only
            STATUS        current 
            DESCRIPTION 
				""
			::= {zxr10EponOltPortStatEntry 10}         
				
	oltStatisOutUniPkts   OBJECT-TYPE      	    
            SYNTAX        Counter64             
            MAX-ACCESS    read-only
            STATUS        current 
            DESCRIPTION 
				""
			::= {zxr10EponOltPortStatEntry 11}      					
			
	oltStatisOutMultiPkts  OBJECT-TYPE      	    
            SYNTAX        Counter64            
            MAX-ACCESS    read-only
            STATUS        current 
            DESCRIPTION 
				""
			::= {zxr10EponOltPortStatEntry 12}      
					
	oltStatisOutBroadPkts  OBJECT-TYPE      	    
            SYNTAX        Counter64            
            MAX-ACCESS    read-only
            STATUS        current 
            DESCRIPTION 
				""
			::= {zxr10EponOltPortStatEntry 13}    					
			
	oamFramesCounters  OBJECT-TYPE      	    
            SYNTAX        Counter64            
            MAX-ACCESS    read-only
            STATUS        current 
            DESCRIPTION 
				""
			::= {zxr10EponOltPortStatEntry 14}         
					
	standardOamStatistics  OBJECT-TYPE      	    
            SYNTAX        Counter64            
            MAX-ACCESS    read-only
            STATUS        current 
            DESCRIPTION 
				""
			::= {zxr10EponOltPortStatEntry 15}    					
			
	standardOamMpcpStatistic  OBJECT-TYPE      	    
            SYNTAX        Counter64            
            MAX-ACCESS    read-only
            STATUS        current 
            DESCRIPTION 
				""
			::= {zxr10EponOltPortStatEntry 16}  					
	cpuPortsOctets OBJECT-TYPE      	    
            SYNTAX        Counter64            
            MAX-ACCESS    read-only
            STATUS        current 
            DESCRIPTION 
				""
			::= {zxr10EponOltPortStatEntry 17}               
				
	cpuPortsFrames  OBJECT-TYPE      	    
            SYNTAX        Counter64            
            MAX-ACCESS    read-only
            STATUS        current 
            DESCRIPTION 
				""
			::= {zxr10EponOltPortStatEntry 18}            					
	
	transmittedFramesPerLLID OBJECT-TYPE      	    
            SYNTAX        Counter64            
            MAX-ACCESS    read-only
            STATUS        current 
            DESCRIPTION 
				""
			::= {zxr10EponOltPortStatEntry 19}    					
			
	droppedFramesPerLLID OBJECT-TYPE      	    
            SYNTAX        Counter64            
            MAX-ACCESS    read-only
            STATUS        current 
            DESCRIPTION 
				""
			::= {zxr10EponOltPortStatEntry 20}        
			
	transmittedOctetsPerLLID  OBJECT-TYPE      	    
            SYNTAX        Counter64            
            MAX-ACCESS    read-only
            STATUS        current 
            DESCRIPTION 
				""
			::= {zxr10EponOltPortStatEntry 21}  
					
	inRangeLengthErrorsPerLLID OBJECT-TYPE      	    
            SYNTAX        Counter64            
            MAX-ACCESS    read-only
            STATUS        current 
            DESCRIPTION 
				""
			::= {zxr10EponOltPortStatEntry 22}				
					
	frameTooLongErrorsPerLLID OBJECT-TYPE      	    
            SYNTAX        Counter64            
            MAX-ACCESS    read-only
            STATUS        current 
            DESCRIPTION 
				""
			::= {zxr10EponOltPortStatEntry 23}
			
	zxr10EponOnuPortStatTable OBJECT-TYPE      	    
            SYNTAX        SEQUENCE OF Zxr10EponOnuPortStatEntry            
            MAX-ACCESS    not-accessible
            STATUS        current 
            DESCRIPTION 
				""
			::= {zxr10EponLocal 6} 
			
	zxr10EponOnuPortStatEntry OBJECT-TYPE      	    
            SYNTAX        Zxr10EponOnuPortStatEntry            
            MAX-ACCESS    not-accessible
            STATUS        current 
            DESCRIPTION 
				"ifIndex,for example epon-olt_1/1;onuId is the number of the onu" 
			INDEX {ifIndex,onuId}
			::= {zxr10EponOnuPortStatTable 1}
			
    Zxr10EponOnuPortStatEntry ::=
    		SEQUENCE {					
					onuStatisBer                 Counter64,
					onuStatisFer                 Counter64,
					onuStatisInPkts              Counter64,
					onuStatisInOctes             Counter64,
					onuStatisInMultiPkts         Counter64,
					onuStatisInBroadPkts         Counter64,
					onuStatisOutPkts             Counter64,
					onuStatisOutOctes            Counter64,
					onuStatisOutMultiPkts        Counter64,
					onuStatisOutBroadPkts        Counter64				
				    }        
	onuStatisBer OBJECT-TYPE      	    
            SYNTAX        Counter64            
            MAX-ACCESS    read-only
            STATUS        current 
            DESCRIPTION 
				""
			::= {zxr10EponOnuPortStatEntry 1}                					
			
	onuStatisFer OBJECT-TYPE      	    
            SYNTAX        Counter64            
            MAX-ACCESS    read-only
            STATUS        current 
            DESCRIPTION 
				""
			::= {zxr10EponOnuPortStatEntry 2}                					
			
	onuStatisInPkts  OBJECT-TYPE      	    
            SYNTAX        Counter64            
            MAX-ACCESS    read-only
            STATUS        current 
            DESCRIPTION 
				""
			::= {zxr10EponOnuPortStatEntry 3}					
	
	onuStatisInOctes  OBJECT-TYPE      	    
            SYNTAX        Counter64            
            MAX-ACCESS    read-only
            STATUS        current 
            DESCRIPTION 
				""
			::= {zxr10EponOnuPortStatEntry 4}       					
			
	onuStatisInMultiPkts   OBJECT-TYPE      	    
            SYNTAX        Counter64            
            MAX-ACCESS    read-only
            STATUS        current 
            DESCRIPTION 
				""
			::= {zxr10EponOnuPortStatEntry 5}    				
			
	onuStatisInBroadPkts  OBJECT-TYPE      	    
            SYNTAX        Counter64            
            MAX-ACCESS    read-only
            STATUS        current 
            DESCRIPTION 
				""
			::= {zxr10EponOnuPortStatEntry 6}     					
			
	onuStatisOutPkts  OBJECT-TYPE      	    
            SYNTAX        Counter64            
            MAX-ACCESS    read-only
            STATUS        current 
            DESCRIPTION 
				""
			::= {zxr10EponOnuPortStatEntry 7}					
			
	onuStatisOutOctes  OBJECT-TYPE      	    
            SYNTAX        Counter64            
            MAX-ACCESS    read-only
            STATUS        current 
            DESCRIPTION 
				""
			::= {zxr10EponOnuPortStatEntry 8}					
			
	onuStatisOutMultiPkts  OBJECT-TYPE      	    
            SYNTAX        Counter64           
            MAX-ACCESS    read-only
            STATUS        current 
            DESCRIPTION 
				""
			::= {zxr10EponOnuPortStatEntry 9}					
			
	onuStatisOutBroadPkts  OBJECT-TYPE      	    
            SYNTAX        Counter64            
            MAX-ACCESS    read-only
            STATUS        current 
            DESCRIPTION 
				""
			::= {zxr10EponOnuPortStatEntry 10}
     				   				             				
	zxr10EponProtectGroupTable OBJECT-TYPE
		    SYNTAX         SEQUENCE OF Zxr10EponProtectGroupEntry
            MAX-ACCESS     not-accessible 
            STATUS         current 
            DESCRIPTION 
                ""     
            ::= {zxr10EponLocal 7} 
            
    zxr10EponProtectGroupEntry OBJECT-TYPE
            SYNTAX         Zxr10EponProtectGroupEntry
            MAX-ACCESS     not-accessible 
            STATUS         current 
            DESCRIPTION 
                ""   
            INDEX    { protectGroupid }  
            ::= {zxr10EponProtectGroupTable 1}  
            
    Zxr10EponProtectGroupEntry::=
    		SEQUENCE {
    				protectGroupid                  Integer32,         
    				protectOltMasterIfName          DisplayString,
    				protectOltBackupIfName          DisplayString,  
    				protectOltActiveIfName          DisplayString,
    				protectOltEnableSwitch          INTEGER, 
    				protectReverEnable              INTEGER,
    				protectReverTime                Integer32,
     				protectRowStatus                RowStatus
    				}
    
    protectGroupid OBJECT-TYPE
        SYNTAX      Integer32(1..32)
        MAX-ACCESS  read-only
        STATUS      current
        DESCRIPTION
            ""
        ::= { zxr10EponProtectGroupEntry 1}				      				
	      
    protectOltMasterIfName OBJECT-TYPE
        SYNTAX      DisplayString
        MAX-ACCESS  read-write
        STATUS      current
        DESCRIPTION
            ""
        ::= { zxr10EponProtectGroupEntry 2}        				
  			
    protectOltBackupIfName OBJECT-TYPE
        SYNTAX      DisplayString
        MAX-ACCESS  read-write
        STATUS      current
        DESCRIPTION
            ""
        ::= { zxr10EponProtectGroupEntry 3}	
        
    protectOltActiveIfName OBJECT-TYPE
        SYNTAX      DisplayString
        MAX-ACCESS  read-only
        STATUS      current
        DESCRIPTION
            ""
        ::= { zxr10EponProtectGroupEntry 4}	
        
    protectOltEnableSwitch  OBJECT-TYPE
        SYNTAX      INTEGER
        MAX-ACCESS  read-write
        STATUS      current
        DESCRIPTION
            ""
        ::= { zxr10EponProtectGroupEntry 5}       			
    
    protectReverEnable  OBJECT-TYPE
        SYNTAX      INTEGER
        MAX-ACCESS  read-write
        STATUS      current
        DESCRIPTION
            ""
        ::= { zxr10EponProtectGroupEntry 6}
        
    protectReverTime OBJECT-TYPE
        SYNTAX      Integer32(1..65535)
        MAX-ACCESS  read-write
        STATUS      current
        DESCRIPTION
            ""
        ::= { zxr10EponProtectGroupEntry 7}     
        
    protectRowStatus OBJECT-TYPE
        SYNTAX      RowStatus      
        MAX-ACCESS  read-write
        STATUS      current
        DESCRIPTION
            ""
        ::= { zxr10EponProtectGroupEntry 8}  
        
    zxr10EponSwitchRecordTable OBJECT-TYPE
		    SYNTAX         SEQUENCE OF Zxr10EponSwitchRecordEntry
            MAX-ACCESS     not-accessible 
            STATUS         current 
            DESCRIPTION 
                ""     
            ::= {zxr10EponLocal 8} 
            
    zxr10EponSwitchRecordEntry OBJECT-TYPE
            SYNTAX         Zxr10EponSwitchRecordEntry
            MAX-ACCESS     not-accessible 
            STATUS         current 
            DESCRIPTION 
                ""   
            INDEX    { switchRecordGroupid,switchRecordNum}  
            ::= {zxr10EponSwitchRecordTable 1}
            
    Zxr10EponSwitchRecordEntry ::=
    		SEQUENCE {
    				switchRecordGroupid             Integer32,      
    			    switchRecordNum                 Integer32,
    			    switchTime                   	DisplayString,
    			    switchType                      INTEGER,
    			    switchTypeMtoB               	INTEGER
   		           }
   	
   	switchRecordGroupid  OBJECT-TYPE
        SYNTAX      Integer32(1..32)        
        MAX-ACCESS  read-only
        STATUS      current
        DESCRIPTION
            "index"
        ::= { zxr10EponSwitchRecordEntry 1}
   		                   
    switchRecordNum OBJECT-TYPE
        SYNTAX      Integer32(1..50)        
        MAX-ACCESS  read-only
        STATUS      current
        DESCRIPTION
            "index"
        ::= { zxr10EponSwitchRecordEntry 2}
   
    switchTime OBJECT-TYPE
        SYNTAX      DisplayString
        MAX-ACCESS  read-only
        STATUS      current
        DESCRIPTION
            ""
        ::= { zxr10EponSwitchRecordEntry 3}
    
    switchType OBJECT-TYPE
        SYNTAX      INTEGER{auto(1),force(2),retiver(3),alarm(4),ifchange(5)}
        MAX-ACCESS  read-only
        STATUS      current
        DESCRIPTION
            ""
        ::= { zxr10EponSwitchRecordEntry 4} 
       
    switchTypeMtoB OBJECT-TYPE
        SYNTAX      INTEGER{no(0),yes(1)}
        MAX-ACCESS  read-only
        STATUS      current
        DESCRIPTION
            ""
        ::= { zxr10EponSwitchRecordEntry 5}  
    
    zxr10EponAlarmTable OBJECT-TYPE
		    SYNTAX         SEQUENCE OF Zxr10EponAlarmEntry
            MAX-ACCESS     not-accessible 
            STATUS         current 
            DESCRIPTION 
                ""     
            ::= {zxr10EponLocal 9} 
            
    zxr10EponAlarmEntry OBJECT-TYPE
            SYNTAX         Zxr10EponAlarmEntry
            MAX-ACCESS     not-accessible 
            STATUS         current 
            DESCRIPTION 
                "epon-olt_1/1"   
            INDEX    { ifIndex}  
            ::= {zxr10EponAlarmTable 1}
            
    Zxr10EponAlarmEntry ::=
    		SEQUENCE {
    			 oltAlarmSwitch             DisplayString,
					oltAlarmDirectSwitch       DisplayString,
					oltAlarmThreshold         DisplayString
					}
       
    oltAlarmSwitch  OBJECT-TYPE
            SYNTAX    DisplayString
            MAX-ACCESS     read-write 
            STATUS         current 
            DESCRIPTION 
                ""   
            ::= {zxr10EponAlarmEntry 1}
            
   oltAlarmDirectSwitch  OBJECT-TYPE
            SYNTAX         DisplayString
            MAX-ACCESS     read-write 
            STATUS         current 
            DESCRIPTION 
                "default is downlink"   
            ::= {zxr10EponAlarmEntry 2}  
            
   oltAlarmThreshold     OBJECT-TYPE
            SYNTAX         DisplayString
            MAX-ACCESS     read-write 
            STATUS         current 
            DESCRIPTION 
                "bit-error-rate and frame-error-rate threshold value ,and default value is 10"   
            ::= {zxr10EponAlarmEntry 3} 
            
--------------------------------------------------------------------     				
--  ONU remote manage                                              
--------------------------------------------------------------------
    
	zxr10EponRemoteOnuInfoTable	OBJECT-TYPE 	
    		SYNTAX         SEQUENCE OF Zxr10EponRemoteOnuInfoEntry
            MAX-ACCESS     not-accessible 
            STATUS         current 
            DESCRIPTION 
                ""     
            ::= {zxr10EponRemoteOnu 1}        
            
    zxr10EponRemoteOnuInfoEntry  OBJECT-TYPE 	
    		SYNTAX         Zxr10EponRemoteOnuInfoEntry
            MAX-ACCESS     not-accessible 
            STATUS         current 
            DESCRIPTION 
                "index,for example epon-olt_1/1;onuId is the number of the onu"  
            INDEX {ifIndex,onuId}   
            ::= {zxr10EponRemoteOnuInfoTable 1}
			
    Zxr10EponRemoteOnuInfoEntry ::=
    		SEQUENCE { 
    				remoteOnuVendorId                  DisplayString,
    				remoteOnuModel                     DisplayString,
					remoteOnuId                        MacAddress, 
					remoteHardwareVersion              DisplayString,
					remoteSoftwareVersion              DisplayString,
					remoteFirmwareVersion              DisplayString,
					remoteChipVendorId                 DisplayString,
					remoteChipModel                    DisplayString,
					remoteChipRevison                  DisplayString,
					remoteIcVersion                    DisplayString,
					remoteGePortNum                    Integer32,
					remoteBitmapGePort                 DisplayString,
					remoteFePortNum                    Integer32,
					remoteBitmapFePort                 DisplayString,
					remotePortsNum                     Integer32,
					remoteE1PortNum                    Integer32,
					remoteUsQueuesNum                  Integer32,
					remoteMaxQueuesPerUSport           Integer32,
					remoteDSQueuesNum                  Integer32,
					remoteMaxQueuesPerDSport           Integer32,
					remoteBatteryBackup                INTEGER
				 	}
      
	remoteOnuVendorId   OBJECT-TYPE 	
    		SYNTAX         DisplayString
            MAX-ACCESS     read-only 
            STATUS         current 
            DESCRIPTION 
                ""   
            ::= {zxr10EponRemoteOnuInfoEntry 1}
      
    remoteOnuModel OBJECT-TYPE 	
    		SYNTAX         DisplayString
            MAX-ACCESS     read-only 
            STATUS         current 
            DESCRIPTION 
                ""   
            ::= {zxr10EponRemoteOnuInfoEntry 2}   
      
    remoteOnuId  OBJECT-TYPE 	
    		SYNTAX         MacAddress
            MAX-ACCESS     read-only 
            STATUS         current 
            DESCRIPTION 
                ""   
            ::= {zxr10EponRemoteOnuInfoEntry 3} 
      
    remoteHardwareVersion  OBJECT-TYPE 	
    		SYNTAX         DisplayString
            MAX-ACCESS     read-only 
            STATUS         current 
            DESCRIPTION 
                ""   
            ::= {zxr10EponRemoteOnuInfoEntry 4} 
      
    remoteSoftwareVersion  OBJECT-TYPE 	
    		SYNTAX         DisplayString
            MAX-ACCESS     read-only 
            STATUS         current 
            DESCRIPTION 
                ""   
            ::= {zxr10EponRemoteOnuInfoEntry 5}
      
    remoteFirmwareVersion  OBJECT-TYPE 	
    		SYNTAX         DisplayString
            MAX-ACCESS     read-only 
            STATUS         current 
            DESCRIPTION 
                ""   
            ::= {zxr10EponRemoteOnuInfoEntry 6}
   
    remoteChipVendorId     OBJECT-TYPE 	
    		SYNTAX         DisplayString
            MAX-ACCESS     read-only 
            STATUS         current 
            DESCRIPTION 
                ""   
            ::= {zxr10EponRemoteOnuInfoEntry 7}
     
    remoteChipModel   OBJECT-TYPE 	
    		SYNTAX         DisplayString
            MAX-ACCESS     read-only 
            STATUS         current 
            DESCRIPTION 
                ""   
            ::= {zxr10EponRemoteOnuInfoEntry 8}   
   
    remoteChipRevison  OBJECT-TYPE 	
    		SYNTAX         DisplayString
            MAX-ACCESS     read-only 
            STATUS         current 
            DESCRIPTION 
                ""   
            ::= {zxr10EponRemoteOnuInfoEntry 9}
   
    remoteIcVersion  OBJECT-TYPE 	
    		SYNTAX         DisplayString
            MAX-ACCESS     read-only 
            STATUS         current 
            DESCRIPTION 
                ""   
            ::= {zxr10EponRemoteOnuInfoEntry 10}
            
    remoteGePortNum   OBJECT-TYPE 	
    		SYNTAX         Integer32
            MAX-ACCESS     read-only 
            STATUS         current 
            DESCRIPTION 
                ""   
            ::= {zxr10EponRemoteOnuInfoEntry 11}      
    
    remoteBitmapGePort  OBJECT-TYPE 	
    		SYNTAX         DisplayString
            MAX-ACCESS     read-only 
            STATUS         current 
            DESCRIPTION 
                ""   
            ::= {zxr10EponRemoteOnuInfoEntry 12} 
            
    remoteFePortNum   OBJECT-TYPE 	
    		SYNTAX         Integer32
            MAX-ACCESS     read-only 
            STATUS         current 
            DESCRIPTION 
                ""   
            ::= {zxr10EponRemoteOnuInfoEntry 13} 
            
    remoteBitmapFePort  OBJECT-TYPE 	
    		SYNTAX         DisplayString
            MAX-ACCESS     read-only 
            STATUS         current 
            DESCRIPTION 
                ""   
            ::= {zxr10EponRemoteOnuInfoEntry 14}
          
    remotePortsNum   OBJECT-TYPE 	
    		SYNTAX         Integer32
            MAX-ACCESS     read-only 
            STATUS         current 
            DESCRIPTION 
                ""   
            ::= {zxr10EponRemoteOnuInfoEntry 15}        
            
    remoteE1PortNum  OBJECT-TYPE 	
    		SYNTAX         Integer32
            MAX-ACCESS     read-only 
            STATUS         current 
            DESCRIPTION 
                ""   
            ::= {zxr10EponRemoteOnuInfoEntry 16}
            
    remoteUsQueuesNum  OBJECT-TYPE 	
    		SYNTAX         Integer32
            MAX-ACCESS     read-only 
            STATUS         current 
            DESCRIPTION 
                ""   
            ::= {zxr10EponRemoteOnuInfoEntry 17}
            
    remoteMaxQueuesPerUSport OBJECT-TYPE 	
    		SYNTAX         Integer32
            MAX-ACCESS     read-only 
            STATUS         current 
            DESCRIPTION 
                ""   
            ::= {zxr10EponRemoteOnuInfoEntry 18}
            
    remoteDSQueuesNum  OBJECT-TYPE 	
    		SYNTAX         Integer32
            MAX-ACCESS     read-only 
            STATUS         current 
            DESCRIPTION 
                ""   
            ::= {zxr10EponRemoteOnuInfoEntry 19}
            
    remoteMaxQueuesPerDSport  OBJECT-TYPE 	
    		SYNTAX         Integer32
            MAX-ACCESS     read-only 
            STATUS         current 
            DESCRIPTION 
                ""   
            ::= {zxr10EponRemoteOnuInfoEntry 20}
       
    remoteBatteryBackup  OBJECT-TYPE 	
    		SYNTAX         INTEGER{
    							no(0),
    							yes(1)
    							}            
    		MAX-ACCESS     read-only 
            STATUS         current 
            DESCRIPTION 
                ""   
            ::= {zxr10EponRemoteOnuInfoEntry 21}                                     
                                     
     zxr10EponRemoteOnuDbaTable OBJECT-TYPE 	
    		SYNTAX         SEQUENCE OF Zxr10EponRemoteOnuDbaEntry
            MAX-ACCESS     not-accessible 
            STATUS         current 
            DESCRIPTION 
                "DBA queueSet"     
            ::= {zxr10EponRemoteOnu 2}
   
     zxr10EponRemoteOnuDbaEntry  OBJECT-TYPE 	
    		SYNTAX         Zxr10EponRemoteOnuDbaEntry
            MAX-ACCESS     not-accessible 
            STATUS         current 
            DESCRIPTION 
                "index,for example epon-olt_1/1;onuId is the number of the onu"  
            INDEX {ifIndex,onuId,queueSetId}    
            ::= {zxr10EponRemoteOnuDbaTable 1}  
            
     Zxr10EponRemoteOnuDbaEntry::=
     		SEQUENCE {
                    queueSetId                   Integer32,
                    queueValue1                  Integer32,
                    queueValue2                  Integer32,   
                    queueValue3                  Integer32,  
                    queueValue4                  Integer32,    				
                    queueValue5                  Integer32,    				
                    queueValue6                  Integer32,    
                    queueValue7                  Integer32,    				
                    queueValue8                  Integer32,
                    dbaQueueActive               Integer32,
                    onuDbaRowStatus   	         RowStatus			
    				}
     
     queueSetId OBJECT-TYPE 	
    		SYNTAX         Integer32(1..3)
            MAX-ACCESS     read-only 
            STATUS         current 
            DESCRIPTION 
                "index"     
            ::= {zxr10EponRemoteOnuDbaEntry 1}			
    				
     queueValue1 OBJECT-TYPE 	
    		SYNTAX         Integer32(1..65535)
            MAX-ACCESS     read-write 
            STATUS         current 
            DESCRIPTION 
                ""     
            ::= {zxr10EponRemoteOnuDbaEntry 2}				
    				
     queueValue2 OBJECT-TYPE 	
    		SYNTAX         Integer32(1..65535)
            MAX-ACCESS     read-write
            STATUS         current 
            DESCRIPTION 
                ""     
            ::= {zxr10EponRemoteOnuDbaEntry 3}				
    				
     queueValue3 OBJECT-TYPE 	
    		SYNTAX         Integer32(1..65535)
            MAX-ACCESS     read-write 
            STATUS         current 
            DESCRIPTION 
                ""     
            ::= {zxr10EponRemoteOnuDbaEntry 4}				
    				
     queueValue4 OBJECT-TYPE 	
    		SYNTAX         Integer32(1..65535)
            MAX-ACCESS     read-write 
            STATUS         current 
            DESCRIPTION 
                ""     
            ::= {zxr10EponRemoteOnuDbaEntry 5}				
    				
     queueValue5 OBJECT-TYPE 	
    		SYNTAX         Integer32(1..65535)
            MAX-ACCESS     read-write
            STATUS         current 
            DESCRIPTION 
                ""     
            ::= {zxr10EponRemoteOnuDbaEntry 6}				
   				
     queueValue6 OBJECT-TYPE 	
    		SYNTAX         Integer32(1..65535)
            MAX-ACCESS     read-write
            STATUS         current 
            DESCRIPTION 
                ""     
            ::= {zxr10EponRemoteOnuDbaEntry 7}				
    				
     queueValue7 OBJECT-TYPE 	
    		SYNTAX         Integer32(1..65535)
            MAX-ACCESS     read-write 
            STATUS         current 
            DESCRIPTION 
                ""     
            ::= {zxr10EponRemoteOnuDbaEntry 8}				
    				
     queueValue8 OBJECT-TYPE 	
    		SYNTAX         Integer32(1..65535)
            MAX-ACCESS     read-write
            STATUS         current 
            DESCRIPTION 
                ""     
            ::= {zxr10EponRemoteOnuDbaEntry 9}	
    
        dbaQueueActive  OBJECT-TYPE 	
    		SYNTAX         Integer32(1..3)
            MAX-ACCESS     read-write
            STATUS         current 
            DESCRIPTION 
                ""     
            ::= {zxr10EponRemoteOnuDbaEntry 10}
        
    onuDbaRowStatus OBJECT-TYPE 	
    		SYNTAX         RowStatus
            MAX-ACCESS     read-write
            STATUS         current 
            DESCRIPTION 
                ""     
            ::= {zxr10EponRemoteOnuDbaEntry 11}	        			       
            
    zxr10EponRemoteOnuClassRuleTable OBJECT-TYPE 	
    		SYNTAX         SEQUENCE OF Zxr10EponRemoteOnuClassRuleEntry            
    		MAX-ACCESS     not-accessible 
            STATUS         current 
            DESCRIPTION 
                "class rule"     
            ::= {zxr10EponRemoteOnu 3}       
            
    zxr10EponRemoteOnuClassRuleEntry OBJECT-TYPE 	
    		SYNTAX         Zxr10EponRemoteOnuClassRuleEntry       
    		MAX-ACCESS     not-accessible 
            STATUS         current 
            DESCRIPTION 
               "index,for example epon-olt_1/1;onuId is the number of the onu" 
            INDEX {ifIndex,onuId,ruleProfileNum }    
            ::= {zxr10EponRemoteOnuClassRuleTable 1}        
            
    Zxr10EponRemoteOnuClassRuleEntry ::=
    		SEQUENCE {    			    
    		        ruleProfileNum           Integer32,
    		        queueVlaue               Integer32,                              
                    priorityValue    	     Integer32,
                    ruleRowStatus            RowStatus    
                    }     	                 

    ruleProfileNum  OBJECT-TYPE 	
    		SYNTAX         Integer32(1..8)        
    		MAX-ACCESS     read-only 
            STATUS         current 
            DESCRIPTION 
                ""     
            ::= {zxr10EponRemoteOnuClassRuleEntry 1}
           
    queueVlaue  OBJECT-TYPE 	
    		SYNTAX         Integer32(0..7)        
    		MAX-ACCESS     read-write 
            STATUS         current 
            DESCRIPTION 
                "index"     
            ::= {zxr10EponRemoteOnuClassRuleEntry 2}       
            
    priorityValue  OBJECT-TYPE 	
    		SYNTAX         Integer32(0..7)        
    		MAX-ACCESS     read-write 
            STATUS         current 
            DESCRIPTION 
                ""     
            ::= {zxr10EponRemoteOnuClassRuleEntry 3}
            
    ruleRowStatus OBJECT-TYPE 	
    		SYNTAX         RowStatus        
    		MAX-ACCESS     read-write 
            STATUS         current 
            DESCRIPTION 
                ""     
            ::= {zxr10EponRemoteOnuClassRuleEntry 4}              
    
    zxr10EponRemoteOnuClassCondiTable  OBJECT-TYPE 	
    		SYNTAX         SEQUENCE OF Zxr10EponRemoteOnuClassCondiEntry           
    		MAX-ACCESS     not-accessible 
            STATUS         current 
            DESCRIPTION 
                "class condition"     
            ::= {zxr10EponRemoteOnu 4} 
    
    zxr10EponRemoteOnuClassCondiEntry  OBJECT-TYPE 	
    		SYNTAX         Zxr10EponRemoteOnuClassCondiEntry           
    		MAX-ACCESS     not-accessible 
            STATUS         current 
            DESCRIPTION 
                "index,for example epon-olt_1/1;onuId is the number of the onu"
            INDEX {ifIndex,onuId,conditionProfileNum }     
            ::= {zxr10EponRemoteOnuClassCondiTable 1}
    
    Zxr10EponRemoteOnuClassCondiEntry ::=
    		SEQUENCE {
    		        conditionProfileNum           Integer32,  
    		        conditionMacAddressType    	  INTEGER, 
    		        conditionMacAddress           MacAddress,
    		        conditionIpAddressType        INTEGER,
    		        conditionIpAddress            IpAddress,
                    conditionPriority             Integer32,
                    conditionVlanId               Integer32,
                    conditionDscp                 Integer32,
                    conditionL4PortType           INTEGER,
                    conditionPortNum              Integer32,
                    conditionEthType              Integer32,
                    conditionIpProtocolType       Integer32,
		    		conditionOperatorType         INTEGER,
		   		 	conditionRowStatus            RowStatus
		        }
	
	conditionProfileNum OBJECT-TYPE 	
    		SYNTAX         Integer32(1..8)        
    		MAX-ACCESS     read-only 
            STATUS         current 
            DESCRIPTION 
                ""     
            ::= {zxr10EponRemoteOnuClassCondiEntry 1}				
					
	conditionMacAddressType OBJECT-TYPE 	
    		SYNTAX         INTEGER{
    						source-mac(0),dest-mac(1),null(-1)
    						}        
    		MAX-ACCESS     read-write 
            STATUS         current 
            DESCRIPTION 
                ""     
            ::= {zxr10EponRemoteOnuClassCondiEntry 2}				
					
	conditionMacAddress OBJECT-TYPE 	
    		SYNTAX         MacAddress       
    		MAX-ACCESS     read-write 
            STATUS         current 
            DESCRIPTION 
                ""     
            ::= {zxr10EponRemoteOnuClassCondiEntry 3}				    
    
     conditionIpAddressType OBJECT-TYPE 	
    		SYNTAX         INTEGER{
    						destIp(5),sourceIp(6),null(-1)
    						}       
    		MAX-ACCESS     read-write 
            STATUS         current 
            DESCRIPTION 
                ""     
            ::= {zxr10EponRemoteOnuClassCondiEntry 4}
    
     conditionIpAddress OBJECT-TYPE 	
    		SYNTAX         IpAddress       
    		MAX-ACCESS     read-write 
            STATUS         current 
            DESCRIPTION 
                ""     
            ::= {zxr10EponRemoteOnuClassCondiEntry 5}
    
     conditionPriority OBJECT-TYPE 	
    		SYNTAX         Integer32(0..7)       
    		MAX-ACCESS     read-write 
            STATUS         current 
            DESCRIPTION 
                ""     
            ::= {zxr10EponRemoteOnuClassCondiEntry 6}
    
     conditionVlanId OBJECT-TYPE 	
    		SYNTAX         Integer32(1..4094)       
    		MAX-ACCESS     read-write 
            STATUS         current 
            DESCRIPTION 
                ""     
            ::= {zxr10EponRemoteOnuClassCondiEntry 7}
    
     conditionDscp OBJECT-TYPE 	
    		SYNTAX         Integer32(1..64)       
    		MAX-ACCESS     read-write 
            STATUS         current 
            DESCRIPTION 
                ""     
            ::= {zxr10EponRemoteOnuClassCondiEntry 8}   
            
     conditionL4PortType OBJECT-TYPE 	
    		SYNTAX         INTEGER{
    						l4SourcePort(10),l4DestPort(11),null(-1)
    						}        
    		MAX-ACCESS     read-write 
            STATUS         current 
            DESCRIPTION 
                ""     
            ::= {zxr10EponRemoteOnuClassCondiEntry 9}       
            
     conditionPortNum  OBJECT-TYPE 	
    		SYNTAX         Integer32(1..79)       
    		MAX-ACCESS     read-write 
            STATUS         current 
            DESCRIPTION 
                ""     
            ::= {zxr10EponRemoteOnuClassCondiEntry 10}      
     
     conditionEthType  OBJECT-TYPE 	
    		SYNTAX         Integer32(1..65535)       
    		MAX-ACCESS     read-write 
            STATUS         current 
            DESCRIPTION 
                ""     
            ::= {zxr10EponRemoteOnuClassCondiEntry 11}       
            
     conditionIpProtocolType OBJECT-TYPE 	
    		SYNTAX         Integer32(1..65535)       
    		MAX-ACCESS     read-write 
            STATUS         current 
            DESCRIPTION 
                ""     
            ::= {zxr10EponRemoteOnuClassCondiEntry 12}       
            
     conditionOperatorType  OBJECT-TYPE 	
    		SYNTAX         INTEGER{
    						never-match(0),equal(1),
    						not-equal(2),less-equal(3),
    						greater-equal(4),exists(5),
    						not-exists(6),always-match(7)    						
    						}        
    		MAX-ACCESS     read-write 
            STATUS         current 
            DESCRIPTION 
                ""     
            ::= {zxr10EponRemoteOnuClassCondiEntry 13} 
            
     conditionRowStatus  OBJECT-TYPE 	
    		SYNTAX         RowStatus       
    		MAX-ACCESS     read-write 
            STATUS         current 
            DESCRIPTION 
                ""     
            ::= {zxr10EponRemoteOnuClassCondiEntry 14} 
                      
     zxr10EponRemoteOnuPortTable  OBJECT-TYPE 	
    		SYNTAX         SEQUENCE OF Zxr10EponRemoteOnuPortEntry            
    		MAX-ACCESS     not-accessible 
            STATUS         current 
            DESCRIPTION 
                "onu port"     
            ::= {zxr10EponRemoteOnu 5} 
            
    zxr10EponRemoteOnuPortEntry  OBJECT-TYPE 	
    		SYNTAX         Zxr10EponRemoteOnuPortEntry           
    		MAX-ACCESS     not-accessible 
            STATUS         current 
            DESCRIPTION 
                "index,for example epon-olt_1/1;onuId is the number of the onu;and the onuIfIndex is the port of onu"
            INDEX {ifIndex,onuId,onuEthUniNumber}     
            ::= {zxr10EponRemoteOnuPortTable 1}          
            
    Zxr10EponRemoteOnuPortEntry ::=
    		SEQUENCE {
    		        onuEthUniNumber               Integer32, 
    		        onuPortFlowControl            INTEGER,
    		        onuPortUpPolicySwitch         INTEGER,   
    		        onuPortUpPolicyCIR            Integer32,
    		        onuPortUpPolicyCBS            Integer32,
    		        onuPortUpPolicyEBS            Integer32,
    		        onuPortDownPolicySwitch       INTEGER,
    		        onuPortDownPolicyCIR          Integer32,
    		        onuPortDownPolicyPIR          Integer32,
    		        onuPortVlanMode               INTEGER,
    		        onuPortVlanTagValue  		  Integer32,
    		        onuDefaultVlan                Integer32,
    		        onuVlanDelVid1                Integer32,
    		        onuVlanAddVid1                Integer32,
    		        onuVlanDelVid2                Integer32,
    		        onuVlanAddVid2                Integer32,
    		        onuVlanDelVid3                Integer32,
    		        onuVlanAddVid3                Integer32,
    		        onuVlanDelVid4                Integer32,
    		        onuVlanAddVid4                Integer32,
    		        onuVlanDelVid5                Integer32,
    		        onuVlanAddVid5                Integer32,
    		        onuVlanDelVid6                Integer32,
    		        onuVlanAddVid6                Integer32,
    		        onuVlanDelVid7                Integer32,
    		        onuVlanAddVid7                Integer32,
    		        onuVlanDelVid8                Integer32,
    		        onuVlanAddVid8                Integer32,
    		        onuRulePrecedenceSwitch       INTEGER, 
    		        onuRulePrecedenceNum          Integer32,
    		        onuRuleProfile                DisplayString,
    		        onuConditionList              DisplayString,
    		        onuMultiVlanSwitch            INTEGER,             
    		        onuMultiVlanList              DisplayString,
    		        onuMultiVlanTagStripe         INTEGER,
        			onuMultiGroupMaxNum    		  Integer32,         		        
    		        onuPortRowStatus              RowStatus 
   		        }        
            
     onuEthUniNumber  OBJECT-TYPE 	
    		SYNTAX         Integer32(1..79)           
    		MAX-ACCESS     read-only 
            STATUS         current 
            DESCRIPTION 
                "index:UniNumber,linearity index "   
            ::= {zxr10EponRemoteOnuPortEntry 1}     
            
     onuPortFlowControl  OBJECT-TYPE 	
    		SYNTAX         INTEGER{disable(0),enable(1)}           
    		MAX-ACCESS     read-write 
            STATUS         current 
            DESCRIPTION 
                ""   
            ::= {zxr10EponRemoteOnuPortEntry 2}      
            
     onuPortUpPolicySwitch OBJECT-TYPE 	
    		SYNTAX         INTEGER{disable(0),enable(1)}           
    		MAX-ACCESS     read-write 
            STATUS         current 
            DESCRIPTION 
                ""   
            ::= {zxr10EponRemoteOnuPortEntry 3}       
            
     onuPortUpPolicyCIR  OBJECT-TYPE 	
    		SYNTAX         Integer32(0..16777215)           
    		MAX-ACCESS     read-write 
            STATUS         current 
            DESCRIPTION 
                ""   
            ::= {zxr10EponRemoteOnuPortEntry 4}      
            
     onuPortUpPolicyCBS  OBJECT-TYPE 	
    		SYNTAX         Integer32(0..16777215)           
    		MAX-ACCESS     read-write 
            STATUS         current 
            DESCRIPTION 
                ""   
            ::= {zxr10EponRemoteOnuPortEntry 5}      
            
     onuPortUpPolicyEBS  OBJECT-TYPE 	
    		SYNTAX         Integer32(0..16777215)           
    		MAX-ACCESS     read-write 
            STATUS         current 
            DESCRIPTION 
                ""   
            ::= {zxr10EponRemoteOnuPortEntry 6}        
            
     onuPortDownPolicySwitch  OBJECT-TYPE 	
    		SYNTAX         INTEGER{disable(0),enable(1)}           
    		MAX-ACCESS     read-write 
            STATUS         current 
            DESCRIPTION 
                ""   
            ::= {zxr10EponRemoteOnuPortEntry 7}      
            
     onuPortDownPolicyCIR  OBJECT-TYPE 	
    		SYNTAX         Integer32(0..16777215)           
    		MAX-ACCESS     read-write 
            STATUS         current 
            DESCRIPTION 
                ""   
            ::= {zxr10EponRemoteOnuPortEntry 8}      
            
     onuPortDownPolicyPIR  OBJECT-TYPE 	
    		SYNTAX         Integer32(0..16777215)           
    		MAX-ACCESS     read-write 
            STATUS         current 
            DESCRIPTION 
                ""   
            ::= {zxr10EponRemoteOnuPortEntry 9}      
            
     onuPortVlanMode  OBJECT-TYPE 	
    		SYNTAX         INTEGER{
    						transparent(0),tag(1),translation(2)
    						}
            MAX-ACCESS     read-write 
            STATUS         current 
            DESCRIPTION 
                ""     
            ::= {zxr10EponRemoteOnuPortEntry 10}       
            
    onuPortVlanTagValue  OBJECT-TYPE 	
    		SYNTAX         Integer32(1..4094)
            MAX-ACCESS     read-write 
            STATUS         current 
            DESCRIPTION 
                ""     
            ::= {zxr10EponRemoteOnuPortEntry 11}
            
    onuDefaultVlan  OBJECT-TYPE 	
    		SYNTAX         Integer32(1..4094)
            MAX-ACCESS     read-write 
            STATUS         current 
            DESCRIPTION 
                ""     
            ::= {zxr10EponRemoteOnuPortEntry 12}                                               
                                              
    onuVlanDelVid1 OBJECT-TYPE 	
    		SYNTAX         Integer32(1..4094)
            MAX-ACCESS     read-write 
            STATUS         current 
            DESCRIPTION 
                ""     
            ::= {zxr10EponRemoteOnuPortEntry 13}        
            
    onuVlanAddVid1  OBJECT-TYPE 	
    		SYNTAX         Integer32(1..4094)
            MAX-ACCESS     read-write
            STATUS         current 
            DESCRIPTION 
                ""     
            ::= {zxr10EponRemoteOnuPortEntry 14} 
            
    onuVlanDelVid2 OBJECT-TYPE 	
    		SYNTAX         Integer32(1..4094)
            MAX-ACCESS     read-write 
            STATUS         current 
            DESCRIPTION 
                ""     
            ::= {zxr10EponRemoteOnuPortEntry 15}        
            
    onuVlanAddVid2  OBJECT-TYPE 	
    		SYNTAX         Integer32(1..4094)
            MAX-ACCESS     read-write
            STATUS         current 
            DESCRIPTION 
                ""     
            ::= {zxr10EponRemoteOnuPortEntry 16}
            
    onuVlanDelVid3 OBJECT-TYPE 	
    		SYNTAX         Integer32(1..4094)
            MAX-ACCESS     read-write 
            STATUS         current 
            DESCRIPTION 
                ""     
            ::= {zxr10EponRemoteOnuPortEntry 17}        
            
    onuVlanAddVid3  OBJECT-TYPE 	
    		SYNTAX         Integer32(1..4094)
            MAX-ACCESS     read-write
            STATUS         current 
            DESCRIPTION 
                ""     
            ::= {zxr10EponRemoteOnuPortEntry 18}
            
    onuVlanDelVid4 OBJECT-TYPE 	
    		SYNTAX         Integer32(1..4094)
            MAX-ACCESS     read-write 
            STATUS         current 
            DESCRIPTION 
                ""     
            ::= {zxr10EponRemoteOnuPortEntry 19}        
            
    onuVlanAddVid4  OBJECT-TYPE 	
    		SYNTAX         Integer32(1..4094)
            MAX-ACCESS     read-write
            STATUS         current 
            DESCRIPTION 
                ""     
            ::= {zxr10EponRemoteOnuPortEntry 20}
            
    onuVlanDelVid5 OBJECT-TYPE 	
    		SYNTAX         Integer32(1..4094)
            MAX-ACCESS     read-write 
            STATUS         current 
            DESCRIPTION 
                ""     
            ::= {zxr10EponRemoteOnuPortEntry 21}        
            
    onuVlanAddVid5  OBJECT-TYPE 	
    		SYNTAX         Integer32(1..4094)
            MAX-ACCESS     read-write
            STATUS         current 
            DESCRIPTION 
                ""     
            ::= {zxr10EponRemoteOnuPortEntry 22}
            
    onuVlanDelVid6 OBJECT-TYPE 	
    		SYNTAX         Integer32 (1..4094)
            MAX-ACCESS     read-write 
            STATUS         current 
            DESCRIPTION 
                ""     
            ::= {zxr10EponRemoteOnuPortEntry 23}        
            
    onuVlanAddVid6  OBJECT-TYPE 	
    		SYNTAX         Integer32(1..4094)
            MAX-ACCESS     read-write
            STATUS         current 
            DESCRIPTION 
                ""     
            ::= {zxr10EponRemoteOnuPortEntry 24}
            
    onuVlanDelVid7 OBJECT-TYPE 	
    		SYNTAX         Integer32(1..4094)
            MAX-ACCESS     read-write 
            STATUS         current 
            DESCRIPTION 
                ""     
            ::= {zxr10EponRemoteOnuPortEntry 25}        
            
    onuVlanAddVid7  OBJECT-TYPE 	
    		SYNTAX         Integer32(1..4094)
            MAX-ACCESS     read-write
            STATUS         current 
            DESCRIPTION 
                ""     
            ::= {zxr10EponRemoteOnuPortEntry 26}
            
    onuVlanDelVid8 OBJECT-TYPE 	
    		SYNTAX         Integer32(1..4094)
            MAX-ACCESS     read-write 
            STATUS         current 
            DESCRIPTION 
                ""     
            ::= {zxr10EponRemoteOnuPortEntry 27}        
            
    onuVlanAddVid8  OBJECT-TYPE 	
    		SYNTAX         Integer32(1..4094)
            MAX-ACCESS     read-write
            STATUS         current 
            DESCRIPTION 
                ""     
            ::= {zxr10EponRemoteOnuPortEntry 28}                                                              
            
    onuRulePrecedenceSwitch  OBJECT-TYPE 	
    		SYNTAX         INTEGER{add(0),null(-1)}
            MAX-ACCESS     read-write
            STATUS         current 
            DESCRIPTION 
                ""     
            ::= {zxr10EponRemoteOnuPortEntry 29} 
            
    onuRulePrecedenceNum  OBJECT-TYPE 	
    		SYNTAX         Integer32
            MAX-ACCESS     read-write
            STATUS         current 
            DESCRIPTION 
                ""     
            ::= {zxr10EponRemoteOnuPortEntry 30}
            
    onuRuleProfile   OBJECT-TYPE 	
    		SYNTAX         DisplayString
            MAX-ACCESS     read-write
            STATUS         current 
            DESCRIPTION 
                ""     
            ::= {zxr10EponRemoteOnuPortEntry 31}  
            
    onuConditionList   OBJECT-TYPE 	
    		SYNTAX         DisplayString
            MAX-ACCESS     read-write
            STATUS         current 
            DESCRIPTION 
                ""     
            ::= {zxr10EponRemoteOnuPortEntry 32}                
            
    onuMultiVlanSwitch  OBJECT-TYPE 	
    		SYNTAX         INTEGER{add(0),delete(1),clear(2),null(-1)}
            MAX-ACCESS     read-write
            STATUS         current 
            DESCRIPTION 
                ""     
            ::= {zxr10EponRemoteOnuPortEntry 33} 
            
    onuMultiVlanList OBJECT-TYPE 	
    		SYNTAX         DisplayString
            MAX-ACCESS     read-write
            STATUS         current 
            DESCRIPTION 
                ""     
            ::= {zxr10EponRemoteOnuPortEntry 34}      
                             
    onuMultiVlanTagStripe  OBJECT-TYPE 	
    		SYNTAX         INTEGER{disable(0),enable(1)}
            MAX-ACCESS     read-write
            STATUS         current 
            DESCRIPTION 
                ""     
            ::= {zxr10EponRemoteOnuPortEntry 35}       
            
    onuMultiGroupMaxNum   OBJECT-TYPE 	
    		SYNTAX         Integer32(1..255)
            MAX-ACCESS     read-write
            STATUS         current 
            DESCRIPTION 
                ""     
            ::= {zxr10EponRemoteOnuPortEntry 36} 
            
    onuPortRowStatus   OBJECT-TYPE 	
    		SYNTAX         RowStatus
            MAX-ACCESS     read-write
            STATUS         current 
            DESCRIPTION 
                ""     
            ::= {zxr10EponRemoteOnuPortEntry 37}
            
    zxr10EponRemoteFastRebootTable  OBJECT-TYPE 	
    		SYNTAX         SEQUENCE OF Zxr10EponRemoteFastRebootEntry            
    		MAX-ACCESS     not-accessible 
            STATUS         current 
            DESCRIPTION 
                ""     
            ::= {zxr10EponRemoteOnu 6} 
            
    zxr10EponRemoteFastRebootEntry  OBJECT-TYPE 	
    		SYNTAX         Zxr10EponRemoteFastRebootEntry           
    		MAX-ACCESS     not-accessible 
            STATUS         current 
            DESCRIPTION 
                "index,for example epon-olt_1/1;onuId is the number of the onu"
            INDEX {ifIndex,onuId}     
            ::= {zxr10EponRemoteFastRebootTable 1}          
            
    Zxr10EponRemoteFastRebootEntry ::=
    		SEQUENCE {
    				remoteMultiFastLeave            INTEGER,
                    remoteReboot                    INTEGER
                    }
    
    remoteMultiFastLeave  OBJECT-TYPE 	
    		SYNTAX         INTEGER{
    							disable(1),
    							enable(2)
    							}
            MAX-ACCESS     read-write 
            STATUS         current 
            DESCRIPTION 
                "only to write"   
            ::= {zxr10EponRemoteFastRebootEntry 1} 
            
    remoteReboot  OBJECT-TYPE 	
    		SYNTAX         INTEGER{
    							disable(0),
    							enable(1)
    							}
            MAX-ACCESS     read-write 
            STATUS         current 
            DESCRIPTION 
                "only to write"   
            ::= {zxr10EponRemoteFastRebootEntry 2} 
            
   zxr10EponRemoteOnuVoipTable  OBJECT-TYPE 	
    		SYNTAX         SEQUENCE OF Zxr10EponRemoteOnuVoipEntry           
    		MAX-ACCESS     not-accessible 
            STATUS         current 
            DESCRIPTION 
                ""  
            ::= {zxr10EponRemoteOnu 7}
            
    zxr10EponRemoteOnuVoipEntry  OBJECT-TYPE 	
    		SYNTAX         Zxr10EponRemoteOnuVoipEntry           
    		MAX-ACCESS     not-accessible 
            STATUS         current 
            DESCRIPTION 
                "index,for example epon-olt_1/1;onuId is the number of the onu"
            INDEX {ifIndex,onuId,onuVoipUniNumber}     
            ::= {zxr10EponRemoteOnuVoipTable 1}          
            
    Zxr10EponRemoteOnuVoipEntry ::=
    		SEQUENCE { 
    				 onuVoipUniNumber         Integer32,
                     onuVoipEnableSwitch      INTEGER
                     }
    
    onuVoipUniNumber   OBJECT-TYPE 	
    		SYNTAX         Integer32(1..64)
            MAX-ACCESS     read-only 
            STATUS         current 
            DESCRIPTION 
                ""   
            ::= {zxr10EponRemoteOnuVoipEntry 1}
                     
    onuVoipEnableSwitch  OBJECT-TYPE 	
    		SYNTAX         INTEGER{disable(0),enable(1)}
            MAX-ACCESS     read-write 
            STATUS         current 
            DESCRIPTION 
                ""   
            ::= {zxr10EponRemoteOnuVoipEntry 2}
            
    zxr10EponRemoteOnuE1Table  OBJECT-TYPE 	
    		SYNTAX         SEQUENCE OF Zxr10EponRemoteOnuE1Entry           
    		MAX-ACCESS     not-accessible 
            STATUS         current 
            DESCRIPTION 
                ""    
            ::= {zxr10EponRemoteOnu 8}                        
                             
    zxr10EponRemoteOnuE1Entry  OBJECT-TYPE 	
    		SYNTAX         Zxr10EponRemoteOnuE1Entry           
    		MAX-ACCESS     not-accessible 
            STATUS         current 
            DESCRIPTION 
               "index,for example epon-olt_1/1;onuId is the number of the onu"
            INDEX {ifIndex,onuId,onuE1UniNumber}     
            ::= {zxr10EponRemoteOnuE1Table 1}          
            
    Zxr10EponRemoteOnuE1Entry ::=
    		SEQUENCE { 
    				 onuE1UniNumber         Integer32,
                     onuE1EnableSwitch      INTEGER
                     }
    
    onuE1UniNumber   OBJECT-TYPE 	
    		SYNTAX         Integer32(1..16)
            MAX-ACCESS     read-only 
            STATUS         current 
            DESCRIPTION 
                ""   
            ::= {zxr10EponRemoteOnuE1Entry 1}
                     
    onuE1EnableSwitch  OBJECT-TYPE 	
    		SYNTAX         INTEGER{disable(0),enable(1)}
            MAX-ACCESS     read-write 
            STATUS         current 
            DESCRIPTION 
                ""   
            ::= {zxr10EponRemoteOnuE1Entry 2}    
                     
END

--  ************************************************
--  $Id: ZXR10-ETH-MGT.mib 12 2005-07-13 01:01:17Z taowq $
--
--  ZXR10-ETH-MGT.mib: ZXR10 ethnet query and  configuration MIB file
--  
--  Jun. 2005, Tao wenqiang
--   
--  Copyright(c) 2005 by ZTE Corporaton
--  All rights reservered
--
--  ************************************************

ZXR10-ETH-MGT-MIB DEFINITIONS ::= BEGIN

IMPORTS
    MODULE-IDENTITY, 
    OBJECT-TYPE, 
    Integer32,
    Counter64
        FROM SNMPv2-SMI

    RowStatus                           
        FROM SNMPv2-TC

    IpAddress
        FROM RFC1155-SMI
        
    zxr10interfaces
        FROM ZXR10-SMI;

		 
		 
		 
    zxr10EthMgtMIB MODULE-IDENTITY
    LAST-UPDATED "200504120000Z"  -- April 12, 2005
    ORGANIZATION "ZTE Corporation"
    CONTACT-INFO
        "ZTE Corporation 
         Nanjing Institute of ZTE Corporation
         
         No.68 Zijinghua Rd. Yuhuatai District, Nanjing, China
         
         Tel: +86-25-52870000"

    DESCRIPTION
        "ZXROS v4.6.03 ethnet query and configuration MIB"

    REVISION "200504120000Z"  -- April 12, 2005
    DESCRIPTION
       ""

    ::= { zxr10interfaces 2 }

    zxr10EthMgtMIBObjects       OBJECT IDENTIFIER ::= { zxr10EthMgtMIB 1 }   
    
    zxr10EthQuery OBJECT IDENTIFIER
        ::=  { zxr10EthMgtMIBObjects 1 }
        
    zxr10EthConfiguration OBJECT IDENTIFIER
        ::=  { zxr10EthMgtMIBObjects 2 }     
        
    zxr10EthStats OBJECT IDENTIFIER
        ::=  { zxr10EthMgtMIBObjects 3 }            

    DisplayString ::= OCTET STRING
    --  This data type is used to model textual information taken
    --  from the NVT ASCII character set.  By convention, objects
    --  with this syntax are declared as having
    --  SIZE (0..255)
    
    InterfaceIndex ::= TEXTUAL-CONVENTION
        DISPLAY-HINT "d"
        STATUS       current
        DESCRIPTION
            "A unique value, greater than zero, for each interface or
            interface sub-layer in the managed system.  It is
            recommended that values are assigned contiguously starting
            from 1.  The value for each interface sub-layer must remain
            constant at least from one re-initialization of the entity's
            network management system to the next re-initialization."
        SYNTAX       Integer32 (1..2147483647)
    
    EthEncapsulationType ::= TEXTUAL-CONVENTION
        DISPLAY-HINT "d"
        STATUS       current
        DESCRIPTION
            "Ethnet encapsulation type such as 802.1Q"
        SYNTAX    
            INTEGER {
                encap-802dot1Q(1)
            }
            
    IfSpeedType ::= TEXTUAL-CONVENTION
        DISPLAY-HINT "d"
        STATUS       current
        DESCRIPTION
            "Ethnet encapsulation type such as 802.1Q"
        SYNTAX    
            INTEGER {
            	speed-auto(0),
   				speed-1000mbps(2),
   				speed-100mbps(3),
   				speed-10mbps(4)            
            }
                        

            
    EthPhyFrameType ::= TEXTUAL-CONVENTION
        DISPLAY-HINT "d"
        STATUS       current
        DESCRIPTION
            "Ethnet encapsulation type such as 802.1Q"
        SYNTAX    
            INTEGER {
               ethernet-II(1)            
            }
            
            
    EthPhyWorkType ::= TEXTUAL-CONVENTION
        DISPLAY-HINT "d"
        STATUS       current
        DESCRIPTION
            "Ethnet encapsulation type such as 802.1Q"
        SYNTAX    
            INTEGER {
                full-duplex(1),
                half-duplex(2)               
            }      
            
    EthNegotiationType ::= TEXTUAL-CONVENTION
        DISPLAY-HINT "d"
        STATUS       current
        DESCRIPTION
            "Ethnet encapsulation type such as 802.1Q"
        SYNTAX    
            INTEGER {
               auto(1),
               no-auto(0)               
            }                              
        
--- Sub interface query table

    zxr10EthSubIfQueryTable  OBJECT-TYPE
        SYNTAX  SEQUENCE OF Zxr10EthSubIfQueryEntry
        MAX-ACCESS  not-accessible
        STATUS  current
        DESCRIPTION
            "Ethnet sub interface query table"
        ::= { zxr10EthQuery 1 }

    zxr10EthSubIfQueryEntry  OBJECT-TYPE
        SYNTAX  Zxr10EthSubIfQueryEntry
        MAX-ACCESS  not-accessible
        STATUS  current
        DESCRIPTION
            ""
        INDEX  { zxr10EthSubIfParentIfIndex,zxr10EthSubIfIndex }
        ::= { zxr10EthSubIfQueryTable 1 }

    Zxr10EthSubIfQueryEntry ::=
        SEQUENCE {
            zxr10EthSubIfIndex
                InterfaceIndex,
            zxr10EthSubIfParentIfIndex
                InterfaceIndex,
            zxr10EthSubIfName
                DisplayString,
            zxr10EthSubIfParentIfName
                DisplayString

    }

    zxr10EthSubIfIndex  OBJECT-TYPE
        SYNTAX  InterfaceIndex 
        MAX-ACCESS  read-only 
        STATUS  current
        DESCRIPTION
            "Sub interface ifIndex "
        ::= { zxr10EthSubIfQueryEntry 1 }

    zxr10EthSubIfParentIfIndex  OBJECT-TYPE
        SYNTAX   InterfaceIndex
        MAX-ACCESS  read-only 
        STATUS  current
        DESCRIPTION
            "Sub interface's parent interface ifIndex"
        ::= { zxr10EthSubIfQueryEntry 2 }
        
    zxr10EthSubIfName  OBJECT-TYPE
        SYNTAX   DisplayString(SIZE(0..32))
        MAX-ACCESS  read-only 
        STATUS  current
        DESCRIPTION
        "Sub interface's name"        
         ::= { zxr10EthSubIfQueryEntry 3 }        

    zxr10EthSubIfParentIfName  OBJECT-TYPE
        SYNTAX   DisplayString(SIZE(0..32))
        MAX-ACCESS  read-only 
        STATUS  current
        DESCRIPTION
        "Parent interface's name"        
         ::= { zxr10EthSubIfQueryEntry 4 }    

-- Sub interface configuration table

    zxr10EthSubIfConfigTable  OBJECT-TYPE
        SYNTAX  SEQUENCE OF Zxr10EthSubIfConfigEntry
        MAX-ACCESS  not-accessible
        STATUS  current
        DESCRIPTION
            "Sub interface cnfigration table"
        ::= { zxr10EthConfiguration 1 }
        
    zxr10EthSubIfConfigEntry  OBJECT-TYPE
        SYNTAX  Zxr10EthSubIfConfigEntry
        MAX-ACCESS  not-accessible
        STATUS  current
        DESCRIPTION
            ""
        INDEX  { zxr10EthSubIfConfigParentIfIndex,zxr10EthSubIfConfigSubIfName }
        ::= { zxr10EthSubIfConfigTable 1 }

    Zxr10EthSubIfConfigEntry ::=
        SEQUENCE {
            zxr10EthSubIfConfigParentIfIndex
                Integer32,
            zxr10EthSubIfConfigParentIfName
                DisplayString,
            zxr10EthSubIfConfigSubIfIndex
                Integer32,                
            zxr10EthSubIfConfigSubIfName
                DisplayString,
            zxr10EthSubIfConfigVlanID
                Integer32,
            zxr10EthSubIfConfigEncapType
                EthEncapsulationType,
            zxr10EthSubIfConfigRowStatus
                RowStatus                
              
    }

    zxr10EthSubIfConfigParentIfIndex  OBJECT-TYPE
        SYNTAX  Integer32 
        MAX-ACCESS  read-only 
        STATUS  current
        DESCRIPTION
            "Parent interface ifIndex"
        ::= { zxr10EthSubIfConfigEntry 1 }    


    zxr10EthSubIfConfigParentIfName OBJECT-TYPE
        SYNTAX   DisplayString(SIZE(0..32))
        MAX-ACCESS  read-only
        STATUS  current
        DESCRIPTION
            " Parent interface name"
        ::= { zxr10EthSubIfConfigEntry 2 }          

    zxr10EthSubIfConfigSubIfIndex OBJECT-TYPE
        SYNTAX  Integer32 
        MAX-ACCESS  read-only
        STATUS  current
        DESCRIPTION
            "Sub interface ifIndex "
        ::= { zxr10EthSubIfConfigEntry 3 }          

    zxr10EthSubIfConfigSubIfName OBJECT-TYPE
        SYNTAX   DisplayString(SIZE(0..32))
        MAX-ACCESS  read-only
        STATUS  current
        DESCRIPTION
        "Sub interface name"
        ::= { zxr10EthSubIfConfigEntry 4 }           

    zxr10EthSubIfConfigVlanID OBJECT-TYPE
        SYNTAX   Integer32
        MAX-ACCESS  read-write
        STATUS  current
        DESCRIPTION
        "Vlan ID of this sub interface"
        ::= { zxr10EthSubIfConfigEntry 5 }         
        
    zxr10EthSubIfConfigEncapType OBJECT-TYPE
        SYNTAX   EthEncapsulationType
        MAX-ACCESS  read-write
        STATUS  current
        DESCRIPTION
        "Ethnet encapsulation type such as 802.1Q"
        ::= { zxr10EthSubIfConfigEntry 6 }                
    
    zxr10EthSubIfConfigRowStatus OBJECT-TYPE
        SYNTAX   RowStatus
        MAX-ACCESS  read-write
        STATUS  current
        DESCRIPTION
        "This object is used to manage creation and deletion of rows
         in this table.

         zxr10SecondaryIpAddrRowStatus must be set to 'creatAndGo' to create 
         an entry and set to 'destroy' to delete an entry.

         The value in any column may be modified any time even the
         value of this entry rowStatus object is 'active'.

         Caution has to be taken before destroying any entry. 
         Example: Need to change the IP address of an interface,
         which provides sole network connectivity.
         This has to be done by destroying the entry and creating
         a new one. The device would loose network connectivity
         after the entry is destroyed. In this case, the destroy 
         of the old entry and the creation on the new entry
         should be packed in the same PDU."
         ::= { zxr10EthSubIfConfigEntry 7 }        

    
    
-- Ethnet physic interface configuration table

    zxr10EthPhyIfTable  OBJECT-TYPE
        SYNTAX  SEQUENCE OF Zxr10EthPhyIfEntry
        MAX-ACCESS  not-accessible
        STATUS  current
        DESCRIPTION
            "Ethnet configuration table"
        ::= { zxr10EthConfiguration 3 }
        
    zxr10EthPhyIfEntry  OBJECT-TYPE
        SYNTAX  Zxr10EthPhyIfEntry
        MAX-ACCESS  not-accessible
        STATUS  current
        DESCRIPTION
            ""
        INDEX  { zxr10EthPhyIfIndex }
        ::= { zxr10EthPhyIfTable 1 }

    Zxr10EthPhyIfEntry ::=
        SEQUENCE {
            zxr10EthPhyIfIndex
                Integer32,
            zxr10EthPhyIfFrameType
                EthPhyFrameType,
            zxr10EthPhyIfNegotiation
                EthNegotiationType,
            zxr10EthPhyWorkType
                EthPhyWorkType,                
            zxr10EthPhyIfSpeed
                IfSpeedType,
            zxr10EthPhyIfMTU
                Integer32
    }

    zxr10EthPhyIfIndex  OBJECT-TYPE
        SYNTAX  Integer32 
        MAX-ACCESS  read-only 
        STATUS  current
        DESCRIPTION
            "Physical Ethnet interface ifIndex"
        ::= { zxr10EthPhyIfEntry 1 }    


    zxr10EthPhyIfFrameType OBJECT-TYPE
        SYNTAX   EthPhyFrameType
        MAX-ACCESS  read-write
        STATUS  current
        DESCRIPTION
            " "
        ::= { zxr10EthPhyIfEntry 2 }          

    zxr10EthPhyIfNegotiation OBJECT-TYPE
        SYNTAX  EthNegotiationType
        MAX-ACCESS  read-write
        STATUS  current
        DESCRIPTION
            ""
        ::= { zxr10EthPhyIfEntry 3 }          

    zxr10EthPhyWorkType OBJECT-TYPE
        SYNTAX   EthPhyWorkType
        MAX-ACCESS  read-write
        STATUS  current
        DESCRIPTION
        ""
        ::= { zxr10EthPhyIfEntry 4 }           

    zxr10EthPhyIfSpeed OBJECT-TYPE
        SYNTAX   IfSpeedType
        MAX-ACCESS  read-write
        STATUS  current
        DESCRIPTION
        ""
        ::= { zxr10EthPhyIfEntry 5 }         
        
    zxr10EthPhyIfMTU OBJECT-TYPE
        SYNTAX   Integer32
        MAX-ACCESS  read-write
        STATUS  current
        DESCRIPTION
        "Ethnet encapsulation type such as 802.1Q"
        ::= { zxr10EthPhyIfEntry 6 }       
    
-- Ethnet stats table

    zxr10EthRecvStatsTable  OBJECT-TYPE
        SYNTAX  SEQUENCE OF Zxr10EthRecvStatsEntry
        MAX-ACCESS  not-accessible
        STATUS  current
        DESCRIPTION
            "Ethnet configuration table"
        ::= { zxr10EthStats 1 }
        
    zxr10EthRecvStatsEntry  OBJECT-TYPE
        SYNTAX  Zxr10EthRecvStatsEntry
        MAX-ACCESS  not-accessible
        STATUS  current
        DESCRIPTION
            ""
        INDEX  { zxr10EthPhyIfIndex }
        ::= { zxr10EthRecvStatsTable 1 }

    Zxr10EthRecvStatsEntry ::=
        SEQUENCE {
            zxr10EthRecvStatsIfIndex
                Integer32,
            zxr10EthRecvPktsUnder64Octects
                Counter64,
            zxr10EthRecvPkts64Octects
                Counter64,
            zxr10EthRecvPkts65to127Octects
                Counter64,
            zxr10EthRecvPkts128to255Octects
                Counter64,                
            zxr10EthRecvPkts255to511Octects
                Counter64,
            zxr10EthRecvPkts512to1023Octects
                Counter64,
            zxr10EthRecvPkts1024to1518Octects
                Counter64,
            zxr10EthRecvPktsOverSize
                Counter64, 
            zxr10EthRecvPktsCRCError
                Counter64, 
            zxr10EthRecvClearCounts
                INTEGER
                              
                                                                                                                                                 
    }

    zxr10EthRecvStatsIfIndex  OBJECT-TYPE
        SYNTAX  Integer32 
        MAX-ACCESS  read-only 
        STATUS  current
        DESCRIPTION
            "Physical Ethnet interface ifIndex"
        ::= { zxr10EthRecvStatsEntry 1 }    


    zxr10EthRecvPktsUnder64Octects OBJECT-TYPE
        SYNTAX   Counter64
        MAX-ACCESS  read-only
        STATUS  current
        DESCRIPTION
            " "
        ::= { zxr10EthRecvStatsEntry 2 }          

    zxr10EthRecvPkts64Octects OBJECT-TYPE
        SYNTAX  Counter64
        MAX-ACCESS  read-only
        STATUS  current
        DESCRIPTION
            ""
        ::= { zxr10EthRecvStatsEntry 3 }          

    zxr10EthRecvPkts65to127Octects OBJECT-TYPE
        SYNTAX   Counter64
        MAX-ACCESS  read-only
        STATUS  current
        DESCRIPTION
        ""
        ::= { zxr10EthRecvStatsEntry 4 }           

    zxr10EthRecvPkts128to255Octects OBJECT-TYPE
        SYNTAX   Counter64
        MAX-ACCESS  read-only
        STATUS  current
        DESCRIPTION
        ""
        ::= { zxr10EthRecvStatsEntry 5 }         
        
    zxr10EthRecvPkts255to511Octects OBJECT-TYPE
        SYNTAX   Counter64
        MAX-ACCESS  read-only
        STATUS  current
        DESCRIPTION
        ""
        ::= { zxr10EthRecvStatsEntry 6 }       

    zxr10EthRecvPkts512to1023Octects OBJECT-TYPE
        SYNTAX   Counter64
        MAX-ACCESS  read-only
        STATUS  current
        DESCRIPTION
        ""
        ::= { zxr10EthRecvStatsEntry 7 }               

    zxr10EthRecvPkts1024to1518Octects OBJECT-TYPE
        SYNTAX   Counter64
        MAX-ACCESS  read-only
        STATUS  current
        DESCRIPTION
        ""
        ::= { zxr10EthRecvStatsEntry 8 } 
        
    zxr10EthRecvPktsOverSize OBJECT-TYPE
        SYNTAX   Counter64
        MAX-ACCESS  read-only
        STATUS  current
        DESCRIPTION
        ""
        ::= { zxr10EthRecvStatsEntry 9 } 
        
    zxr10EthRecvPktsCRCError OBJECT-TYPE
        SYNTAX   Counter64
        MAX-ACCESS  read-only
        STATUS  current
        DESCRIPTION
        ""
        ::= { zxr10EthRecvStatsEntry 10 } 
       
    zxr10EthRecvClearCounts OBJECT-TYPE
        SYNTAX INTEGER{clear(1)}
        MAX-ACCESS  read-write
        STATUS  current
        DESCRIPTION
        " If set value to 1 ,clear interface counters"
        ::= { zxr10EthRecvStatsEntry 11 } 
                
-- Send stats Table
       
    zxr10EthSndStatsTable  OBJECT-TYPE
        SYNTAX  SEQUENCE OF Zxr10EthSndStatsEntry
        MAX-ACCESS  not-accessible
        STATUS  current
        DESCRIPTION
            "Ethnet configuration table"
        ::= { zxr10EthStats 2 }
        
    zxr10EthSndStatsEntry  OBJECT-TYPE
        SYNTAX  Zxr10EthSndStatsEntry
        MAX-ACCESS  not-accessible
        STATUS  current
        DESCRIPTION
            ""
        INDEX  { zxr10EthPhyIfIndex }
        ::= { zxr10EthSndStatsTable 1 }

    Zxr10EthSndStatsEntry ::=
        SEQUENCE {
            zxr10EthSndStatsIfIndex
                Integer32,
            zxr10EthSndPktsUnder64Octects
                Counter64,
            zxr10EthSndPkts64Octects
                Counter64,
            zxr10EthSndPkts65to127Octects
                Counter64,
            zxr10EthSndPkts128to255Octects
                Counter64,                
            zxr10EthSndPkts255to511Octects
                Counter64,
            zxr10EthSndPkts512to1023Octects
                Counter64,
            zxr10EthSndPkts1024to1518Octects
                Counter64,
            zxr10EthSndPktsOverSize
                Counter64, 
            zxr10EthSndClearCounts                               
                INTEGER
                                                                                                                                                 
    }

    zxr10EthSndStatsIfIndex  OBJECT-TYPE
        SYNTAX  Integer32 
        MAX-ACCESS  read-only 
        STATUS  current
        DESCRIPTION
            "Physical Ethnet interface ifIndex"
        ::= { zxr10EthSndStatsEntry 1 }    


    zxr10EthSndPktsUnder64Octects OBJECT-TYPE
        SYNTAX   Counter64
        MAX-ACCESS  read-only
        STATUS  current
        DESCRIPTION
            " "
        ::= { zxr10EthSndStatsEntry 2 }          

    zxr10EthSndPkts64Octects OBJECT-TYPE
        SYNTAX  Counter64
        MAX-ACCESS  read-only
        STATUS  current
        DESCRIPTION
            ""
        ::= { zxr10EthSndStatsEntry 3 }          

    zxr10EthSndPkts65to127Octects OBJECT-TYPE
        SYNTAX   Counter64
        MAX-ACCESS  read-only
        STATUS  current
        DESCRIPTION
        ""
        ::= { zxr10EthSndStatsEntry 4 }           

    zxr10EthSndPkts128to255Octects OBJECT-TYPE
        SYNTAX   Counter64
        MAX-ACCESS  read-only
        STATUS  current
        DESCRIPTION
        ""
        ::= { zxr10EthSndStatsEntry 5 }         
        
    zxr10EthSndPkts255to511Octects OBJECT-TYPE
        SYNTAX   Counter64
        MAX-ACCESS  read-only
        STATUS  current
        DESCRIPTION
        ""
        ::= { zxr10EthSndStatsEntry 6 }       

    zxr10EthSndPkts512to1023Octects OBJECT-TYPE
        SYNTAX   Counter64
        MAX-ACCESS  read-only
        STATUS  current
        DESCRIPTION
        ""
        ::= { zxr10EthSndStatsEntry 7 }               

    zxr10EthSndPkts1024to1518Octects OBJECT-TYPE
        SYNTAX   Counter64
        MAX-ACCESS  read-only
        STATUS  current
        DESCRIPTION
        ""
        ::= { zxr10EthSndStatsEntry 8 } 
        

    zxr10EthSndPktsOverSize OBJECT-TYPE
        SYNTAX   Counter64
        MAX-ACCESS  read-only
        STATUS  current
        DESCRIPTION
        ""
        ::= { zxr10EthSndStatsEntry 9 } 

    zxr10EthSndClearCounts  OBJECT-TYPE
        SYNTAX INTEGER{clear(1)}
        MAX-ACCESS  read-write
        STATUS  current
        DESCRIPTION
        "If set value to 1,clear interface counters"
        ::= { zxr10EthSndStatsEntry 10 }           
        
    zxr10EthLoopBackTable  OBJECT-TYPE
        SYNTAX  SEQUENCE OF Zxr10EthLoopBackEntry
        MAX-ACCESS  not-accessible
        STATUS  current
        DESCRIPTION
            "Ethnet loopback interface table"
        ::= { zxr10EthConfiguration 4 }

    zxr10EthLoopBackEntry  OBJECT-TYPE
        SYNTAX  Zxr10EthLoopBackEntry
        MAX-ACCESS  not-accessible
        STATUS  current
        DESCRIPTION
            ""
        INDEX  { zxr10EthLoopBackNo}
        ::= { zxr10EthLoopBackTable 1 }

    Zxr10EthLoopBackEntry ::=
        SEQUENCE {
            zxr10EthLoopBackIfIndex
                InterfaceIndex,
            zxr10EthLoopBackIfName
                DisplayString,
            zxr10EthLoopBackNo
           		INTEGER,   
            zxr10EthLoopBackRowStatus
            	RowStatus
	    }
	    
    zxr10EthLoopBackIfIndex OBJECT-TYPE
        SYNTAX   InterfaceIndex
        MAX-ACCESS  read-only
        STATUS  current
        DESCRIPTION
        ""
        ::= { zxr10EthLoopBackEntry 1 } 	    

    zxr10EthLoopBackIfName OBJECT-TYPE
        SYNTAX   DisplayString(SIZE(0..32))
        MAX-ACCESS  read-only
        STATUS  current
        DESCRIPTION
        ""
        ::= { zxr10EthLoopBackEntry 2 } 	    
                                       
    zxr10EthLoopBackNo OBJECT-TYPE
        SYNTAX   INTEGER(1..64)
        MAX-ACCESS  read-only 
        STATUS  current
        DESCRIPTION
        ""
        ::= { zxr10EthLoopBackEntry 3 } 	    
                                       
    zxr10EthLoopBackRowStatus OBJECT-TYPE
        SYNTAX   RowStatus
        MAX-ACCESS  read-write
        STATUS  current
        DESCRIPTION
        ""
        ::= { zxr10EthLoopBackEntry 4 } 	    
                                       


    END

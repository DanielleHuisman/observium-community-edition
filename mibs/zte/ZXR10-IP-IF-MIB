--  ************************************************
--  $Id: ZXR10-IP-IF.mib 13 2005-07-13 01:01:26Z taowq $
--
--  zxr10-IP-IF.mib: ZXR10 IP Interface Configuration MIB file
--  
--  Jun. 2005, Tao wenqiang
--   
--  Copyright(c) 2005 by ZTE Corporaton
--  All rights reservered
--
--  ************************************************

ZXR10-IP-IF-MIB DEFINITIONS ::= BEGIN

IMPORTS
    MODULE-IDENTITY, 
    OBJECT-TYPE, 
    Integer32 
        FROM SNMPv2-SMI

    RowStatus                           
        FROM SNMPv2-TC

    IpAddress
        FROM RFC1155-SMI
        
    zxr10interfaces
        FROM ZXR10-SMI

    ifIndex            
		 FROM RFC1213-MIB;
		 
		 
		 
    zxr10IPIfMIB MODULE-IDENTITY
    LAST-UPDATED "200504120000Z"  -- April 12, 2005
    ORGANIZATION "ZTE Corporation"
    CONTACT-INFO
        "ZTE Corporation 
         Nanjing Institute of ZTE Corporation
         
         No.68 Zijinghua Rd. Yuhuatai District, Nanjing, China
         
         Tel: +86-25-52870000"

    DESCRIPTION
        "ZXROS v4.6.02 Interfaces config MIB"

    REVISION "200504120000Z"  -- April 12, 2005
    DESCRIPTION
       ""

    ::= { zxr10interfaces 1 }

    zxr10IPIfMIBObjects       OBJECT IDENTIFIER ::= { zxr10IPIfMIB 1 }   
    
    zxr10IPAddressConfiguration OBJECT IDENTIFIER
        ::=  { zxr10IPIfMIBObjects 1 }

    DisplayString ::= OCTET STRING
    --  This data type is used to model textual information taken
    --  from the NVT ASCII character set.  By convention, objects
    --  with this syntax are declared as having
    --  SIZE (0..255)

--- Primary Ip address table

    zxr10IPAddrTable  OBJECT-TYPE
        SYNTAX  SEQUENCE OF Zxr10IPAddrEntry
        MAX-ACCESS  not-accessible
        STATUS  current
        DESCRIPTION
            "Ip address config table."
        ::= { zxr10IPAddressConfiguration 1 }

    zxr10IPAddrEntry  OBJECT-TYPE
        SYNTAX  Zxr10IPAddrEntry
        MAX-ACCESS  not-accessible
        STATUS  current
        DESCRIPTION
            ""
        INDEX  { ifIndex }
        ::= { zxr10IPAddrTable 1 }

    Zxr10IPAddrEntry ::=
        SEQUENCE {
            zxr10IPAddrPrimaryIp
                IpAddress,
            zxr10IPAddrPrimaryIpMask
                IpAddress,
            zxr10IPAddrBroadcast
                IpAddress,
            zxr10IPAddrRowStatus
                RowStatus,
            zxr10IPAddrIfName
                DisplayString
    }

    zxr10IPAddrPrimaryIp  OBJECT-TYPE
        SYNTAX  IpAddress 
        MAX-ACCESS  read-write 
        STATUS  current
        DESCRIPTION
            "The main Ip address on this interface "
        ::= { zxr10IPAddrEntry 1 }

    zxr10IPAddrPrimaryIpMask  OBJECT-TYPE
        SYNTAX   IpAddress
        MAX-ACCESS  read-write
        STATUS  current
        DESCRIPTION
            "The mask of primary Ip address on this interface"
        ::= { zxr10IPAddrEntry 2 }
     
    zxr10IPAddrBroadcast    OBJECT-TYPE
        SYNTAX   IpAddress
        MAX-ACCESS  read-write
        STATUS  current
        DESCRIPTION
            "The Broadcast address on this interface"
        ::= { zxr10IPAddrEntry 3}

       
    zxr10IPAddrRowStatus  OBJECT-TYPE
        SYNTAX   RowStatus
        MAX-ACCESS  read-write
        STATUS  current
        DESCRIPTION
        "This object is used to manage creation and deletion of rows
         in this table.

         zxr10IpAddrRowStatus must be set to 'creatAndGo' to create 
         an entry and set to 'destroy' to delete an entry.

         The value in any column may be modified any time even the
         value of this entry rowStatus object is 'active'.

         Caution has to be taken before destroying any entry. 
         Example: Need to change the IP address of an interface,
         which provides sole network connectivity.
         This has to be done by destroying the entry and creating
         a new one. The device would loose network connectivity
         after the entry is destroyed. In this case, the destroy 
         of the old entry and the creation on the new entry
         should be packed in the same PDU."        
         ::= { zxr10IPAddrEntry 4 }        

    zxr10IPAddrIfName    OBJECT-TYPE
        SYNTAX   DisplayString(SIZE(0..32))
        MAX-ACCESS  read-only
        STATUS  current
        DESCRIPTION
            "Interface name"
        ::= { zxr10IPAddrEntry 5}

-- secondary Ip address configration table

    zxr10IPSecondaryAddrTable  OBJECT-TYPE
        SYNTAX  SEQUENCE OF Zxr10IPSecondaryAddrEnry
        MAX-ACCESS  not-accessible
        STATUS  current
        DESCRIPTION
            "Secondary Ip address config table."
        ::= { zxr10IPAddressConfiguration 2 }
        
    zxr10IPSecondaryAddrEnry  OBJECT-TYPE
        SYNTAX  Zxr10IPSecondaryAddrEnry
        MAX-ACCESS  not-accessible
        STATUS  current
        DESCRIPTION
            ""
        INDEX  { ifIndex,zxr10IPSecondaryAddr }
        ::= { zxr10IPSecondaryAddrTable 1 }

    Zxr10IPSecondaryAddrEnry ::=
        SEQUENCE {
            zxr10IPSecondaryAddr
                IpAddress,
            zxr10IPSecondaryAddrMask
                IpAddress,
            zxr10IPSecondaryAddrRowStatus
                RowStatus,
            zxr10IPSecondaryIfName
                DisplayString                
    }

    zxr10IPSecondaryAddr OBJECT-TYPE
        SYNTAX   IpAddress
        MAX-ACCESS  read-write
        STATUS  current
        DESCRIPTION
            "  Secondary Ip address on this interface"
        ::= { zxr10IPSecondaryAddrEnry 1 }          

    zxr10IPSecondaryAddrMask OBJECT-TYPE
        SYNTAX   IpAddress
        MAX-ACCESS  read-write
        STATUS  current
        DESCRIPTION
            "  Secondary Ip mask on this interface   "
        ::= { zxr10IPSecondaryAddrEnry 2 }          

    zxr10IPSecondaryAddrRowStatus OBJECT-TYPE
        SYNTAX   RowStatus
        MAX-ACCESS  read-write
        STATUS  current
        DESCRIPTION
        "This object is used to manage creation and deletion of rows
         in this table.

         zxr10SecondaryIpAddrRowStatus must be set to 'creatAndGo' to create 
         an entry and set to 'destroy' to delete an entry.

         The value in any column may be modified any time even the
         value of this entry rowStatus object is 'active'.

         Caution has to be taken before destroying any entry. 
         Example: Need to change the IP address of an interface,
         which provides sole network connectivity.
         This has to be done by destroying the entry and creating
         a new one. The device would loose network connectivity
         after the entry is destroyed. In this case, the destroy 
         of the old entry and the creation on the new entry
         should be packed in the same PDU."
        ::= { zxr10IPSecondaryAddrEnry 3 }           

    zxr10IPSecondaryIfName OBJECT-TYPE
        SYNTAX   DisplayString(SIZE(0..32))
        MAX-ACCESS  read-only
        STATUS  current
        DESCRIPTION
            "  Interface name   "
        ::= { zxr10IPSecondaryAddrEnry 4 }     

    
    END

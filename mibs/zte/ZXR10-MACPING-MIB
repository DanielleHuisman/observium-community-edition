--  ************************************************
--  $Id: zxr10ping.mib 8 2005-07-28 12:17:08Z zhanglh $
--
--  zxr10macping.mib: ZXR10 Ping MIB file
--  
--  JUL. 2005, Zhang lihui
--   
--  Copyright(c) 2005 by ZTE Corporaton
--  All rights reservered
--
--  ************************************************

ZXR10-MACPING-MIB DEFINITIONS ::= BEGIN

IMPORTS
    MODULE-IDENTITY, 
    OBJECT-TYPE, 
    NOTIFICATION-TYPE,
    experimental, 
    Integer32, 
    Unsigned32, 
    Counter32
        FROM SNMPv2-SMI

    MODULE-COMPLIANCE, 
    OBJECT-GROUP, 
    NOTIFICATION-GROUP
        FROM SNMPv2-CONF
    enterprises                      
        FROM SNMPv2-SMI     
        
    MacAddress,RowStatus,TruthValue                           
        FROM SNMPv2-TC   
      
    zxr10L2vpn
        FROM ZXR10-SMI                                  

    mgmt, 
    NetworkAddress, 
    IpAddress, 
    Counter, 
    Gauge
        FROM RFC1155-SMI;

    zxr10MacPingMIB OBJECT IDENTIFIER ::= { zxr10L2vpn 4}

    DisplayString ::= OCTET STRING
    --  This data type is used to model textual information taken
    --  from the NVT ASCII character set.  By convention, objects
    --  with this syntax are declared as having
    --  SIZE (0..255)

    OptionType ::= INTEGER
                      {
                        ce(0),
                        pe(1)
                      }

    zxr10MacPingTable  OBJECT-TYPE
        SYNTAX  SEQUENCE OF Zxr10MacPingEntry
        MAX-ACCESS  not-accessible
        STATUS  current
        DESCRIPTION
            "mac ping information table."
        ::= { zxr10MacPingMIB 1 }

    zxr10MacPingEntry  OBJECT-TYPE
        SYNTAX  Zxr10MacPingEntry
        MAX-ACCESS  not-accessible
        STATUS  current
        DESCRIPTION
            ""
        INDEX  { zxr10PingMacSerial }
        ::= { zxr10MacPingTable 1 }

    Zxr10MacPingEntry ::=
        SEQUENCE {        
            zxr10PingMacSerial 
                Integer32,
            zxr10PingMacDestMac
                MacAddress,
            zxr10PingMacControlOutEtherIf
                INTEGER,    
            zxr10PingMacIfOption
                INTEGER,    
            zxr10PingMacPacketCount 
                Integer32,   
            zxr10PingMacTimeOut   
                Integer32,  
            zxr10PingMacHops     
                Integer32,    
            zxr10PingMacControlResultType 
                INTEGER,
            zxr10PingMacTrapOncompletion    
                TruthValue,
            zxr10PingMacRosStatus
                INTEGER,    
            zxr10PingMacEntryOwner  
                DisplayString,
            zxr10PingMacIfPeOption
                OptionType,
            zxr10PingMacVfiName
                DisplayString,
            zxr10PingMacPeerAddress
                IpAddress                      
    }

    zxr10PingMacSerial  OBJECT-TYPE
        SYNTAX  Integer32 
        MAX-ACCESS  read-only 
        STATUS  current
        DESCRIPTION
            ""
        ::= { zxr10MacPingEntry 1 }      
        
    zxr10PingMacDestMac  OBJECT-TYPE
        SYNTAX  MacAddress 
        MAX-ACCESS  read-write 
        STATUS  current
        DESCRIPTION
            "dest mac"
        ::= { zxr10MacPingEntry 2 }          
        
    zxr10PingMacControlOutEtherIf  OBJECT-TYPE
        SYNTAX  INTEGER 
        MAX-ACCESS  read-write 
        STATUS  current
        DESCRIPTION
            "output interface if-index"
        ::= { zxr10MacPingEntry 3 }     
        
    zxr10PingMacIfOption  OBJECT-TYPE
        SYNTAX  INTEGER {none(0),option(1)}
        MAX-ACCESS  read-write 
        STATUS  current
        DESCRIPTION
            "option,default:none "
        ::= { zxr10MacPingEntry 4 }        
                
        
    zxr10PingMacPacketCount  OBJECT-TYPE
        SYNTAX  Integer32 
        MAX-ACCESS  read-write 
        STATUS  current
        DESCRIPTION
            "packet count"
        ::= { zxr10MacPingEntry 5 }             
            
    zxr10PingMacTimeOut  OBJECT-TYPE
        SYNTAX  Integer32 (1..60)
        MAX-ACCESS  read-write 
        STATUS  current
        DESCRIPTION
            "timeout  "
        ::= { zxr10MacPingEntry 6 }      
        
    zxr10PingMacHops  OBJECT-TYPE
        SYNTAX  Integer32 (1..10)
        MAX-ACCESS  read-write 
        STATUS  current
        DESCRIPTION
            "hops   "
        ::= { zxr10MacPingEntry 7 }     
        
    zxr10PingMacControlResultType  OBJECT-TYPE
        SYNTAX  INTEGER {summary(0),detail(1)}
        MAX-ACCESS  read-write 
        STATUS  current
        DESCRIPTION
            "result type "
        ::= { zxr10MacPingEntry 8 }               
        
     
    zxr10PingMacTrapOncompletion  OBJECT-TYPE
        SYNTAX  TruthValue 
        MAX-ACCESS  read-write 
        STATUS  current
        DESCRIPTION
            ""
        DEFVAL       { true }    
        ::= { zxr10MacPingEntry 9 }         
        
        
    zxr10PingMacRosStatus  OBJECT-TYPE
        SYNTAX  INTEGER{not-active(1),start-ping(2),ping-processing(3),ping-completed(4)} 
        MAX-ACCESS  read-write 
        STATUS  current
        DESCRIPTION
            ""
        DEFVAL       { 1 }    
        ::= { zxr10MacPingEntry 10 }       
        
        
    zxr10PingMacEntryOwner  OBJECT-TYPE
        SYNTAX  DisplayString 
        MAX-ACCESS  read-write 
        STATUS  current
        DESCRIPTION
            ""
        ::= { zxr10MacPingEntry 11 }            
    
    zxr10PingMacIfPeOption  OBJECT-TYPE
        SYNTAX  OptionType 
        MAX-ACCESS  read-write 
        STATUS  current
        DESCRIPTION
            ""
        ::= { zxr10MacPingEntry 12 }
                    
    zxr10PingMacVfiName  OBJECT-TYPE
        SYNTAX  DisplayString 
        MAX-ACCESS  read-write 
        STATUS  current
        DESCRIPTION
            ""
        ::= { zxr10MacPingEntry 13 }
 
     zxr10PingMacPeerAddress  OBJECT-TYPE
        SYNTAX  IpAddress 
        MAX-ACCESS  read-write 
        STATUS  current
        DESCRIPTION
            ""
        ::= { zxr10MacPingEntry 14 }
    
    
 --- mac ping result 

        
    zxr10PingMacResultTable  OBJECT-TYPE
        SYNTAX  SEQUENCE OF Zxr10pingMacResultEntry
        MAX-ACCESS  not-accessible
        STATUS  current
        DESCRIPTION
            "mac ping result table."
        ::= { zxr10MacPingMIB 2 }

    zxr10pingMacResultEntry  OBJECT-TYPE
        SYNTAX  Zxr10pingMacResultEntry
        MAX-ACCESS  not-accessible
        STATUS  current
        DESCRIPTION
            ""
        INDEX  { zxr10PingMacResultSerial }
        ::= { zxr10PingMacResultTable 1 }    
    
    
    Zxr10pingMacResultEntry ::=
        SEQUENCE {
            zxr10PingMacResultSerial 
                Integer32,
            zxr10PingMacResultSentPkts
                Integer32,
            zxr10PingMacResultRcvPkts
                Integer32,
            zxr10PingMacResultRoundTripMinTime
                Integer32,
            zxr10PingMacResultRoundTripMaxTime
                Integer32,    
            zxr10PingMacResultRoundTripAvgTime
                Integer32,       
            zxr10PingMacResultType 
                INTEGER,   
            zxr10PingMacExtResultDestIfName
                DisplayString,
            zxr10PingMacExtResultDestHostName
                DisplayString,
            zxr10PingMacExtResultSourceIfName
                DisplayString,
            zxr10PingMacExtResultSourceHostName
                DisplayString,  
            zxr10PingMacExtResultOutVlanId
                Integer32,
            zxr10PingMacExtResultInVlanId
                Integer32,                    
            zxr10PingMacResultEntryOwner
                DisplayString,     
            zxr10PingMacResultRoundWobbleMinTime
            	Integer32, 
   			zxr10PingMacResultRoundWobbleMaxTime
   				Integer32, 
   			zxr10PingMacResultRoundWobbleAvgTime
   				Integer32   
    }
    
     zxr10PingMacResultSerial  OBJECT-TYPE
        SYNTAX  Integer32 
        MAX-ACCESS  read-only 
        STATUS  current
        DESCRIPTION
            ""
        ::= { zxr10pingMacResultEntry 1 }
    
     zxr10PingMacResultSentPkts  OBJECT-TYPE
        SYNTAX  Integer32 
        MAX-ACCESS  read-only 
        STATUS  current
        DESCRIPTION
            "send packets"
        ::= { zxr10pingMacResultEntry 2 }
   
   
     zxr10PingMacResultRcvPkts  OBJECT-TYPE
        SYNTAX  Integer32 
        MAX-ACCESS  read-only 
        STATUS  current
        DESCRIPTION
            "receive packets"
        ::= { zxr10pingMacResultEntry 3 } 
    
     zxr10PingMacResultRoundTripMinTime  OBJECT-TYPE
        SYNTAX  Integer32 
        MAX-ACCESS  read-only 
        STATUS  current
        DESCRIPTION
            "min RTT"
        ::= { zxr10pingMacResultEntry 4 }  
    
     zxr10PingMacResultRoundTripMaxTime  OBJECT-TYPE
        SYNTAX  Integer32 
        MAX-ACCESS  read-only 
        STATUS  current
        DESCRIPTION
            "max RTT"
        ::= { zxr10pingMacResultEntry 5 }  
    
     zxr10PingMacResultRoundTripAvgTime  OBJECT-TYPE
        SYNTAX  Integer32 
        MAX-ACCESS  read-only 
        STATUS  current
        DESCRIPTION
            "average RTT"
        ::= { zxr10pingMacResultEntry 6 }     
        
     zxr10PingMacResultType  OBJECT-TYPE
        SYNTAX  INTEGER {summary(0),detail(1)}
        MAX-ACCESS  read-only 
        STATUS  current
        DESCRIPTION
            "result type:(0:summary,1:detail)"
        ::= { zxr10pingMacResultEntry 7 }           
        
     zxr10PingMacExtResultDestIfName  OBJECT-TYPE
        SYNTAX  DisplayString (SIZE(0..32))
        MAX-ACCESS  read-only 
        STATUS  current
        DESCRIPTION
            "destion interface"
        ::= { zxr10pingMacResultEntry 8 }            
        
     zxr10PingMacExtResultDestHostName  OBJECT-TYPE
        SYNTAX  DisplayString (SIZE(0..17))
        MAX-ACCESS  read-only 
        STATUS  current
        DESCRIPTION
            "destion hostname"
        ::= { zxr10pingMacResultEntry 9 }    
        
        
     zxr10PingMacExtResultSourceIfName  OBJECT-TYPE
        SYNTAX  DisplayString (SIZE(0..32))
        MAX-ACCESS  read-only 
        STATUS  current
        DESCRIPTION
            "source interface"
        ::= { zxr10pingMacResultEntry 10 }             
                     
     zxr10PingMacExtResultSourceHostName  OBJECT-TYPE
        SYNTAX  DisplayString (SIZE(0..17))
        MAX-ACCESS  read-only 
        STATUS  current
        DESCRIPTION
            "source hostname"
        ::= { zxr10pingMacResultEntry 11 }        
        
        
     zxr10PingMacExtResultOutVlanId  OBJECT-TYPE
        SYNTAX  Integer32 (0..4096)
        MAX-ACCESS  read-only 
        STATUS  current
        DESCRIPTION
            "out vlanid"
        ::= { zxr10pingMacResultEntry 12 }         
                          
     zxr10PingMacExtResultInVlanId  OBJECT-TYPE
        SYNTAX  Integer32 (0..4096)
        MAX-ACCESS  read-only 
        STATUS  current
        DESCRIPTION
            "in vlanid"
        ::= { zxr10pingMacResultEntry 13 }         
        
        
     zxr10PingMacResultEntryOwner  OBJECT-TYPE
        SYNTAX  DisplayString 
        MAX-ACCESS  read-only 
        STATUS  current
        DESCRIPTION
            ""
        ::= { zxr10pingMacResultEntry 14 }           
                                            
     zxr10PingMacResultRoundWobbleMinTime  OBJECT-TYPE
     	SYNTAX  Integer32 
        MAX-ACCESS  read-only 
        STATUS  current
        DESCRIPTION
            "min RWT"
        ::= { zxr10pingMacResultEntry 15 }
        
   	 zxr10PingMacResultRoundWobbleMaxTime  OBJECT-TYPE
   	 	SYNTAX  Integer32 
        MAX-ACCESS  read-only 
        STATUS  current
        DESCRIPTION
            "max RWT"
        ::= { zxr10pingMacResultEntry 16 }
        
	 zxr10PingMacResultRoundWobbleAvgTime  OBJECT-TYPE
		SYNTAX  Integer32 
        MAX-ACCESS  read-only 
        STATUS  current
        DESCRIPTION
            "average RWT"
        ::= { zxr10pingMacResultEntry 17 }
        
             
                                            
-- *******************************************************************
--   Trap Definitions
-- *******************************************************************

 macpingNotifications   OBJECT IDENTIFIER ::= { zxr10MacPingMIB 3 }




     macpingTrapResult NOTIFICATION-TYPE
     OBJECTS      { zxr10PingMacResultSerial,
                    zxr10PingMacResultSentPkts,
                    zxr10PingMacResultRcvPkts,
                    zxr10PingMacResultRoundTripMinTime,
                    zxr10PingMacResultRoundTripMaxTime,
                    zxr10PingMacResultRoundTripAvgTime


                  }
     STATUS       current
     DESCRIPTION
         "The newMaster trap indicates that the sending agent
         has transitioned to 'Master' state."
     ::= { macpingNotifications 1 }                                         
                      
                      
    END

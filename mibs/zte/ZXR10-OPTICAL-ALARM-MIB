--  ************************************************
--  $Id: opticalAlarm.mib  2008-04-18 yuly155208 $
--
--  opticalAlarm.mib: ZXR10 opticalAlarm file
--
--  April. 2008, Yu Liyuan
--
--  Copyright(c) 2008 by ZTE Corporaton
--  All rights reservered
--
--  ************************************************

   
         ZXR10-OPTICAL-ALARM-MIB DEFINITIONS ::= BEGIN
         IMPORTS
				    MODULE-IDENTITY,
				    OBJECT-TYPE,
				    NOTIFICATION-TYPE,
				    Unsigned32				    
				        FROM SNMPv2-SMI
				
				    TEXTUAL-CONVENTION, 
				    DisplayString
				        FROM SNMPv2-TC   
				        
				    zxr10					    
				    	FROM ZXR10-SMI
				    	;
                  
                  zxr10OpticalAlarmMIB MODULE-IDENTITY
                  LAST-UPDATED "200804180000Z" -- 
                  ORGANIZATION "ZTE"
                  CONTACT-INFO
                           "           "
                  DESCRIPTION
                           ""
                  REVISION "200804180000Z" -- 
                  DESCRIPTION
                           ""
                  ::= { zxr10 126 }                       
                                    

                  zxr10Notifications OBJECT IDENTIFIER ::= { zxr10OpticalAlarmMIB 0 }                                                 
                  zxr10MIBObjects OBJECT IDENTIFIER ::= { zxr10OpticalAlarmMIB 1 }
  
                                                               
-- ******************************************************************
-- Textual conventions
-- ******************************************************************  
         Zxr10optAlarmType ::= TEXTUAL-CONVENTION
                  STATUS current
                  DESCRIPTION
                           "   
                             "
                  REFERENCE
                           "   
                             "
                  SYNTAX INTEGER {
                           alarmTemperature 	(0),
                           alarmVoltage 		(1),   
                           alarmCurrent 		(2),
                           alarmTxPower 		(3),  
                           alarmRxPower 		(4)
                           }

         Zxr10optAlarmOverType ::= TEXTUAL-CONVENTION
                  STATUS current
                  DESCRIPTION
                           "    
                              "
                  REFERENCE
                           "    
                              "
                  SYNTAX INTEGER { 		                  
		                 highAlarm  	(1),    
		                 highWarning 	(2),
		                 lowWarning   	(3),    
		                 lowAlarm   	(4)
                           }                        
--add by songchan
        OptStatType  ::= INTEGER
		                {
					sfpOffline                  (1),
					sfpNotSupportDom              (2),
					sfpOnlineAndHaveData          (3),
					sfpOnlineButNoData            (4)
						}
--end 
-- ******************************************************************
-- The zxr10optAlarmTable Table
-- ******************************************************************
         zxr10optAlarmTable OBJECT-TYPE
                  SYNTAX SEQUENCE OF Zxr10optAlarmEntry
                  MAX-ACCESS not-accessible
                  STATUS current
                  DESCRIPTION
                           "   
                             "
                  REFERENCE
                           " 
                                "
                  ::= { zxr10MIBObjects 1 }
         zxr10optAlarmEntry OBJECT-TYPE
                  SYNTAX Zxr10optAlarmEntry
                  MAX-ACCESS not-accessible
                  STATUS current
                  DESCRIPTION
                           "
                           "
                  INDEX {zxr10optAlarmIndex }
                  ::= { zxr10optAlarmTable 1 }
         Zxr10optAlarmEntry ::= SEQUENCE {    
              	  zxr10optAlarmIndex Unsigned32,         
                  zxr10optIfIndex Unsigned32,
                  zxr10optIfName DisplayString,	     
                  zxr10optAlarmType Zxr10optAlarmType,   
                  zxr10optAlarmOverType Zxr10optAlarmOverType,
                  zxr10optAlarmOverCurValue DisplayString,	    
                  zxr10optHighAlarmValue DisplayString,
                  zxr10optHighWarnValue DisplayString,   
                  zxr10optLowWarnValue DisplayString,   
                  zxr10optLowAlarmValue DisplayString   
                  }                
                  
         zxr10optAlarmIndex OBJECT-TYPE
                  SYNTAX Unsigned32
                  MAX-ACCESS read-only
                  STATUS current
                  DESCRIPTION
                           " The index of the alarm Entry.
                                 "
                  ::= { zxr10optAlarmEntry 1 }
         zxr10optIfIndex OBJECT-TYPE
                  SYNTAX Unsigned32
                  MAX-ACCESS read-only
                  STATUS current
                  DESCRIPTION
                           " The index of the interface.   
                                "
                  REFERENCE
                           "   
                                "
                  ::= { zxr10optAlarmEntry 2 }
         zxr10optIfName OBJECT-TYPE
                  SYNTAX DisplayString
                  MAX-ACCESS read-only
                  STATUS current
                  DESCRIPTION
                           "    
                               "
                  REFERENCE
                           " The textual name of the interface.    
                               "
                  ::= { zxr10optAlarmEntry 3 }
         zxr10optAlarmType OBJECT-TYPE
                  SYNTAX Zxr10optAlarmType
                  MAX-ACCESS read-only
                  STATUS current
                  DESCRIPTION
                           "    
                              "
                  REFERENCE
                           "    
                              "
                  ::= { zxr10optAlarmEntry 4 } 
                                     
         zxr10optAlarmOverType OBJECT-TYPE
                  SYNTAX Zxr10optAlarmOverType
                  MAX-ACCESS read-only
                  STATUS current
                  DESCRIPTION
                           "    
                              "
                  REFERENCE
                           "    
                              "
                  ::= { zxr10optAlarmEntry 5 } 
                  
         zxr10optAlarmOverCurValue OBJECT-TYPE
                  SYNTAX DisplayString
                  MAX-ACCESS read-only
                  STATUS current
                  DESCRIPTION
                           "    
                              "
                  REFERENCE
                           "    
                              "
                  ::= { zxr10optAlarmEntry 6 } 
                                     
         zxr10optHighAlarmValue OBJECT-TYPE
                  SYNTAX DisplayString
                  MAX-ACCESS read-only
                  STATUS current
                  DESCRIPTION
                           "    
                              "
                  REFERENCE
                           "   
                               "
                  ::= { zxr10optAlarmEntry 7 } 
                         
         zxr10optHighWarnValue OBJECT-TYPE
                  SYNTAX DisplayString
                  MAX-ACCESS read-only
                  STATUS current
                  DESCRIPTION
                           "    
                              "
                  REFERENCE
                           "   
                               "
                  ::= { zxr10optAlarmEntry 8 } 
                   
         zxr10optLowWarnValue OBJECT-TYPE
                  SYNTAX DisplayString
                  MAX-ACCESS read-only
                  STATUS current
                  DESCRIPTION
                           "   
                               "
                  REFERENCE
                           "   
                               "
                  ::= { zxr10optAlarmEntry 9 }   
                  
         zxr10optLowAlarmValue OBJECT-TYPE
                  SYNTAX DisplayString
                  MAX-ACCESS read-only
                  STATUS current
                  DESCRIPTION
                           "   
                               "
                  REFERENCE
                           "   
                               "
                  ::= { zxr10optAlarmEntry 10 } 
                  
                                                       
                  
                  
                  
                                                               
                                                               
                                                                                                   
-- ******************************************************************
-- NOTIFICATIONS (TRAPS)
-- These notifications will be sent to the management entity
-- whenever a optAlarm present
-- ******************************************************************               
         zxr10optAlarmTrap NOTIFICATION-TYPE
                  OBJECTS {              
			              	  zxr10optAlarmIndex ,         
			                  zxr10optIfIndex ,
			                  zxr10optIfName ,	     
			                  zxr10optAlarmType ,   
			                  zxr10optAlarmOverType ,
			                  zxr10optAlarmOverCurValue ,	    
			                  zxr10optHighAlarmValue ,
			                  zxr10optHighWarnValue ,   
			                  zxr10optLowWarnValue ,   
			                  zxr10optLowAlarmValue   
                           }
                  STATUS current
                  DESCRIPTION
                           "    
                                 "
                  REFERENCE
                           "                  
                                 "
                  ::= { zxr10Notifications 1 }
                                             
   
-- ******************************************************************
-- The zxr10opticalTable Table 
-- add by songchan 
-- ******************************************************************
         zxr10opticalTable OBJECT-TYPE
                  SYNTAX SEQUENCE OF Zxr10opticalEntry
                  MAX-ACCESS not-accessible
                  STATUS current
                  DESCRIPTION
                           "   
                             "
                  REFERENCE
                           " 
                                "
                  ::= { zxr10MIBObjects 2 }

          zxr10opticalEntry OBJECT-TYPE
                  SYNTAX Zxr10opticalEntry
                  MAX-ACCESS not-accessible
                  STATUS current
                  DESCRIPTION
                           "
                           "
                  INDEX {zxr10opticalIfIndex }
                  ::= { zxr10opticalTable 1 }
  
       Zxr10opticalEntry ::= SEQUENCE {    
              	  zxr10opticalIfIndex   Unsigned32,
              	  zxr10opticalState     OptStatType,
              	  zxr10opticalTxPower   DisplayString,     
              	  zxr10opticalRxPower   DisplayString,
              	  zxr10opticalTxCurrent DisplayString,  
              	  zxr10opticalVoltage   DisplayString,
                  zxr10opticalTemperature   DisplayString 
                  }             

       zxr10opticalIfIndex OBJECT-TYPE
                  SYNTAX Unsigned32
                  MAX-ACCESS read-only
                  STATUS current
                  DESCRIPTION
                           " The index of the optiacl Entry.
                                 "
                  ::= { zxr10opticalEntry 1 }

       zxr10opticalState OBJECT-TYPE
                  SYNTAX OptStatType
                  MAX-ACCESS read-only
                  STATUS current
                  DESCRIPTION
                           " 
                                 "
                  ::= { zxr10opticalEntry 2 }

       zxr10opticalTxPower OBJECT-TYPE
                  SYNTAX DisplayString
                  MAX-ACCESS read-only
                  STATUS current
                  DESCRIPTION
                           " 
                                 "
                  ::= { zxr10opticalEntry 3 }
				  
       zxr10opticalRxPower OBJECT-TYPE
                  SYNTAX DisplayString
                  MAX-ACCESS read-only
                  STATUS current
                  DESCRIPTION
                           " 
                                 "
                  ::= { zxr10opticalEntry 4 }
				  
      zxr10opticalTxCurrent OBJECT-TYPE
                  SYNTAX DisplayString
                  MAX-ACCESS read-only
                  STATUS current
                  DESCRIPTION
                           " 
                                 "
                  ::= { zxr10opticalEntry 5 }

      zxr10opticalVoltage OBJECT-TYPE
                  SYNTAX DisplayString
                  MAX-ACCESS read-only
                  STATUS current
                  DESCRIPTION
                           " 
                                 "
                  ::= { zxr10opticalEntry 6 }

      zxr10opticalTemperature OBJECT-TYPE
                  SYNTAX DisplayString
                  MAX-ACCESS read-only
                  STATUS current
                  DESCRIPTION
                           " 
                                 "
                  ::= { zxr10opticalEntry 7 }


                      
END

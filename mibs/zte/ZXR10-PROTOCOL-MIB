--  Protocol private MIB Definitions
--  if compiles this mib with mg-soft, there must be mpls-vpn.mib and zxr10.mib files in
--  the same director.

     ZXR10-PROTOCOL-MIB DEFINITIONS ::= BEGIN

   IMPORTS
   OBJECT-TYPE,    Integer32      FROM SNMPv2-SMI

       enterprises                      FROM SNMPv2-SMI

   IpAddress                         FROM RFC1155-SMI;


       
   zte OBJECT IDENTIFIER ::= { enterprises 3902 }
   zxr10 OBJECT IDENTIFIER ::= { zte 3}
    zxr10protocol OBJECT IDENTIFIER ::= { zxr10 101}
    zxr10ip OBJECT IDENTIFIER ::= { zxr10protocol 1}
    zxr10tcp OBJECT IDENTIFIER ::= { zxr10protocol 2}
    
      DisplayString ::= OCTET STRING
          --  This data type is used to model textual information taken
          --  from the NVT ASCII character set.  By convention, objects
          --  with this syntax are declared as having
          --
          --       SIZE (0..255)


--vrf address mib define ,added by chenwei 2004-2-9 9:26

    zxr10ipvrfaddrTable  OBJECT-TYPE
              SYNTAX  SEQUENCE OF Zxr10IpVrfAddrEntry
              MAX-ACCESS  not-accessible
              STATUS  current
              DESCRIPTION
                      "The description of zxr10 vrf address table.
                       It is a list of vrf address entries."
               ::= { zxr10ip 1 }

    zxr10ipvrfaddrEntry  OBJECT-TYPE
              SYNTAX  Zxr10IpVrfAddrEntry
              MAX-ACCESS  not-accessible
              STATUS  current
              DESCRIPTION
                      "A vrf address entry containing objects that
                       vrf interface address infomation,such as:
                       vrf ifindex, vrf address, mask."
              INDEX  { zxr10ipVrfVpnName,
                       zxr10ipVrfAddr }
              ::= { zxr10ipvrfaddrTable 1 }

    Zxr10IpVrfAddrEntry ::=
              SEQUENCE {
                zxr10ipVrfVpnName
                    DisplayString,
                zxr10ipVrfAddr
                    IpAddress,
                zxr10ipVrfNetMask
                    IpAddress,
                zxr10ipVrfIfIndex
                    Integer32,
                zxr10ipVrfBcastAddr
                    Integer32,
                zxr10ipVrfReasmMaxSize
                    Integer32
              }

   zxr10ipVrfVpnName  OBJECT-TYPE
              SYNTAX  DisplayString (SIZE(0..64))
              MAX-ACCESS  read-only --not-accessible
              STATUS  current
              DESCRIPTION
                      "The IP address of this vrf interface."
              ::= { zxr10ipvrfaddrEntry 1 }

   zxr10ipVrfAddr  OBJECT-TYPE
              SYNTAX  IpAddress
              MAX-ACCESS  read-only
              STATUS  current
              DESCRIPTION
                      "The IP address of this vrf interface."
              ::= { zxr10ipvrfaddrEntry 2 }

   zxr10ipVrfNetMask OBJECT-TYPE
              SYNTAX  IpAddress
              MAX-ACCESS  read-only
              STATUS  current
              DESCRIPTION
                  "The subnet mask associated with the IP address of
                  this vrf interface.  The value of the mask is an IP
                  address with all the network bits set to 1 and all
                  the hosts bits set to 0."
             ::= { zxr10ipvrfaddrEntry 3 }

   zxr10ipVrfIfIndex OBJECT-TYPE
             SYNTAX  Integer32
             MAX-ACCESS  read-only
             STATUS  current
             DESCRIPTION
                     "The index value which uniquely identifies the vrf
                     interface.  The interface identified by a particular value of this
                     index is the same interface as identified by the
                     same value of ifIndex."
             ::= { zxr10ipvrfaddrEntry 4 }

   zxr10ipVrfBcastAddr OBJECT-TYPE
             SYNTAX  Integer32
             MAX-ACCESS  read-only
             STATUS  current
             DESCRIPTION
                     "The value of the least-significant bit in the IP
                     broadcast address used for sending datagrams on
                     the vrf interface associated with the IP address.
                     For example, when the Internet standard all-ones 
                     broadcast address is used, the value will be 1. 
                     This value applies to both the subnet and network 
                     broadcasts addresses used by the vrf interface."
             ::= { zxr10ipvrfaddrEntry 5 }
  
   zxr10ipVrfReasmMaxSize OBJECT-TYPE
             SYNTAX  Integer32 (0..65535)
             MAX-ACCESS  read-only
             STATUS  current
             DESCRIPTION
                     "The size of the largest IP datagram which this
                     vrf interface can re-assemble from incoming IP fragmented
                     datagrams received on this interface."
             ::= { zxr10ipvrfaddrEntry 6 }
             
          
          -- the TCP Connection table

          -- The TCP connection table contains information about this
          -- entity's existing TCP connections.

          zxr10tcpConnTable OBJECT-TYPE
              SYNTAX  SEQUENCE OF Zxr10TcpConnEntry
              MAX-ACCESS  not-accessible
              STATUS  current
              DESCRIPTION
                      "A table containing TCP connection-specific
                      information."
              ::= { zxr10tcp 1 }

          zxr10tcpconnEntry OBJECT-TYPE
              SYNTAX  Zxr10TcpConnEntry
              MAX-ACCESS  not-accessible
              STATUS  current
              DESCRIPTION
                      "Information about a particular current TCP
                      connection.  An object of this type is transient,
                      in that it ceases to exist when (or soon after)
                      the connection makes the transition to the CLOSED
                      state."
              INDEX   { 
              		zxr10tcpConnVrfVpnName,
              		zxr10tcpConnLocalAddress,
                        zxr10tcpConnLocalPort,
                        zxr10tcpConnRemAddress,
                        zxr10tcpConnRemPort 
                        }
              ::= { zxr10tcpConnTable 1 }

          Zxr10TcpConnEntry ::=
              SEQUENCE {
                  zxr10tcpConnVrfVpnName
                    DisplayString,
                  zxr10tcpConnState
                      INTEGER,
                  zxr10tcpConnLocalAddress
                      IpAddress,
                  zxr10tcpConnLocalPort
                      INTEGER (0..65535),
                  zxr10tcpConnRemAddress
                      IpAddress,
                  zxr10tcpConnRemPort
                      INTEGER (0..65535)
              }


	   zxr10tcpConnVrfVpnName  OBJECT-TYPE
              SYNTAX  DisplayString (SIZE(0..64))
              MAX-ACCESS  read-only --not-accessible
              STATUS  current
              DESCRIPTION
                      "The IP address of this vrf interface."
              ::= { zxr10tcpconnEntry  1 }


          zxr10tcpConnState OBJECT-TYPE
              SYNTAX  INTEGER {
                          closed(1),
                          listen(2),
                          synSent(3),
                          synReceived(4),
                          established(5),
                          finWait1(6),
                          finWait2(7),
                          closeWait(8),
                          lastAck(9),
                          closing(10),
                          timeWait(11),
                          deleteTCB(12)
                      }
              MAX-ACCESS  read-write
              STATUS  current
              DESCRIPTION
                      "The state of this TCP connection.

                      The only value which may be set by a management
                      station is deleteTCB(12).  Accordingly, it is
                      appropriate for an agent to return a `badValue'
                      response if a management station attempts to set
                      this object to any other value.

                      If a management station sets this object to the
                      value deleteTCB(12), then this has the effect of
                      deleting the TCB (as defined in RFC 793) of the
                      corresponding connection on the managed node,
                      resulting in immediate termination of the
                      connection.

                      As an implementation-specific option, a RST
                      segment may be sent from the managed node to the
                      other TCP endpoint (note however that RST segments
                      are not sent reliably)."
              ::= { zxr10tcpconnEntry 2 }

          zxr10tcpConnLocalAddress OBJECT-TYPE
              SYNTAX  IpAddress
              MAX-ACCESS  read-only
              STATUS  current
              DESCRIPTION
                      "The local IP address for this TCP connection.  In
                      the case of a connection in the listen state which
                      is willing to accept connections for any IP
                      interface associated with the node, the value
                      0.0.0.0 is used."
              ::= { zxr10tcpconnEntry 3 }

          zxr10tcpConnLocalPort OBJECT-TYPE
              SYNTAX  INTEGER (0..65535)
              MAX-ACCESS  read-only
              STATUS  current
              DESCRIPTION
                      "The local port number for this TCP connection."
              ::= { zxr10tcpconnEntry 4 }

          zxr10tcpConnRemAddress OBJECT-TYPE
              SYNTAX  IpAddress
              MAX-ACCESS  read-only
              STATUS  current
              DESCRIPTION
                      "The remote IP address for this TCP connection."
              ::= { zxr10tcpconnEntry 5 }

          zxr10tcpConnRemPort OBJECT-TYPE
              SYNTAX  INTEGER (0..65535)
              MAX-ACCESS  read-only
              STATUS  current
              DESCRIPTION
                      "The remote port number for this TCP connection."
              ::= { zxr10tcpconnEntry 6 }



-- end added by chenwei for vrf private mib


     END

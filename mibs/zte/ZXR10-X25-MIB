ZXR10-X25-MIB DEFINITIONS ::= BEGIN

   IMPORTS
       MODULE-IDENTITY, OBJECT-TYPE, Counter32, Gauge32,
       Integer32, TimeTicks, Counter64,
       NOTIFICATION-TYPE,
       enterprises                      FROM SNMPv2-SMI
       ifIndex            
		                                FROM RFC1213-MIB
       RowStatus
                                        FROM SNMPv2-TC		                              
       mgmt, NetworkAddress, IpAddress, Counter, Gauge
                         FROM RFC1155-SMI
      --         Counter, TimeTicks     FROM RFC1155-SMI
      -- IpAddress,DisplayString, mib-2   FROM RFC1213-MIB
      --            OBJECT-TYPE            FROM RFC-1212
                  TRAP-TYPE              FROM RFC-1215;

   zte OBJECT IDENTIFIER ::= { enterprises 3902 }
   zxr10 OBJECT IDENTIFIER ::= { zte 3}
   
   zxr10X25 OBJECT IDENTIFIER ::= { zxr10 4000}
   
   DisplayString ::= OCTET STRING
   
   zxr10X25OprTable OBJECT-TYPE
              SYNTAX  SEQUENCE OF Zxr10X25OprEntry
              MAX-ACCESS  not-accessible
              STATUS  current
              DESCRIPTION
                      "X.25 operation table"
               ::= { zxr10X25 1 }
   
   zxr10X25OprEntry  OBJECT-TYPE
              SYNTAX  Zxr10X25OprEntry
              MAX-ACCESS  not-accessible
              STATUS  current
              DESCRIPTION
                      "X.25 operation table entry"
              INDEX  { ifIndex }
              ::= { zxr10X25OprTable 1 }
   
   
   
    Zxr10X25OprEntry ::=
              SEQUENCE {
                zxr10X25OprXconnenctIfName
                    DisplayString,
                zxr10X25OprLocalswitchIfName
                    DisplayString,
                zxr10X25OprDLCI
                    Integer32,
                zxr10X25OprType
                    INTEGER,
                zxr10X25OprStatus
                    RowStatus
              }
   
   
   zxr10X25OprXconnenctIfName OBJECT-TYPE
              SYNTAX  DisplayString(SIZE(0..32))
              MAX-ACCESS  read-write
              STATUS  current
              DESCRIPTION
                      "X.25 entry -> X.25 xconnect interface DLCI"
              ::= { zxr10X25OprEntry 1 }
              
   zxr10X25OprLocalswitchIfName OBJECT-TYPE
              SYNTAX  DisplayString(SIZE(0..32))
              MAX-ACCESS  read-write
              STATUS  current
              DESCRIPTION
                      "X.25 entry -> X.25 interface"
              ::= { zxr10X25OprEntry 2 }

   
   zxr10X25OprDLCI OBJECT-TYPE
              SYNTAX  Integer32
              MAX-ACCESS  read-write
              STATUS  current
              DESCRIPTION
                      "X.25 DLCI size : from 16 to 1007"
              ::= { zxr10X25OprEntry 3 }
              
              
   zxr10X25OprType OBJECT-TYPE
              SYNTAX  INTEGER{localswitch(1),xconnect(2),both(3)}
              MAX-ACCESS  read-write
              STATUS  current
              DESCRIPTION
                      ""
              ::= { zxr10X25OprEntry 4 }
 
   zxr10X25OprStatus OBJECT-TYPE
              SYNTAX  RowStatus
              MAX-ACCESS  read-write
              STATUS  current
              DESCRIPTION
              "The status of this conceptual row.
              To create a row in this table, a manager must
              set this object to createAndGo(4) 
              
              Until instances of all corresponding columns are
              appropriately configured, the value of the
              corresponding instance of the zxr10X25OprStatus
              column is 'notReady'"

              ::= { zxr10X25OprEntry 5 }

END

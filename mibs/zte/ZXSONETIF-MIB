ZXSONETIF-MIB DEFINITIONS ::= BEGIN

IMPORTS
     MODULE-IDENTITY, OBJECT-TYPE, Integer32
          FROM SNMPv2-SMI                    -- [RFC2578]
     DisplayString, TruthValue
          FROM SNMPv2-TC                     -- [RFC2579]
     InterfaceIndex
          FROM IF-MIB                        -- [RFC2863]
    
     zxPwCTDM
        FROM ZTE-MASTER-MIB
    ;

zxSonetIfMIB MODULE-IDENTITY
    LAST-UPDATED    "200708180000Z"  -- Aug 18, 2007
    ORGANIZATION    "Zhongxing Telcom Co. Ltd."
    CONTACT-INFO    "Zhongxing Telcom Co. Ltd.
                     E-mail: info@mail.zte.com.cn
                     http  : www.zte.com.cn or www.zhongxing.com"

    DESCRIPTION
         "The MIB module to describe DS1, E1, DS2, and
          E2 interfaces objects.
         "
    ::= { zxPwCTDM 3 }
    
------------------------------------------------------------------------------
--  define objects in ZXSONETIF-MIB
------------------------------------------------------------------------------
zxSonetCfgTable OBJECT-TYPE
    SYNTAX  SEQUENCE OF ZxSonetCfgEntry
    MAX-ACCESS  not-accessible
    STATUS  current
    DESCRIPTION
      "The SONET/SDH Medium table."
    ::= { zxSonetIfMIB 1 }
  
zxSonetCfgEntry OBJECT-TYPE
    SYNTAX  ZxSonetCfgEntry
    MAX-ACCESS  not-accessible
    STATUS  current
    DESCRIPTION
      "An entry in the SONET/SDH Medium table."
    INDEX   { zxSonetIfIndex }
      ::= { zxSonetCfgTable 1 }
  
ZxSonetCfgEntry ::=
    SEQUENCE {
                zxSonetIfIndex                    InterfaceIndex,
                zxSonetLoopBackType               INTEGER,
                zxSonetClockSource                INTEGER,
                zxSonetConfigType                 INTEGER,
                zxSonetConfigMapType              INTEGER,
                zxSonetCfgInfoSend                TruthValue
            }
            
zxSonetIfIndex OBJECT-TYPE
    SYNTAX  InterfaceIndex
    MAX-ACCESS  not-accessible
    STATUS  deprecated
    DESCRIPTION
          "The 4 bytes index includes:
          interface type(bit31~28);shelfId(bit27~24);slotId(bit23~16);
          portId(bit15~8);reserved(bit7~bit0)
          ."
    ::= { zxSonetCfgEntry 1 }

zxSonetLoopBackType OBJECT-TYPE
    SYNTAX  INTEGER  {
              noLoopback(1),
              lineLoop(2),
              inwardLoop(3)
           }
    MAX-ACCESS  read-write
    STATUS  current
    DESCRIPTION
      "Represents the desired loopback configuration of the SONET line.
       noLoopback: Not in the loopback state.
      
       lineLoop:
          The received signal at this interface does not go
          through the device (minimum penetration) but is
          looped back out.
       
       inwardLoop
          The transmitted signal at this interface is
          looped back and received by the same interface.
          What is transmitted onto the line is product
          dependent."
    ::= { zxSonetCfgEntry 2 }
    
zxSonetClockSource OBJECT-TYPE
     SYNTAX  INTEGER {
              loopTiming(1),
              localTiming(2)
           }
    MAX-ACCESS  read-write
    STATUS  current
    DESCRIPTION
     "The source of Transmit Clock.
      'loopTiming' indicates that the recovered
      receive clock is used as the transmit clock.
       
      'localTiming' indicates that a local clock
     source is used or when an external clock is
     attached to the box containing the interface.
     "
    ::= { zxSonetCfgEntry 3 }
    
zxSonetConfigType OBJECT-TYPE
    SYNTAX  INTEGER  {
              sonetSts3c(1),
              sonetStm1(2),
              sonetSts12c(3),
              sonetStm4(4),
              sonetSts48c(5),
              sonetStm16(6),
              sonetSts192c(7),
              sonetStm64(8)
           }
    MAX-ACCESS  read-only
    STATUS  current
    DESCRIPTION
      "Represents the configured line type.This object is used to switch
       between SONET(North American)and SDH(European) format.
       Sts is SONET format, while Stm is SDH format.
       "
    ::= { zxSonetCfgEntry 4 }
    
zxSonetConfigMapType OBJECT-TYPE
    SYNTAX  INTEGER  {
              other(0),
              au3tu11(1),
              au3tu12(2),
              au4tu11(3),
              au4tu12(4)
           }
    MAX-ACCESS  read-write
    STATUS  current
    DESCRIPTION
      " "
    ::= { zxSonetCfgEntry 5 } 
       
zxSonetCfgInfoSend OBJECT-TYPE
    SYNTAX       TruthValue
    MAX-ACCESS   read-write
    STATUS       current
    DESCRIPTION
          "The action to send the configuration of 
           Sonet line to corresponding card."    
    ::= { zxSonetCfgEntry 6 } 
           
zxSonetMediumTable OBJECT-TYPE
    SYNTAX  SEQUENCE OF ZxSonetMediumEntry
    MAX-ACCESS  not-accessible
    STATUS  current
    DESCRIPTION
      "The SONET/SDH Medium table."
    ::= { zxSonetIfMIB 2 }

zxSonetMediumEntry OBJECT-TYPE
    SYNTAX  ZxSonetMediumEntry
    MAX-ACCESS  not-accessible
    STATUS  current
    DESCRIPTION
      "An entry in the SONET/SDH Medium table."
    INDEX   { zxSonetIfIndex }
    ::= { zxSonetMediumTable 1 }

ZxSonetMediumEntry ::=
    SEQUENCE {                 
        zxSonetMediumType               INTEGER,
        zxSonetMediumTimeElapsed        Integer32,
        zxSonetMediumValidIntervals     Integer32,
        zxSonetMediumLineCoding         INTEGER,
        zxSonetMediumLineType           INTEGER,
        zxSonetMediumCircuitIdentifier  DisplayString,
        zxSonetMediumInvalidIntervals   Integer32,
        zxSonetMediumLoopbackConfig     BITS
    }

zxSonetMediumType OBJECT-TYPE
    SYNTAX  INTEGER  {
              sonet(1),
              sdh(2)
           }
    MAX-ACCESS  read-write
    STATUS  current
    DESCRIPTION
      "This variable identifies whether a SONET
      or a SDH signal is used across this interface."
    ::= { zxSonetMediumEntry 1 }

zxSonetMediumTimeElapsed OBJECT-TYPE
    SYNTAX  Integer32 (1..900)
    MAX-ACCESS  read-only
    STATUS  current
    DESCRIPTION
      "The number of seconds, including partial seconds,
      that have elapsed since the beginning of the current
      measurement period. If, for some reason, such as an
      adjustment in the system's time-of-day clock, the
      current interval exceeds the maximum value, the
      agent will return the maximum value."
    ::= { zxSonetMediumEntry 2 }

zxSonetMediumValidIntervals OBJECT-TYPE
    SYNTAX  Integer32 (0..96)
    MAX-ACCESS  read-only
    STATUS  current
    DESCRIPTION
      "The number of previous 15-minute intervals
      for which data was collected.
      A SONET/SDH interface must be capable
      of supporting at least n intervals.
      The minimum value of n is 4.
      The default of n is 32.
      The maximum value of n is 96.
      The value will be <n> unless the measurement was
      (re-)started within the last (<n>*15) minutes, in which
      case the value will be the number of complete 15
      minute intervals for which the agent has at least
      some data. In certain cases (e.g., in the case
      where the agent is a proxy) it is possible that some
      intervals are unavailable.  In this case, this
      interval is the maximum interval number for
      which data is available. "
    ::= { zxSonetMediumEntry 3 }

zxSonetMediumLineCoding OBJECT-TYPE
    SYNTAX  INTEGER {
               sonetMediumOther(1),
               sonetMediumB3ZS(2),
               sonetMediumCMI(3),
               sonetMediumNRZ(4),
               sonetMediumRZ(5)
           }
    MAX-ACCESS  read-write
    STATUS  current
    DESCRIPTION
      "This variable describes the line coding for
      this interface. The B3ZS and CMI are used for
      electrical SONET/SDH signals (STS-1 and STS-3).
      The Non-Return to Zero (NRZ) and the Return
      to Zero are used for optical SONET/SDH signals."
    ::= { zxSonetMediumEntry 4 }

zxSonetMediumLineType OBJECT-TYPE
    SYNTAX  INTEGER {
               sonetOther(1),
               sonetShortSingleMode(2),
               sonetLongSingleMode(3),
               sonetMultiMode(4),
               sonetCoax(5),
               sonetUTP(6)
           }
    MAX-ACCESS  read-write
    STATUS  current
    DESCRIPTION
      "This variable describes the line type for
      this interface. The line types are
      Short and Long Range
      Single Mode fiber or Multi-Mode fiber interfaces,
      and coax and UTP for electrical interfaces.  The
      value zxSonetOther should be used when the Line Type is
      not one of the listed values."
    ::= { zxSonetMediumEntry 5 }

zxSonetMediumCircuitIdentifier OBJECT-TYPE
    SYNTAX  DisplayString (SIZE (0..255))
    MAX-ACCESS  read-write
    STATUS  current
    DESCRIPTION
      "This variable contains the transmission
      vendor's circuit identifier, for the
      purpose of facilitating troubleshooting.
      Note that the circuit identifier, if available,
      is also represented by ifPhysAddress."
    ::= { zxSonetMediumEntry 6 }

zxSonetMediumInvalidIntervals OBJECT-TYPE
    SYNTAX  Integer32 (0..96)
    MAX-ACCESS  read-only
    STATUS  current
    DESCRIPTION
       "The number of intervals in the range from
       0 to zxSonetMediumValidIntervals for which no
       data is available. This object will typically
       be zero except in cases where the data for some
       intervals are not available (e.g., in proxy
       situations)."
    ::= { zxSonetMediumEntry 7 }

zxSonetMediumLoopbackConfig OBJECT-TYPE
    SYNTAX      BITS {
                 sonetNoLoop(0),
                 sonetFacilityLoop(1),
                 sonetTerminalLoop(2),
                 sonetOtherLoop(3) }
    MAX-ACCESS  read-write
    STATUS      current
    DESCRIPTION
      "The current loopback state of the SONET/SDH interface.  The
       values mean:
    
         sonetNoLoop
            Not in the loopback state. A device that is not
            capable of performing a loopback on this interface
            shall always return this value.
    
         sonetFacilityLoop
            The received signal at this interface is looped back
            out through the corresponding transmitter in the return
            direction.
    
         sonetTerminalLoop
            The signal that is about to be transmitted is connected
            to the associated incoming receiver.
    
         sonetOtherLoop
            Loopbacks that are not defined here."
    
    ::= { zxSonetMediumEntry 8 }
     
zxSonetVTConfigTable OBJECT-TYPE
    SYNTAX  SEQUENCE OF ZxSonetVTConfigEntry
    MAX-ACCESS  not-accessible
    STATUS  current
    DESCRIPTION
          "The Sonet VT Configuration table."
    ::= { zxSonetIfMIB 3 }

zxSonetVTConfigEntry OBJECT-TYPE
    SYNTAX  ZxSonetVTConfigEntry
    MAX-ACCESS  not-accessible
    STATUS  current
    DESCRIPTION
          "An entry in the Sonet VT Configuration table."
    INDEX   { zxSonetVTIfIndex }
    ::= { zxSonetVTConfigTable 1 }

ZxSonetVTConfigEntry ::=
    SEQUENCE {
          zxSonetVTIfIndex                          InterfaceIndex,
          zxSonetVTLoopbackConfig                   INTEGER,
          zxSonetVTTransmitClockSource              INTEGER,
          zxSonetVTClockStatus                      INTEGER,
          zxSonetVTCfgInfoSend                      TruthValue
        }

zxSonetVTIfIndex OBJECT-TYPE
    SYNTAX  InterfaceIndex
    MAX-ACCESS  not-accessible
    STATUS  deprecated
    DESCRIPTION
          "The 4 bytes index includes:
          interface type(bit31~28);shelfId(bit27~24);slotId(bit23~19);portId(bit18~16);augno(bit15~bit10);
          au3/au4no(bit9~bit8);tug3no(bit7~bit6);tug2no(bit5~bit3);tu12/tu11no(bit2~bit0)."
    ::= { zxSonetVTConfigEntry 1 }

zxSonetVTLoopbackConfig OBJECT-TYPE
    SYNTAX  INTEGER {
               noLoop(1),
               payloadLoop(2),
               lineLoop(3),
               otherLoop(4),
               inwardLoop(5),
               dualLoop(6)
             }
    MAX-ACCESS  read-write
    STATUS  current
    DESCRIPTION
          "This variable represents the desired loopback
          configuration of the Sonet VT.  Agents
          supporting read/write access should return
          inconsistentValue in response to a requested
          loopback state that the interface does not
          support.  The values mean:
    
          noLoop
          Not in the loopback state. 
    
          payloadLoop
          The received signal at this interface is looped
          through the device.  Typically the received signal
          is looped back for retransmission after it has
          passed through the device's framing function.
    
          lineLoop
          The received signal at this interface does not go
          through the device (minimum penetration) but is
          looped back out.
    
          otherLoop
          Loopbacks that are not defined here.
    
          inwardLoop
          The transmitted signal at this interface is
          looped back and received by the same interface.
          What is transmitted onto the line is product
          dependent.
    
          dualLoop
          Both lineLoop and inwardLoop will be
          active simultaneously."
    ::= { zxSonetVTConfigEntry 2 }

zxSonetVTTransmitClockSource OBJECT-TYPE
    SYNTAX  INTEGER {
              loopTiming(1),
              localTiming(2),
              throughTiming(3),
              adaptive (4),
              enhancedAdaptive (5),
              differential(6)
          }
    MAX-ACCESS  read-write
    STATUS  current
    DESCRIPTION
     "The source of Transmit Clock.
      'loopTiming' indicates that the recovered
      receive clock is used as the transmit clock.
    
      'localTiming' indicates that a local clock
     source is used or when an external clock is
     attached to the box containing the interface.
    
      'throughTiming' indicates that recovered
     receive clock from another interface is used as
     the transmit clock.
    
      'adaptive' indicates that the clock is recovered
     based on the data flow and not based on the
     physical layer.
     
     The last two values 'enhanced-adaptive' and 'inband-differential' 
     are customed values."
    ::= { zxSonetVTConfigEntry 3 }
    
zxSonetVTClockStatus  OBJECT-TYPE
     SYNTAX      INTEGER (0..127)
     MAX-ACCESS  read-only
     STATUS      current
     DESCRIPTION
            "The current clock state of the sonet VT interface. the value can be:
               FREERUN 0
               HOLDOVER 1 
               ACQUIRING 2
               ACUIRED 3.
               "
     ::= { zxSonetVTConfigEntry 4 } 
     
zxSonetVTCfgInfoSend  OBJECT-TYPE
    SYNTAX       TruthValue
    MAX-ACCESS   read-write
    STATUS       current
    DESCRIPTION
          "The action to send the configuration on 
           Sonet VT to corresponding card."
    ::= { zxSonetVTConfigEntry 5 }    

END

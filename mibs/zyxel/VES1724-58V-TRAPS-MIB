------------------------------------------------------------
-- Version 1.0
-- Change history
-- 1.0
------------------------------------------------------------

VES1724-58V-TRAPS-MIB DEFINITIONS ::= BEGIN

    IMPORTS

	OBJECT-TYPE, Unsigned32, NOTIFICATION-TYPE, Counter64
		FROM SNMPv2-SMI
	DisplayString, ifIndex
	  	FROM RFC1213-MIB
	ifAdminStatus, ifOperStatus
	  	FROM IF-MIB
	ves1724-58v, slotModuleIdVes1724-58v, voltageConfIndex, voltageCurValue,
	voltageConfHighThreshold, voltageConfLowThreshold,
	temperatureConfIndex, temperatureCurValue, 
	temperatureConfHighThreshold, temperatureConfLowThreshold,
	fanConfIndex, fanRpmCurValue,
	fanConfHighThreshold, fanConfLowThreshold,
	externalAlarmName, coaConfIssueThreshold, coaConfAnalyticMethod,
	externalBatteryStatsTemperature, externalBatteryStatsVoltage,
	externalBatteryConfTempHighThreshold, externalBatteryConfTempLowThreshold,
	externalBatteryConfDcCriticThreshold, 
	externalBatteryConfDcLowThreshold,
	externalBatteryConfDcErrThreshold,
	gePmCurr15minTxOctets,
	gePmCurr15minTxPkts,
	gePmCurr15minTxBroadcastPkts,
	gePmCurr15minTxMulticastPkts,
	gePmCurr15minRxOctets,
	gePmCurr15minRxPkts,
	gePmCurr15minRxBroadcastPkts,
	gePmCurr15minRxMulticastPkts,
	gePmCurr15minRxCRCAlignErrors,
	gePmCurr15minRxUndersizePkts,
	gePmCurr15minRxOversizePkts,
	gePmCurr15minRxFragments,
	gePmCurr15minCollisions,
	gePmCurr15minPkts64Octets,
	gePmCurr15minPkts65to127Octets,
	gePmCurr15minPkts128to255Octets,
	gePmCurr15minPkts256to511Octets,
	gePmCurr15minPkts512to1023Octets,
	gePmCurr15minPkts1024to1518Octets,
	gePmCurr15minPkts1519to1522Octets,
	geUtilTxCurrentPercent,        
	geUtilRxCurrentPercent,
	geUtilTxIssueLvl1Threshold,
	geUtilTxIssueLvl2Threshold,
	geUtilRxIssueLvl1Threshold,
	geUtilRxIssueLvl2Threshold,
	gePmThreshProfTxOctets,
	gePmThreshProfTxPkts,
	gePmThreshProfTxBroadcastPkts,
	gePmThreshProfTxMulticastPkts,
	gePmThreshProfRxOctets,
	gePmThreshProfRxPkts,
	gePmThreshProfRxBroadcastPkts,
	gePmThreshProfRxMulticastPkts,
	gePmThreshProfRxCRCAlignErrors,
	gePmThreshProfRxUndersizePkts,
	gePmThreshProfRxOversizePkts,
	gePmThreshProfRxFragments,
	gePmThreshProfCollisions,
	gePmThreshProfPkts64Octets,
	gePmThreshProfPkts65to127Octets,
	gePmThreshProfPkts128to255Octets,
	gePmThreshProfPkts256to511Octets,
	gePmThreshProfPkts512to1023Octets,
	gePmThreshProfPkts1024to1518Octets,
	gePmThreshProfPkts1519to1522Octets,
	fxsPmCurr15minRtpElapsedTime,
	fxsPmCurr15minRtpTxBytes,
	fxsPmCurr15minRtpRxBytes,				
	fxsPmCurr15minRtpTxPackets,
	fxsPmCurr15minRtpRxPackets,
	fxsPmCurr15minRtpTxLostPackets,	
	fxsPmCurr15minRtpRxLostPackets,	
	fxsPmThreshProfRtpElapsedTime,
	fxsPmThreshProfRtpTxBytes,
	fxsPmThreshProfRtpRxBytes,				
	fxsPmThreshProfRtpTxPackets,
	fxsPmThreshProfRtpRxPackets,
	fxsPmThreshProfRtpTxLostPackets,	
	fxsPmThreshProfRtpRxLostPackets,		
	dslPmCurr15minTxOctets,
	dslPmCurr15minTxPkts,
	dslPmCurr15minTxUnicastPkts,
	dslPmCurr15minTxBroadcastPkts,
	dslPmCurr15minTxMulticastPkts,
	dslPmCurr15minTxDiscardPkts,
	dslPmCurr15minRxOctets,
	dslPmCurr15minRxPkts,
	dslPmCurr15minRxUnicastPkts,
	dslPmCurr15minRxBroadcastPkts,
	dslPmCurr15minRxMulticastPkts,
	dslPmCurr15minRxDiscardPkts,
	dslPmThreshProfTxOctets,
	dslPmThreshProfTxPkts,
	dslPmThreshProfTxUnicastPkts,
	dslPmThreshProfTxBroadcastPkts,
	dslPmThreshProfTxMulticastPkts,
	dslPmThreshProfTxDiscardPkts,
	dslPmThreshProfRxOctets,
	dslPmThreshProfRxPkts,
	dslPmThreshProfRxUnicastPkts,
	dslPmThreshProfRxBroadcastPkts,
	dslPmThreshProfRxMulticastPkts,
	dslPmThreshProfRxDiscardPkts,
	sysPmSyncUrl,
	sysPmSyncStatus,
	xdsl2PMLCurr15MLofs,
	vdsl2LineAlarmConfProfileXtucThresh15MinLofs,
	vdsl2LineAlarmConfProfileXturThresh15MinLofs,
	xdsl2PMLInitCurr15MLprs,
	vdsl2LineAlarmConfProfileXturThresh15MinLprs,
	h248MgcIpDn,
	sipProfileRegSvr,
	xdslBondingStatusName,
	xdslBondingStatusTransferMode
		FROM VES1724-58V-MIB;


	trap		OBJECT IDENTIFIER ::= { ves1724-58v 19 }

----------------------------------------
-- trap
----------------------------------------

	object			OBJECT IDENTIFIER ::= { trap 1 }
	dsltrap			OBJECT IDENTIFIER ::= { trap 2 }
	equipment		OBJECT IDENTIFIER ::= { trap 3 }
	systrap			OBJECT IDENTIFIER ::= { trap 4 }
	getrap			OBJECT IDENTIFIER ::= { trap 5 }
	voiptrap		OBJECT IDENTIFIER ::= { trap 6 }
	fxstrap			OBJECT IDENTIFIER ::= { trap 7 }

--------------------
-- object
--------------------

        dslLgSenderIfIndex OBJECT-TYPE
    	SYNTAX      INTEGER
    	MAX-ACCESS  not-accessible
   	STATUS      current
    	DESCRIPTION
	            "A unique value, greater than zero, for each interface.
	            The index of sender interface which sends detected loop guard probe packet."
    	::= { object 1 }

        sysProblemCause OBJECT-TYPE
        SYNTAX  DisplayString
        MAX-ACCESS  not-accessible
        STATUS  current
        DESCRIPTION
                      	"It describes the problem occurred in the system, e.g. maintenance
                      	operation failures, system reboot, error log, ...etc."
        ::= { object 2 }

	sysMacAntiSpoofOrig OBJECT-TYPE
	SYNTAX INTEGER
	MAX-ACCESS not-accessible
	STATUS current
	DESCRIPTION
		"The Original ifIndex of Mac-AntiSpoofing."
	::= { object 3 }

	sysMacAntiSpoofNew OBJECT-TYPE
	SYNTAX INTEGER
	MAX-ACCESS not-accessible
	STATUS current
	DESCRIPTION
		"The New ifIndex of Mac-AntiSpoofing."
	::= { object 4 }

	sysMacAntiSpoofMAC OBJECT-TYPE
	SYNTAX DisplayString
	MAX-ACCESS not-accessible
	STATUS current
	DESCRIPTION
		"The MAC of Mac-AntiSpoofing."
	::= { object 5 }

        sysCoaIssuedLoad OBJECT-TYPE
    	SYNTAX      Unsigned32
    	MAX-ACCESS  not-accessible
   	STATUS      current
    	DESCRIPTION
	            "CPU analyzed utilization when CPU overload alarm is issued."
    	::= { object 6 }

	voipDevId OBJECT-TYPE
	SYNTAX INTEGER
	MAX-ACCESS not-accessible
	STATUS current
	DESCRIPTION
		"The device ID of the DUT.
		chip id 1 ~ 8, one chip has 8 FXS ports."
	::= { object 7 }

	voipCount OBJECT-TYPE
	SYNTAX INTEGER
	MAX-ACCESS not-accessible
	STATUS current
	DESCRIPTION
		"The number of ringer fault."
	::= { object 8 }

	voipPhoneState OBJECT-TYPE
	SYNTAX INTEGER {
        		disable(1),
        		onHook(2),
        		offHook(3),
        		ringing(4),
        		testing(5),
        		powerCutDown(6),
        		fault(7),
        		bad(8),
        		uninitialized(9)
        	}
	MAX-ACCESS not-accessible
	STATUS current
	DESCRIPTION
		"Phone status of the line."
	::= { object 9 }

	voipBatType OBJECT-TYPE
	SYNTAX INTEGER{
        		batteryLow(0),
        		batteryHigh(1),
        		batteryPositive(2)
        		}
	MAX-ACCESS not-accessible
	STATUS current
	DESCRIPTION
		"Battery type."
	::= { object 10 }

        voipRingSegment OBJECT-TYPE
    	SYNTAX      Unsigned32
    	MAX-ACCESS  not-accessible
   	STATUS      current
    	DESCRIPTION
	            "Ring segment."
    	::= { object 11 }

        voipRingTimerId OBJECT-TYPE
    	SYNTAX      Unsigned32
    	MAX-ACCESS  not-accessible
   	STATUS      current
    	DESCRIPTION
	            "Ring Timer ID."
    	::= { object 12 }

	xdslDevId OBJECT-TYPE
	SYNTAX INTEGER
	MAX-ACCESS not-accessible
	STATUS current
	DESCRIPTION
		"The device ID of the DUT.

		For LAL32
		chip id 1 for LAL, one chip has 32 DSL ports.

		For LVL24
		chip id 1 ~ 2 for LVL, one chip has 12 DSL ports."
	::= { object 13 }

        voipCodecType OBJECT-TYPE
	SYNTAX INTEGER{
        		g711(0),
        		g711mu(1),
        		g723(2),
        		g726x16(3),
        		g726x24(4),
        		g726x32(5),
        		g726x40(6),
        		g729ab(7)
        		}
    	MAX-ACCESS  not-accessible
   	STATUS      current
    	DESCRIPTION
	            "voip Codec type."
    	::= { object 14 }

        voipOpType OBJECT-TYPE
	SYNTAX INTEGER{
        		offHookShort(0),
        		offHookLong(1),
        		ringing(2),
        		cardInsert(3)
        		}
    	MAX-ACCESS  not-accessible
   	STATUS      current
    	DESCRIPTION
	            "voip Operation type."
    	::= { object 15 }

--        sysCardType OBJECT-TYPE
--	SYNTAX INTEGER{
--        		lal(0),
--        		lvl(1),
--        		lvo(2),
--        		none(3)
--        		}
--    	MAX-ACCESS  not-accessible
--   	STATUS      current
--    	DESCRIPTION
--	            "linecard type."
--    	::= { object 16 }

        voipPwrExceedCounter OBJECT-TYPE
	SYNTAX INTEGER
    	MAX-ACCESS  not-accessible
   	STATUS      current
    	DESCRIPTION
	            "alarm counter."
    	::= { object 17 }

--	{ object 18 } ~ { object 27 } is reserved by TIU-xx
--	timeref1ppsSource OBJECT-TYPE
--		SYNTAX INTEGER
--		MAX-ACCESS read-only
--		STATUS current
--		DESCRIPTION
--			"The system receive 1PPS signal correctly.
--			The varable in the binding list is current reference, 
--			0: freerun,
--			1: GPS module,
--			2: IEEE 1588"
--		::= { object 18 }

--	dhcpServerIpv4Address OBJECT-TYPE
--		SYNTAX Unsigned32
--		MAX-ACCESS read-only
--		STATUS current
--		DESCRIPTION
--			"IPv4 address of DHCP server address.
--			Note: if an IPv4 address is a.b.c.d then it converts to be (a<<24 + b<<16 + c<<8 + d)"
--		::= { object 19 }

--	dhcpLeasedIpv4Address OBJECT-TYPE
--		SYNTAX Unsigned32
--		MAX-ACCESS read-only
--		STATUS current
--		DESCRIPTION
--			"The leased IPv4 address from a DHCP server
--			Note: if an IPv4 address is a.b.c.d then it converts to be (a<<24 + b<<16 + c<<8 + d)"
--		::= { object 20 }

--	dhcpIfIndex OBJECT-TYPE
--		SYNTAX Unsigned32
--		MAX-ACCESS read-only
--		STATUS current
--		DESCRIPTION
--			"The DHCP client inteface interface to 1 - TCU, 2 - OSS"
--		::= { object 21 }
		
--	currBondingIfIndex OBJECT-TYPE
--		SYNTAX Unsigned32
--		MAX-ACCESS read-only
--		STATUS current
--		DESCRIPTION
--			"The current bonding ifIndex which a DSL port joined.
--			The range is from 101 to 148 for TIUV48 product"
--		::= { object 22 }

--	lastBondingIfIndex OBJECT-TYPE
--		SYNTAX Unsigned32
--		MAX-ACCESS read-only
--		STATUS current
--		DESCRIPTION
--			"The last bonding ifIndex which a DSL port joined.
--			The range is from 101 to 148 for TIUV48 product"
--		::= { object 23 }

--    sysRestartCause OBJECT-TYPE
--        SYNTAX  INTEGER
--        MAX-ACCESS  not-accessible
--        STATUS  current
--        DESCRIPTION
--        	"The variable describes system reset caused by below category.
--        	1: restart caused from hardware status change.
--        	2: restart caused from software exception.
--        	3: restart caused from administor operation."
--        ::= { object 24 }

--    sysRestartErrorCode OBJECT-TYPE
--        SYNTAX  INTEGER
--        MAX-ACCESS  not-accessible
--        STATUS  current
--        DESCRIPTION
--        	"The variable describes system reset sub-cause according to by sysResetCause.
--        	sysResetCause is '1' (hardware related) and if sysRestartErrorCode is 
--        		1: power input missing
--        		2: hardware watchdog triggered
--        		3: overheat triggered
--        		4: maintenance button pressed > 8 seconds
--        	sysResetCause is '2' (software related) and if sysRestartCode is
--        		1: triggered by software watchdog
--        		2: restart caused by program exception (additional context stored for reference)
--        		3: restart caused by software program intentionally (error condidtion found at sysRestartAdditionalInfo).
--        	sysResetCause is '3' (operation related) and if sysRestartErrorCode is
--        		1: operator press maintenance button 7 seconds
--        		2: operator reset manually (either by SNMP or CLI command)
--        		3: firmware upgrade"  
--        ::= { object 25 }

--    sysRestartAdditionalInfo OBJECT-TYPE
--        SYNTAX  DisplayString
--        MAX-ACCESS  not-accessible
--        STATUS  current
--        DESCRIPTION "This a string to indicate what meaning could be for cause and error code."  
--        ::= { object 26 }




	    voipVtipVoltage OBJECT-TYPE
	    SYNTAX INTEGER
	    MAX-ACCESS not-accessible
	    STATUS current
	    DESCRIPTION
	    	"The DC voltage of TIP line. The unit is 0.1 V."
	    ::= { object 30 }

	    voipVringVoltage OBJECT-TYPE
	    SYNTAX INTEGER
	    MAX-ACCESS not-accessible
	    STATUS current
	    DESCRIPTION
	    	"The DC voltage of RING line. The unit is 0.1 V."
	    ::= { object 31 }


--------------------
-- dsltrap
--------------------
	dslLinkDown	NOTIFICATION-TYPE
				OBJECTS { ifIndex, ifAdminStatus, ifOperStatus }
				STATUS  current
				DESCRIPTION
				"The trap signifies one dsl port is linked down."
				::= { dsltrap 1 }

	dslLinkUp NOTIFICATION-TYPE
	    OBJECTS { ifIndex, ifAdminStatus, ifOperStatus }
	    STATUS  current
	    DESCRIPTION
	            "The trap signifies one dsl port is linked up."
	    ::= { dsltrap 2 }

	xdslXtucLof	NOTIFICATION-TYPE
				OBJECTS { ifIndex }
				STATUS  current
				DESCRIPTION	"The trap signifies XTU-C Loss of Framing."
				::= { dsltrap 3 }

	xdslXtucLos	NOTIFICATION-TYPE
				OBJECTS { ifIndex }
				STATUS  current
				DESCRIPTION	"The trap signifies XTU-C Loss of Signal."
				::= { dsltrap 4 }

	xdslXturLof	NOTIFICATION-TYPE
				OBJECTS { ifIndex }
				STATUS  current
				DESCRIPTION	"The trap signifies XTU-R Loss of Framing."
				::= { dsltrap 5 }

	xdslXturLos	NOTIFICATION-TYPE
				OBJECTS { ifIndex }
				STATUS  current
				DESCRIPTION	"The trap signifies XTU-R Loss of Signal."
				::= { dsltrap 6 }

	xdslXturLpr	NOTIFICATION-TYPE
				OBJECTS { ifIndex }
				STATUS  current
				DESCRIPTION	"The trap signifies XTU-R Loss of Power."
				::= { dsltrap 7 }

	xdslXtucLofClear	NOTIFICATION-TYPE
				OBJECTS { ifIndex }
				STATUS  current
				DESCRIPTION	"The trap signifies XTU-C Loss of Framing is cleared."
				::= { dsltrap 8 }

	xdslXtucLosClear	NOTIFICATION-TYPE
				OBJECTS { ifIndex }
				STATUS  current
				DESCRIPTION	"The trap signifies XTU-C Loss of Signal is cleared."
				::= { dsltrap 9 }

	xdslXturLofClear	NOTIFICATION-TYPE
				OBJECTS { ifIndex }
				STATUS  current
				DESCRIPTION	"The trap signifies XTU-R Loss of Framing is cleared."
				::= { dsltrap 10 }

	xdslXturLosClear	NOTIFICATION-TYPE
				OBJECTS { ifIndex }
				STATUS  current
				DESCRIPTION	"The trap signifies XTU-R Loss of Signal is cleared."
				::= { dsltrap 11 }

	xdslXturLprClear	NOTIFICATION-TYPE
				OBJECTS { ifIndex }
				STATUS  current
				DESCRIPTION	"The trap signifies XTU-R Loss of Power is cleared."
				::= { dsltrap 12 }

	xdslLoopguard		NOTIFICATION-TYPE
				OBJECTS { ifIndex, dslLgSenderIfIndex }
				STATUS  current
				DESCRIPTION	"The trap signifies loop is detected by ifIndex."
				::= { dsltrap 13 }

	xdslLoopguardClear	NOTIFICATION-TYPE
				OBJECTS { ifIndex, dslLgSenderIfIndex }
				STATUS  current
				DESCRIPTION	"The trap signifies loop in ifIndex is cleared."
				::= { dsltrap 14 }

	xdslDspDownloadFail	NOTIFICATION-TYPE
				OBJECTS { slotModuleIdVes1724-58v,
					xdslDevId
				}
				STATUS  current
				DESCRIPTION	"The trap signifies DSL modem code download failed."
				::= { dsltrap 15 }

	xdslDspDownloadFailClear	NOTIFICATION-TYPE
				OBJECTS { slotModuleIdVes1724-58v,
					xdslDevId
				}
				STATUS  current
				DESCRIPTION	"The trap signifies DSL modem code download fail is cleared."
				::= { dsltrap 16 }

	xdslDspInoperable	NOTIFICATION-TYPE
				OBJECTS { slotModuleIdVes1724-58v,
					xdslDevId
				}
				STATUS  current
				DESCRIPTION	"The trap signifies a DSL chip failure due to
				             modem code download faied for 10 times."
				::= { dsltrap 17 }

	xdslHtPortPolicer	NOTIFICATION-TYPE
				OBJECTS { ifIndex }
				STATUS  current
				DESCRIPTION	"The trap signifies host was attacked from port layer"
				::= { dsltrap 18 }

	xdslLinePerfLOFSThreshXtuc	NOTIFICATION-TYPE
				OBJECTS { xdsl2PMLCurr15MLofs, vdsl2LineAlarmConfProfileXtucThresh15MinLofs }
				STATUS  current
				DESCRIPTION	"This notification indicates that the LOFS seconds threshold has been reached/exceeded for the referred xTU-C."
				::= { dsltrap 19 }

	xdslLinePerfLOFSThreshXtur	NOTIFICATION-TYPE
				OBJECTS { xdsl2PMLCurr15MLofs, vdsl2LineAlarmConfProfileXturThresh15MinLofs }
				STATUS  current
				DESCRIPTION	"This notification indicates that the LOFS seconds threshold has been reached/exceeded for the referred xTU-R."
				::= { dsltrap 20 }

	xdslLinePerfLPRSThreshXtur	NOTIFICATION-TYPE
				OBJECTS { xdsl2PMLInitCurr15MLprs, vdsl2LineAlarmConfProfileXturThresh15MinLprs }
				STATUS  current
				DESCRIPTION	"This notification indicates that the LPRS seconds threshold has been reached/exceeded for the referred xTU-R."
				::= { dsltrap 21 }

	xdslPmTrapTxOctets NOTIFICATION-TYPE
				OBJECTS { ifIndex, dslPmCurr15minTxOctets, dslPmThreshProfTxOctets }
				STATUS  current
				DESCRIPTION
	            "Threshold trap for TX Octets"
				::= { dsltrap 22 }
	
	xdslPmTrapTxPkts NOTIFICATION-TYPE
				OBJECTS { ifIndex, dslPmCurr15minTxPkts, dslPmThreshProfTxPkts }
				STATUS  current
				DESCRIPTION
	            "Threshold trap for TX packets"
				::= { dsltrap 23 }
				
	xdslPmTrapTxUnicastPkts NOTIFICATION-TYPE
				OBJECTS { ifIndex, dslPmCurr15minTxUnicastPkts, dslPmThreshProfTxUnicastPkts }
				STATUS  current
				DESCRIPTION
	            "Threshold trap for TX unicast packets"
				::= { dsltrap 24 }
	
	xdslPmTrapTxBroadcastPkts NOTIFICATION-TYPE
				OBJECTS { ifIndex, dslPmCurr15minTxBroadcastPkts, dslPmThreshProfTxBroadcastPkts }
				STATUS  current
				DESCRIPTION
	            "Threshold trap for TX broadcast packets"
				::= { dsltrap 25 }
	
	xdslPmTrapTxMulticastPkts NOTIFICATION-TYPE
				OBJECTS { ifIndex, dslPmCurr15minTxMulticastPkts, dslPmThreshProfTxMulticastPkts }
				STATUS  current
				DESCRIPTION
	            "Threshold trap for TX multicast packets"
				::= { dsltrap 26 }
	
	xdslPmTrapTxDiscardPkts NOTIFICATION-TYPE
				OBJECTS { ifIndex, dslPmCurr15minTxDiscardPkts, dslPmThreshProfTxDiscardPkts }
				STATUS  current
				DESCRIPTION
	            "Threshold trap for TX discard packets"
				::= { dsltrap 27 }
	
	xdslPmTrapRxOctets NOTIFICATION-TYPE
				OBJECTS { ifIndex, dslPmCurr15minRxOctets, dslPmThreshProfRxOctets }
				STATUS  current
				DESCRIPTION
	            "Threshold trap for RX Octets"
				::= { dsltrap 28 }
	
	xdslPmTrapRxPkts NOTIFICATION-TYPE
				OBJECTS { ifIndex, dslPmCurr15minRxPkts, dslPmThreshProfRxPkts }
				STATUS  current
				DESCRIPTION
	            "Threshold trap for RX packets"
				::= { dsltrap 29 }
				
	xdslPmTrapRxUnicastPkts NOTIFICATION-TYPE
				OBJECTS { ifIndex, dslPmCurr15minRxUnicastPkts, dslPmThreshProfRxUnicastPkts }
				STATUS  current
				DESCRIPTION
	            "Threshold trap for RX unicast packets"
				::= { dsltrap 30 }
	
	xdslPmTrapRxBroadcastPkts NOTIFICATION-TYPE
				OBJECTS { ifIndex, dslPmCurr15minRxBroadcastPkts, dslPmThreshProfRxBroadcastPkts }
				STATUS  current
				DESCRIPTION
	            "Threshold trap for RX broadcast packets"
				::= { dsltrap 31 }
	
	xdslPmTrapRxMulticastPkts NOTIFICATION-TYPE
				OBJECTS { ifIndex, dslPmCurr15minRxMulticastPkts, dslPmThreshProfRxMulticastPkts }
				STATUS  current
				DESCRIPTION
	            "Threshold trap for RX multicast packets"
				::= { dsltrap 32 }
	
	xdslPmTrapRxDiscardPkts NOTIFICATION-TYPE
				OBJECTS { ifIndex, dslPmCurr15minRxDiscardPkts, dslPmThreshProfRxDiscardPkts }
				STATUS  current
				DESCRIPTION
	            "Threshold trap for RX discard packets"
				::= { dsltrap 33 }
				
	xdslBondLinkUp NOTIFICATION-TYPE
				OBJECTS { xdslBondingStatusName, xdslBondingStatusTransferMode}
				STATUS  current
				DESCRIPTION
	            "The trap signifies the dsl bonding group has linked up."
				::= { dsltrap 34 }
				
	xdslBondLinkDown NOTIFICATION-TYPE
				OBJECTS { xdslBondingStatusName, xdslBondingStatusTransferMode}
				STATUS  current
				DESCRIPTION
	            "The trap signifies the dsl bonding group has linked down."
				::= { dsltrap 35 }
				
	xdslBondPortLinkUp NOTIFICATION-TYPE
				OBJECTS { xdslBondingStatusName, ifIndex}
				STATUS  current
				DESCRIPTION
	            "The trap signifies a port in dsl bonding group has linked up."
				::= { dsltrap 36 }
				
	xdslBondPortLinkDown NOTIFICATION-TYPE
				OBJECTS { xdslBondingStatusName, ifIndex}
				STATUS  current
				DESCRIPTION
	            "The trap signifies a port in dsl bonding group has linked down."
				::= { dsltrap 37 }	
--------------------
-- equipment
--------------------

	hwMonitorFail 		NOTIFICATION-TYPE
				OBJECTS { slotModuleIdVes1724-58v }
				STATUS current
				DESCRIPTION
					"Hardware monitor diagnosis is failed."
				::= { equipment 1 }

	voltageOutOfRange	NOTIFICATION-TYPE
				OBJECTS { slotModuleIdVes1724-58v,
				          voltageConfIndex,
				          voltageCurValue,
				          voltageConfHighThreshold,
				          voltageConfLowThreshold }
				STATUS  current
				DESCRIPTION	"Send a message to notify the manager that the voltage of the system is out of range.
				             The variable in the binding list is the current voltage in volt
				             of the system."
				::= { equipment 2 }

	voltageNormal		NOTIFICATION-TYPE
				OBJECTS { slotModuleIdVes1724-58v,
				          voltageConfIndex,
				          voltageCurValue,
				          voltageConfHighThreshold,
				          voltageConfLowThreshold }
				STATUS  current
				DESCRIPTION	"Send a message to notify the manager that the out-of-range condition is over.
				             The variable in the binding list is the current voltage in volt
				             of the system."
				::= { equipment 3 }

	temperatureOutOfRange		NOTIFICATION-TYPE
				OBJECTS { slotModuleIdVes1724-58v,
				          temperatureConfIndex,
				          temperatureCurValue,
				          temperatureConfHighThreshold,
				          temperatureConfLowThreshold }
				STATUS  current
				DESCRIPTION	"Send a message to notify the manager that the system is out of range.
				             The variable in the binding list is the current temperature in Celsius
				             of the system."
				::= { equipment 4 }

	temperatureNormal		NOTIFICATION-TYPE
				OBJECTS { slotModuleIdVes1724-58v,
				          temperatureConfIndex,
				          temperatureCurValue,
				          temperatureConfHighThreshold,
				          temperatureConfLowThreshold }
				STATUS  current
				DESCRIPTION	"Send a message to notify the manager that the out-of-range condition is over.
				             The variable in the binding list is the current temperature in Celsius
				             of the system."
				::= { equipment 5 }

	fanRpmOutOfRange		NOTIFICATION-TYPE
				OBJECTS { fanConfIndex,
				          fanRpmCurValue,
				          fanConfHighThreshold,
				          fanConfLowThreshold }
				STATUS  current
				DESCRIPTION	"Send a message to notify the manager that the rpm of the fan is out of range.
				             The variable in the binding list is the current rpm of the fan."
				::= { equipment 6 }

	fanRpmNormal		NOTIFICATION-TYPE
				OBJECTS { fanConfIndex,
				          fanRpmCurValue,
				          fanConfHighThreshold,
				          fanConfLowThreshold }
				STATUS  current
				DESCRIPTION	"Send a message to notify the manager that the out-of-range condition of the fan is over.
				             The variable in the binding list is the current rpm of the fan."
				::= { equipment 7 }

	hwRtcFail		NOTIFICATION-TYPE
				STATUS  current
				DESCRIPTION	"Send a message to notify the manager that the hardware RTC is failed."
				::= { equipment 8 }

	extAlarmInput1Trigger	NOTIFICATION-TYPE
				OBJECTS { externalAlarmName }
				STATUS  current
				DESCRIPTION	"The trap signifies that the external alarm input 1 of MSC card
				             is triggered."
				::= { equipment 9 }

	extAlarmInput1Release	NOTIFICATION-TYPE
				OBJECTS { externalAlarmName }
				STATUS  current
				DESCRIPTION	"The trap signifies that the external alarm input 1 of MSC card
				             is released."
				::= { equipment 10 }

	extAlarmInput2Trigger	NOTIFICATION-TYPE
				OBJECTS { externalAlarmName }
				STATUS  current
				DESCRIPTION	"The trap signifies that the external alarm input 2 of MSC card
				             is triggered."
				::= { equipment 11 }

	extAlarmInput2Release	NOTIFICATION-TYPE
				OBJECTS { externalAlarmName }
				STATUS  current
				DESCRIPTION	"The trap signifies that the external alarm input 2 of MSC card
				             is released."
				::= { equipment 12 }

	extAlarmInput3Trigger	NOTIFICATION-TYPE
				OBJECTS { externalAlarmName }
				STATUS  current
				DESCRIPTION	"The trap signifies that the external alarm input 3 of MSC card
				             is triggered."
				::= { equipment 13 }

	extAlarmInput3Release	NOTIFICATION-TYPE
				OBJECTS { externalAlarmName }
				STATUS  current
				DESCRIPTION	"The trap signifies that the external alarm input 3 of MSC card
				             is released."
				::= { equipment 14 }

	extAlarmInput4Trigger	NOTIFICATION-TYPE
				OBJECTS { externalAlarmName }
				STATUS  current
				DESCRIPTION	"The trap signifies that the external alarm input 4 of MSC card
				             is triggered."
				::= { equipment 15 }

	extAlarmInput4Release	NOTIFICATION-TYPE
				OBJECTS { externalAlarmName }
				STATUS  current
				DESCRIPTION	"The trap signifies that the external alarm input 4 of MSC card
				             is released."
				::= { equipment 16 }

	acDown	NOTIFICATION-TYPE
				STATUS  current
				DESCRIPTION	"The trap signifies AC power is down"
				::= { equipment 38 }
				
	acDownClear	NOTIFICATION-TYPE
				STATUS  current
				DESCRIPTION	"The trap signifies AC power down is cleared"
				::= { equipment 39 }
				
	battTempSensorAbsent	NOTIFICATION-TYPE
				STATUS  current
				DESCRIPTION	"The trap signifies the battery temperature sensor is absent"
				::= { equipment 43 }  
				
	battTempSensorAbsentClear	NOTIFICATION-TYPE
				STATUS  current
				DESCRIPTION	"The trap signifies battTempSensorAbsent alarm is cleared"
				::= { equipment 44 }
				
	batteryTempOutofRange	NOTIFICATION-TYPE
				OBJECTS { externalBatteryStatsTemperature,
				externalBatteryConfTempHighThreshold,
				externalBatteryConfTempLowThreshold
				}
				STATUS  current
				DESCRIPTION	"The trap signifies battery temperature not between normal threshold"
				::= { equipment 45 }
				
	batteryTempNormal	NOTIFICATION-TYPE
				OBJECTS { externalBatteryStatsTemperature,
				externalBatteryConfTempHighThreshold,
				externalBatteryConfTempLowThreshold
				}
				STATUS  current
				DESCRIPTION	"The trap signifies battery temperature abnormal is cleared"
				::= { equipment 46 }
				

				
	dcCriticIssue	NOTIFICATION-TYPE
				OBJECTS { externalBatteryStatsVoltage,
				externalBatteryConfDcCriticThreshold
				}
				STATUS  current
				DESCRIPTION	"The trap signifies AC power is down and battery voltage under the threshold"
				::= { equipment 49 }
				
	dcCriticClear	NOTIFICATION-TYPE
				OBJECTS { externalBatteryStatsVoltage,
				externalBatteryConfDcCriticThreshold
				}
				STATUS  current
				DESCRIPTION	"The trap signifies DC critic alarm is cleared"
				::= { equipment 50 }



	dcLowIssue	NOTIFICATION-TYPE
				OBJECTS { externalBatteryStatsVoltage,
				externalBatteryConfDcLowThreshold
				}
				STATUS  current
				DESCRIPTION	"The trap signifies AC power is down and battery voltage under the threshold"
				::= { equipment 51 }
				
	dcLowClear	NOTIFICATION-TYPE
				OBJECTS { externalBatteryStatsVoltage,
				externalBatteryConfDcLowThreshold
				}
				STATUS  current
				DESCRIPTION	"The trap signifies DC Low alarm is cleared"
				::= { equipment 52 }
	
	dcErrorIssue	NOTIFICATION-TYPE
				OBJECTS { externalBatteryStatsVoltage,
				externalBatteryConfDcErrThreshold
				}
				STATUS  current
				DESCRIPTION	"The trap signifies the battery is too low to be charged"
				::= { equipment 53 }  
				
	dcErrorClear	NOTIFICATION-TYPE
				OBJECTS { externalBatteryStatsVoltage,
				externalBatteryConfDcErrThreshold
				}
				STATUS  current
				DESCRIPTION	"The trap signifies dc error alarm is cleared"
				::= { equipment 54 }
				
	dcFailIssue	NOTIFICATION-TYPE
				STATUS  current
				DESCRIPTION	"The trap signifies the battery is absent"
				::= { equipment 55 }  
				
	dcFailClear	NOTIFICATION-TYPE
				STATUS  current
				DESCRIPTION	"The trap signifies dc fail alarm is cleared"
				::= { equipment 56 }

	
--------------------
-- systrap
--------------------

	sysMacAntiSpoofing NOTIFICATION-TYPE
				OBJECTS {
					sysMacAntiSpoofOrig,
					sysMacAntiSpoofNew,
					sysMacAntiSpoofMAC
				}
				STATUS current
				DESCRIPTION
					"MAC Anti-spoofing."
				::= { systrap 1 }

	sysAlarmClearEnable NOTIFICATION-TYPE
				STATUS current
				DESCRIPTION
					"Alarm clear is activated."
				::= { systrap 2 }

	sysLoginFailure NOTIFICATION-TYPE
				STATUS current
				DESCRIPTION
					"User login is failed."
				::= { systrap 3 }

	reboot		NOTIFICATION-TYPE
				OBJECTS { sysProblemCause }
				STATUS  current
				DESCRIPTION	"Send a message to the manager that the system is going to shutdown.
				             The variable is the reason that causes the system to shutdown."
				::= { systrap 4 }

	cpuOverload		NOTIFICATION-TYPE
				OBJECTS { sysCoaIssuedLoad, coaConfIssueThreshold, coaConfAnalyticMethod }
				STATUS  current
				DESCRIPTION	"Signifies cpu is overload."
				::= { systrap 5 }

	cpuOverloadClear	NOTIFICATION-TYPE
				OBJECTS { sysCoaIssuedLoad, coaConfIssueThreshold, coaConfAnalyticMethod }
				STATUS  current
				DESCRIPTION	"Signifies cpu overload is cleared."
				::= { systrap 6 }

	cfgUploadFail		NOTIFICATION-TYPE
				STATUS  current
				DESCRIPTION	"Signifies configuration file uploading to EMS failed."
				::= { systrap 7 }

	cfgReloadFail		NOTIFICATION-TYPE
				STATUS  current
				DESCRIPTION	"Signifies configuration file reload from FLASH failed."
				::= { systrap 8 }

	writeFlashFail		NOTIFICATION-TYPE
				STATUS  current
				DESCRIPTION	"Signifies writing to flash failed."
				::= { systrap 9 }

	mfgDataFail		NOTIFICATION-TYPE
				STATUS  current
				DESCRIPTION	"Signifies invalid manufacturing data."
				::= { systrap 10 }

--	pmUploadNotification		NOTIFICATION-TYPE
--				OBJECTS { sysPmSyncUrl, sysPmSyncStatus }
--			STATUS  current 	
--			DESCRIPTION	"Sig	nifies PM file uploading status."
--			::= { systrap 17	 }

--	swDownloadNotification		NOTIFICATION-TYPE
--				OBJECTS { sysFwUpgradeUrl, sysFwUpgradeStatus, sysFwUpgradeVersion }
--				STATUS  current
--				DESCRIPTION	"Signifies SW image downloading/installing/restoring/reverting status."
--				::= { systrap 18 }

--	cfgChangeNotification		NOTIFICATION-TYPE
--				OBJECTS { sysCmSyncRefCounter }
--				STATUS  current
--				DESCRIPTION	"Signifies configuration change from CLI command."
--				::= { systrap 19 }

--	{ systrap 20 } is reserved by TIU-xx
--	{ systrap 21 } is reserved by TIU-xx
--	dhcpLeasedNotification		NOTIFICATION-TYPE
--				OBJECTS { dhcpIfIndex, dhcpServerIpv4Address, dhcpLeasedIpv4Address }
--				STATUS  current
--				DESCRIPTION	"To indicate the system complete DHCP lease process and attached to TCU-02 or external OSS.
--							The variable bindings are:
--							1) 1: tcu management interface; 2: oss management interface.  
--							2) the IP address of TCU DHCP server.
--							3) the IP address leased from TCU DHCP server."
--				::= { systrap 20 }

--	sysRestartNotification		NOTIFICATION-TYPE
--				OBJECTS { sysBootupFwVersion, sysRestartCause, sysRestartErrorCode, sysResetAdditionalInfo}
--				STATUS  current
--				DESCRIPTION	"This is a trap to unify system restart trap definition.
--							The standard ones ('warm start' and 'cold start') are no longer supported.
--							1) sysBootupFwVersion: the system happened restart with booting up firmware version.
--							2) sysRestartCause: what reason caused system restart.
--							3) sysRestartErrorCode: if this is a restart caused by software problem then error code is specified.
--							   '0': is specified is not related to software.
--							4) sysResetAdditionalInfo: short description of restart reason.
--							Note: this notification shall be sent after system restarts."
--				::= { systrap 21 }

--------------------
-- getrap
--------------------

	geLinkDown NOTIFICATION-TYPE
	    OBJECTS { ifIndex, ifAdminStatus, ifOperStatus }
	    STATUS  current
	    DESCRIPTION
	            "The trap signifies one ethernet port is linked down."
	    ::= { getrap 1 }

	geLinkUp NOTIFICATION-TYPE
	    OBJECTS { ifIndex, ifAdminStatus, ifOperStatus }
	    STATUS  current
	    DESCRIPTION
	            "The trap signifies one ethernet port is linked up."
	    ::= { getrap 2 }

	gePmTrapTxOctets NOTIFICATION-TYPE
	    OBJECTS { ifIndex, gePmCurr15minTxOctets, gePmThreshProfTxOctets }
	    STATUS  current
	    DESCRIPTION
	            "Threshold trap for TX Octets"
	    ::= { getrap 3 }

	gePmTrapTxPkts NOTIFICATION-TYPE
	    OBJECTS { ifIndex, gePmCurr15minTxPkts, gePmThreshProfTxPkts }
	    STATUS  current
	    DESCRIPTION
	            "Threshold trap for TX packets"
	    ::= { getrap 4 }

	gePmTrapTxBroadcastPkts NOTIFICATION-TYPE
	    OBJECTS { ifIndex, gePmCurr15minTxBroadcastPkts, gePmThreshProfTxBroadcastPkts }
	    STATUS  current
	    DESCRIPTION
	            "Threshold trap for TX Broadcast packets"
	    ::= { getrap 5 }

	gePmTrapTxMulticastPkts NOTIFICATION-TYPE
	    OBJECTS { ifIndex, gePmCurr15minTxMulticastPkts, gePmThreshProfTxMulticastPkts }
	    STATUS  current
	    DESCRIPTION
	            "Threshold trap for TX Multicast packets"
	    ::= { getrap 6 }

	gePmTrapRxOctets NOTIFICATION-TYPE
	    OBJECTS { ifIndex, gePmCurr15minRxOctets, gePmThreshProfRxOctets }
	    STATUS  current
	    DESCRIPTION
	            "Threshold trap for RX Octets"
	    ::= { getrap 7 }

	gePmTrapRxPkts NOTIFICATION-TYPE
	    OBJECTS { ifIndex, gePmCurr15minRxPkts, gePmThreshProfRxPkts }
	    STATUS  current
	    DESCRIPTION
	            "Threshold trap for RX packets"
	    ::= { getrap 8 }

	gePmTrapRxBroadcastPkts NOTIFICATION-TYPE
	    OBJECTS { ifIndex, gePmCurr15minRxBroadcastPkts, gePmThreshProfRxBroadcastPkts }
	    STATUS  current
	    DESCRIPTION
	            "Threshold trap for RX Broadcast packets"
	    ::= { getrap 9 }

	gePmTrapRxMulticastPkts NOTIFICATION-TYPE
	    OBJECTS { ifIndex, gePmCurr15minRxMulticastPkts, gePmThreshProfRxMulticastPkts }
	    STATUS  current
	    DESCRIPTION
	            "Threshold trap for RX Multicast packets"
	    ::= { getrap 10 }

	gePmTrapRxCRCAlignErrors NOTIFICATION-TYPE
	    OBJECTS { ifIndex, gePmCurr15minRxCRCAlignErrors, gePmThreshProfRxCRCAlignErrors }
	    STATUS  current
	    DESCRIPTION
	            "Threshold trap for RX CRC or Alignment error"
	    ::= { getrap 11 }

	gePmTrapRxUndersizePkts NOTIFICATION-TYPE
	    OBJECTS { ifIndex, gePmCurr15minRxUndersizePkts, gePmThreshProfRxUndersizePkts }
	    STATUS  current
	    DESCRIPTION
	            "Threshold trap for RX undersize"
	    ::= { getrap 12 }

	gePmTrapRxOversizePkts NOTIFICATION-TYPE
	    OBJECTS { ifIndex, gePmCurr15minRxOversizePkts, gePmThreshProfRxOversizePkts }
	    STATUS  current
	    DESCRIPTION
	            "Threshold trap for RX oversize"
	    ::= { getrap 13 }

	gePmTrapRxFragments NOTIFICATION-TYPE
	    OBJECTS { ifIndex, gePmCurr15minRxFragments, gePmThreshProfRxFragments }
	    STATUS  current
	    DESCRIPTION
	            "Threshold trap for RX Fragments"
	    ::= { getrap 14 }

	gePmTrapCollisions NOTIFICATION-TYPE
	    OBJECTS { ifIndex, gePmCurr15minCollisions, gePmThreshProfCollisions }
	    STATUS  current
	    DESCRIPTION
	            "Threshold trap for Collisions"
	    ::= { getrap 15 }

	gePmTrapPkts64Octets NOTIFICATION-TYPE
	    OBJECTS { ifIndex, gePmCurr15minPkts64Octets, gePmThreshProfPkts64Octets }
	    STATUS  current
	    DESCRIPTION
	            "Threshold trap for packets <= 64 octets"
	    ::= { getrap 16 }

	gePmTrapPkts65to127Octets NOTIFICATION-TYPE
	    OBJECTS { ifIndex, gePmCurr15minPkts65to127Octets, gePmThreshProfPkts65to127Octets }
	    STATUS  current
	    DESCRIPTION
	            "Threshold trap for packets 65 to 127 octets"
	    ::= { getrap 17 }

	gePmTrapPkts128to255Octets NOTIFICATION-TYPE
	    OBJECTS { ifIndex, gePmCurr15minPkts128to255Octets, gePmThreshProfPkts128to255Octets }
	    STATUS  current
	    DESCRIPTION
	            "Threshold trap for packets 128 to 255 octets"
	    ::= { getrap 18 }

	gePmTrapPkts256to511Octets NOTIFICATION-TYPE
	    OBJECTS { ifIndex, gePmCurr15minPkts256to511Octets, gePmThreshProfPkts256to511Octets }
	    STATUS  current
	    DESCRIPTION
	            "Threshold trap for packets 256 to 511 octets"
	    ::= { getrap 19 }

	gePmTrapPkts512to1023Octets NOTIFICATION-TYPE
	    OBJECTS { ifIndex, gePmCurr15minPkts512to1023Octets, gePmThreshProfPkts512to1023Octets }
	    STATUS  current
	    DESCRIPTION
	            "Threshold trap for packets 512 to 1023 octets"
	    ::= { getrap 20 }

	gePmTrapPkts1024to1518Octets NOTIFICATION-TYPE
	    OBJECTS { ifIndex, gePmCurr15minPkts1024to1518Octets, gePmThreshProfPkts1024to1518Octets }
	    STATUS  current
	    DESCRIPTION
	            "Threshold trap for packets 1024 to 1518 octets"
	    ::= { getrap 21 }

	gePmTrapPkts1519to1522Octets NOTIFICATION-TYPE
	    OBJECTS { ifIndex, gePmCurr15minPkts1519to1522Octets, gePmThreshProfPkts1519to1522Octets }
	    STATUS  current
	    DESCRIPTION
	            "Threshold trap for packets 1519 to 1522 octets"
	    ::= { getrap 22 }

	geTxUtilizationLevel1Over NOTIFICATION-TYPE
	    OBJECTS { ifIndex, geUtilTxIssueLvl1Threshold, geUtilTxCurrentPercent }
	    STATUS  current
	    DESCRIPTION
	            "Trap for ge utilization exceed configured level one threshold in Tx direction"
	    ::= { getrap 23 }

	geTxUtilizationLevel1Normal NOTIFICATION-TYPE
	    OBJECTS { ifIndex, geUtilTxIssueLvl1Threshold, geUtilTxCurrentPercent }
	    STATUS  current
	    DESCRIPTION
	            "Trap for ge utilization is under level one threshold in Tx direction"
	    ::= { getrap 24 }       
	    
	geTxUtilizationLevel2Over NOTIFICATION-TYPE
	    OBJECTS { ifIndex, geUtilTxIssueLvl2Threshold, geUtilTxCurrentPercent }
	    STATUS  current
	    DESCRIPTION
	            "Trap for ge utilization exceed configured level two threshold in Tx direction"
	    ::= { getrap 25 }

	geTxUtilizationLevel2Normal NOTIFICATION-TYPE
	    OBJECTS { ifIndex, geUtilTxIssueLvl2Threshold, geUtilTxCurrentPercent }
	    STATUS  current
	    DESCRIPTION
	            "Trap for ge utilization is under level two threshold in Tx direction"
	    ::= { getrap 26 }
	    
           
	geRxUtilizationLevel1Over NOTIFICATION-TYPE
	    OBJECTS { ifIndex, geUtilRxIssueLvl1Threshold, geUtilRxCurrentPercent }
	    STATUS  current
	    DESCRIPTION
	            "Trap for ge utilization exceed configured level one threshold in Rx direction"
	    ::= { getrap 27 }

	geRxUtilizationLevel1Normal NOTIFICATION-TYPE
	    OBJECTS { ifIndex, geUtilRxIssueLvl1Threshold, geUtilRxCurrentPercent }
	    STATUS  current
	    DESCRIPTION
	            "Trap for ge utilization is under level one threshold in Rx direction"
	    ::= { getrap 28 }
           
	                       
	geRxUtilizationLevel2Over NOTIFICATION-TYPE
	    OBJECTS { ifIndex, geUtilRxIssueLvl2Threshold, geUtilRxCurrentPercent }
	    STATUS  current
	    DESCRIPTION
	            "Trap for ge utilization exceed configured level two threshold in Rx direction"
	    ::= { getrap 29 }

	geRxUtilizationLevel2Normal NOTIFICATION-TYPE
	    OBJECTS { ifIndex, geUtilRxIssueLvl2Threshold, geUtilRxCurrentPercent }
	    STATUS  current
	    DESCRIPTION
	            "Trap for ge utilization is under level two threshold in Rx direction"
	    ::= { getrap 30 }
	                       
--	enetSfpDisallow NOTIFICATION-TYPE
--	    OBJECTS { ifIndex, sfpVendorName }
--	    STATUS  current
--	    DESCRIPTION
--	            "SFP module is not allowed"
--	    ::= { enettrap 22 }

--	enetSfpDisallowClear NOTIFICATION-TYPE
--	    OBJECTS { ifIndex }
--	    STATUS  current
--	    DESCRIPTION
--	            "SFP module is allowed"
--	    ::= { enettrap 23 }

--------------------
-- voiptrap
--------------------
	voipBatteryFail NOTIFICATION-TYPE
				OBJECTS { slotModuleIdVes1724-58v,
					voipDevId,
					voipBatType
				}
				STATUS current
				DESCRIPTION
					"Battery fault trigger."
				::= { voiptrap 1 }

	voipBatteryClear NOTIFICATION-TYPE
				OBJECTS { slotModuleIdVes1724-58v,
					voipDevId,
					voipBatType
				}
				STATUS current
				DESCRIPTION
					"Battery fault release."
				::= { voiptrap 2 }

	voipClockFail NOTIFICATION-TYPE
				OBJECTS { slotModuleIdVes1724-58v,
					voipDevId
				}
				STATUS current
				DESCRIPTION
					"Clock fault trigger."
				::= { voiptrap 3 }

	voipClockClear NOTIFICATION-TYPE
				OBJECTS { slotModuleIdVes1724-58v,
					voipDevId
				}
				STATUS current
				DESCRIPTION
					"Clock fault release."
				::= { voiptrap 4 }

	voipTempError NOTIFICATION-TYPE
				OBJECTS {	ifIndex,
						voipPhoneState
				}
				STATUS current
				DESCRIPTION
					"Temperature error trigger."
				::= { voiptrap 5 }

	voipTempClear NOTIFICATION-TYPE
				OBJECTS {	ifIndex,
						voipPhoneState
				}
				STATUS current
				DESCRIPTION
					"Temperature error release."
				::= { voiptrap 6 }

	voipDcPowerFail NOTIFICATION-TYPE
				OBJECTS {	ifIndex,
						voipPhoneState
				}
				STATUS current
				DESCRIPTION
					"DC power error trigger."
				::= { voiptrap 7 }

	voipDcPowerClear NOTIFICATION-TYPE
				OBJECTS {	ifIndex,
						voipPhoneState
				}
				STATUS current
				DESCRIPTION
					"DC power error release."
				::= { voiptrap 8 }

	voipAcPowerFail NOTIFICATION-TYPE
				OBJECTS {	ifIndex,
						voipPhoneState
				}
				STATUS current
				DESCRIPTION
					"AC power error trigger."
				::= { voiptrap 9 }

	voipAcPowerClear NOTIFICATION-TYPE
				OBJECTS {	ifIndex,
						voipPhoneState
				}
				STATUS current
				DESCRIPTION
					"AC power error release."
				::= { voiptrap 10 }

	voipRingTimerFail NOTIFICATION-TYPE
				OBJECTS {	voipRingSegment,
						voipRingTimerId
				}
				STATUS current
				DESCRIPTION
					"Ring timer fail trigger."
				::= { voiptrap 11 }

	voipRingRsrceFail NOTIFICATION-TYPE
				OBJECTS { ifIndex
				}
				STATUS current
				DESCRIPTION
					"This trap signify loads exceed the number of REN."
				::= { voiptrap 12 }

	voipNoFreeDspChannel NOTIFICATION-TYPE
				OBJECTS { ifIndex, voipCodecType
				}
				STATUS current
				DESCRIPTION
					"This trap signify there is no free DSP channel."
				::= { voiptrap 13 }

	voipPortServiceUp NOTIFICATION-TYPE
				OBJECTS { ifIndex }
				STATUS current
				DESCRIPTION
					"This trap signify the VoIP port service state is up."
				::= { voiptrap 14 }

	voipPortServiceDown NOTIFICATION-TYPE
				OBJECTS { ifIndex }
				STATUS current
				DESCRIPTION
					"This trap signify the VoIP port service state is down."
				::= { voiptrap 15 }

	voipMgcUp NOTIFICATION-TYPE
				OBJECTS { h248MgcIpDn
				}
				STATUS current
				DESCRIPTION
					"This trap signify MGC registration is successful."
				::= { voiptrap 20 }	      
				
	voipMgcDown NOTIFICATION-TYPE
				OBJECTS { h248MgcIpDn
				}
				STATUS current
				DESCRIPTION
					"This trap signify MGC registration is failed."
				::= { voiptrap 21 }					
                                          
	voipSipSvrUp NOTIFICATION-TYPE
				OBJECTS { sipProfileRegSvr
				}
				STATUS current
				DESCRIPTION
					"This trap signify registration to a specific SIP server is successful."
				::= { voiptrap 22 }	      
				
	voipSipSvrDown NOTIFICATION-TYPE
				OBJECTS { sipProfileRegSvr
				}
				STATUS current
				DESCRIPTION
					"This trap signify registration to a specific SIP server is failed."
				::= { voiptrap 23 }	                                          
--------------------
-- fxstrap
--------------------

	fxsPmTrapRtpElapsedTime NOTIFICATION-TYPE
	    OBJECTS { ifIndex, fxsPmCurr15minRtpElapsedTime, fxsPmThreshProfRtpElapsedTime }
	    STATUS  current
	    DESCRIPTION
	            "Threshold trap for RTP Elapsed Time"
	    ::= { fxstrap 1 }

	fxsPmTrapRtpTxBytes NOTIFICATION-TYPE
	    OBJECTS { ifIndex, fxsPmCurr15minRtpTxBytes, fxsPmThreshProfRtpTxBytes }
	    STATUS  current
	    DESCRIPTION
	            "Threshold trap for RTP transmitted bytes"
	    ::= { fxstrap 2 }

	fxsPmTrapRtpRxBytes NOTIFICATION-TYPE
	    OBJECTS { ifIndex, fxsPmCurr15minRtpRxBytes, fxsPmThreshProfRtpRxBytes }
	    STATUS  current
	    DESCRIPTION
	            "Threshold trap for RTP received bytes"
	    ::= { fxstrap 3 }

	fxsPmTrapRtpTxPkts NOTIFICATION-TYPE
	    OBJECTS { ifIndex, fxsPmCurr15minRtpTxPackets, fxsPmThreshProfRtpTxPackets }
	    STATUS  current
	    DESCRIPTION
	            "Threshold trap for RTP transmitted packets"
	    ::= { fxstrap 4 }       
	    
	fxsPmTrapRtpRxPkts NOTIFICATION-TYPE
	    OBJECTS { ifIndex, fxsPmCurr15minRtpRxPackets, fxsPmThreshProfRtpRxPackets }
	    STATUS  current
	    DESCRIPTION
	            "Threshold trap for RTP received packets"
	    ::= { fxstrap 5 }
	    

	fxsPmTrapRtpTxLostPkts NOTIFICATION-TYPE
	    OBJECTS { ifIndex, fxsPmCurr15minRtpTxLostPackets, fxsPmThreshProfRtpTxLostPackets }
	    STATUS  current
	    DESCRIPTION
	            "Threshold trap for RTP Transmitted lost packets"
	    ::= { fxstrap 6 }

	fxsPmTrapRtpRxLostPkts NOTIFICATION-TYPE
	    OBJECTS { ifIndex, fxsPmCurr15minRtpRxLostPackets, fxsPmThreshProfRtpRxLostPackets }
	    STATUS  current
	    DESCRIPTION
	            "Threshold trap for RTP received lost packets"
	    ::= { fxstrap 7 }
                   

END

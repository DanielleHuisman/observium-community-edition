-- ZyXEL Communications Corporation
-- Private Enterprise MIB definition 
  
-- This file describes the ZyXEL Communications Corporation Enterprise MIB.
-- It contains ZyXEL products OIDs, and common managed objects.

-- $Log: ZYXEL-DHCP-RELAY-MIB.mib $ 
-- Revision 1.6  2013/12/06 07:03:22  ccho 
-- remove uncessary imports 
-- Revision 1.5  2012/09/19 07:31:00  Kevin 
-- if it's leaf node, revise the vender name from zyxel to zy 
-- Revision 1.4  2012/08/22 09:47:18  Kevin 
-- clean warning for SNMPc 
-- Revision 1.3  2012/08/22 03:38:27  jasper 
-- Add new feature DHCP option82 per VLAN and per port 
-- Revision 1.2  2012/07/05 06:22:28  Kevin 
-- 1. upgrade from SNMP to SNMPv2  
-- 2. clean warning 
-- Revision 1.1  2012/05/30 07:48:43  Kevin 
-- Initial revision 

ZYXEL-DHCP-RELAY-MIB DEFINITIONS ::= BEGIN

    IMPORTS
	OBJECT-TYPE
		FROM SNMPv2-SMI			-- RFC2578	
		
	MODULE-IDENTITY
		FROM SNMPv2-SMI
	
	RowStatus
		FROM SNMPv2-TC			-- RFC2579
		
	DisplayString                                          
	  	FROM SNMPv2-TC
	  	
	EnabledStatus
		FROM  P-BRIDGE-MIB

	dot1dBasePort
		FROM BRIDGE-MIB


	IpAddress
		FROM SNMPv2-SMI

	esMgmt			
		FROM ZYXEL-ES-SMI;

	zyxelDhcpRelay MODULE-IDENTITY
		LAST-UPDATED	"201207010000Z"    
		ORGANIZATION "Enterprise Solution ZyXEL"     
		CONTACT-INFO
			""	   
		DESCRIPTION
			"The subtree for dhcp relay"
		::= { esMgmt 18 }	

	zyxelDhcpRelaySetup 	OBJECT IDENTIFIER ::= { zyxelDhcpRelay 1 }		

    zyxelDhcpRelayGlobalRelay 	OBJECT IDENTIFIER ::= { zyxelDhcpRelaySetup 1 }
	zyxelDhcpRelayVlanRelay 	OBJECT IDENTIFIER ::= { zyxelDhcpRelaySetup 2 }
  
	zyxelDhcpRelayStatus 	OBJECT IDENTIFIER ::= { zyxelDhcpRelay 2 }		

  	zyxelDhcpRelayVlanRelayInfo 	OBJECT IDENTIFIER ::= { zyxelDhcpRelayStatus 1 }	
  
 -- 1.zyxelDhcpRelayGlobalRelay
 
        zyDhcpRelayGlobalRelayState OBJECT-TYPE
        SYNTAX  EnabledStatus
        MAX-ACCESS  read-write
        STATUS  current
        DESCRIPTION
        "Enable/Disable global DHCP Relay."
        ::= { zyxelDhcpRelayGlobalRelay 1 }

        zyDhcpRelayGlobalRelayRemoteServerMaxNumberOfServers OBJECT-TYPE
        SYNTAX  INTEGER
        MAX-ACCESS  read-only
        STATUS  current
        DESCRIPTION
        "The maximum number of remote DHCP servers that can be created."
        ::= { zyxelDhcpRelayGlobalRelay 2 }

-- 		zyxelDhcpRelayGlobalRelayRemoteServerTable
        zyxelDhcpRelayGlobalRelayRemoteServerTable OBJECT-TYPE
        SYNTAX	SEQUENCE OF ZyxelDhcpRelayGlobalRelayRemoteServerEntry
        MAX-ACCESS  not-accessible
        STATUS  current
        DESCRIPTION
        "The table contains global DHCP relay remote server configuration."
        ::= { zyxelDhcpRelayGlobalRelay 3 }
        
		zyxelDhcpRelayGlobalRelayRemoteServerEntry OBJECT-TYPE
        SYNTAX	ZyxelDhcpRelayGlobalRelayRemoteServerEntry
        MAX-ACCESS	not-accessible
        STATUS	current
        DESCRIPTION    	
		"An entry contains global DHCP relay remote server configuration."
        INDEX          	{ zyDhcpRelayGlobalRelayRemoteServerIpAddress }
        ::= { zyxelDhcpRelayGlobalRelayRemoteServerTable 1 }

        ZyxelDhcpRelayGlobalRelayRemoteServerEntry ::=
           SEQUENCE {
        	zyDhcpRelayGlobalRelayRemoteServerIpAddress	IpAddress,
        	zyDhcpRelayGlobalRelayRemoteServerRowStatus	RowStatus
           }

        zyDhcpRelayGlobalRelayRemoteServerIpAddress OBJECT-TYPE
        SYNTAX  IpAddress
        MAX-ACCESS  not-accessible
        STATUS  current
        DESCRIPTION
        "IP address of the remote DHCP server."
        ::= { zyxelDhcpRelayGlobalRelayRemoteServerEntry 1 }

        zyDhcpRelayGlobalRelayRemoteServerRowStatus OBJECT-TYPE
        SYNTAX  RowStatus
        MAX-ACCESS  read-create
        STATUS  current
        DESCRIPTION
        "This object allows a remote DHCP server to be created and deleted."
        ::= { zyxelDhcpRelayGlobalRelayRemoteServerEntry 2 }
 
        zyDhcpRelayGlobalRelayOption82Profile OBJECT-TYPE
        SYNTAX  DisplayString
        MAX-ACCESS  read-write
        STATUS  current
        DESCRIPTION
        "Name of DHCP option 82 profile."
        ::= { zyxelDhcpRelayGlobalRelay 4 }

-- option82byport
		zyDhcpRelayGlobalRelayMaxNumberOfOption82Port OBJECT-TYPE
        SYNTAX  INTEGER
        MAX-ACCESS  read-only
        STATUS  current
        DESCRIPTION
        "The maximum number of DHCP global relay Option82 port entries that can be created."
        ::= { zyxelDhcpRelayGlobalRelay 5 } 

		zyxelDhcpRelayGlobalRelayOption82PortTable OBJECT-TYPE
        SYNTAX	SEQUENCE OF ZyxelDhcpRelayGlobalRelayOption82PortEntry
        MAX-ACCESS  not-accessible
        STATUS  current
        DESCRIPTION
        "The table contains DHCP global relay Option82 port configuration."
        ::= { zyxelDhcpRelayGlobalRelay 6 }	
		
		zyxelDhcpRelayGlobalRelayOption82PortEntry OBJECT-TYPE
        SYNTAX	ZyxelDhcpRelayGlobalRelayOption82PortEntry
        MAX-ACCESS	not-accessible
        STATUS	current
        DESCRIPTION    	
		"An entry contains DHCP global relay Option82 port configuration. "
        INDEX          	{ dot1dBasePort  }
        ::= { zyxelDhcpRelayGlobalRelayOption82PortTable 1 } 
 
		ZyxelDhcpRelayGlobalRelayOption82PortEntry ::=
        SEQUENCE { zyDhcpRelayGlobalRelayOption82PortProfile	DisplayString } 
		   
		zyDhcpRelayGlobalRelayOption82PortProfile OBJECT-TYPE
        SYNTAX  DisplayString
        MAX-ACCESS  read-create
        STATUS  current
        DESCRIPTION
        "DHCP option 82 profile in specified port."
        ::= { zyxelDhcpRelayGlobalRelayOption82PortEntry 1 }
		
		
-- 2. zyxelDhcpRelayVlanRelay

	 	zyDhcpRelayVlanRelayMaxNumberOfRelays OBJECT-TYPE
        SYNTAX  INTEGER
        MAX-ACCESS  read-only
        STATUS  current
        DESCRIPTION
        "The maximum numbers of DHCP relay entries that can be created. 
		 A value of 0 for this object implies that there exist settings for global DHCP relay."
        ::= { zyxelDhcpRelayVlanRelay 1 }
        
     	zyDhcpRelayVlanRelayRemoteServerMaxNumberOfServers OBJECT-TYPE
        SYNTAX  INTEGER
        MAX-ACCESS  read-only
        STATUS  current
        DESCRIPTION
        "The maximum number of remote DHCP servers that can be created."
        ::= { zyxelDhcpRelayVlanRelay 2 }
       
-- 		zyxelDhcpRelayVlanRelayRemoteServerTable
        zyxelDhcpRelayVlanRelayRemoteServerTable OBJECT-TYPE
        SYNTAX	SEQUENCE OF ZyxelDhcpRelayVlanRelayRemoteServerEntry
        MAX-ACCESS  not-accessible
        STATUS  current
        DESCRIPTION
        "The table contains DHCP relay remote server configuration."
        ::= { zyxelDhcpRelayVlanRelay 3 }
        
		zyxelDhcpRelayVlanRelayRemoteServerEntry OBJECT-TYPE
        SYNTAX	ZyxelDhcpRelayVlanRelayRemoteServerEntry
        MAX-ACCESS	not-accessible
        STATUS	current
        DESCRIPTION    	
		"An entry contains DHCP relay remote server configuration."
        INDEX          	{  zyDhcpRelayVlanRelayRemoteServerServeVid, zyDhcpRelayVlanRelayRemoteServerIpAddress }
        ::= { zyxelDhcpRelayVlanRelayRemoteServerTable 1 }

        ZyxelDhcpRelayVlanRelayRemoteServerEntry ::=
           SEQUENCE {  
            	zyDhcpRelayVlanRelayRemoteServerServeVid	INTEGER,
           		zyDhcpRelayVlanRelayRemoteServerIpAddress	IpAddress,
        		zyDhcpRelayVlanRelayRemoteServerRowStatus	RowStatus
           }     
           
        zyDhcpRelayVlanRelayRemoteServerServeVid OBJECT-TYPE
        SYNTAX  INTEGER
        MAX-ACCESS  not-accessible
        STATUS  current
        DESCRIPTION
        "The VLAN ID to which these DHCP settings apply."
        ::= { zyxelDhcpRelayVlanRelayRemoteServerEntry 1 }   
        
        zyDhcpRelayVlanRelayRemoteServerIpAddress OBJECT-TYPE
        SYNTAX  IpAddress
        MAX-ACCESS  not-accessible
        STATUS  current
        DESCRIPTION
        "IP address of a remote DHCP server."
        ::= { zyxelDhcpRelayVlanRelayRemoteServerEntry 2 }

        zyDhcpRelayVlanRelayRemoteServerRowStatus OBJECT-TYPE
        SYNTAX  RowStatus
        MAX-ACCESS  read-create
        STATUS  current
        DESCRIPTION
        "This object allows remote DHCP servers entries to be created and deleted for the specified VLAN."
        ::= { zyxelDhcpRelayVlanRelayRemoteServerEntry 3 }
          	
-- 		zyxelDhcpRelayVlanRelayTable   
        
        zyxelDhcpRelayVlanRelayTable OBJECT-TYPE
        SYNTAX	SEQUENCE OF ZyxelDhcpRelayVlanRelayEntry
        MAX-ACCESS  not-accessible
        STATUS  current
        DESCRIPTION
        "The table contains DHCP VLAN relay configuration."
        ::= { zyxelDhcpRelayVlanRelay 4 }  	


		zyxelDhcpRelayVlanRelayEntry OBJECT-TYPE
        SYNTAX	ZyxelDhcpRelayVlanRelayEntry
        MAX-ACCESS	not-accessible
        STATUS	current
        DESCRIPTION    	
		"An entry contains DHCP VLAN relay configuration. "
        INDEX          	{ zyDhcpRelayVlanRelayRemoteServerServeVid }
        ::= { zyxelDhcpRelayVlanRelayTable 1 }

        ZyxelDhcpRelayVlanRelayEntry ::=
           SEQUENCE {
			zyDhcpRelayVlanRelayOption82Profile    DisplayString
           }

        zyDhcpRelayVlanRelayOption82Profile OBJECT-TYPE
        SYNTAX  DisplayString
        MAX-ACCESS  read-write
        STATUS  current
        DESCRIPTION
        "Name of DHCP option 82 profile."
        ::= { zyxelDhcpRelayVlanRelayEntry 1 }   
                          
-- option82byport
		zyDhcpRelayVlanRelayMaxNumberOfOption82VlanPort OBJECT-TYPE
        SYNTAX  INTEGER
        MAX-ACCESS  read-only
        STATUS  current
        DESCRIPTION
        "The maximum number of DHCP VLAN relay Option82 VLAN port entries that can be created."
        ::= { zyxelDhcpRelayVlanRelay 5 } 

		zyxelDhcpRelayVlanRelayOption82VlanPortTable OBJECT-TYPE
        SYNTAX	SEQUENCE OF ZyxelDhcpRelayVlanRelayOption82VlanPortEntry
        MAX-ACCESS  not-accessible
        STATUS  current
        DESCRIPTION
        "The table contains DHCP VLAN relay Option82 VLAN port configuration."
        ::= { zyxelDhcpRelayVlanRelay 6 }	
		
		zyxelDhcpRelayVlanRelayOption82VlanPortEntry OBJECT-TYPE
        SYNTAX	ZyxelDhcpRelayVlanRelayOption82VlanPortEntry
        MAX-ACCESS	not-accessible
        STATUS	current
        DESCRIPTION    	
		"An entry contains DHCP VLAN relay Option82 VLAN port configuration. "
        INDEX          	{ zyDhcpRelayVlanRelayRemoteServerServeVid ,dot1dBasePort  }
        ::= { zyxelDhcpRelayVlanRelayOption82VlanPortTable 1 } 
 
		ZyxelDhcpRelayVlanRelayOption82VlanPortEntry ::=
        SEQUENCE {  
            	zyDhcpRelayVlanRelayOption82VlanPortProfile	DisplayString
        } 
		   
		zyDhcpRelayVlanRelayOption82VlanPortProfile OBJECT-TYPE
        SYNTAX  DisplayString
        MAX-ACCESS  read-create
        STATUS  current
        DESCRIPTION
        "DHCP option 82 profile in specified VLAN and port."
        ::= { zyxelDhcpRelayVlanRelayOption82VlanPortEntry 1 }		
 
-- 		zyxelDhcpRelayVlanRelaySourceAddressTable           
        zyxelDhcpRelayVlanRelaySourceAddressTable OBJECT-TYPE
        SYNTAX	SEQUENCE OF ZyxelDhcpRelayVlanRelaySourceAddressEntry
        MAX-ACCESS  not-accessible
        STATUS  current
        DESCRIPTION
        "The table contains DHCP VLAN relay source ip address configuration. "
        ::= { zyxelDhcpRelayVlanRelay 7 }  	


		zyxelDhcpRelayVlanRelaySourceAddressEntry OBJECT-TYPE
        SYNTAX	ZyxelDhcpRelayVlanRelaySourceAddressEntry
        MAX-ACCESS	not-accessible
        STATUS	current
        DESCRIPTION    	
		"An entry contains DHCP relay  source ip address configuration.  "
        INDEX          	{ zyDhcpRelayVlanRelayRemoteServerServeVid }
        ::= { zyxelDhcpRelayVlanRelaySourceAddressTable 1 }

        ZyxelDhcpRelayVlanRelaySourceAddressEntry ::=
           SEQUENCE {
			zyDhcpRelayVlanRelaySourceAddress    IpAddress
           }

        zyDhcpRelayVlanRelaySourceAddress OBJECT-TYPE
        SYNTAX  IpAddress
        MAX-ACCESS  read-write
        STATUS  current
        DESCRIPTION
        "IP address of DHCP relay source Ip address"
        ::= { zyxelDhcpRelayVlanRelaySourceAddressEntry 1 }   	
 

-- 2.zyxelDhcpRelayVlanRelayInfo         
        zyxelDhcpRelayVlanRelaySourceAddressInfoTable OBJECT-TYPE
        SYNTAX	SEQUENCE OF ZyxelDhcpRelayVlanRelaySourceAddressInfoEntry
        MAX-ACCESS  not-accessible
        STATUS  current
        DESCRIPTION
        "The table contains Current DHCP VLAN relay source ip address. "
        ::= { zyxelDhcpRelayVlanRelayInfo 1 }  	


		zyxelDhcpRelayVlanRelaySourceAddressInfoEntry OBJECT-TYPE
        SYNTAX	ZyxelDhcpRelayVlanRelaySourceAddressInfoEntry
        MAX-ACCESS	not-accessible
        STATUS	current
        DESCRIPTION    	
		"An entry contains Current DHCP relay  source ip address .  "
        INDEX          	{ zyDhcpRelayVlanRelayRemoteServerServeVid }
        ::= { zyxelDhcpRelayVlanRelaySourceAddressInfoTable 1 }

        ZyxelDhcpRelayVlanRelaySourceAddressInfoEntry ::=
           SEQUENCE {
			zyDhcpRelayVlanRelayCurrentSourceAddress    IpAddress
           }

        zyDhcpRelayVlanRelayCurrentSourceAddress OBJECT-TYPE
        SYNTAX  IpAddress
        MAX-ACCESS  read-only
        STATUS  current
        DESCRIPTION
        "DHCP relay Current source Ip address."
        ::= { zyxelDhcpRelayVlanRelaySourceAddressInfoEntry 1 }   
		
 
END

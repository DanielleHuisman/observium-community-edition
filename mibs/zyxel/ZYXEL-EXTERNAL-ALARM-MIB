-- ZyXEL Communications Corporation
-- Private Enterprise MIB definition 
  
-- This file describes the ZyXEL Communications Corporation Enterprise MIB.
-- It contains ZyXEL products OIDs, and common managed objects.

-- $Log: ZYXEL-EXTERNAL-ALARM-MIB.mib $ 
-- Revision 1.4  2013/12/06 07:04:39  ccho 
-- remove uncessary imports 
-- Revision 1.3  2012/09/19 07:33:00  Kevin 
-- if it's leaf node, revise the vender name from zyxel to zy 
-- Revision 1.2  2012/07/05 06:22:41  Kevin 
-- 1. upgrade from SNMP to SNMPv2  
-- 2. clean warning 
-- Revision 1.1  2012/05/30 07:48:49  Kevin 
-- Initial revision 

ZYXEL-EXTERNAL-ALARM-MIB DEFINITIONS ::= BEGIN

     IMPORTS
	OBJECT-TYPE
		FROM SNMPv2-SMI			-- RFC2578	
		
	MODULE-IDENTITY
		FROM SNMPv2-SMI

	NOTIFICATION-TYPE
		FROM SNMPv2-SMI
		
	esMgmt			
		FROM ZYXEL-ES-SMI;

	zyxelExternalAlarm MODULE-IDENTITY
		LAST-UPDATED	"201207010000Z"    
		ORGANIZATION "Enterprise Solution ZyXEL"     
		CONTACT-INFO
			""	   
		DESCRIPTION
			"The subtree for external alarm"
		::= { esMgmt 25 }	

	zyxelExternalAlarmTrapInfoObjects  	OBJECT IDENTIFIER ::= { zyxelExternalAlarm 1 } 
	zyxelExternalAlarmNotifications		OBJECT IDENTIFIER ::= { zyxelExternalAlarm 2 }			

--  25.ExternalAlarm
	   
	   	zyExternalAlarmTrapAlarmId OBJECT-TYPE
        SYNTAX  INTEGER
        MAX-ACCESS  read-only
        STATUS  current  
       	DESCRIPTION
        "This trap displays which ID of external alarm is detected."
        ::= { zyxelExternalAlarmTrapInfoObjects 1 }
      
	   
	   zyExternalAlarmDetect NOTIFICATION-TYPE  
	   OBJECTS {
			zyExternalAlarmTrapAlarmId
       }
	   STATUS  current
       DESCRIPTION
       "External alarm is detected."
       ::= { zyxelExternalAlarmNotifications 1 }


		
  END

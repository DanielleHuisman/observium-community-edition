-- ZyXEL Communications Corporation
-- Private Enterprise MIB definition 
  
-- This file describes the ZyXEL Communications Corporation Enterprise MIB.
-- It contains ZyXEL products OIDs, and common managed objects.

-- $Log: ZYXEL-IGMP-MIB.mib $ 
-- Revision 1.6  2013/12/06 07:05:51  ccho 
-- remove uncessary imports 
-- Revision 1.5  2013/11/20 06:51:09  ccho 
-- renaming identifier name for SMI.V2 
-- Revision 1.4  2013/11/06 05:41:14  ccho 
-- fix mib style 
-- Revision 1.3  2012/09/19 07:36:22  Kevin 
-- if it's leaf node, revise the vender name from zyxel to zy 
-- Revision 1.2  2012/07/05 06:22:52  Kevin 
-- 1. upgrade from SNMP to SNMPv2  
-- 2. clean warning 
-- Revision 1.1  2012/05/30 07:48:42  Kevin 
-- Initial revision 

ZYXEL-IGMP-MIB DEFINITIONS ::= BEGIN

    IMPORTS
	OBJECT-TYPE
		FROM SNMPv2-SMI			-- RFC2578	
		
	MODULE-IDENTITY
		FROM SNMPv2-SMI
	
	EnabledStatus
		FROM  P-BRIDGE-MIB

  zyRouteDomainIpAddress, zyRouteDomainIpMaskBits		
		FROM ZYXEL-IP-FORWARD-MIB
		
	esMgmt			
		FROM ZYXEL-ES-SMI;

	zyxelIgmp MODULE-IDENTITY
		LAST-UPDATED	"201207010000Z"    
		ORGANIZATION "Enterprise Solution ZyXEL"     
		CONTACT-INFO
			""	   
		DESCRIPTION
			"The subtree for Internet Group Management Protocol (IGMP)"
		::= { esMgmt 29 }	

	zyxelIgmpSetup     		OBJECT IDENTIFIER ::= { zyxelIgmp 1 }		

        zyIgmpState OBJECT-TYPE
        SYNTAX  EnabledStatus
        MAX-ACCESS  read-write
        STATUS  current
        DESCRIPTION
        "Enable/Disable IGMP on the switch."
        ::= { zyxelIgmpSetup 1 }

-- 		routerDomainIpTable
        zyxelIgmpRouteDomainTable OBJECT-TYPE
        SYNTAX	SEQUENCE OF ZyxelIgmpRouteDomainEntry
        MAX-ACCESS  not-accessible
        STATUS  current
        DESCRIPTION
        "The table contains IGMP route domain configuration."
        ::= { zyxelIgmpSetup 2 }
        
		zyxelIgmpRouteDomainEntry OBJECT-TYPE
        SYNTAX	ZyxelIgmpRouteDomainEntry
        MAX-ACCESS	not-accessible
        STATUS	current
        DESCRIPTION    	
		"An entry contains IGMP route domain configuration."
        INDEX          	{ zyRouteDomainIpAddress, zyRouteDomainIpMaskBits }
        ::= { zyxelIgmpRouteDomainTable 1 }

        ZyxelIgmpRouteDomainEntry ::=
        SEQUENCE {
        	zyIgmpRouteDomainVersion	INTEGER
            }   
           
        zyIgmpRouteDomainVersion OBJECT-TYPE
        SYNTAX  INTEGER {
        	none(0),
        	igmpV1(1),
        	igmpV2(2),
        	igmpV3(3)
        }
        MAX-ACCESS  read-write
        STATUS  current
        DESCRIPTION
        "IGMP version which controls the format and the multicasting method of the IGMP packets that the switch sends."
        ::= { zyxelIgmpRouteDomainEntry 1 }


END

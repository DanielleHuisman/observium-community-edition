-- ZyXEL Communications Corporation
-- Private Enterprise MIB definition 
  
-- This file describes the ZyXEL Communications Corporation Enterprise MIB.
-- It contains ZyXEL products OIDs, and common managed objects.

-- $Log: ZYXEL-IPV6-RIP-MIB.mib $ 
-- Revision 1.1  2017/09/08 07:50:31  Bruno
-- Initial revision 

ZYXEL-IPV6-RIP-MIB DEFINITIONS ::= BEGIN

	 IMPORTS
	OBJECT-TYPE
		FROM SNMPv2-SMI			-- RFC2578	
		
	MODULE-IDENTITY
		FROM SNMPv2-SMI
	
	EnabledStatus
		FROM  P-BRIDGE-MIB

   	zyIpv6IfIndex              
		FROM ZYXEL-IPV6-MIB

	esMgmt			
		FROM ZYXEL-ES-SMI;

	zyxelIpv6Rip MODULE-IDENTITY
		LAST-UPDATED	"201709080000Z"    
		ORGANIZATION "Enterprise Solution ZyXEL"     
		CONTACT-INFO
			""	   
		DESCRIPTION
			"The subtree for IPv6 RIP"
		::= { esMgmt 115 }
		
	zyxelIpv6RipSetup     		OBJECT IDENTIFIER ::= { zyxelIpv6Rip 1 }
	zyxelIpv6RipNotifications   OBJECT IDENTIFIER ::= { zyxelIpv6Rip 4 }


  
-- *******************************************************************
-- *
-- * zyxelIpv6RipSetup
-- *
-- *******************************************************************

-- zyIpv6RipState
		zyIpv6RipState OBJECT-TYPE
        SYNTAX  EnabledStatus
        MAX-ACCESS  read-write
        STATUS  current
        DESCRIPTION
            "Enabled/Disabled IPv6 RIP on the Switch."
        ::= { zyxelIpv6RipSetup 1 }

-- zyIpv6RipUpdateTimer
		zyIpv6RipUpdateTimer OBJECT-TYPE
        SYNTAX  INTEGER	(1..65535)
        MAX-ACCESS  read-write
        STATUS  current
        DESCRIPTION
            "Update timer value configuration."
        ::= { zyxelIpv6RipSetup 2 }
		
-- zyIpv6RipTimeoutTimer
		zyIpv6RipTimeoutTimer OBJECT-TYPE
        SYNTAX  INTEGER	(1..65535)
        MAX-ACCESS  read-write
        STATUS  current
        DESCRIPTION
            "Timeout timer value configuration."
        ::= { zyxelIpv6RipSetup 3 }
		
-- zyIpv6RipGarbageCollectionTimer
		zyIpv6RipGarbageCollectionTimer OBJECT-TYPE
        SYNTAX  INTEGER	(1..65535)
        MAX-ACCESS  read-write
        STATUS  current
        DESCRIPTION
            "Garbage-collection timer value configuration."
        ::= { zyxelIpv6RipSetup 4 }
		
-- zyIpv6RipDistance
		zyIpv6RipDistance OBJECT-TYPE
       SYNTAX  INTEGER	(10..255)
        MAX-ACCESS  read-write
        STATUS  current
        DESCRIPTION
            "The administrative distance of IPv6 RIP routes."
        ::= { zyxelIpv6RipSetup 5 }
		

-- zyxelIpv6RipInterfaceTable
		zyxelIpv6RipInterfaceTable OBJECT-TYPE
        SYNTAX	SEQUENCE OF ZyxelIpv6RipInterfaceEntry
        MAX-ACCESS  not-accessible
        STATUS  current
        DESCRIPTION
            "The table contains IPv6 RIP Interface configuration."
        ::= { zyxelIpv6RipSetup 6 }

-- zyxelIpv6RipInterfaceEntry
		zyxelIpv6RipInterfaceEntry OBJECT-TYPE
        SYNTAX	ZyxelIpv6RipInterfaceEntry
        MAX-ACCESS	not-accessible
        STATUS	current
        DESCRIPTION    	
            "An entry contains IPv6 RIP Interface configuration."
		INDEX {           
			zyIpv6IfIndex              
        }
        ::= { zyxelIpv6RipInterfaceTable 1 }
		
		
        ZyxelIpv6RipInterfaceEntry ::=
		SEQUENCE {			
        	zyIpv6RipInterfaceState	 EnabledStatus,
        	zyIpv6RipInterfaceMetric INTEGER,
            zyIpv6RipInterfaceMethod INTEGER
        }

-- zyIpv6RipInterfaceState		
        zyIpv6RipInterfaceState OBJECT-TYPE
        SYNTAX  EnabledStatus 
        MAX-ACCESS  read-write
        STATUS  current
        DESCRIPTION
			"IPv6 RIP state on the interface."
        ::= { zyxelIpv6RipInterfaceEntry 1 }

-- zyIpv6RipInterfaceMetric		
	    zyIpv6RipInterfaceMetric OBJECT-TYPE
        SYNTAX  INTEGER	(1..15)
        MAX-ACCESS  read-write
        STATUS  current
        DESCRIPTION
			"IPv6 RIP metric on the interface."
        ::= { zyxelIpv6RipInterfaceEntry 2 }

-- zyIpv6RipInterfaceMethod		
        zyIpv6RipInterfaceMethod OBJECT-TYPE
        SYNTAX  INTEGER {
			no_horizon(1), 
			split_horizon(2), 
			poison_reverse(3)
        }        
        MAX-ACCESS  read-write
        STATUS  current
        DESCRIPTION
			"IPv6 RIP update algorithm method configuration."
        ::= { zyxelIpv6RipInterfaceEntry 3 }

-- *******************************************************************
-- *
-- * zyxelIpv6RipNotifications
-- *
-- *******************************************************************	
       zyIpv6RipExceedMaxDynamicRoute NOTIFICATION-TYPE
	   STATUS  current
       DESCRIPTION
       "Received dynamic route is over the max route"
       ::= { zyxelIpv6RipNotifications 1 }
	
END

-- ZyXEL Communications Corporation
-- Private Enterprise MIB definition 
  
-- This file describes the ZyXEL Communications Corporation Enterprise MIB.
-- It contains ZyXEL products OIDs, and common managed objects.



ZYXEL-NLB-MIB DEFINITIONS ::= BEGIN
	IMPORTS
	OBJECT-TYPE
		FROM SNMPv2-SMI			-- RFC2578	
		
	MODULE-IDENTITY
		FROM SNMPv2-SMI
	
	RowStatus, MacAddress
		FROM SNMPv2-TC			-- RFC2579
	
	PortList
		FROM  Q-BRIDGE-MIB
		
	IpAddress
		FROM SNMPv2-SMI  
		
	InetAddressType, InetAddress
		FROM INET-ADDRESS-MIB		-- RFC2851	

	EnabledStatus
		FROM  P-BRIDGE-MIB 
		
	DisplayString                                          
	  	FROM SNMPv2-TC
		
	dot1dBasePort
       	FROM BRIDGE-MIB

	esMgmt			
		FROM ZYXEL-ES-SMI;	

	zyxelNlb MODULE-IDENTITY
		LAST-UPDATED	"201708170000Z"    
		ORGANIZATION "Enterprise Solution ZyXEL"     
		CONTACT-INFO
			""	   
		DESCRIPTION
			"The subtree for NLB"
		::= { esMgmt 114 }

	zyxelNlbSetup 				OBJECT IDENTIFIER ::= { zyxelNlb 1 }

-- 	******************************************************************
-- *
-- 1.zyxelNlbSetup
-- *
-- ******************************************************************         

--	NlbMacForwardTable 
        zyNlbMaxNumberOfMacForwards OBJECT-TYPE
        SYNTAX  INTEGER
        MAX-ACCESS  read-only
        STATUS  current
        DESCRIPTION
		"The maximum number of NLB mac forward entries that can be created"
        ::= { zyxelNlbSetup 1 }        

		zyxelNlbMacForwardTable OBJECT-TYPE
		SYNTAX	SEQUENCE OF ZyxelNlbMacForwardEntry
        MAX-ACCESS  not-accessible
        STATUS  current
        DESCRIPTION   
        "The table contains NLB mac forward configuration."		
		::=	{ zyxelNlbSetup 2 }
		
		zyxelNlbMacForwardEntry OBJECT-TYPE
		SYNTAX  ZyxelNlbMacForwardEntry
        MAX-ACCESS	not-accessible              
        STATUS	current
        DESCRIPTION	
        "An entry contains  NLB mac forward configuration."
		INDEX	{zyNlbMacForwardVlan, zyNlbMacForwardMacAddress}
		::={ zyxelNlbMacForwardTable 1 }
		
		ZyxelNlbMacForwardEntry ::=
			SEQUENCE {
				zyNlbMacForwardVlan			INTEGER,
				zyNlbMacForwardMacAddress	MacAddress,
				zyNlbMacForwardEgressPorts	PortList,
				zyNlbMacForwardName			OCTET STRING,
				zyNlbMacForwardRowStatus	RowStatus
			}
		
		
		zyNlbMacForwardVlan OBJECT-TYPE
		SYNTAX 	INTEGER  (1.. 4094)
        MAX-ACCESS	not-accessible
        STATUS	current
        DESCRIPTION	
        "This parameter specifies the VLAN identification nember."
		::={ zyxelNlbMacForwardEntry 1 }
		
		zyNlbMacForwardMacAddress OBJECT-TYPE
		SYNTAX 	MacAddress
        MAX-ACCESS	not-accessible
        STATUS	current
        DESCRIPTION	
        "This parameter specifies the MAC address assigned to the NLB mac forward in this entry."
		::={ zyxelNlbMacForwardEntry 2 }


		zyNlbMacForwardEgressPorts OBJECT-TYPE
		SYNTAX 	PortList
        MAX-ACCESS	read-write
        STATUS	current
        DESCRIPTION	
        "The set of ports which should transmit egress packets  for this mac forward entry. "
		::={ zyxelNlbMacForwardEntry 3 }

		zyNlbMacForwardName OBJECT-TYPE
		SYNTAX 	OCTET STRING
        MAX-ACCESS	read-write
        STATUS	current
        DESCRIPTION	
        "A descriptive name for identification purposes."
		::={ zyxelNlbMacForwardEntry 4 }		

		zyNlbMacForwardRowStatus OBJECT-TYPE
		SYNTAX 	RowStatus
        MAX-ACCESS	read-create
        STATUS	current
        DESCRIPTION	
        "This object allow NLB mac forward entries to be create and deleted from NLB mac forward table."
		::={ zyxelNlbMacForwardEntry 5 }        
                

--	NlbIpTable 
        zyNlbMaxNumberOfIps OBJECT-TYPE
        SYNTAX  INTEGER
        MAX-ACCESS  read-only
        STATUS  current
        DESCRIPTION
		"The maximum number of NLB IP entries that can be created"
        ::= { zyxelNlbSetup 3 }        

		zyxelNlbIpTable OBJECT-TYPE
		SYNTAX	SEQUENCE OF ZyxelNlbIpEntry
        MAX-ACCESS  not-accessible
        STATUS  current
        DESCRIPTION   
        "The table contains NLB IP configuration."		
		::=	{ zyxelNlbSetup 4 }
		
		zyxelNlbIpEntry OBJECT-TYPE
		SYNTAX  ZyxelNlbIpEntry
        MAX-ACCESS	not-accessible              
        STATUS	current
        DESCRIPTION	
        "An entry contains  NLB IP configuration."
		INDEX	{ zyNlbIpInetAddressType, zyNlbIpInetAddress}
		::={ zyxelNlbIpTable 1 }
		
		ZyxelNlbIpEntry ::=
			SEQUENCE {
				zyNlbIpInetAddressType	InetAddressType,
				zyNlbIpInetAddress		InetAddress,
				zyNlbIpMacAddress		MacAddress,
				zyNlbIpName				OCTET STRING,
				zyNlbIpRowStatus		RowStatus
			}
		
		zyNlbIpInetAddressType OBJECT-TYPE
		SYNTAX 	InetAddressType
        MAX-ACCESS	not-accessible
        STATUS	current
        DESCRIPTION	
        "The type of Internet address of this NLB IP entry."
		::={ zyxelNlbIpEntry 1 }
		
		zyNlbIpInetAddress OBJECT-TYPE
		SYNTAX 	InetAddress
        MAX-ACCESS	not-accessible
        STATUS	current
        DESCRIPTION	
        "The Internet address of this NLB IP entry.  
		 The type of this address is determined by the value of the zyNlbIpInetAddressType object."
		::={ zyxelNlbIpEntry 2 }

		zyNlbIpMacAddress OBJECT-TYPE
		SYNTAX 	MacAddress
        MAX-ACCESS	read-write
        STATUS	current
        DESCRIPTION	
        "This parameter specifies the MAC address assigned to the NLB IP address in this entry."
		::={ zyxelNlbIpEntry 3 }

		zyNlbIpName OBJECT-TYPE
		SYNTAX 	OCTET STRING
        MAX-ACCESS	read-write
        STATUS	current
        DESCRIPTION	
        "A descriptive name for identification purposes."
		::={ zyxelNlbIpEntry 4 }		

		zyNlbIpRowStatus OBJECT-TYPE
		SYNTAX 	RowStatus
        MAX-ACCESS	read-create
        STATUS	current
        DESCRIPTION	
        "This object allow NLB IP entries to be create and deleted from NLB IP table."
		::={ zyxelNlbIpEntry 5 }        
                

END

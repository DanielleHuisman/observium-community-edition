-- ZyXEL Communications Corporation
-- Private Enterprise MIB definition 
  
-- This file describes the ZyXEL Communications Corporation Enterprise MIB.
-- It contains ZyXEL products OIDs, and common managed objects.

-- $Log: ZYXEL-OUT-OF-BAND-MIB.mib $ 
-- Revision 1.4  2013/12/06 07:07:51  ccho 
-- remove uncessary imports 
-- Revision 1.3  2012/09/19 07:43:31  Kevin 
-- if it's leaf node, revise the vender name from zyxel to zy 
-- Revision 1.2  2012/07/05 06:24:09  Kevin 
-- 1. upgrade from SNMP to SNMPv2  
-- 2. clean warning 
-- Revision 1.1  2012/05/30 07:50:22  Kevin 
-- Initial revision 

ZYXEL-OUT-OF-BAND-MIB DEFINITIONS ::= BEGIN

    IMPORTS
	OBJECT-TYPE
		FROM SNMPv2-SMI			-- RFC2578	
		
	MODULE-IDENTITY
		FROM SNMPv2-SMI

    IpAddress
        FROM SNMPv2-SMI

	esMgmt			
		FROM ZYXEL-ES-SMI;

	zyxelOutOfBand MODULE-IDENTITY
		LAST-UPDATED	"201207010000Z"    
		ORGANIZATION "Enterprise Solution ZyXEL"     
		CONTACT-INFO
			""	   
		DESCRIPTION
			"The subtree for out-of-band management IP address"
		::= { esMgmt 58 }
		
	zyxelOutOfBandIpSetup   OBJECT IDENTIFIER ::= { zyxelOutOfBand 1 }

  
-- *******************************************************************
-- *
-- * zyxelOoutOfBandIpSetup
-- *
-- *******************************************************************

-- zyxelOutOfBandIpAddress
        zyOutOfBandIpAddress OBJECT-TYPE
        SYNTAX  IpAddress 
        MAX-ACCESS  read-write
        STATUS  current
        DESCRIPTION
                      "Enter the out-of-band management IP address of your switch in dotted decimal notation. For example, 192.168.0.1."
        ::= { zyxelOutOfBandIpSetup 1 }	
	
-- zyxelOutOfBandSubnetMask
        zyOutOfBandSubnetMask OBJECT-TYPE
        SYNTAX  IpAddress 
        MAX-ACCESS  read-write
        STATUS  current
        DESCRIPTION
                      "Enter the IP subnet mask of your switch in dotted decimal notation, for example, 255.255.255.0."
        ::= { zyxelOutOfBandIpSetup 2 }	

-- zyxelOutOfBandGateway
        zyOutOfBandGateway OBJECT-TYPE
        SYNTAX  IpAddress 
        MAX-ACCESS  read-write
        STATUS  current
        DESCRIPTION
                      "Enter the IP address of the default outgoing gateway in dotted decimal notation, for example, 192.168.0.254."
        ::= { zyxelOutOfBandIpSetup 3 }

END

-- ZyXEL Communications Corporation
-- Private Enterprise MIB definition 
  
-- This file describes the ZyXEL Communications Corporation Enterprise MIB.
-- It contains ZyXEL products OIDs, and common managed objects.

-- $Log: ZYXEL-STORM-CONTROL-MIB.mib $ 
-- Revision 1.7  2016/06/17 06:59:13  Viktor 
-- add new object in storm control trap to show storm type 
-- Revision 1.6  2015/02/09 08:51:41  neng 
-- support storm control log trap. 
-- Revision 1.5  2013/12/06 07:08:31  ccho 
-- remove uncessary imports 
-- Revision 1.4  2012/09/19 07:46:51  Kevin 
-- if it's leaf node, revise the vender name from zyxel to zy 
-- Revision 1.3  2012/08/22 09:49:20  Kevin 
-- clean warning for SNMPc 
-- Revision 1.2  2012/07/05 06:24:41  Kevin 
-- 1. upgrade from SNMP to SNMPv2  
-- 2. clean warning 
-- Revision 1.1  2012/05/30 07:50:47  Kevin 
-- Initial revision 

ZYXEL-STORM-CONTROL-MIB DEFINITIONS ::= BEGIN

    IMPORTS
	OBJECT-TYPE
		FROM SNMPv2-SMI			-- RFC2578	
		
	MODULE-IDENTITY
		FROM SNMPv2-SMI
		
	EnabledStatus
		FROM  P-BRIDGE-MIB

	dot1dBasePort
       	FROM BRIDGE-MIB

	esMgmt			
		FROM ZYXEL-ES-SMI
		
	ifIndex
    	FROM IF-MIB;				-- RFC2863

	zyxelStormControl MODULE-IDENTITY
		LAST-UPDATED	"201207010000Z"    
		ORGANIZATION "Enterprise Solution ZyXEL"     
		CONTACT-INFO
			""	   
		DESCRIPTION
			"The subtree for storm control"
		::= { esMgmt 78 }

	zyxelStormControlSetup   		OBJECT IDENTIFIER ::= { zyxelStormControl 1 }
	zyxelStormControlNotifications	OBJECT IDENTIFIER ::= { zyxelStormControl 2 }
	zyxelStormControlTrapInfoObject OBJECT IDENTIFIER ::= { zyxelStormControl 3 }	
	
-- *******************************************************************
-- *
-- * zyxelStormControlSetup
-- *
-- *******************************************************************

-- zyxelStromControlState
		zyStromControlState OBJECT-TYPE
        SYNTAX  EnabledStatus
        MAX-ACCESS  read-write
        STATUS  current
        DESCRIPTION
                    "Enabled/Disabled traffic storm control on the switch."
        ::= { zyxelStormControlSetup 1 }

-- zyxelStromControlPortTable
        zyxelStromControlPortTable OBJECT-TYPE
        SYNTAX	SEQUENCE OF ZyxelStromControlPortEntry
        MAX-ACCESS  not-accessible
        STATUS  current
        DESCRIPTION
                 	"The table cantains storm control port configuration."
        ::= { zyxelStormControlSetup 2 }
        
		zyxelStromControlPortEntry OBJECT-TYPE
        SYNTAX	ZyxelStromControlPortEntry
        MAX-ACCESS	not-accessible
        STATUS	current
        DESCRIPTION    	
					"A entry cantains storm control port configuration."
        INDEX          	{ dot1dBasePort }
        ::= { zyxelStromControlPortTable 1 }

        ZyxelStromControlPortEntry ::=
           SEQUENCE {
        	zyStromControlPortBroadcastState	EnabledStatus,
			zyStromControlPortBroadcastRate		INTEGER,
			zyStromControlPortMulticastState	EnabledStatus,
			zyStromControlPortMulticastRate		INTEGER,
			zyStromControlPortDlfState			EnabledStatus,
			zyStromControlPortDlfRate			INTEGER
           }

        zyStromControlPortBroadcastState OBJECT-TYPE
        SYNTAX  EnabledStatus
        MAX-ACCESS  read-write
        STATUS  current
        DESCRIPTION
                      	"Enabled/Disabled broadcast rate limit on the indicated port."
        ::= { zyxelStromControlPortEntry 1 }
        
        zyStromControlPortBroadcastRate OBJECT-TYPE
        SYNTAX  INTEGER
        MAX-ACCESS  read-write
        STATUS  current
        DESCRIPTION
                      	"Allowed broadcast rate in pkts/s. 
						For FE port, the maximum value is 148800 pkts/s. 
						For GE port, the maximum value is 262143 pkts/s."
        ::= { zyxelStromControlPortEntry 2 }
        
        zyStromControlPortMulticastState OBJECT-TYPE
        SYNTAX  EnabledStatus
        MAX-ACCESS  read-write
        STATUS  current
        DESCRIPTION
                      	"Enabled/Disabled multicast rate limit on the indicated port."
        ::= { zyxelStromControlPortEntry 3 }

        zyStromControlPortMulticastRate OBJECT-TYPE
        SYNTAX  INTEGER
        MAX-ACCESS  read-write
        STATUS  current
        DESCRIPTION
                      	"Allowed mullticast rate in pkts/s. 
						For FE port, the maximum value is 148800 pkts/s. 
						For GE port, the maximum value is 262143 pkts/s."
        ::= { zyxelStromControlPortEntry 4 }

        zyStromControlPortDlfState OBJECT-TYPE
        SYNTAX  EnabledStatus
        MAX-ACCESS  read-write
        STATUS  current
        DESCRIPTION
                      	"Enabled/Disabled destination lookup failure frames rate limit on the indicated port."
        ::= { zyxelStromControlPortEntry 5 }

        zyStromControlPortDlfRate OBJECT-TYPE
        SYNTAX  INTEGER
        MAX-ACCESS  read-write
        STATUS  current
        DESCRIPTION
                      	"Allowed destination lookup failure frames rate in pkts/s. 
						For FE port, the maximum value is 148800 pkts/s. 
						For GE port, the maximum value is 262143 pkts/s."
        ::= { zyxelStromControlPortEntry 6 }

-- *******************************************************************
-- *
-- * zyxelStormControlNotifications
-- *
-- *******************************************************************
    
	   zyPortStormControlTrap NOTIFICATION-TYPE
       OBJECTS {
				ifIndex,
				zyStormControlType
        }       
	   STATUS  current
       DESCRIPTION
						"A storm control is detected on specific port. 
						A packet filter action has been applied on the interface."
       ::= { zyxelStormControlNotifications 1 }
	   
-- *******************************************************************
-- *
-- * zyxelStormControlTrapInfoObject
-- *
-- *******************************************************************	
		
		zyStormControlType OBJECT-TYPE
        SYNTAX  INTEGER
		{
        	broadcast-storm(1),
			multicast-storm(2)
        }
        MAX-ACCESS   read-only
        STATUS  current
        DESCRIPTION
						"The detected storm control type."             
        ::= { zyxelStormControlTrapInfoObject 1 } 
  
END

-- ZyXEL Communications Corporation
-- Private Enterprise MIB definition 
  
-- This file describes the ZyXEL Communications Corporation Enterprise MIB.
-- It contains ZyXEL products OIDs, and common managed objects.



ZYXEL-WOL-RELAY-MIB DEFINITIONS ::= BEGIN
	IMPORTS
	OBJECT-TYPE
		FROM SNMPv2-SMI			-- RFC2578	
		
	MODULE-IDENTITY
		FROM SNMPv2-SMI
	
	RowStatus, MacAddress
		FROM SNMPv2-TC			-- RFC2579

	esMgmt			
		FROM ZYXEL-ES-SMI;	

	zyxelWolRelay MODULE-IDENTITY
		LAST-UPDATED	"201708170000Z"    
		ORGANIZATION "Enterprise Solution ZyXEL"     
		CONTACT-INFO
			""	   
		DESCRIPTION
			"The subtree for Wol Relay"
		::= { esMgmt 116 }

	zyxelWolRelaySetup 				OBJECT IDENTIFIER ::= { zyxelWolRelay 1 }

-- 	******************************************************************
-- *
-- 1.zyxelWolRelaySetup
-- *
-- ******************************************************************         

--	zyxelWolRelayTable 
        zyMaxNumberOfWolRelayEntry OBJECT-TYPE
        SYNTAX  INTEGER
        MAX-ACCESS  read-only
        STATUS  current
        DESCRIPTION
		"The maximum number of Wol relay entries that can be created"
        ::= { zyxelWolRelaySetup 1 }        

		zyxelWolRelayTable OBJECT-TYPE
		SYNTAX	SEQUENCE OF ZyxelWolRelayEntry
        MAX-ACCESS  not-accessible
        STATUS  current
        DESCRIPTION   
        "The table contains Wol relay configuration."		
		::=	{ zyxelWolRelaySetup 2 }
		
		zyxelWolRelayEntry OBJECT-TYPE
		SYNTAX  ZyxelWolRelayEntry
        MAX-ACCESS	not-accessible              
        STATUS	current
        DESCRIPTION	
        "An entry contains  Wol relay configuration."
		INDEX	{ zyWolRelayUdpPort}
		::={ zyxelWolRelayTable 1 }
		
		ZyxelWolRelayEntry ::=
			SEQUENCE {
				zyWolRelayUdpPort			INTEGER,
				zyWolRelaySourceVlanMap1k	OCTET STRING,
				zyWolRelaySourceVlanMap2k	OCTET STRING,
				zyWolRelaySourceVlanMap3k	OCTET STRING,
				zyWolRelaySourceVlanMap4k	OCTET STRING,
				zyWolRelayDestinationVlanMap1k	OCTET STRING,
				zyWolRelayDestinationVlanMap2k	OCTET STRING,
				zyWolRelayDestinationVlanMap3k	OCTET STRING,
				zyWolRelayDestinationVlanMap4k	OCTET STRING,
				zyWolRelayRowStatus     	RowStatus
			}	
		
		zyWolRelayUdpPort OBJECT-TYPE
		SYNTAX 	INTEGER  (0.. 65535)
        MAX-ACCESS	not-accessible
        STATUS	current
        DESCRIPTION	
        "This parameter specifies the UDP port identification nember."
		::={ zyxelWolRelayEntry 1 }
		
		zyWolRelaySourceVlanMap1k OBJECT-TYPE
            SYNTAX      OCTET STRING (SIZE (0..128))
            MAX-ACCESS  read-write
            STATUS      current
            DESCRIPTION
           "A string of octets containing one bit per VLAN. The
  			first octet corresponds to VLANs with VlanIndex values
  			1 through 8; the second octet to VLANs 9 through
  			16 etc.  The most significant bit of each octet
  			corresponds to the lowest VlanIndex value in that octet.
  
  			For each VLAN that is set to this wol relay source VLAN,
  			the bit corresponding to that VLAN is set to '1'.
  			Empty (zero) most significant octes are not mandatory."
    	::= { zyxelWolRelayEntry 2 }
		
        zyWolRelaySourceVlanMap2k      OBJECT-TYPE
            SYNTAX  OCTET STRING (SIZE (0..128))
            MAX-ACCESS  read-write
            STATUS  current
            DESCRIPTION
            "A string of octets containing one bit per VLAN for
  			 VLANS with VlanIndex values 1024 through 2047. The
  			 first octet corresponds to VLANs with VlanIndex values
  			 1024 through 1031; the second octet to VLANs 1032
  			 through 1039 etc.  The most significant bit of each
  			 octet corresponds to the lowest VlanIndex value in that
  			 octet.
  
  			 For each VLAN that is set to this wol relay source VLAN,
  			 the bit corresponding to that VLAN is set to '1'.
  			 Empty (zero) most significant octes are not mandatory."
         ::= { zyxelWolRelayEntry 3 }
        
        zyWolRelaySourceVlanMap3k      OBJECT-TYPE
            SYNTAX      OCTET STRING (SIZE (0..128))
            MAX-ACCESS  read-write
            STATUS      current
            DESCRIPTION
            "A string of octets containing one bit per VLAN for
             VLANS with VlanIndex values 2048 through 3071. The
             first octet corresponds to VLANs with VlanIndex values
             of 2048 through 2055; the second octet to VLANs 2056
             through 2063 etc.  The most significant bit of each
             octet corresponds to the lowest VlanIndex value in that
             octet.

             For each VLAN that is set to this wol relay source VLAN,
             the bit corresponding to that VLAN is set to '1'.
             Empty (zero) most significant octes are not mandatory."
         ::= { zyxelWolRelayEntry 4 }
        
        zyWolRelaySourceVlanMap4k      OBJECT-TYPE
            SYNTAX      OCTET STRING (SIZE (0..128))
            MAX-ACCESS  read-write
            STATUS      current
            DESCRIPTION
            "A string of octets containing one bit per VLAN for
             VLANS with VlanIndex values 3072 through 4095. The
             first octet corresponds to VLANs with VlanIndex values
             3072 through 3079; the second octet to VLANs 3080
             through 3087 etc.  The most significant bit of each
             octet corresponds to the lowest VlanIndex value in that
             octet.
        
             For each VLAN that is set to this wol relay source VLAN,
             the bit corresponding to that VLAN is set to '1'.       
             Empty (zero) most significant octes are not mandatory."
         ::= { zyxelWolRelayEntry 5 } 
  		
  		zyWolRelayDestinationVlanMap1k OBJECT-TYPE
            SYNTAX      OCTET STRING (SIZE (0..128))
            MAX-ACCESS  read-write
            STATUS      current
            DESCRIPTION
           "A string of octets containing one bit per VLAN. The
  			first octet corresponds to VLANs with VlanIndex values
  			1 through 8; the second octet to VLANs 9 through
  			16 etc.  The most significant bit of each octet
  			corresponds to the lowest VlanIndex value in that octet.
  
  			For each VLAN that is set to this wol relay destination VLAN,
  			the bit corresponding to that VLAN is set to '1'.
  			Empty (zero) most significant octes are not mandatory."
    	::= { zyxelWolRelayEntry 6 }
		
        zyWolRelayDestinationVlanMap2k      OBJECT-TYPE
            SYNTAX  OCTET STRING (SIZE (0..128))
            MAX-ACCESS  read-write
            STATUS  current
            DESCRIPTION
            "A string of octets containing one bit per VLAN for
  			 VLANS with VlanIndex values 1024 through 2047. The
  			 first octet corresponds to VLANs with VlanIndex values
  			 1024 through 1031; the second octet to VLANs 1032
  			 through 1039 etc.  The most significant bit of each
  			 octet corresponds to the lowest VlanIndex value in that
  			 octet.
  
  			 For each VLAN that is set to this wol relay destination VLAN,
  			 the bit corresponding to that VLAN is set to '1'.
  			 Empty (zero) most significant octes are not mandatory."
         ::= { zyxelWolRelayEntry 7 }
        
        zyWolRelayDestinationVlanMap3k      OBJECT-TYPE
            SYNTAX      OCTET STRING (SIZE (0..128))
            MAX-ACCESS  read-write
            STATUS      current
            DESCRIPTION
            "A string of octets containing one bit per VLAN for
             VLANS with VlanIndex values 2048 through 3071. The
             first octet corresponds to VLANs with VlanIndex values
             of 2048 through 2055; the second octet to VLANs 2056
             through 2063 etc.  The most significant bit of each
             octet corresponds to the lowest VlanIndex value in that
             octet.

             For each VLAN that is set to this wol relay destination VLAN,
             the bit corresponding to that VLAN is set to '1'.
             Empty (zero) most significant octes are not mandatory."
         ::= { zyxelWolRelayEntry 8 }
        
        zyWolRelayDestinationVlanMap4k      OBJECT-TYPE
            SYNTAX      OCTET STRING (SIZE (0..128))
            MAX-ACCESS  read-write
            STATUS      current
            DESCRIPTION
            "A string of octets containing one bit per VLAN for
             VLANS with VlanIndex values 3072 through 4095. The
             first octet corresponds to VLANs with VlanIndex values
             3072 through 3079; the second octet to VLANs 3080
             through 3087 etc.  The most significant bit of each
             octet corresponds to the lowest VlanIndex value in that
             octet.
        
             For each VLAN that is set to this wol relay destination VLAN,
             the bit corresponding to that VLAN is set to '1'.       
             Empty (zero) most significant octes are not mandatory."
         ::= { zyxelWolRelayEntry 9 }       		

		zyWolRelayRowStatus OBJECT-TYPE
		SYNTAX 	RowStatus
        MAX-ACCESS	read-create
        STATUS	current
        DESCRIPTION	
        "This object allow Wol relay entries to be create and deleted from Wol relay table."
		::={ zyxelWolRelayEntry 10 }        
 END

-- ZyXEL Communications Corporation
-- Private Enterprise MIB definition

-- This file describes the ZyXEL Communications Corporation Enterprise MIB.
-- It contains ZyXEL products OIDs, and common managed objects.


ZYXEL-ves1616pe54-MIB DEFINITIONS ::= BEGIN

    IMPORTS
	enterprises		FROM RFC1155-SMI

	OBJECT-TYPE
		FROM SNMPv2-SMI			-- RFC2578
	RowStatus, DateAndTime, TruthValue, StorageType, MacAddress
		FROM SNMPv2-TC			-- RFC2579
	DisplayString
	  	FROM RFC1213-MIB
	EnabledStatus
		FROM  P-BRIDGE-MIB
	PortList
		FROM  Q-BRIDGE-MIB
	dot1dBasePort
        	FROM BRIDGE-MIB
	InterfaceIndexOrZero			-- RFC2863
		FROM IF-MIB
	SnmpAdminString
		FROM SNMP-FRAMEWORK-MIB		-- RFC2571
	InetAddressType, InetAddress
		FROM INET-ADDRESS-MIB		-- RFC2851
	OperationResponseStatus
		FROM DISMAN-PING-MIB
	vdslLineConfProfileName 
		FROM VDSL-LINE-MIB	
	vdslLineAlarmConfProfileName 
		FROM VDSL-LINE-MIB
	vdslPerf1DayIntervalNumber
		FROM VDSL-LINE-MIB
	vdslPhysSide
		FROM VDSL-LINE-MIB
	ifIndex
		FROM IF-MIB
	vdslPerfIntervalNumber
		FROM VDSL-LINE-MIB
	dot1qVlanIndex
		FROM  Q-BRIDGE-MIB
	Dot1agCfmMepId
		FROM IEEE8021-CFM-MIB
	Xdsl2RaMode
		FROM VDSL2-LINE-TC-MIB	
	Xdsl2LineLdsf
	    FROM VDSL2-LINE-TC-MIB	
	xdsl2PMChHist1DInterval
	    FROM VDSL2-LINE-MIB
	xdsl2LineBand
	    FROM VDSL2-LINE-MIB
	xdsl2LineSegmentDirection
	    FROM VDSL2-LINE-MIB
	xdsl2LineSegment
	    FROM VDSL2-LINE-MIB
	xdsl2SCStatusDirection
	    FROM VDSL2-LINE-MIB
	xdsl2SCStatusBand
	    FROM VDSL2-LINE-MIB
	xdsl2PMLHist15MUnit
	    FROM VDSL2-LINE-MIB
	xdsl2PMLHist15MInterval
	    FROM VDSL2-LINE-MIB
	xdsl2PMLHist1DUnit
	    FROM VDSL2-LINE-MIB
	xdsl2PMLHist1DInterval
	    FROM VDSL2-LINE-MIB
	xdsl2PMChCurrUnit
	    FROM VDSL2-LINE-MIB
	xdsl2PMChHist15MUnit
	    FROM VDSL2-LINE-MIB
	xdsl2PMChHist15MInterval
	    FROM VDSL2-LINE-MIB
	xdsl2PMLCurrUnit
	    FROM VDSL2-LINE-MIB
	xdsl2PMChHist1DUnit
	    FROM VDSL2-LINE-MIB
	xdsl2LConfTempTemplateName
	    FROM VDSL2-LINE-MIB
	xdsl2LConfProfProfileName
	    FROM VDSL2-LINE-MIB
	xdsl2ChConfProfProfileName
	    FROM VDSL2-LINE-MIB
	xdsl2LAlarmConfTempTemplateName
	    FROM VDSL2-LINE-MIB
	xdsl2LineAlarmConfProfileName
	    FROM VDSL2-LINE-MIB
	xdsl2ChAlarmConfProfileName
	    FROM VDSL2-LINE-MIB
			
    IpAddress
        FROM SNMPv2-SMI
    Ipv6Address    
    	FROM IPV6-TC

    NOTIFICATION-TYPE
        FROM SNMPv2-SMI
    sysObjectID
        FROM RFC1213-MIB  
    BridgeId, Timeout
        FROM BRIDGE-MIB


   HCPerfIntervalThreshold,
   HCPerfTimeElapsed
      FROM  HC-PerfHist-TC-MIB;   -- [RFC3705]

    	zyxel		OBJECT IDENTIFIER ::= { enterprises 890 }
	products	OBJECT IDENTIFIER ::= { zyxel 1 }
	accessSwitch  	OBJECT IDENTIFIER ::= { products 5 }
	vesSeries	OBJECT IDENTIFIER ::= { accessSwitch 12 }
	ves1616pe54		OBJECT IDENTIFIER ::= { vesSeries 37 }

   --
   -- textual conventions used in this MIB
   --
   
   Vdsl2Band ::= TEXTUAL-CONVENTION
     STATUS current
     DESCRIPTION
        "Identifies a band in a
        VDSL2/ADSL/ADSL2/ADSL2+
        link. For a band in the upstream direction,
        transmission is from the remote end (xTU-R)
        towards the central office end (xTU-C).
        A band in the upstream direction is
        indicated by upstream(1) for
        ADSL/ADSL2/ADSL2+ single band, or any of
        us0(3), us1(5), us2(7), us3(9), or us4(11) for
        VDSL2 multiple bands.
        For a band in the downstream direction,
        transmission is from the xTU-C towards the xTU-R.
        A band in the downstream direction is
        indicated by downstream(2) for
        ADSL/ADSL2/ADSL2+ single band, or any of
        ds1(4), ds2(6), ds3(8), or ds4(10) for
        VDSL2 multiple bands.
        Specified as an INTEGER,
        the values are defined as follows:"
     SYNTAX INTEGER {
        upstream(1),   -- Transmission from the ATU-R to the ATU-C
                       -- (ADSL/ADSL2/ADSL2+).
        downstream(2), -- Transmission from the ATU-C to the ATU-R
                       --(ADSL/ADSL2/ADSL2+).
        us0(3),        -- Upstream band number 0 (US0) (VDSL2).
        ds1(4),        -- Downstream band number 1 (DS1) (VDSL2).
        us1(5),        -- Upstream band number 1 (US1) (VDSL2).
        ds2(6),        -- Downstream band number 2 (DS2) (VDSL2).
        us2(7),        -- Upstream band number 2 (US2) (VDSL2).
        ds3(8),        -- Downstream band number 3 (DS3) (VDSL2).
        us3(9),        -- Upstream band number 3 (US3) (VDSL2).
        ds4(10),       -- Downstream band number 4 (DS4) (VDSL2).
        us4(11)        -- Upstream band number 4 (US4) (VDSL2).
            }

--  sysInfo
	sysInfo     	OBJECT IDENTIFIER ::= { ves1616pe54 1 }

        sysSwPlatformMajorVers OBJECT-TYPE
        SYNTAX  INTEGER
        ACCESS  read-only
        STATUS  mandatory
        DESCRIPTION
                      "SW platform major version, e.g. 3."
        ::= { sysInfo 1 }

        sysSwPlatformMinorVers OBJECT-TYPE
        SYNTAX  INTEGER
        ACCESS  read-only
        STATUS  mandatory
        DESCRIPTION
                      "SW platform minor version, e.g. 50."
        ::= { sysInfo 2 }

        sysSwModelString OBJECT-TYPE
        SYNTAX  DisplayString
        ACCESS  read-only
        STATUS  mandatory
        DESCRIPTION
                      "Model letters, e.g. TJ"
        ::= { sysInfo 3 }

        sysSwVersionControlNbr OBJECT-TYPE
        SYNTAX  INTEGER
        ACCESS  read-only
        STATUS  mandatory
        DESCRIPTION
                      "Version control number, e.g. 0."
        ::= { sysInfo 4 }

        sysSwDay OBJECT-TYPE
        SYNTAX  INTEGER
        ACCESS  read-only
        STATUS  mandatory
        DESCRIPTION
                      "SW compilation day, e.g. 19."
        ::= { sysInfo 5 }

        sysSwMonth OBJECT-TYPE
        SYNTAX  INTEGER
        ACCESS  read-only
        STATUS  mandatory
        DESCRIPTION
                      "SW compilation month, e.g. 8."
        ::= { sysInfo 6 }

        sysSwYear OBJECT-TYPE
        SYNTAX  INTEGER
        ACCESS  read-only
        STATUS  mandatory
        DESCRIPTION
                      "SW compilation year, e.g. 2004."
        ::= { sysInfo 7 }

        sysHwMajorVers OBJECT-TYPE
        SYNTAX  INTEGER
        ACCESS  read-only
        STATUS  mandatory
        DESCRIPTION
                      "HW major version number, e.g. 1."
        ::= { sysInfo 8 }

        sysHwMinorVers OBJECT-TYPE
        SYNTAX  INTEGER
        ACCESS  read-only
        STATUS  mandatory
        DESCRIPTION
                      "HW minor version number, e.g. 0."
        ::= { sysInfo 9 }

        sysSerialNumber OBJECT-TYPE
        SYNTAX  DisplayString
        ACCESS  read-only
        STATUS  mandatory
        DESCRIPTION
                      "Serial number"
        ::= { sysInfo 10 }

        sysFirmwareVersion OBJECT-TYPE
        SYNTAX  DisplayString
        ACCESS  read-only
        STATUS  mandatory
        DESCRIPTION
                      "VDSL Switch Firmware Version"
        ::= { sysInfo 11 }        

        sysModemCodeVersion OBJECT-TYPE
        SYNTAX  DisplayString
        ACCESS  read-only
        STATUS  mandatory
        DESCRIPTION
                      "VDSL Modem Code Version"
        ::= { sysInfo 12 }   

        sysPowerInfo OBJECT-TYPE
        SYNTAX  DisplayString
        ACCESS  read-only
        STATUS  mandatory
        DESCRIPTION
                      "CO Power info"
        ::= { sysInfo 13 }  

        sysSwBootUpImage OBJECT-TYPE
        SYNTAX  INTEGER{
         		image_1(1),
         		image_2(2)
        }
        ACCESS  read-only
        STATUS  mandatory
        DESCRIPTION
                      "Current system boot up image,
                      You can change the boot up image of next rebooting by setting sysMgmtBootupImage."
        ::= { sysInfo 14 } 
        
        sysImage1FwVersion OBJECT-TYPE
        SYNTAX  DisplayString
        ACCESS  read-only
        STATUS  mandatory
        DESCRIPTION
                      "VDSL Switch Image 1 Firmware Version"
        ::= { sysInfo 15 }   
        
        sysImage2FwVersion OBJECT-TYPE
        SYNTAX  DisplayString
        ACCESS  read-only
        STATUS  mandatory
        DESCRIPTION
                      "VDSL Switch Image 2 Firmware Version"
        ::= { sysInfo 16 }  
        
         
-- brLimitSetup
	brLimitSetup OBJECT IDENTIFIER ::= { ves1616pe54 3 }

        brLimitState OBJECT-TYPE
        SYNTAX  EnabledStatus
        ACCESS  read-write
        STATUS  mandatory
        DESCRIPTION
                      	"Broadcast/multicast/DLF rate limiting enabled/disabled for the switch."
        ::= { brLimitSetup 1 }

-- brLimitPortTable
        brLimitPortTable OBJECT-TYPE
        SYNTAX	SEQUENCE OF BrLimitPortEntry
        ACCESS  not-accessible
        STATUS  mandatory
        DESCRIPTION
                 	""
        ::= { brLimitSetup 2 }

	brLimitPortEntry OBJECT-TYPE
        SYNTAX	BrLimitPortEntry
        ACCESS	not-accessible
        STATUS	mandatory
        DESCRIPTION    	"An entry in brLimitPortTable."
        INDEX          	{ dot1dBasePort }
        ::= { brLimitPortTable 1 }

        BrLimitPortEntry ::=
           SEQUENCE {
        	brLimitPortBrState	EnabledStatus,
		brLimitPortBrRate	INTEGER,
		brLimitPortMcState	EnabledStatus,
		brLimitPortMcRate	INTEGER,
		brLimitPortDlfState	EnabledStatus,
		brLimitPortDlfRate	INTEGER
           }

        brLimitPortBrState OBJECT-TYPE
        SYNTAX  EnabledStatus
        ACCESS  read-write
        STATUS  mandatory
        DESCRIPTION
                      	"Broadcast rate limiting enabled/disabled on the port."
        ::= { brLimitPortEntry 1 }

        brLimitPortBrRate OBJECT-TYPE
        SYNTAX  INTEGER
        ACCESS  read-write
        STATUS  mandatory
        DESCRIPTION
                      	"Allowed broadcast rate in pkts/s. For FE port,
                      	the maximum value is 148800. For GE port, the maximum value is 262143."
        ::= { brLimitPortEntry 2 }

        brLimitPortMcState OBJECT-TYPE
        SYNTAX  EnabledStatus
        ACCESS  read-write
        STATUS  mandatory
        DESCRIPTION
                      	"Multicast rate limiting enabled/disabled on the port."
        ::= { brLimitPortEntry 3 }

        brLimitPortMcRate OBJECT-TYPE
        SYNTAX  INTEGER
        ACCESS  read-write
        STATUS  mandatory
        DESCRIPTION
                      	"AAllowed mullticast rate in pkts/s. For FE port,
                      	the maximum value is 148800. For GE port, the maximum value is 262143."
        ::= { brLimitPortEntry 4 }

        brLimitPortDlfState OBJECT-TYPE
        SYNTAX  EnabledStatus
        ACCESS  read-write
        STATUS  mandatory
        DESCRIPTION
                      	"Destination lookup failure frames rate limiting enabled/disabled on the port."
        ::= { brLimitPortEntry 5 }

        brLimitPortDlfRate OBJECT-TYPE
        SYNTAX  INTEGER
        ACCESS  read-write
        STATUS  mandatory
        DESCRIPTION
                      	"Allowed destination lookup failure frames rate in pkts/s.
                      	For FE port, the maximum value is 148800. For GE port, the maximum value is 262143."
        ::= { brLimitPortEntry 6 }

-- portSecuritySetup
	portSecuritySetup OBJECT IDENTIFIER ::= { ves1616pe54 4 }

	portSecurityState OBJECT-TYPE
        SYNTAX  INTEGER
        ACCESS  read-write
        STATUS  mandatory
        DESCRIPTION
        "0: disable, 1:enable port security, 2:enable vlan security"
        ::= { portSecuritySetup 1 }

        portSecurityPortTable OBJECT-TYPE
        SYNTAX	SEQUENCE OF PortSecurityPortEntry
        ACCESS  not-accessible
        STATUS  mandatory
        DESCRIPTION
                 	""
        ::= { portSecuritySetup 2 }

	portSecurityPortEntry OBJECT-TYPE
        SYNTAX	PortSecurityPortEntry
        ACCESS	not-accessible
        STATUS	mandatory
        DESCRIPTION    	"An entry in portSecurityPortTable."
        INDEX          	{ dot1dBasePort }
        ::= { portSecurityPortTable 1 }

        PortSecurityPortEntry ::=
           SEQUENCE {
        	portSecurityPortState		EnabledStatus,
		portSecurityPortLearnState	EnabledStatus,
		portSecurityPortCount		INTEGER
           }

        portSecurityPortState OBJECT-TYPE
        SYNTAX  EnabledStatus
        ACCESS  read-write
        STATUS  mandatory
        DESCRIPTION
                      	"Port Security enabled/disabled on the port.
                      	Active(1) means this port only accept frames from static MAC addresses that are configured for the port,
                      	and dynamic MAC address frames up to the number specified by portSecurityPortCount object."
        ::= { portSecurityPortEntry 1 }

        portSecurityPortLearnState OBJECT-TYPE
        SYNTAX  EnabledStatus
        ACCESS  read-write
        STATUS  mandatory
        DESCRIPTION
                      	"MAC address learning  enabled/disable on the port."
        ::= { portSecurityPortEntry 2 }

        portSecurityPortCount OBJECT-TYPE
        SYNTAX  INTEGER
        ACCESS  read-write
        STATUS  mandatory
        DESCRIPTION
                      	"Number of (dynamic) MAC addresses that may be learned on the port."
        ::= { portSecurityPortEntry 3 }

	portSecurityMacFreeze OBJECT-TYPE
        SYNTAX  PortList
        ACCESS  read-write
        STATUS  mandatory
        DESCRIPTION
                      	"This entry is used to execute MacFreeze action to port.
                      	It's meaningless while reading this entry."
        ::= { portSecuritySetup 3 }

-- vlanTrunkPortTable
	vlanTrunkSetup OBJECT IDENTIFIER ::= { ves1616pe54 5 }

        vlanTrunkPortTable OBJECT-TYPE
        SYNTAX	SEQUENCE OF VlanTrunkPortEntry
        ACCESS  not-accessible
        STATUS  mandatory
        DESCRIPTION
                 	""
        ::= { vlanTrunkSetup 1 }

	vlanTrunkPortEntry OBJECT-TYPE
        SYNTAX	VlanTrunkPortEntry
        ACCESS	not-accessible
        STATUS	mandatory
        DESCRIPTION    	"An entry in vlanTrunkPortTable."
        INDEX          	{ dot1dBasePort }
        ::= { vlanTrunkPortTable 1 }

        VlanTrunkPortEntry ::=
           SEQUENCE {
        	vlanTrunkPortState		EnabledStatus
           }

        vlanTrunkPortState OBJECT-TYPE
        SYNTAX  EnabledStatus
        ACCESS  read-write
        STATUS  mandatory
        DESCRIPTION
                      	"VlanTrunking enabled/disabled on the port.
                      	Active(1) to allow frames belonging to unknown
                      	VLAN groups to pass through the switch."
        ::= { vlanTrunkPortEntry 1 }

--  ctlProtTransSetup
	ctlProtTransSetup OBJECT IDENTIFIER ::= { ves1616pe54 6 }

        ctlProtTransState OBJECT-TYPE
        SYNTAX  EnabledStatus
        ACCESS  read-write
        STATUS  mandatory
        DESCRIPTION
                      	"Bridge control protocol transparency enabled/disabled for the switch"
        ::= { ctlProtTransSetup 1 }

-- ctlProtTransTunnelPortTable

        ctlProtTransTunnelPortTable OBJECT-TYPE
        SYNTAX	SEQUENCE OF CtlProtTransTunnelPortEntry
        ACCESS  not-accessible
        STATUS  mandatory
        DESCRIPTION
                 	""
        ::= { ctlProtTransSetup 2 }

	ctlProtTransTunnelPortEntry OBJECT-TYPE
        SYNTAX	CtlProtTransTunnelPortEntry
        ACCESS	not-accessible
        STATUS	mandatory
        DESCRIPTION    	"An entry in ctlProtTransTunnelPortTable."
        INDEX          	{ dot1dBasePort }
        ::= { ctlProtTransTunnelPortTable 1 }

        CtlProtTransTunnelPortEntry ::=
           SEQUENCE {
        	ctlProtTransTunnelMode	INTEGER
           }

        ctlProtTransTunnelMode OBJECT-TYPE
        SYNTAX  INTEGER{
		peer(0),
		tunnel(1),
		discard(2),
		network(3)
        }
        ACCESS  read-write
        STATUS  mandatory
        DESCRIPTION
                      	"Bridge control protocol transparency mode for the port.
                      	Modes:  Peer(0), Tunnel(1), Discard(2),  Network(3)"
        ::= { ctlProtTransTunnelPortEntry 1 }

--  vlanStackSetup
	vlanStackSetup OBJECT IDENTIFIER ::= { ves1616pe54 7 }

        vlanStackState OBJECT-TYPE
        SYNTAX  EnabledStatus
        ACCESS  read-write
        STATUS  mandatory
        DESCRIPTION
                      "VLAN Stacking enabled/disabled for the switch."
        ::= { vlanStackSetup 1 }

        vlanStackTpid OBJECT-TYPE
        SYNTAX  INTEGER
        ACCESS  read-write
        STATUS  mandatory
        DESCRIPTION
                      "SP TPID in hex format, e.g. 8100."
        ::= { vlanStackSetup 2 }

-- vlanStackPortTable

        vlanStackPortTable OBJECT-TYPE
        SYNTAX	SEQUENCE OF VlanStackPortEntry
        ACCESS  not-accessible
        STATUS  mandatory
        DESCRIPTION
                 	""
        ::= { vlanStackSetup 3 }

	vlanStackPortEntry OBJECT-TYPE
        SYNTAX	VlanStackPortEntry
        ACCESS	not-accessible
        STATUS	mandatory
        DESCRIPTION    	"An entry in vlanStackPortTable."
        INDEX          	{ dot1dBasePort }
        ::= { vlanStackPortTable 1 }

        VlanStackPortEntry ::=
           SEQUENCE {
        	vlanStackPortMode		INTEGER,
        	vlanStackPortVid		INTEGER,
        	vlanStackPortPrio		INTEGER,
        	vlanStackTunnelPortTpid		INTEGER,
        	vlanStackPCopyCtagPrio		EnabledStatus
           }

        vlanStackPortMode OBJECT-TYPE
        SYNTAX  INTEGER {
        normal(1),
		access(2),
		tunnel(3)
	}
        ACCESS  read-write
        STATUS  mandatory
        DESCRIPTION
                      	"Mode of the port. Set Normal to have the switch ignore frames received 
                      	(or transmitted) on this port with VLAN stacking tags. 
                      	Anything you configure in SPVID and Priority are ignored. 
			Set Access mode to have the switch add the SP TPID tag to all incoming
			frames received on this port. Set Access  mode for ingress ports at the
			edge of the service provider's network. Set Tunnel mode (available for
			Gigabit ports only) for egress ports at the edge of the service provider's
			network. In order to support VLAN stacking on a port, the port must be able
			to allow frames of 1526 Bytes (1522 Bytes + 4 Bytes for the second tag)
			to pass through it. normal (1), Access (2),  tunnel (3)"
        ::= { vlanStackPortEntry 1 }

        vlanStackPortVid OBJECT-TYPE
        SYNTAX  INTEGER
        ACCESS  read-write
        STATUS  mandatory
        DESCRIPTION
                      	"VLAN ID used in service provider tag."
        ::= { vlanStackPortEntry 2 }

        vlanStackPortPrio OBJECT-TYPE
        SYNTAX  INTEGER {
        		prioriry-0(0),
        		prioriry-1(1),
        		prioriry-2(2),
        		prioriry-3(3),
        		prioriry-4(4),
        		prioriry-5(5),
        		prioriry-6(6),
        		prioriry-7(7)
        }

        ACCESS  read-write
        STATUS  mandatory
        DESCRIPTION
                      	"Priority value for service provider tag.
                      	0 is the lowest priority level and 7 is the highest."
        ::= { vlanStackPortEntry 3 }

        vlanStackTunnelPortTpid OBJECT-TYPE
        SYNTAX  INTEGER
        ACCESS  read-write
        STATUS  mandatory
        DESCRIPTION
                      	"Tunnel Port TPID in hex format, e.g. 8100."
        ::= { vlanStackPortEntry 4 }

        vlanStackPCopyCtagPrio OBJECT-TYPE
        SYNTAX  EnabledStatus
        ACCESS  read-create
        STATUS  mandatory
        DESCRIPTION
                      	""
        ::= { vlanStackPortEntry 5 }
        
        
-- selectiveQinQTable
        selectiveQinQTable OBJECT-TYPE
        SYNTAX	SEQUENCE OF SelectiveQinQEntry
        ACCESS  not-accessible
        STATUS  mandatory
        DESCRIPTION
                 	""
        ::= { vlanStackSetup 4 }
        
	selectiveQinQEntry OBJECT-TYPE
        SYNTAX	SelectiveQinQEntry
        ACCESS	not-accessible
        STATUS	mandatory
        DESCRIPTION    	"An entry in selective qinq table"
        INDEX          	{ selectiveQinQPort, selectiveQinQCvid }
        ::= { selectiveQinQTable 1 }

        SelectiveQinQEntry ::=
           SEQUENCE {
           	selectiveQinQName		DisplayString,
        	selectiveQinQPort		INTEGER,
        	selectiveQinQCvid		INTEGER,
        	selectiveQinQSpvid		INTEGER,
        	selectiveQinQPriority	INTEGER,
        	selectiveQinQRowStatus	RowStatus,
		selectiveQinQACtivePrio		EnabledStatus
           }

        selectiveQinQName OBJECT-TYPE
        SYNTAX  DisplayString
        ACCESS  read-write
        STATUS  mandatory
        DESCRIPTION
                      	"The name of selective qinq entry"
        ::= { selectiveQinQEntry 1 }

        selectiveQinQPort OBJECT-TYPE
        SYNTAX  INTEGER
        ACCESS  read-only
        STATUS  mandatory
        DESCRIPTION
                     	"interface port id"
        ::= { selectiveQinQEntry 2 }

        selectiveQinQCvid OBJECT-TYPE
        SYNTAX  INTEGER
        ACCESS  read-only
        STATUS  mandatory
        DESCRIPTION
                     	"inner vid"
        ::= { selectiveQinQEntry 3 }
        
        selectiveQinQSpvid OBJECT-TYPE
        SYNTAX  INTEGER
        ACCESS  read-write
        STATUS  mandatory
        DESCRIPTION
                     	"outer vid"
        ::= { selectiveQinQEntry 4 }
        
        selectiveQinQPriority OBJECT-TYPE
        SYNTAX  INTEGER {
        		prioriry-0(0),
        		prioriry-1(1),
        		prioriry-2(2),
        		prioriry-3(3),
        		prioriry-4(4),
        		prioriry-5(5),
        		prioriry-6(6),
        		prioriry-7(7)
        }

        ACCESS  read-write
        STATUS  mandatory
        DESCRIPTION
                     	"priority"
        ::= { selectiveQinQEntry 5 }

        selectiveQinQACtivePrio OBJECT-TYPE
        SYNTAX  EnabledStatus
        ACCESS  read-write
        STATUS  mandatory
        DESCRIPTION
                     	"Use the value for priority for Stag"
        ::= { selectiveQinQEntry 7 }
        
        selectiveQinQRowStatus OBJECT-TYPE
        SYNTAX  RowStatus
        ACCESS  read-create
        STATUS  mandatory
        DESCRIPTION
                     	""
        ::= { selectiveQinQEntry 6 }

-- PortBasedInnerQTable
        
        portBasedInnerQTable OBJECT-TYPE
        SYNTAX	SEQUENCE OF PortBasedInnerQEntry
        ACCESS  not-accessible
        STATUS  mandatory
        DESCRIPTION
                 	""
        ::= { vlanStackSetup 5 }
        
	portBasedInnerQEntry OBJECT-TYPE
        SYNTAX	PortBasedInnerQEntry
        ACCESS	not-accessible
        STATUS	mandatory
        DESCRIPTION    	"An entry in PortBasedInnerQTable."
        INDEX          	{ dot1dBasePort }
        ::= { portBasedInnerQTable 1 }

        PortBasedInnerQEntry ::=
           SEQUENCE {
        	portBasedInnerQVid			INTEGER,
        	portBasedInnerQPrio			INTEGER,
        	portBasedInnerQActive		EnabledStatus,
        	portBasedInnerQTxUntag		EnabledStatus
           }


        portBasedInnerQVid OBJECT-TYPE
        SYNTAX  INTEGER
        ACCESS  read-write
        STATUS  mandatory
        DESCRIPTION
                      	"VLAN ID used in inner tag."
        ::= { portBasedInnerQEntry 1 }

        portBasedInnerQPrio OBJECT-TYPE
        SYNTAX  INTEGER {
        		prioriry-0(0),
        		prioriry-1(1),
        		prioriry-2(2),
        		prioriry-3(3),
        		prioriry-4(4),
        		prioriry-5(5),
        		prioriry-6(6),
        		prioriry-7(7)
        }
        
        ACCESS  read-write
        STATUS  mandatory
        DESCRIPTION
                      	"Priority value for inner tag.  
                      	0 is the lowest priority level and 7 is the highest."
        ::= { portBasedInnerQEntry 2 }
        

        portBasedInnerQActive OBJECT-TYPE
        SYNTAX  EnabledStatus
        ACCESS  read-write
        STATUS  mandatory
        DESCRIPTION
                      	""
        ::= { portBasedInnerQEntry 3 }
        
        portBasedInnerQTxUntag OBJECT-TYPE
        SYNTAX  EnabledStatus
        ACCESS  read-write
        STATUS  mandatory
        DESCRIPTION
                      	"Tx without Ctag (Only active when innerQ is enable)"
        ::= { portBasedInnerQEntry 4 }
        
--  dot1xSetup
	dot1xSetup OBJECT IDENTIFIER ::= { ves1616pe54 8 }

--  portAuthState
        portAuthState OBJECT-TYPE
        SYNTAX  EnabledStatus
        ACCESS  read-write
        STATUS  mandatory
        DESCRIPTION
                      	"802.1x port authentication enabled/disabled for the switch."
        ::= { dot1xSetup 3 }


-- 8021xPortAuthTable

        portAuthTable OBJECT-TYPE
        SYNTAX	SEQUENCE OF PortAuthEntry
        ACCESS  not-accessible
        STATUS  mandatory
        DESCRIPTION
                 	""
        ::= { dot1xSetup 4 }

		portAuthEntry OBJECT-TYPE
        SYNTAX	PortAuthEntry
        ACCESS	not-accessible
        STATUS	mandatory
        DESCRIPTION    	"An entry in portAuthTable."
        INDEX          	{ dot1dBasePort }
        ::= { portAuthTable 1 }

        PortAuthEntry ::=
           SEQUENCE {
        	portAuthEntryState	EnabledStatus,
        	portReAuthEntryState	EnabledStatus,
        	portReAuthEntryTimer	INTEGER
           }

        portAuthEntryState OBJECT-TYPE
        SYNTAX  EnabledStatus
        ACCESS  read-write
        STATUS  mandatory
        DESCRIPTION
                      	"802.1x port authentication enabled or disabled on the port."
        ::= { portAuthEntry 1 }

        portReAuthEntryState OBJECT-TYPE
        SYNTAX  EnabledStatus
        ACCESS  read-write
        STATUS  mandatory
        DESCRIPTION
                      	"802.1x port re-authentication enabled or disabled on the port."
        ::= { portAuthEntry 2 }

        portReAuthEntryTimer OBJECT-TYPE
        SYNTAX  INTEGER
        ACCESS  read-write
        STATUS  mandatory
        DESCRIPTION
                      	"Re-authentication timer in seconds."
        ::= { portAuthEntry 3 }

-- hardwareInfo
	hwMonitorInfo OBJECT IDENTIFIER ::= { ves1616pe54 9 }

-- fabRpmTable

        fanRpmTable	OBJECT-TYPE
        SYNTAX	SEQUENCE OF FanRpmEntry
        ACCESS  not-accessible
        STATUS  current
        DESCRIPTION
                 	""
        ::= { hwMonitorInfo 1 }

	fanRpmEntry OBJECT-TYPE
        SYNTAX	FanRpmEntry
        ACCESS	not-accessible
        STATUS	current
        DESCRIPTION    	"An entry in fanRpmTable."
        INDEX          	{ fanRpmIndex }
        ::= { fanRpmTable 1 }

        FanRpmEntry ::=
           SEQUENCE {
        	fanRpmIndex	INTEGER,
        	fanRpmCurValue	INTEGER,
        	fanRpmMaxValue	INTEGER,
        	fanRpmMinValue	INTEGER,
        	fanRpmLowThresh	INTEGER,
        	fanRpmDescr	DisplayString
           }

        fanRpmIndex OBJECT-TYPE
        SYNTAX  INTEGER
        ACCESS  read-only
        STATUS  current
        DESCRIPTION
                      	"Index of FAN."
        ::= { fanRpmEntry 1 }

        fanRpmCurValue OBJECT-TYPE
        SYNTAX  INTEGER
        ACCESS  read-only
        STATUS  current
        DESCRIPTION
                      	"Current speed in Revolutions Per Minute (RPM) on the fan."
        ::= { fanRpmEntry 2 }

        fanRpmMaxValue OBJECT-TYPE
        SYNTAX  INTEGER
        ACCESS  read-only
        STATUS  current
        DESCRIPTION
                      	"Maximum speed measured in Revolutions Per Minute (RPM) on the fan."
        ::= { fanRpmEntry 3 }

        fanRpmMinValue OBJECT-TYPE
        SYNTAX  INTEGER
        ACCESS  read-only
        STATUS  current
        DESCRIPTION
                      	"Minimum speed measured in Revolutions Per Minute (RPM) on the fan."
        ::= { fanRpmEntry 4 }

        fanRpmLowThresh OBJECT-TYPE
        SYNTAX  INTEGER
        ACCESS  read-only
        STATUS  current
        DESCRIPTION
                      	"The minimum speed at which a normal fan should work."
        ::= { fanRpmEntry 5 }

        fanRpmDescr OBJECT-TYPE
        SYNTAX  DisplayString
        ACCESS  read-only
        STATUS  current
        DESCRIPTION
                      	"'Normal' indicates that this fan is functioning above the minimum speed.
                      	'Error' indicates that this fan is functioning below the minimum speed."
        ::= { fanRpmEntry 6 }

-- tempTable

        tempTable	OBJECT-TYPE
        SYNTAX	SEQUENCE OF TempEntry
        ACCESS  not-accessible
        STATUS  current
        DESCRIPTION
                 	""
        ::= { hwMonitorInfo 2 }

	tempEntry OBJECT-TYPE
        SYNTAX	TempEntry
        ACCESS	not-accessible
        STATUS	current
        DESCRIPTION    	"An entry in tempTable."
        INDEX          	{ tempIndex }
        ::= { tempTable 1 }

        TempEntry ::=
           SEQUENCE {
        	tempIndex	INTEGER,
        	tempCurValue	INTEGER,
        	tempMaxValue	INTEGER,
        	tempMinValue	INTEGER,
        	tempHighThresh	INTEGER,
        	tempDescr	DisplayString
           }

        tempIndex OBJECT-TYPE
        SYNTAX  INTEGER {
        	mac (1),
        	cpu (2),
        	phy (3)
        }
        ACCESS  read-only
        STATUS  current
        DESCRIPTION
                      	"Index of temperature unit. 1:MAC, 2:CPU, 3:PHY"
        ::= { tempEntry 1 }

        tempCurValue OBJECT-TYPE
        SYNTAX  INTEGER
        ACCESS  read-only
        STATUS  current
        DESCRIPTION
                      	"The current temperature measured at this sensor."
        ::= { tempEntry 2 }

        tempMaxValue OBJECT-TYPE
        SYNTAX  INTEGER
        ACCESS  read-only
        STATUS  current
        DESCRIPTION
                      	"The maximum temperature measured at this sensor."
        ::= { tempEntry 3 }

        tempMinValue OBJECT-TYPE
        SYNTAX  INTEGER
        ACCESS  read-only
        STATUS  current
        DESCRIPTION
                      	"The minimum temperature measured at this sensor."
        ::= { tempEntry 4 }

        tempHighThresh OBJECT-TYPE
        SYNTAX  INTEGER
        ACCESS  read-only
        STATUS  current
        DESCRIPTION
                      	"The upper temperature limit at this sensor."
        ::= { tempEntry 5 }

        tempDescr OBJECT-TYPE
        SYNTAX  DisplayString
        ACCESS  read-only
        STATUS  current
        DESCRIPTION
                      	"'Normal' indicates temperatures below the threshold and 'Error' for those above."
        ::= { tempEntry 6 }

-- voltageTable

        voltageTable	OBJECT-TYPE
        SYNTAX	SEQUENCE OF VoltageEntry
        ACCESS  not-accessible
        STATUS  current
        DESCRIPTION
                 	""
        ::= { hwMonitorInfo 3 }

	voltageEntry OBJECT-TYPE
        SYNTAX	VoltageEntry
        ACCESS	not-accessible
        STATUS	current
        DESCRIPTION    	"An entry in voltageTable."
        INDEX          	{ voltageIndex }
        ::= { voltageTable 1 }

        VoltageEntry ::=
           SEQUENCE {
        	voltageIndex		INTEGER,
        	voltageCurValue		INTEGER,
        	voltageMaxValue		INTEGER,
        	voltageMinValue		INTEGER,
        	voltageNominalValue	INTEGER,
        	voltageLowThresh	INTEGER,
        	voltageDescr		DisplayString
           }

        voltageIndex OBJECT-TYPE
        SYNTAX  INTEGER
        ACCESS  read-only
        STATUS  current
        DESCRIPTION
                      	"Index of voltage."
        ::= { voltageEntry 1 }

        voltageCurValue OBJECT-TYPE
        SYNTAX  INTEGER
        ACCESS  read-only
        STATUS  current
        DESCRIPTION
                      	"The current voltage reading."
        ::= { voltageEntry 2 }

        voltageMaxValue OBJECT-TYPE
        SYNTAX  INTEGER
        ACCESS  read-only
        STATUS  current
        DESCRIPTION
                      	"The maximum voltage measured at this point."
        ::= { voltageEntry 3 }

        voltageMinValue OBJECT-TYPE
        SYNTAX  INTEGER
        ACCESS  read-only
        STATUS  current
        DESCRIPTION
                      	"The minimum voltage measured at this point."
        ::= { voltageEntry 4 }

        voltageNominalValue OBJECT-TYPE
        SYNTAX  INTEGER
        ACCESS  read-only
        STATUS  current
        DESCRIPTION
                      	"The normal voltage at wchich the switch work."
        ::= { voltageEntry 5 }

        voltageLowThresh OBJECT-TYPE
        SYNTAX  INTEGER
        ACCESS  read-only
        STATUS  current
        DESCRIPTION
                      	"The minimum voltage at which the switch should work."
        ::= { voltageEntry 6 }

        voltageDescr OBJECT-TYPE
        SYNTAX  DisplayString
        ACCESS  read-only
        STATUS  current
        DESCRIPTION
                      	"'Normal' indicates that the voltage is within an acceptable operating range
                      	at this point; otherwise 'Error' is displayed."
        ::= { voltageEntry 7 }

-- snmpSetup
	snmpSetup OBJECT IDENTIFIER ::= { ves1616pe54 10 }

        snmpGetCommunity OBJECT-TYPE
        SYNTAX  DisplayString
        ACCESS  read-write
        STATUS  mandatory
        DESCRIPTION
                      	""
        ::= { snmpSetup 1 }

        snmpSetCommunity OBJECT-TYPE
        SYNTAX  DisplayString
        ACCESS  read-write
        STATUS  mandatory
        DESCRIPTION
                      	""
        ::= { snmpSetup 2 }

        snmpTrapCommunity OBJECT-TYPE
        SYNTAX  DisplayString
        ACCESS  read-write
        STATUS  mandatory
        DESCRIPTION
                      	""
        ::= { snmpSetup 3 }

--  snmpTrapDestTable
        snmpTrapDestTable	OBJECT-TYPE
        SYNTAX	SEQUENCE OF SnmpTrapDestEntry
        ACCESS  not-accessible
        STATUS  mandatory
        DESCRIPTION
                 	""
        ::= { snmpSetup 4 }

	snmpTrapDestEntry OBJECT-TYPE
        SYNTAX	SnmpTrapDestEntry
        ACCESS	not-accessible
        STATUS	mandatory
        DESCRIPTION    	"An entry in snmpTrapDestTable."
        INDEX          	{ snmpTrapDestIP }
        ::= { snmpTrapDestTable 1 }

        SnmpTrapDestEntry ::=
           SEQUENCE {
        	snmpTrapDestIP	IpAddress,
        	snmpTrapDestRowStatus RowStatus,
        	snmpTrapDestPort		INTEGER,
        	snmpTrapVersion			INTEGER,
        	snmpTrapUserName		DisplayString  
           }

        snmpTrapDestIP OBJECT-TYPE
        SYNTAX  IpAddress
        ACCESS  read-only
        STATUS  mandatory
        DESCRIPTION
                      	"IP address of trap destination."
        ::= { snmpTrapDestEntry 1 }

        snmpTrapDestRowStatus OBJECT-TYPE
        SYNTAX  RowStatus
        ACCESS  read-create
        STATUS  mandatory
        DESCRIPTION
                      	""
        ::= { snmpTrapDestEntry 2 }

        snmpTrapDestPort OBJECT-TYPE
        SYNTAX INTEGER
        MAX-ACCESS read-write
        STATUS  mandatory
        DESCRIPTION
                      	"The UDP port of the trap destination."
        ::= { snmpTrapDestEntry 3 }
        
        snmpTrapVersion OBJECT-TYPE
        SYNTAX  INTEGER {
			v1(0),
			v2c(1),
			v3(2)
		}
        MAX-ACCESS read-write
        STATUS  mandatory
        DESCRIPTION
                      	"The SNMP protocol version to send traps."
        ::= { snmpTrapDestEntry 4 }

        snmpTrapUserName OBJECT-TYPE
        SYNTAX DisplayString
        MAX-ACCESS read-write
        STATUS  mandatory
        DESCRIPTION
                      	"The user name for sending SNMPv3 traps."
        ::= { snmpTrapDestEntry 5 }   

--  snmpTrapGroupTable
        snmpTrapGroupTable	OBJECT-TYPE
        SYNTAX	SEQUENCE OF SnmpTrapGroupEntry
        ACCESS  not-accessible
        STATUS  mandatory
        DESCRIPTION
                 	""
        ::= { snmpSetup 5 }
	snmpTrapGroupEntry OBJECT-TYPE
        SYNTAX	SnmpTrapGroupEntry
        ACCESS	not-accessible
        STATUS	mandatory
        DESCRIPTION    	"An entry in snmpTrapGroupTable."
        INDEX          	{ snmpTrapDestIP }
        ::= { snmpTrapGroupTable 1 }

        SnmpTrapGroupEntry ::=
           SEQUENCE {
        	snmpTrapSystemGroup	 BITS,
        	snmpTrapInterfaceGroup	 BITS,
        	snmpTrapAAAGroup  BITS,
        	snmpTrapSwitchGroup	 BITS,
        	snmpTrapVdslGroup	 BITS
           }

        snmpTrapSystemGroup OBJECT-TYPE
        	SYNTAX	BITS {
		coldStart(0),
		warmStart(1),
		fanSpeed(2),
		temperature(3),
		voltage(4),
		reset (5),
--		timeSync (6),
		externalalarm(7),
--		instrusionlock (8),
		loopguard (9),
		lpr (10)

--		fanSpeed(2),
--		temperature(3),
--		voltage(4),
--		bps (5),
--		reset (6),
--		timeSync (7),
--		intrusionlock(8),
--		externalalarm(9)
	}
        ACCESS  read-write
        STATUS  mandatory
        DESCRIPTION
                      	""
        ::= { snmpTrapGroupEntry 1 }
        
        snmpTrapInterfaceGroup OBJECT-TYPE
               	SYNTAX	BITS {
		linkup(0),
		linkdown(1),
		autonegotiation(2)
	}
        ACCESS  read-write
        STATUS  mandatory
        DESCRIPTION
                      	""
        ::= { snmpTrapGroupEntry 2 }
        
        snmpTrapAAAGroup OBJECT-TYPE
               	SYNTAX	BITS {
		authentication(0),
		accounting(1)  
	}
        ACCESS  read-write
        STATUS  mandatory
        DESCRIPTION
                      	""
        ::= { snmpTrapGroupEntry 3 }        
        
        snmpTrapSwitchGroup OBJECT-TYPE
               	SYNTAX	BITS {
		stp(0),
		mactable(1),
		rmon(2)
	}
        ACCESS  read-write
        STATUS  mandatory
        DESCRIPTION
                      	""
        ::= { snmpTrapGroupEntry 5 }       
        
        snmpTrapVdslGroup OBJECT-TYPE
               	SYNTAX	BITS {
		alarmprofile(0),
		others(1)
	}
        ACCESS  read-write
        STATUS  mandatory
        DESCRIPTION
                      	""
        ::= { snmpTrapGroupEntry 6 } 

--snmpVersion
        snmpVersion OBJECT-TYPE
		SYNTAX 	INTEGER {
			v2c(0),
			v3(1),
			v3v2c(2)
		}
        ACCESS  read-write
        STATUS  mandatory
        DESCRIPTION
		"The SNMP version to be used. v3v2c means that the manager 
		can get/set by SNMPv3 and can get by SNMPv2c."
        ::= { snmpSetup 6 }

-- snmpUserTable
	
	snmpUserTable OBJECT-TYPE
    	SYNTAX SEQUENCE OF SnmpUserEntry
    	MAX-ACCESS not-accessible
    	STATUS current
    	DESCRIPTION
                "A table that contains SNMPv3 user information."
    	::= { snmpSetup 7 }

    	snmpUserEntry OBJECT-TYPE
        SYNTAX SnmpUserEntry
        MAX-ACCESS not-accessible
        STATUS current
        DESCRIPTION
        	"An entry of snmpUserTable."
        INDEX { snmpUserName }
        ::= { snmpUserTable 1 }

   	SnmpUserEntry ::=
        	SEQUENCE {
            		snmpUserName		DisplayString,
            		snmpUserSecurityLevel	INTEGER,
            		snmpUserAuthProtocol	INTEGER,
            		snmpUserPrivProtocol	INTEGER
    	   	} 

	snmpUserName OBJECT-TYPE
	SYNTAX DisplayString
	MAX-ACCESS read-only
	STATUS current
	DESCRIPTION
		"The user name."
	::= { snmpUserEntry 1 }

	snmpUserSecurityLevel OBJECT-TYPE
	SYNTAX  INTEGER {
			noAuthNoPriv(0),
			authNoPriv(1),
			authPriv(2)
		}
	MAX-ACCESS read-write
	STATUS current
	DESCRIPTION
		"The level of security at which SNMP messages can be sent or 
		with which operations are being processed."
	::= { snmpUserEntry 2 }	

	snmpUserAuthProtocol OBJECT-TYPE
	SYNTAX  INTEGER {
			md5(0),
			sha(1)
		}
	MAX-ACCESS read-write
	STATUS current
	DESCRIPTION
		"The type of authentication protocol to be used."
	::= { snmpUserEntry 3 }

	snmpUserPrivProtocol OBJECT-TYPE
	SYNTAX 	INTEGER {
			des(0),
			aes(1)
		}
	MAX-ACCESS read-write
	STATUS current
	DESCRIPTION
		"The type of privacy protocol to be used."
	::= { snmpUserEntry 4 }

--  snmpTrapDestInfoTable
    snmpTrapDestInfoTable	OBJECT-TYPE
        SYNTAX	SEQUENCE OF SnmpTrapDestInfoEntry
        ACCESS  not-accessible
        STATUS  mandatory
        DESCRIPTION
                 	""
        ::= { snmpSetup 8 }
           
	snmpTrapDestInfoEntry OBJECT-TYPE
        SYNTAX	SnmpTrapDestInfoEntry
        ACCESS	not-accessible
        STATUS	mandatory
        DESCRIPTION    	"An entry in snmpTrapDestInfoTable."
        INDEX          	{ snmpTrapDestInfoIpAddrType, snmpTrapDestInfoIpAddr }
        ::= { snmpTrapDestInfoTable 1 }

        SnmpTrapDestInfoEntry ::=
            SEQUENCE {
           		snmpTrapDestInfoIpAddrType	InetAddressType,
        		snmpTrapDestInfoIpAddr		InetAddress,
        		snmpTrapDestInfoRowStatus	RowStatus,
        		snmpTrapDestInfoPort		INTEGER,
        		snmpTrapDestInfoVersion		INTEGER,
        		snmpTrapDestInfoUserName	DisplayString  
			}
        
        snmpTrapDestInfoIpAddrType OBJECT-TYPE
        SYNTAX  InetAddressType { ipv4(1), ipv6(2) }
        ACCESS  read-only
        STATUS  mandatory
        DESCRIPTION
                      	"IP address of trap destination."
        ::= { snmpTrapDestInfoEntry 1 }
           
        snmpTrapDestInfoIpAddr OBJECT-TYPE
        SYNTAX  InetAddress
        ACCESS  read-only
        STATUS  mandatory
        DESCRIPTION
                      	"IP address of trap destination."
        ::= { snmpTrapDestInfoEntry 2 }

        snmpTrapDestInfoRowStatus OBJECT-TYPE
        SYNTAX  RowStatus
        ACCESS  read-create
        STATUS  mandatory
        DESCRIPTION
                      	""
        ::= { snmpTrapDestInfoEntry 3 }

        snmpTrapDestInfoPort OBJECT-TYPE
        SYNTAX INTEGER
        MAX-ACCESS read-write
        STATUS  mandatory
        DESCRIPTION
                      	"The UDP port of the trap destination."
        ::= { snmpTrapDestInfoEntry 4 }
           
        snmpTrapDestInfoVersion OBJECT-TYPE
        SYNTAX  INTEGER {
			v1(0),
			v2c(1),
			v3(2)
		}
        MAX-ACCESS read-write
        STATUS  mandatory
        DESCRIPTION
                      	"The SNMP protocol version to send traps."
        ::= { snmpTrapDestInfoEntry 5 }

        snmpTrapDestInfoUserName OBJECT-TYPE
        SYNTAX DisplayString
        MAX-ACCESS read-write
        STATUS  mandatory
        DESCRIPTION
                      	"The user name for sending SNMPv3 traps."
        ::= { snmpTrapDestInfoEntry 6 }           

--  snmpTrapGroupInfoTable
        snmpTrapGroupInfoTable	OBJECT-TYPE
        SYNTAX	SEQUENCE OF SnmpTrapGroupInfoEntry
        ACCESS  not-accessible
        STATUS  mandatory
        DESCRIPTION
                 	""
        ::= { snmpSetup 9 }

	snmpTrapGroupInfoEntry OBJECT-TYPE
        SYNTAX	SnmpTrapGroupInfoEntry
        ACCESS	not-accessible
        STATUS	mandatory
        DESCRIPTION    	"An entry in snmpTrapGroupInfoTable."
        INDEX          	{ snmpTrapDestInfoIpAddrType, snmpTrapDestInfoIpAddr }
        ::= { snmpTrapGroupInfoTable 1 }

        SnmpTrapGroupInfoEntry ::=
           SEQUENCE {
        	snmpTrapSystemGroup	 BITS,
        	snmpTrapInterfaceGroup	 BITS,
        	snmpTrapAAAGroup  BITS,
        	snmpTrapSwitchGroup	 BITS,
        	snmpTrapVdslGroup	 BITS
           }

        snmpTrapSystemGroup OBJECT-TYPE
        	SYNTAX	BITS {
		coldStart(0),
		warmStart(1),
		fanSpeed(2),
		temperature(3),
		voltage(4),
		reset (5),
--		timeSync (6),
		externalalarm(7),
--		instrusionlock (8),
		loopguard (9),
		lpr (10)

--		fanSpeed(2),
--		temperature(3),
--		voltage(4),
--		bps (5),
--		reset (6),
--		timeSync (7),
--		intrusionlock(8),
--		externalalarm(9)
	}
        ACCESS  read-write
        STATUS  mandatory
        DESCRIPTION
                      	""
        ::= { snmpTrapGroupInfoEntry 1 }
        
        snmpTrapInterfaceGroup OBJECT-TYPE
               	SYNTAX	BITS {
		linkup(0),
		linkdown(1),
		autonegotiation(2)
	}
        ACCESS  read-write
        STATUS  mandatory
        DESCRIPTION
                      	""
        ::= { snmpTrapGroupInfoEntry 2 }
           
        snmpTrapAAAGroup OBJECT-TYPE
               	SYNTAX	BITS {
		authentication(0),
		accounting(1)  
	}
        ACCESS  read-write
        STATUS  mandatory
        DESCRIPTION
                      	""
        ::= { snmpTrapGroupInfoEntry 3 }        
           

        snmpTrapSwitchGroup OBJECT-TYPE
               	SYNTAX	BITS {
		stp(0),
		mactable(1),
		rmon(2)
	}
        ACCESS  read-write
        STATUS  mandatory
        DESCRIPTION
                      	""
        ::= { snmpTrapGroupInfoEntry 5 }       

        snmpTrapVdslGroup OBJECT-TYPE
               	SYNTAX	BITS {
		alarmprofile(0),
		others(1)
	}
        ACCESS  read-write
        STATUS  mandatory
        DESCRIPTION
                      	""
        ::= { snmpTrapGroupInfoEntry 6 }         

--  dateTimeServerSetup
	dateTimeServerSetup     	OBJECT IDENTIFIER ::= { ves1616pe54 11 }

        dateTimeServerType OBJECT-TYPE
        SYNTAX  INTEGER {
        		none(1),
			daytime(2),
			time(3),
			ntp(4)
        }
        ACCESS  read-write
        STATUS  mandatory
        DESCRIPTION
                      "The time service protocol."
        ::= { dateTimeServerSetup 1 }

        dateTimeServerIP OBJECT-TYPE
        SYNTAX  IpAddress
        ACCESS  read-write
        STATUS  mandatory
        DESCRIPTION
                      "IP address of time server, IPv4 only."
        ::= { dateTimeServerSetup 2 }

        dateTimeZone OBJECT-TYPE
        SYNTAX  INTEGER
        ACCESS  read-write
        STATUS  mandatory
        DESCRIPTION
                      "The time difference between UTC. Ex: +01"
        ::= { dateTimeServerSetup 3 }

        dateTimeNewDateYear OBJECT-TYPE
        SYNTAX  INTEGER
        ACCESS  read-write
        STATUS  mandatory
        DESCRIPTION
                      "The new date in year."
        ::= { dateTimeServerSetup 4 }

        dateTimeNewDateMonth OBJECT-TYPE
        SYNTAX  INTEGER
        ACCESS  read-write
        STATUS  mandatory
        DESCRIPTION
                      "The new date in month."
        ::= { dateTimeServerSetup 5 }

        dateTimeNewDateDay OBJECT-TYPE
        SYNTAX  INTEGER
        ACCESS  read-write
        STATUS  mandatory
        DESCRIPTION
                      "The new date in day."
        ::= { dateTimeServerSetup 6 }

        dateTimeNewTimeHour OBJECT-TYPE
        SYNTAX  INTEGER
        ACCESS  read-write
        STATUS  mandatory
        DESCRIPTION
                      "The new time in hour."
        ::= { dateTimeServerSetup 7 }

        dateTimeNewTimeMinute OBJECT-TYPE
        SYNTAX  INTEGER
        ACCESS  read-write
        STATUS  mandatory
        DESCRIPTION
                      "The new time in minute."
        ::= { dateTimeServerSetup 8 }

        dateTimeNewTimeSecond OBJECT-TYPE
        SYNTAX  INTEGER
        ACCESS  read-write
        STATUS  mandatory
        DESCRIPTION
                      "The new time in second."
        ::= { dateTimeServerSetup 9 }

-- dateTimeDaylightSavingTimeSetup OBJECT-TYPE
	dateTimeDaylightSavingTimeSetup     	OBJECT IDENTIFIER ::= { dateTimeServerSetup 10 }
	
        daylightSavingTimeState OBJECT-TYPE
        SYNTAX  EnabledStatus
        ACCESS  read-write
        STATUS  mandatory
        DESCRIPTION
                      "Daylight saving time service enabled/disabled for the switch."
        ::= { dateTimeDaylightSavingTimeSetup 1 }

        daylightSavingTimeStartDateWeek OBJECT-TYPE
        SYNTAX  INTEGER {
         		first(1),
         		second(2),
         		third(3),
         		fourth(4),
         		last(5)
        }
        ACCESS  read-write
        STATUS  mandatory
        DESCRIPTION
                      "Daylight saving time service start week."
        ::= { dateTimeDaylightSavingTimeSetup 2 }

        daylightSavingTimeStartDateDay OBJECT-TYPE
        SYNTAX  INTEGER {
         		sunday(0),
         		monday(1),
         		tuesday(2),
         		wednesday(3),
         		thursday(4),
         		friday(5),
         		saturday(6)         		
        }
        ACCESS  read-write
        STATUS  mandatory
        DESCRIPTION
                      "Daylight saving time service start day."
        ::= { dateTimeDaylightSavingTimeSetup 3 }

        daylightSavingTimeStartDateMonth OBJECT-TYPE
        SYNTAX  INTEGER {
         		january(1),
         		february(2),
         		march(3),
         		april(4),
         		may(5),
         		june(6),
         		july(7),
         		august(8),
         		september(9),
         		october(10),
         		november(11),
         		december(12)
        }
        ACCESS  read-write
        STATUS  mandatory
        DESCRIPTION
                      "Daylight saving time service start month."
        ::= { dateTimeDaylightSavingTimeSetup 4 }

        daylightSavingTimeStartDateHour OBJECT-TYPE
        SYNTAX  INTEGER 
        ACCESS  read-write
        STATUS  mandatory
        DESCRIPTION
                      "Daylight saving time service start time."
        ::= { dateTimeDaylightSavingTimeSetup 5 }

        daylightSavingTimeEndDateWeek OBJECT-TYPE
        SYNTAX  INTEGER {
         		first(1),
         		second(2),
         		third(3),
         		fourth(4),
         		last(5)
        }
        ACCESS  read-write
        STATUS  mandatory
        DESCRIPTION
                      "Daylight saving time service end week."
        ::= { dateTimeDaylightSavingTimeSetup 6 }

        daylightSavingTimeEndDateDay OBJECT-TYPE
        SYNTAX  INTEGER {
         		sunday(0),
         		monday(1),
         		tuesday(2),
         		wednesday(3),
         		thursday(4),
         		friday(5),
         		saturday(6)         		
        }
        ACCESS  read-write
        STATUS  mandatory
        DESCRIPTION
                      "Daylight saving time service end day."
        ::= { dateTimeDaylightSavingTimeSetup 7 }

        daylightSavingTimeEndDateMonth OBJECT-TYPE
        SYNTAX  INTEGER {
         		january(1),
         		february(2),
         		march(3),
         		april(4),
         		may(5),
         		june(6),
         		july(7),
         		august(8),
         		september(9),
         		october(10),
         		november(11),
         		december(12)
        }
        ACCESS  read-write
        STATUS  mandatory
        DESCRIPTION
                      "Daylight saving time service end month."
        ::= { dateTimeDaylightSavingTimeSetup 8 }

        daylightSavingTimeEndDateHour OBJECT-TYPE
        SYNTAX  INTEGER 
        ACCESS  read-write
        STATUS  mandatory
        DESCRIPTION
                      "Daylight saving time service end time."
        ::= { dateTimeDaylightSavingTimeSetup 9 }
    
        dateTimeServerIPAddrType OBJECT-TYPE
        SYNTAX  InetAddressType { ipv4(1), ipv6(2) }
        ACCESS  read-write
        STATUS  mandatory
        DESCRIPTION
                      "The address type of dateTimeServerIPAddr."
        ::= { dateTimeServerSetup 11 }
        
        dateTimeServerIPAddr OBJECT-TYPE
        SYNTAX  InetAddress
        ACCESS  read-write
        STATUS  mandatory
        DESCRIPTION
                      "The IP address of time server."
        ::= { dateTimeServerSetup 12 }
    
--  sysMgmt
	sysMgmt     	OBJECT IDENTIFIER ::= { ves1616pe54 12 }

        sysMgmtConfigSave OBJECT-TYPE
        SYNTAX  INTEGER {
         		config_1(1),
         		config_2(2)
        }
        ACCESS  read-write
        STATUS  mandatory
        DESCRIPTION
                      "If setting value is given, the variable write index will be set and running-config will be written to the assigned configuration file.
                      If not, running-config will be written to the booting one."
        ::= { sysMgmt 1 }

        sysMgmtBootupConfig OBJECT-TYPE
        SYNTAX  INTEGER {
         		config_1(1),
         		config_2(2)
        }
        ACCESS  read-write
        STATUS  mandatory
        DESCRIPTION
                      "The setting value (read index) will be written into non-volatile memory.
                      While rebooting, the variable write index is equal to read index initially.
                      You can change the value of write index by CLI / MIB."
        ::= { sysMgmt 2 }

        sysMgmtReboot OBJECT-TYPE
        SYNTAX  INTEGER {
        		nothing(0),
        		reboot(1)
        }
        ACCESS  read-write
        STATUS  mandatory
        DESCRIPTION
                      "Reboot switch from SNMP. 1:Reboot, 0:Nothing"
        ::= { sysMgmt 3 }

	sysMgmtDefaultConfig OBJECT-TYPE
        SYNTAX  INTEGER {
        		nothing(0),
        		reset_to_default(1),
        		reset_to_default_keep_ip(2)
        }
        ACCESS  read-write
        STATUS  mandatory
        DESCRIPTION
                      "Erase running config and reset to default."
        ::= { sysMgmt 4 }

	sysMgmtLastActionStatus OBJECT-TYPE
        SYNTAX  INTEGER {
        		none(0),
        		success(1),
        		fail(2)
        }
        ACCESS  read-only
        STATUS  mandatory
        DESCRIPTION
                      "Display status of last mgmt action."
        ::= { sysMgmt 5 }

	sysMgmtSystemStatus OBJECT-TYPE
	SYNTAX	BITS {
		sysAlarmDetected(0),
		sysTemperatureError(1),
		sysFanRPMError(2),
		sysVoltageRangeError(3)
	}
        ACCESS  read-only
        STATUS  mandatory
        DESCRIPTION
		"This variable indicates the status of the system.
 		The sysMgmtAlarmStatus is a bit map represented
 		a sum, therefore, it can represent multiple defects
 		simultaneously. The sysNoDefect should be set if and only if
 		no other flag is set.

	 	The various bit positions are:
			0   sysAlarmDetected
			1   sysTemperatureError
			2   sysFanRPMError
			3   sysVoltageRangeError"
        ::= { sysMgmt 6 }

	sysMgmtCPUUsage OBJECT-TYPE
		SYNTAX  INTEGER
		ACCESS  read-only
		STATUS  mandatory
		DESCRIPTION
			"Show device CPU load in %, it's the snapshot of CPU load when
			getting the values."
		::= { sysMgmt 7 }

	sysMgmtBootupImage OBJECT-TYPE
        SYNTAX  INTEGER {
         		image_1(1),
         		image_2(2)
        }
        ACCESS  read-write
        STATUS  mandatory
        DESCRIPTION
                      "The setting value (read index) will be written into non-volatile memory.
                      When rebooting, the selected image will be used.
                      You can change the value of write index by CLI / MIB."
        ::= { sysMgmt 8 }

	sysMgmtCounterReset OBJECT-TYPE
        SYNTAX  INTEGER {
         		enable(1),
         		disable(2)
        }
        ACCESS  read-write
        STATUS  mandatory
        DESCRIPTION
                      "Reset all port counters."
        ::= { sysMgmt 9 }

-- Tftp service                                                      
        sysMgmtTftpServiceSetup OBJECT IDENTIFIER ::= { sysMgmt 10 }                      

        sysMgmtTftpServerIp OBJECT-TYPE
        SYNTAX  IpAddress
        ACCESS  read-write
        STATUS  mandatory
        DESCRIPTION
                      	" IP address of TFTP server"
        ::= { sysMgmtTftpServiceSetup 1 }
        
        sysMgmtTftpRemoteFileName OBJECT-TYPE
        SYNTAX  DisplayString
        ACCESS  read-write
        STATUS  mandatory
        DESCRIPTION
                      	"The file name that you want to backup to or restore from TFTP server"
        ::= { sysMgmtTftpServiceSetup 2 }     
        
        sysMgmtTftpConfigIndex OBJECT-TYPE
        SYNTAX  INTEGER {
        	    config1(1),
        	    config2(2)
        }
        ACCESS  read-write
        STATUS  mandatory
        DESCRIPTION
                      	"Index of system configuration which you want to restore."
        ::= { sysMgmtTftpServiceSetup 3 }               
                               
        sysMgmtTftpAction OBJECT-TYPE
        SYNTAX  INTEGER {         
        		none(0),
         		backup_config(1),
         		restore_config(2)       		
        }
        ACCESS  read-write
        STATUS  mandatory        
                DESCRIPTION
                      	" Action of tftp service. 1: Backup running-config to tftp server, 2: Restore config from tftp server."
        ::= { sysMgmtTftpServiceSetup 4 }
        
	sysMgmtTftpActionStatus OBJECT-TYPE
        SYNTAX  INTEGER {
        		none(0),
        		success(1),
        		fail(2),
        		under-action(3)
        }
        ACCESS  read-only
        STATUS  mandatory
        DESCRIPTION
                      "Display status of mgmt action."
        ::= { sysMgmtTftpServiceSetup 5 }   
        
	sysMgmtTftpActionErrorInfo OBJECT-TYPE
        SYNTAX  DisplayString
        ACCESS  read-only
        STATUS  mandatory
        DESCRIPTION
                      "Display error information of mgmt action."
        ::= { sysMgmtTftpServiceSetup 6 }                 	
        
        sysMgmtTftpServerAddressType OBJECT-TYPE
        SYNTAX  InetAddressType { ipv4(1), ipv6(2) }
        ACCESS  read-write
        STATUS  mandatory
        DESCRIPTION
              "The address type of the sysMgmtTftpServerAddress entry."
        ::= { sysMgmtTftpServiceSetup 7 }                 	

        sysMgmtTftpServerAddress OBJECT-TYPE
        SYNTAX  InetAddress (SIZE(4|16))
        ACCESS  read-write
        STATUS  mandatory
        DESCRIPTION
                      	"IPv4/IPv6 address of TFTP server"
        ::= { sysMgmtTftpServiceSetup 8 }                 	
        
-- Remote FW upgrade
	sysMgmtRmtFwUpgradeSetup OBJECT IDENTIFIER ::= { sysMgmt 11 }  
	
	sysMgmtRmtFwUpgradeOp OBJECT-TYPE
        SYNTAX INTEGER {
        	    idle(1),
        	    upgrade(2)
        }
        ACCESS  read-write
        STATUS  mandatory
        DESCRIPTION
                      	"Specify remote FW upgrade operation"
        ::= { sysMgmtRmtFwUpgradeSetup 1 }
        
        sysMgmtRmtFwUpgradeTarget OBJECT-TYPE
        SYNTAX  PortList
        ACCESS  read-write
        STATUS  mandatory
        DESCRIPTION
                      	"Specify remote FW upgrade target CPEs"
        ::= { sysMgmtRmtFwUpgradeSetup 2 }    
             
        -- sysMgmtRmtFwUpgradeStatus
		sysMgmtRmtFwUpgradeStatus     	OBJECT IDENTIFIER ::= { sysMgmtRmtFwUpgradeSetup 3 }

	-- rmtFwUpgradeStatusTable

        rmtFwUpgradeStatusTable OBJECT-TYPE
        SYNTAX	SEQUENCE OF RmtFwUpgradeStatusEntry
        ACCESS  not-accessible
        STATUS  mandatory
        DESCRIPTION
                 	""
        ::= { sysMgmtRmtFwUpgradeStatus 1 }

	rmtFwUpgradeStatusEntry OBJECT-TYPE
        SYNTAX	RmtFwUpgradeStatusEntry
        ACCESS	not-accessible
        STATUS	mandatory
        DESCRIPTION    	"An entry in rmtFwUpgradeStatusTable."
        INDEX          	{ dot1dBasePort }
        ::= { rmtFwUpgradeStatusTable 1 }

        RmtFwUpgradeStatusEntry ::=
        SEQUENCE {
        	rmtFwUpgradeStatus	INTEGER
        }

        rmtFwUpgradeStatus OBJECT-TYPE
        SYNTAX INTEGER {
        	    idle(1),
        	    upgrading(2),
        	    success(3),
        	    fail(4)
        }
        ACCESS  read-only
        STATUS  mandatory
        DESCRIPTION
                      	""
        ::= { rmtFwUpgradeStatusEntry 1 }                                                                   

        -- sysMgmtRmtFwStatus
	sysMgmtRmtFwScheduleUpgrade     	OBJECT IDENTIFIER ::= { sysMgmtRmtFwUpgradeSetup 4 }

	sysMgmtRmtFwModel OBJECT-TYPE
        SYNTAX  DisplayString
        ACCESS  read-write
        STATUS  mandatory
        DESCRIPTION
                      	"FW model for upgrade periodically"
        ::= { sysMgmtRmtFwScheduleUpgrade 1 }
        
        sysMgmtRmtFwVersion OBJECT-TYPE
        SYNTAX  DisplayString
        ACCESS  read-write
        STATUS  mandatory
        DESCRIPTION
                      	"FW version for upgrade periodically"
        ::= { sysMgmtRmtFwScheduleUpgrade 2 }    

	-- rmtFwStatusTable

        rmtFwStatusTable OBJECT-TYPE
        SYNTAX	SEQUENCE OF RmtFwStatusEntry
        ACCESS  not-accessible
        STATUS  mandatory
        DESCRIPTION
                 	""
        ::= { sysMgmtRmtFwScheduleUpgrade 3 }

	rmtFwStatusEntry OBJECT-TYPE
        SYNTAX	RmtFwStatusEntry
        ACCESS	not-accessible
        STATUS	mandatory
        DESCRIPTION    	"An entry in rmtFwStatusTable."
        INDEX          	{ dot1dBasePort }
        ::= { rmtFwStatusTable 1 }

        RmtFwStatusEntry ::=
        SEQUENCE {
        	rmtFwStatus	DisplayString
        }

        rmtFwStatus OBJECT-TYPE
        SYNTAX  DisplayString
        ACCESS  read-only
        STATUS  mandatory
        DESCRIPTION
                      	""
        ::= { rmtFwStatusEntry 1 }                                                                   

	sysMgmtPacketBufferUsage OBJECT-TYPE
		SYNTAX  INTEGER
		ACCESS  read-only
		STATUS  mandatory
		DESCRIPTION
			"Show device packet buffer usage in %, it's the snapshot of packet buffer usage ratio when
			getting the values."
		::= { sysMgmt 12 }
		
	sysMgmtMemoryUsage OBJECT-TYPE
		SYNTAX  INTEGER
		ACCESS  read-only
		STATUS  mandatory
		DESCRIPTION
			"Show device memory usage in %, it's the snapshot of the device memory usage ratio when
			getting the values."
		::= { sysMgmt 13 }	
--------------		
--  sysLoginSetup
	sysLoginSetup     	OBJECT IDENTIFIER ::= { sysMgmt 14 }

	loginLimitMaxNumberOfUser OBJECT-TYPE
        SYNTAX  INTEGER
        ACCESS  read-only
        STATUS  mandatory
        DESCRIPTION
                      	""
        ::= { sysLoginSetup 1 }

        sysLoginSetupTable	OBJECT-TYPE
        SYNTAX	SEQUENCE OF SysLoginSetupEntry
        ACCESS  not-accessible
        STATUS  mandatory
        DESCRIPTION
                 	""
        ::= { sysLoginSetup 2 }

	sysLoginSetupEntry OBJECT-TYPE
        SYNTAX	SysLoginSetupEntry
        ACCESS	not-accessible
        STATUS	mandatory
        DESCRIPTION    	"An entry in LoginLimitMaxNumberOfUser."
        INDEX          	{ sysLoginName }
        ::= { sysLoginSetupTable 1 }

        SysLoginSetupEntry ::=
	SEQUENCE {
        	sysLoginName		DisplayString,
        	sysLoginPassword	DisplayString,
        	sysLoginPrivilege	INTEGER,
        	sysLoginRowStatus	RowStatus
        }

        sysLoginName OBJECT-TYPE
        SYNTAX  DisplayString
        ACCESS  read-only
        STATUS  mandatory
        DESCRIPTION
                      	""
        ::= { sysLoginSetupEntry 1 }

        sysLoginPassword OBJECT-TYPE
        SYNTAX  DisplayString
        ACCESS  read-write
        STATUS  mandatory
        DESCRIPTION
	""
        ::= { sysLoginSetupEntry 2 }

        sysLoginPrivilege OBJECT-TYPE
        SYNTAX  INTEGER
        ACCESS  read-write
        STATUS  mandatory
        DESCRIPTION
        ""
        ::= { sysLoginSetupEntry 3 }
        

        sysLoginRowStatus OBJECT-TYPE
        SYNTAX  RowStatus
        ACCESS  read-create
        STATUS  mandatory
        DESCRIPTION
                      	""
        ::= { sysLoginSetupEntry 4 }
        
-- ExternalAlarmSetup
                                                      
        sysMgmtExternalAlarmSetup OBJECT IDENTIFIER ::= { sysMgmt 15 }                      

        sysMgmtExternalAlarm1 OBJECT-TYPE
        SYNTAX  DisplayString
        ACCESS  read-write
        STATUS  mandatory
        DESCRIPTION
                      	" externalalarm1 name setting"
        ::= { sysMgmtExternalAlarmSetup 1 }
        
        sysMgmtExternalAlarm2 OBJECT-TYPE
        SYNTAX  DisplayString
        ACCESS  read-write
        STATUS  mandatory
        DESCRIPTION
                      	" externalalarm2 name setting"
        ::= { sysMgmtExternalAlarmSetup 2 }     
        
        sysMgmtExternalAlarm3 OBJECT-TYPE
        SYNTAX  DisplayString
        ACCESS  read-write
        STATUS  mandatory
        DESCRIPTION
                      	" externalalarm3 name setting"
        ::= { sysMgmtExternalAlarmSetup 3 }               
                               
        sysMgmtExternalAlarm4 OBJECT-TYPE
        SYNTAX  DisplayString
        ACCESS  read-write
        STATUS  mandatory
        DESCRIPTION
                      	" externalalarm4 name setting"
        ::= { sysMgmtExternalAlarmSetup 4 }
        
        sysMgmtExternalAlarmCurrentStatus OBJECT-TYPE
        SYNTAX  DisplayString
        ACCESS  read-only
        STATUS  mandatory
        DESCRIPTION
                      	" externalalarm current status. The first to fourth bit represent externalalarm1 to 4 current status."
        ::= { sysMgmtExternalAlarmSetup 5 }
        
	sysMgmtMacFlush OBJECT-TYPE
        SYNTAX  INTEGER {
         		mac_flush(1)
        }
		ACCESS  read-write
		STATUS  mandatory
		DESCRIPTION
			" Set 1 to execute mac flush operation, read value will always return 0"
		::= { sysMgmt 16 }        
		
	sysMgmtCPUUsageThreshold OBJECT-TYPE
        SYNTAX  INTEGER 
	ACCESS  read-write
	STATUS  mandatory
	DESCRIPTION
		" Set CPU Threshold value"
	::= { sysMgmt 17 }   		
	
	sysMgmtPacketBufferThreshold OBJECT-TYPE
        SYNTAX  INTEGER 
	ACCESS  read-write
	STATUS  mandatory
	DESCRIPTION
		" Set packet buffer usage Threshold value"
	::= { sysMgmt 18 }   		

	sysMgmtMemoryUsageThreshold OBJECT-TYPE
        SYNTAX  INTEGER 
	ACCESS  read-write
	STATUS  mandatory
	DESCRIPTION
		" Set memory usage Threshold value"
	::= { sysMgmt 19 }   		
	
	sysMgmtPlusVersion OBJECT-TYPE
        SYNTAX  INTEGER 
	ACCESS  read-only
	STATUS  mandatory
	DESCRIPTION
		" Get Hardware Plus Version"
	::= { sysMgmt 20 }   		
	
------------------------	
       
--  layer2Setup
	layer2Setup     	OBJECT IDENTIFIER ::= { ves1616pe54 13 }

        vlanTypeSetup OBJECT-TYPE
        SYNTAX  INTEGER {
         		dot1Q(1),
         		port_based(2)
        }
        ACCESS  read-write
        STATUS  mandatory
        DESCRIPTION
                      ""
        ::= { layer2Setup 1 }

        igmpSnoopingStateSetup OBJECT-TYPE
        SYNTAX  INTEGER {
         		disabled(1),
         		enable_igmp_snooping(2),
         		enable_igmp_proxying(3)
        }
        ACCESS  read-write
        STATUS  mandatory
        DESCRIPTION
                      ""
        ::= { layer2Setup 2 }

        tagVlanPortIsolationState OBJECT-TYPE
        SYNTAX  INTEGER
        ACCESS  read-write
        STATUS  mandatory
        DESCRIPTION
                      "This item always returns 0. Set 1(port isolation) or 2 (all-connected) to this item to quickly setup port-based VLAN members. "
        ::= { layer2Setup 3 }

        stpState OBJECT-TYPE
        SYNTAX  EnabledStatus
        ACCESS  read-write
        STATUS  mandatory
        DESCRIPTION
                      ""
        ::= { layer2Setup 4 }

        igmpFilteringStateSetup OBJECT-TYPE
        SYNTAX  EnabledStatus
        ACCESS  read-write
        STATUS  mandatory
        DESCRIPTION
                      ""
        ::= { layer2Setup 5 }

        unknownMulticastFrameForwarding OBJECT-TYPE
        SYNTAX  INTEGER {
         	flooding(1),
         	drop(2)
        }
        ACCESS  read-write
        STATUS  mandatory
        DESCRIPTION
                      ""
        ::= { layer2Setup 6 }

        multicastGrpHostTimeout OBJECT-TYPE
        SYNTAX  INTEGER 
        ACCESS  read-write
        STATUS  mandatory
        DESCRIPTION
                      "Specify host timeout for all multicast groups when the specific port is in auto mode."
        ::= { layer2Setup 7 }
        
        multicastGrpLeaveTimeout OBJECT-TYPE
        SYNTAX  INTEGER 
        ACCESS  read-write
        STATUS  mandatory
        DESCRIPTION
                      "Specify leave timeout for all multicast groups."
        ::= { layer2Setup 8 }

        reservedMulticastFrameForwarding OBJECT-TYPE
        SYNTAX  INTEGER {
         	flooding(1),
         	drop(2)
        }
        ACCESS  read-write
        STATUS  mandatory
        DESCRIPTION
                      ""
        ::= { layer2Setup 9 }  

        igmpsnp8021pPriority OBJECT-TYPE
        SYNTAX  INTEGER
        ACCESS  read-write
        STATUS  mandatory
        DESCRIPTION
                      "Set the 802.1p priority of control messages for igmp-snooping(0~8, 8-No Change)"
        ::= { layer2Setup 10 }  
 
        portBasedVlanPortIsolationState OBJECT-TYPE
        SYNTAX  INTEGER
        ACCESS  read-write
        STATUS  mandatory
        DESCRIPTION
                      "This item always returns 0. Set 1(port isolation) or 2 (all-connected) to this item to quickly setup port-based VLAN members. "
        ::= { layer2Setup 11 }
        

        igmpsnpVlanMode OBJECT-TYPE
        SYNTAX  INTEGER {
         	auto(1),
         	fixed(2)
        }
        ACCESS  read-write
        STATUS  mandatory
        DESCRIPTION
                      ""
        ::= { layer2Setup 12 }                
        
        
        stpMode OBJECT-TYPE
        SYNTAX  INTEGER {
         	rstp(1),
         	mrstp(2),
         	mstp (3)
        }
        ACCESS  read-write
        STATUS  mandatory
        DESCRIPTION
                      ""
        ::= { layer2Setup 13 }                               
        
	mgmdMLDsupport OBJECT-TYPE
	SYNTAX  EnabledStatus
	ACCESS  read-write
	STATUS  mandatory
	DESCRIPTION
		"Enable MLD / Disable MLD"
        ::= { layer2Setup 17 }
        
--  igmpsnpVlanTable
        igmpsnpVlanTable	OBJECT-TYPE
        SYNTAX	SEQUENCE OF IgmpsnpVlanEntry
        ACCESS  not-accessible
        STATUS  mandatory
        DESCRIPTION
                 	""
        ::= { layer2Setup 14 }
        
	igmpsnpVlanEntry OBJECT-TYPE
        SYNTAX	IgmpsnpVlanEntry
        ACCESS	not-accessible
        STATUS	mandatory
        DESCRIPTION    	"An entry in IgmpsnpVlanTable."
        INDEX          	{ igmpsnpVid }
        ::= { igmpsnpVlanTable 1 }

        IgmpsnpVlanEntry ::=
           SEQUENCE {
			igmpsnpVid		INTEGER,
        	igmpsnpVlanName	DisplayString,        	
        	igmpsnpVlanRowStatus RowStatus
           }
           
   
        igmpsnpVid OBJECT-TYPE
        SYNTAX  INTEGER
        ACCESS  read-only
        STATUS  mandatory
        DESCRIPTION
                      	""
        ::= { igmpsnpVlanEntry 1 }        


     igmpsnpVlanName OBJECT-TYPE
        SYNTAX  DisplayString
        ACCESS  read-write
        STATUS  mandatory
        DESCRIPTION
                      	""
        ::= { igmpsnpVlanEntry 2 }
        
        
        igmpsnpVlanRowStatus OBJECT-TYPE
        SYNTAX  RowStatus
        ACCESS  read-create
        STATUS  mandatory
        DESCRIPTION
                      	""
        ::= {  igmpsnpVlanEntry 3 }

--  ipSetup
	ipSetup     	OBJECT IDENTIFIER ::= { ves1616pe54 14 }

        dnsIpAddress OBJECT-TYPE
        SYNTAX  IpAddress
        ACCESS  read-write
        STATUS  mandatory
        DESCRIPTION
                      ""
        ::= { ipSetup 1 }

        defaultMgmt OBJECT-TYPE
        SYNTAX  INTEGER {
        	in_band(0),
        	out_of_band(1)
        }
        ACCESS  read-write
        STATUS  mandatory
        DESCRIPTION
                      ""
        ::= { ipSetup 2 }

	inbandIpSetup     	OBJECT IDENTIFIER ::= { ipSetup 3 }

        inbandIpType OBJECT-TYPE
        SYNTAX  INTEGER {
        	dhcp_client(0),
        	static_ip(1)
        }
        ACCESS  read-write
        STATUS  mandatory
        DESCRIPTION
                      ""
        ::= { inbandIpSetup 1 }

        inbandVid OBJECT-TYPE
        SYNTAX  INTEGER
        ACCESS  read-write
        STATUS  mandatory
        DESCRIPTION
                      ""
        ::= { inbandIpSetup 2 }

        inbandStaticIp OBJECT-TYPE
        SYNTAX  IpAddress
        ACCESS  read-write
        STATUS  mandatory
        DESCRIPTION
                      ""
        ::= { inbandIpSetup 3 }

        inbandStaticSubnetMask OBJECT-TYPE
        SYNTAX  IpAddress
        ACCESS  read-write
        STATUS  mandatory
        DESCRIPTION
                      ""
        ::= { inbandIpSetup 4 }

        inbandStaticGateway OBJECT-TYPE
        SYNTAX  IpAddress
        ACCESS  read-write
        STATUS  mandatory
        DESCRIPTION
                      ""
        ::= { inbandIpSetup 5 }

	outOfBandIpSetup     	OBJECT IDENTIFIER ::= { ipSetup 4 }

        outOfBandIp OBJECT-TYPE
        SYNTAX  IpAddress
        ACCESS  read-write
        STATUS  mandatory
        DESCRIPTION
                      ""
        ::= { outOfBandIpSetup 1 }

        outOfBandSubnetMask OBJECT-TYPE
        SYNTAX  IpAddress
        ACCESS  read-write
        STATUS  mandatory
        DESCRIPTION
                      ""
        ::= { outOfBandIpSetup 2 }

        outOfBandGateway OBJECT-TYPE
        SYNTAX  IpAddress
        ACCESS  read-write
        STATUS  mandatory
        DESCRIPTION
                      ""
        ::= { outOfBandIpSetup 3 }

        maxNumOfInbandIp OBJECT-TYPE
        SYNTAX  INTEGER
        ACCESS  read-only
        STATUS  mandatory
        DESCRIPTION
                      	""
        ::= { ipSetup 5 }

--  inbandIpTable
        inbandIpTable	OBJECT-TYPE
        SYNTAX	SEQUENCE OF InbandIpEntry
        ACCESS  not-accessible
        STATUS  mandatory
        DESCRIPTION
                 	""
        ::= { ipSetup 6 }

	inbandIpEntry OBJECT-TYPE
        SYNTAX	InbandIpEntry
        ACCESS	not-accessible
        STATUS	mandatory
        DESCRIPTION    	"An entry in inbandIpTable."
        INDEX          	{ inbandEntryIp, inbandEntryVid }
        ::= { inbandIpTable 1 }

        InbandIpEntry ::=
	SEQUENCE {
        	inbandEntryIp		IpAddress,
        	inbandEntrySubnetMask	IpAddress,
        	inbandEntryGateway	IpAddress,
        	inbandEntryVid		INTEGER,
        	inbandEntryManageable	EnabledStatus,
        	inbandEntryRowStatus	RowStatus
        }

        inbandEntryIp OBJECT-TYPE
        SYNTAX  IpAddress
        ACCESS  read-only
        STATUS  mandatory
        DESCRIPTION
                      	""
        ::= { inbandIpEntry 1 }

        inbandEntrySubnetMask OBJECT-TYPE
        SYNTAX  IpAddress
        ACCESS  read-write
        STATUS  mandatory
        DESCRIPTION
                      	""
        ::= { inbandIpEntry 2 }

        inbandEntryGateway OBJECT-TYPE
        SYNTAX  IpAddress
        ACCESS  read-write
        STATUS  mandatory
        DESCRIPTION
                      	""
        ::= { inbandIpEntry 3 }

        inbandEntryVid OBJECT-TYPE
        SYNTAX  INTEGER
        ACCESS  read-only
        STATUS  mandatory
        DESCRIPTION
                      	""
        ::= { inbandIpEntry 4 }

        inbandEntryManageable OBJECT-TYPE
        SYNTAX  EnabledStatus
        ACCESS  read-write
        STATUS  mandatory
        DESCRIPTION
                      	""
        ::= { inbandIpEntry 5 }

        inbandEntryRowStatus OBJECT-TYPE
        SYNTAX  RowStatus
        ACCESS  read-create
        STATUS  mandatory
        DESCRIPTION
                      	""
        ::= { inbandIpEntry 6 }

--  filterSetup
	filterSetup     	OBJECT IDENTIFIER ::= { ves1616pe54 15 }

--  filterTable
       	filterTable	OBJECT-TYPE
        SYNTAX	SEQUENCE OF FilterEntry
        ACCESS  not-accessible
        STATUS  mandatory
        DESCRIPTION
                 	""
        ::= { filterSetup 1 }

	filterEntry OBJECT-TYPE
        SYNTAX	FilterEntry
        ACCESS	not-accessible
        STATUS	mandatory
        DESCRIPTION    	"An entry in filterTable."
        INDEX          	{ filterMacAddr, filterVid }
        ::= { filterTable 1 }

        FilterEntry ::=
           SEQUENCE {
         	filterName		DisplayString,
        	filterActionState	INTEGER,
        	filterMacAddr		MacAddress,
        	filterVid		INTEGER,
        	filterRowStatus		RowStatus
           }

        filterName OBJECT-TYPE
        SYNTAX  DisplayString
        ACCESS  read-write
        STATUS  mandatory
        DESCRIPTION
                      	""
        ::= { filterEntry 1 }

        filterActionState OBJECT-TYPE
        SYNTAX  INTEGER {
		discard_source(1),
		discard_destination(2),
		both(3)
	}
        ACCESS  read-write
        STATUS  mandatory
        DESCRIPTION
                      	""
        ::= { filterEntry 2 }

        filterMacAddr OBJECT-TYPE
        SYNTAX  MacAddress
        ACCESS  read-only
        STATUS  mandatory
        DESCRIPTION
                      	""
        ::= { filterEntry 3 }

   	filterVid OBJECT-TYPE
        SYNTAX  INTEGER
        ACCESS  read-only
        STATUS  mandatory
        DESCRIPTION
                      	""
        ::= { filterEntry 4 }

   	filterRowStatus OBJECT-TYPE
        SYNTAX  RowStatus
        ACCESS  read-create
        STATUS  mandatory
        DESCRIPTION
                      	""
        ::= { filterEntry 5 }

--  mirrorSetup
	mirrorSetup     	OBJECT IDENTIFIER ::= { ves1616pe54 16 }

--  mirrorState
        mirrorState OBJECT-TYPE
        SYNTAX  EnabledStatus
        ACCESS  read-write
        STATUS  mandatory
        DESCRIPTION
                      	""
        ::= { mirrorSetup 1 }

        mirrorMonitorPort OBJECT-TYPE
        SYNTAX  INTEGER
        ACCESS  read-write
        STATUS  mandatory
        DESCRIPTION
                      	""
        ::= { mirrorSetup 2 }

        mirrorRspanVid OBJECT-TYPE
        SYNTAX  INTEGER
        ACCESS  read-write
        STATUS  mandatory
        DESCRIPTION
                      	""
        ::= { mirrorSetup 7 }
        
-- mirrorTable

        mirrorTable OBJECT-TYPE
        SYNTAX	SEQUENCE OF MirrorEntry
        ACCESS  not-accessible
        STATUS  mandatory
        DESCRIPTION
                 	""
        ::= { mirrorSetup 3 }

	mirrorEntry OBJECT-TYPE
        SYNTAX	MirrorEntry
        ACCESS	not-accessible
        STATUS	mandatory
        DESCRIPTION    	"An entry in mirrorTable."
        INDEX          	{ dot1dBasePort }
        ::= { mirrorTable 1 }

        MirrorEntry ::=
           SEQUENCE {
        	mirrorMirroredState	EnabledStatus,
        	mirrorDirection		INTEGER
           }

        mirrorMirroredState OBJECT-TYPE
        SYNTAX  EnabledStatus
        ACCESS  read-write
        STATUS  mandatory
        DESCRIPTION
                      	""
        ::= { mirrorEntry 1 }

        mirrorDirection OBJECT-TYPE
        SYNTAX  INTEGER {
        	ingress(0),
        	egress(1),
        	both(2)
        }
        ACCESS  read-write
        STATUS  mandatory
        DESCRIPTION
                      	""
        ::= { mirrorEntry 2 }


-- aggrSetup
	aggrSetup     	OBJECT IDENTIFIER ::= { ves1616pe54 17 }

        aggrState OBJECT-TYPE
        SYNTAX  EnabledStatus
        ACCESS  read-write
        STATUS  mandatory
        DESCRIPTION
                      	""
        ::= { aggrSetup 1 }

        aggrSystemPriority OBJECT-TYPE
        SYNTAX  INTEGER
        ACCESS  read-write
        STATUS  mandatory
        DESCRIPTION
                      	""
        ::= { aggrSetup 2 }

-- aggrGroupTable

        aggrGroupTable OBJECT-TYPE
        SYNTAX	SEQUENCE OF AggrGroupEntry
        ACCESS  not-accessible
        STATUS  mandatory
        DESCRIPTION
                 	""
        ::= { aggrSetup 3 }

	aggrGroupEntry OBJECT-TYPE
        SYNTAX	AggrGroupEntry
        ACCESS	not-accessible
        STATUS	mandatory
        DESCRIPTION    	"An entry in aggrGroupTable."
        INDEX          	{ aggrGroupIndex }
        ::= { aggrGroupTable 1 }

        AggrGroupEntry ::=
           SEQUENCE {
        	aggrGroupIndex		INTEGER,
        	aggrGroupState		EnabledStatus,
        	aggrGroupDynamicState	EnabledStatus
           }

        aggrGroupIndex OBJECT-TYPE
        SYNTAX  INTEGER
        ACCESS  read-only
        STATUS  mandatory
        DESCRIPTION
                      	""
        ::= { aggrGroupEntry 1 }

        aggrGroupState OBJECT-TYPE
        SYNTAX  EnabledStatus
        ACCESS  read-write
        STATUS  mandatory
        DESCRIPTION
                     	""
        ::= { aggrGroupEntry 2 }

        aggrGroupDynamicState OBJECT-TYPE
        SYNTAX  EnabledStatus
        ACCESS  read-write
        STATUS  mandatory
        DESCRIPTION
                     	""
        ::= { aggrGroupEntry 3 }

-- aggrPortTable

        aggrPortTable OBJECT-TYPE
        SYNTAX	SEQUENCE OF AggrPortEntry
        ACCESS  not-accessible
        STATUS  mandatory
        DESCRIPTION
                 	""
        ::= { aggrSetup 4 }

	aggrPortEntry OBJECT-TYPE
        SYNTAX	AggrPortEntry
        ACCESS	not-accessible
        STATUS	mandatory
        DESCRIPTION    	"An entry in aggrPortTable."
        INDEX          	{ dot1dBasePort }
        ::= { aggrPortTable 1 }

        AggrPortEntry ::=
           SEQUENCE {
        	aggrPortGroup			INTEGER,
        	aggrPortDynamicStateTimeout	INTEGER
           }

        aggrPortGroup OBJECT-TYPE
        SYNTAX  INTEGER {
        	none(0),
        	t1(1)
        }
        ACCESS  read-write
        STATUS  mandatory
        DESCRIPTION
                      	""
        ::= { aggrPortEntry 1 }

        aggrPortDynamicStateTimeout OBJECT-TYPE
        SYNTAX  INTEGER
        ACCESS  read-write
        STATUS  mandatory
        DESCRIPTION
                     	""
        ::= { aggrPortEntry 2 }


-- accessCtlSetup
	accessCtlSetup     	OBJECT IDENTIFIER ::= { ves1616pe54 18 }

-- accessCtlTable

        accessCtlTable OBJECT-TYPE
        SYNTAX	SEQUENCE OF AccessCtlEntry
        ACCESS  not-accessible
        STATUS  mandatory
        DESCRIPTION
                 	""
        ::= { accessCtlSetup 1 }

	accessCtlEntry OBJECT-TYPE
        SYNTAX	AccessCtlEntry
        ACCESS	not-accessible
        STATUS	mandatory
        DESCRIPTION    	"An entry in accessCtlTable."
        INDEX          	{ accessCtlService }
        ::= { accessCtlTable 1 }

        AccessCtlEntry ::=
           SEQUENCE {
        	accessCtlService	INTEGER,
        	accessCtlEnable	EnabledStatus,
        	accessCtlServicePort	INTEGER,
        	accessCtlTimeout	INTEGER
           }

        accessCtlService OBJECT-TYPE
        SYNTAX  INTEGER {
        	telnet(1),
        	ssh(2),
        	ftp(3),
        	http(4),
        	https(5),
        	icmp(6),
        	snmp(7)
        }
        ACCESS  read-only
        STATUS  mandatory
        DESCRIPTION
                      	""
        ::= { accessCtlEntry 1 }

        accessCtlEnable OBJECT-TYPE
        SYNTAX  EnabledStatus
        ACCESS  read-write
        STATUS  mandatory
        DESCRIPTION
                     	""
        ::= { accessCtlEntry 2 }

        accessCtlServicePort OBJECT-TYPE
        SYNTAX  INTEGER
        ACCESS  read-write
        STATUS  mandatory
        DESCRIPTION
                     	""
        ::= { accessCtlEntry 3 }

        accessCtlTimeout OBJECT-TYPE
        SYNTAX  INTEGER
        ACCESS  read-write
        STATUS  mandatory
        DESCRIPTION
                     	""
        ::= { accessCtlEntry 4 }

--  securedClientTable
        securedClientTable OBJECT-TYPE
        SYNTAX	SEQUENCE OF SecuredClientEntry
        ACCESS  not-accessible
        STATUS  mandatory
        DESCRIPTION
                 	""
        ::= { accessCtlSetup 2 }

	securedClientEntry OBJECT-TYPE
        SYNTAX	SecuredClientEntry
        ACCESS	not-accessible
        STATUS	mandatory
        DESCRIPTION    	"An entry in securedClientTable."
        INDEX          	{ securedClientIndex }
        ::= { securedClientTable 1 }

        SecuredClientEntry ::=
           SEQUENCE {
           	securedClientIndex	INTEGER,
           	securedClientEnable	EnabledStatus,
        	securedClientStartIp	IpAddress,
        	securedClientEndIp	IpAddress,
        	securedClientService			BITS,
        	securedClientIpAddrType			InetAddressType,
        	securedClientStartIpAddr		InetAddress,
        	securedClientEndIpAddr			InetAddress
           }

        securedClientIndex OBJECT-TYPE
        SYNTAX  INTEGER
        ACCESS  read-only
        STATUS  mandatory
        DESCRIPTION
                      	""
        ::= { securedClientEntry 1 }

        securedClientEnable OBJECT-TYPE
        SYNTAX  EnabledStatus
        ACCESS  read-write
        STATUS  mandatory
        DESCRIPTION
                      	""
        ::= { securedClientEntry 2 }

        securedClientStartIp OBJECT-TYPE
        SYNTAX  IpAddress
        ACCESS  read-write
        STATUS  mandatory
        DESCRIPTION
                      	"IPv4 only"
        ::= { securedClientEntry 3 }

        securedClientEndIp OBJECT-TYPE
        SYNTAX  IpAddress
        ACCESS  read-write
        STATUS  mandatory
        DESCRIPTION
                     	"IPv4 only"
        ::= { securedClientEntry 4 }

        securedClientService OBJECT-TYPE
        SYNTAX	BITS {
			telnet(0),
			ftp(1),
			http(2),
			icmp(3),
			snmp(4),
			ssh(5),
			https(6)
		}
        ACCESS  read-write
        STATUS  mandatory
        DESCRIPTION
                     	""
        ::= { securedClientEntry 5 }

        securedClientIpAddrType OBJECT-TYPE
        SYNTAX  InetAddressType { ipv4(1), ipv6(2) }
        ACCESS  read-write
        STATUS  mandatory
        DESCRIPTION
                      	""
        ::= { securedClientEntry 6 }
        
        securedClientStartIpAddr OBJECT-TYPE
        SYNTAX  InetAddress
        ACCESS  read-write
        STATUS  mandatory
        DESCRIPTION
                      	""
        ::= { securedClientEntry 7 }
        
        securedClientEndIpAddr OBJECT-TYPE
        SYNTAX  InetAddress
        ACCESS  read-write
        STATUS  mandatory
        DESCRIPTION
                      	""
        ::= { securedClientEntry 8 }

--  queuingMethodSetup
	queuingMethodSetup     	OBJECT IDENTIFIER ::= { ves1616pe54 19 }

        queuingMethodType OBJECT-TYPE
        SYNTAX  INTEGER {
        	strictly_priority(0),
        	weighted_fair_scheduling(1),
        	weighted_round_robin(2)
        }
        ACCESS  read-write
        STATUS  mandatory
        DESCRIPTION
                      	""
        ::= { queuingMethodSetup 1 }



-- portQueuingMethodTable
        portQueuingMethodTable OBJECT-TYPE
        SYNTAX	SEQUENCE OF PortQueuingMethodEntry
        ACCESS  not-accessible
        STATUS  mandatory
        DESCRIPTION
                 	""
        ::= { queuingMethodSetup 2 }

	portQueuingMethodEntry OBJECT-TYPE
        SYNTAX	PortQueuingMethodEntry
        ACCESS	not-accessible
        STATUS	mandatory
        DESCRIPTION    	"An entry in portQueuingMethodTable."
        INDEX          	{ dot1dBasePort, portQueuingMethodQueue }
        ::= {portQueuingMethodTable 1}

        PortQueuingMethodEntry ::=
           SEQUENCE {
        	portQueuingMethodQueue	INTEGER,
        	portQueuingMethodWeight	INTEGER
           }

        portQueuingMethodQueue OBJECT-TYPE
        SYNTAX  INTEGER
        ACCESS  read-only
        STATUS  mandatory
        DESCRIPTION
                      	"0...7"
        ::= { portQueuingMethodEntry 1 }

        portQueuingMethodWeight OBJECT-TYPE
        SYNTAX  INTEGER
        ACCESS  read-write
        STATUS  mandatory
        DESCRIPTION
                     	"0...15"
        ::= { portQueuingMethodEntry 2 }

 -- queuingMethodFeSpq
		queuingMethodFeSpq OBJECT-TYPE
        SYNTAX  INTEGER {
        	none(0),
        	q0(1),
        	q1(2),
        	q2(3),
        	q3(4),
        	q4(5),
        	q5(6),
        	q6(7),
        	q7(8)
        }
        ACCESS  read-write
        STATUS  mandatory
        DESCRIPTION
                      	"VDSL port SPQ enable. Qx and higher is SPQ, and the rest of the others are WFQ."
        ::= { queuingMethodSetup 3 }

-- portQueuingMethodGeSpqTable
        portQueuingMethodGeSpqTable OBJECT-TYPE
        SYNTAX	SEQUENCE OF PortQueuingMethodGeSpqEntry
        ACCESS  not-accessible
        STATUS  mandatory
        DESCRIPTION
                 	""
        ::= { queuingMethodSetup 4 }
        
	portQueuingMethodGeSpqEntry OBJECT-TYPE
        SYNTAX	PortQueuingMethodGeSpqEntry
        ACCESS	not-accessible
        STATUS	mandatory
        DESCRIPTION    	"An entry in portQueuingMethodGeSpqTable."
        INDEX          	{ dot1dBasePort }
        ::= {portQueuingMethodGeSpqTable 1}

        PortQueuingMethodGeSpqEntry ::=
           SEQUENCE {
        	portQueuingMethodGeSpq	INTEGER
           }

        portQueuingMethodGeSpq OBJECT-TYPE
		SYNTAX  INTEGER {
        	none(0),
        	q0(1),
        	q1(2),
        	q2(3),
        	q3(4),
        	q4(5),
        	q5(6),
        	q6(7),
        	q7(8)
        }

        ACCESS  read-write
        STATUS  mandatory
        DESCRIPTION
                      	"GE port SPQ enable. Qx and higher is SPQ, and the rest of the others are WFQ."
        ::= { portQueuingMethodGeSpqEntry 1 }

--  dhcpSetup
	dhcpSetup     	OBJECT IDENTIFIER ::= { ves1616pe54 20 }

        globalDhcpRelay OBJECT IDENTIFIER ::= { dhcpSetup 1 }

        globalDhcpRelayEnable OBJECT-TYPE
        SYNTAX  EnabledStatus
        ACCESS  read-write
        STATUS  mandatory
        DESCRIPTION
                      	""
        ::= { globalDhcpRelay 1 }

        globalDhcpRelayOption82Enable OBJECT-TYPE
        SYNTAX  EnabledStatus
        ACCESS  read-write
        STATUS  mandatory
        DESCRIPTION
                      	""
        ::= { globalDhcpRelay 2 }

        globalDhcpRelayInfoEnable OBJECT-TYPE
        SYNTAX  EnabledStatus
        ACCESS  read-write
        STATUS  mandatory
        DESCRIPTION
                      	""
        ::= { globalDhcpRelay 3 }

        globalDhcpRelayInfoData OBJECT-TYPE
        SYNTAX  DisplayString
        ACCESS  read-write
        STATUS  mandatory
        DESCRIPTION
                      	""
        ::= { globalDhcpRelay 4 }

--  globalDhcpRelayRemoteServer

        maxNumberOfGlobalDhcpRelayRemoteServer OBJECT-TYPE
        SYNTAX  INTEGER
        ACCESS  read-only
        STATUS  mandatory
        DESCRIPTION
                      	""
        ::= { globalDhcpRelay 5 }

-- globalDhcpRelayRemoteServerTable
        globalDhcpRelayRemoteServerTable OBJECT-TYPE
        SYNTAX	SEQUENCE OF GlobalDhcpRelayRemoteServerEntry
        ACCESS  not-accessible
        STATUS  mandatory
        DESCRIPTION
                 	""
        ::= { globalDhcpRelay 6 }

	globalDhcpRelayRemoteServerEntry OBJECT-TYPE
        SYNTAX	GlobalDhcpRelayRemoteServerEntry
        ACCESS	not-accessible
        STATUS	mandatory
        DESCRIPTION    	"An entry in globalDhcpRelayRemoteServerTable."
        INDEX          	{ globalDhcpRelayRemoteServerIp }
        ::= { globalDhcpRelayRemoteServerTable 1 }

        GlobalDhcpRelayRemoteServerEntry ::=
           SEQUENCE {
        	globalDhcpRelayRemoteServerIp		IpAddress,
        	globalDhcpRelayRemoteServerRowStatus	RowStatus
           }

        globalDhcpRelayRemoteServerIp OBJECT-TYPE
        SYNTAX  IpAddress
        ACCESS  read-only
        STATUS  mandatory
        DESCRIPTION
                      	""
        ::= { globalDhcpRelayRemoteServerEntry 1 }

        globalDhcpRelayRemoteServerRowStatus OBJECT-TYPE
        SYNTAX  RowStatus
        ACCESS  read-create
        STATUS  mandatory
        DESCRIPTION
                     	""
        ::= { globalDhcpRelayRemoteServerEntry 2 }

--- dhcp option82 remote id field
        globalDhcpRelayRemoteIDEnable OBJECT-TYPE
        SYNTAX  EnabledStatus
        ACCESS  read-write
        STATUS  mandatory
        DESCRIPTION
                      	""
        ::= { globalDhcpRelay 7 }

        globalDhcpRelayRemoteIDData OBJECT-TYPE
        SYNTAX  DisplayString
        ACCESS  read-write
        STATUS  mandatory
        DESCRIPTION
                      	""
        ::= { globalDhcpRelay 8 }

--
	dhcpRelay OBJECT IDENTIFIER ::= { dhcpSetup 3 }

	 maxNumberOfDhcpRelay OBJECT-TYPE
        SYNTAX  INTEGER
        ACCESS  read-only
        STATUS  mandatory
        DESCRIPTION
                      	"The maximum number of DHCP relay entries that can be created. 
                      	A value of 0 for this object implies that there exists settings for 
                      	global DHCP relay."
        ::= { dhcpRelay 1 }
        
     maxNumberOfDhcpRelayRemoteServer OBJECT-TYPE
        SYNTAX  INTEGER
        ACCESS  read-only
        STATUS  mandatory
        DESCRIPTION
                      	""
        ::= { dhcpRelay 2 }
 
 -- dhcpRelayTable   
        
        dhcpRelayTable OBJECT-TYPE
        SYNTAX	SEQUENCE OF DhcpRelayEntry
        ACCESS  not-accessible
        STATUS  mandatory
        DESCRIPTION
                 	""
        ::= { dhcpRelay 3 }  	


	dhcpRelayEntry OBJECT-TYPE
        SYNTAX	DhcpRelayEntry
        ACCESS	not-accessible
        STATUS	mandatory
        DESCRIPTION    	"An entry in dhcpRelayTable."
        INDEX          	{ dhcpRelayVid }
        ::= { dhcpRelayTable 1 }

        DhcpRelayEntry ::=
           SEQUENCE {
        	dhcpRelayOption82Enable   EnabledStatus,
        	dhcpRelayInfoEnable       EnabledStatus,
        	dhcpRelayInfoData   DisplayString,
        	dhcpRelayRemoteIDEnable   EnabledStatus,
        	dhcpRelayRemoteIDData       DisplayString
           }

        dhcpRelayOption82Enable OBJECT-TYPE
        SYNTAX  EnabledStatus
        ACCESS  read-write
        STATUS  mandatory
        DESCRIPTION
                      	""
        ::= { dhcpRelayEntry 1 }

        dhcpRelayInfoEnable OBJECT-TYPE
        SYNTAX  EnabledStatus
        ACCESS  read-write
        STATUS  mandatory
        DESCRIPTION
                      	""
        ::= { dhcpRelayEntry 2 }

        dhcpRelayInfoData OBJECT-TYPE
        SYNTAX  DisplayString
        ACCESS  read-write
        STATUS  mandatory
        DESCRIPTION
                      	""
        ::= { dhcpRelayEntry 3 }
        
--- dhcp option82 remote id field
        dhcpRelayRemoteIDEnable OBJECT-TYPE
        SYNTAX  EnabledStatus
        ACCESS  read-write
        STATUS  mandatory
        DESCRIPTION
                      	""
        ::= { dhcpRelayEntry 4 }

        dhcpRelayRemoteIDData OBJECT-TYPE
        SYNTAX  DisplayString
        ACCESS  read-write
        STATUS  mandatory
        DESCRIPTION
                      	""
        ::= { dhcpRelayEntry 5 }

     -- dhcpRelayRemoteServerTable
        dhcpRelayRemoteServerTable OBJECT-TYPE
        SYNTAX	SEQUENCE OF DhcpRelayRemoteServerEntry
        ACCESS  not-accessible
        STATUS  mandatory
        DESCRIPTION
                 	""
        ::= { dhcpRelay 4 }
        
	dhcpRelayRemoteServerEntry OBJECT-TYPE
        SYNTAX	DhcpRelayRemoteServerEntry
        ACCESS	not-accessible
        STATUS	mandatory
        DESCRIPTION    	"An entry in dhcpRelayRemoteServerTable."
        INDEX          	{  dhcpRelayVid, dhcpRelayRemoteServerIp }
        ::= { dhcpRelayRemoteServerTable 1 }

        DhcpRelayRemoteServerEntry ::=
           SEQUENCE {
            dhcpRelayVid		          INTEGER,
           	dhcpRelayRemoteServerIp		IpAddress,
        	dhcpRelayRemoteServerRowStatus	RowStatus
           }

        dhcpRelayVid OBJECT-TYPE
        SYNTAX  INTEGER
        ACCESS  read-only
        STATUS  mandatory
        DESCRIPTION
                      	""
        ::= { dhcpRelayRemoteServerEntry 1 }   
        
        dhcpRelayRemoteServerIp OBJECT-TYPE
        SYNTAX  IpAddress
        ACCESS  read-only
        STATUS  mandatory
        DESCRIPTION
                      	""
        ::= { dhcpRelayRemoteServerEntry 2 }

        dhcpRelayRemoteServerRowStatus OBJECT-TYPE
        SYNTAX  RowStatus
        ACCESS  read-create
        STATUS  mandatory
        DESCRIPTION
                     	""
        ::= { dhcpRelayRemoteServerEntry 3 }

--  staticRouteSetup
	staticRouteSetup     	OBJECT IDENTIFIER ::= { ves1616pe54 21 }

        maxNumberOfStaticRoutes OBJECT-TYPE
        SYNTAX  INTEGER
        ACCESS  read-only
        STATUS  mandatory
        DESCRIPTION
                      	""
        ::= { staticRouteSetup 1 }

-- staticRouteTable
        staticRouteTable OBJECT-TYPE
        SYNTAX	SEQUENCE OF StaticRouteEntry
        ACCESS  not-accessible
        STATUS  mandatory
        DESCRIPTION
                 	""
        ::= { staticRouteSetup 2 }

	staticRouteEntry OBJECT-TYPE
        SYNTAX	StaticRouteEntry
        ACCESS	not-accessible
        STATUS	mandatory
        DESCRIPTION    	"An entry in staticRouteTable."
        INDEX          	{ staticRouteIp, staticRouteMask }
        ::= { staticRouteTable 1 }

        StaticRouteEntry ::=
           SEQUENCE {
           	staticRouteName		DisplayString,
        	staticRouteIp		IpAddress,
        	staticRouteMask		IpAddress,
        	staticRouteGateway	IpAddress,
        	staticRouteMetric	INTEGER,
        	staticRouteRowStatus	RowStatus
           }

        staticRouteName OBJECT-TYPE
        SYNTAX  DisplayString
        ACCESS  read-write
        STATUS  mandatory
        DESCRIPTION
                      	""
        ::= { staticRouteEntry 1 }

        staticRouteIp OBJECT-TYPE
        SYNTAX  IpAddress
        ACCESS  read-only
        STATUS  mandatory
        DESCRIPTION
                     	""
        ::= { staticRouteEntry 2 }

        staticRouteMask OBJECT-TYPE
        SYNTAX  IpAddress
        ACCESS  read-only
        STATUS  mandatory
        DESCRIPTION
                     	""
        ::= { staticRouteEntry 3 }

        staticRouteGateway OBJECT-TYPE
        SYNTAX  IpAddress
        ACCESS  read-write
        STATUS  mandatory
        DESCRIPTION
                     	""
        ::= { staticRouteEntry 4 }

        staticRouteMetric OBJECT-TYPE
        SYNTAX  INTEGER
        ACCESS  read-write
        STATUS  mandatory
        DESCRIPTION
                     	""
        ::= { staticRouteEntry 5 }

        staticRouteRowStatus OBJECT-TYPE
        SYNTAX  RowStatus
        ACCESS  read-create
        STATUS  mandatory
        DESCRIPTION
                     	""
        ::= { staticRouteEntry 6 }

--  arpInfo
	arpInfo     	OBJECT IDENTIFIER ::= { ves1616pe54 22 }

--  arpTable
      	arpTable	OBJECT-TYPE
        SYNTAX	SEQUENCE OF ArpEntry
        ACCESS  not-accessible
        STATUS  mandatory
        DESCRIPTION
                 	""
        ::= { arpInfo 1 }

		arpEntry OBJECT-TYPE
        SYNTAX	ArpEntry
        ACCESS	not-accessible
        STATUS	mandatory
        DESCRIPTION    	"An entry in arpTable."
        INDEX          	{ arpIpAddr, arpMacVid }
        ::= { arpTable 1 }

        ArpEntry ::=
           SEQUENCE {
           	arpIndex	INTEGER,
        	arpIpAddr	IpAddress,
        	arpMacAddr	MacAddress,
        	arpMacVid	INTEGER,
        	arpType		INTEGER
           }

        arpIndex OBJECT-TYPE
        SYNTAX  INTEGER
        ACCESS  read-only
        STATUS  mandatory
        DESCRIPTION
                      	""
        ::= { arpEntry 1 }

        arpIpAddr OBJECT-TYPE
        SYNTAX  IpAddress
        ACCESS  read-only
        STATUS  mandatory
        DESCRIPTION
                      	""
        ::= { arpEntry 2 }

        arpMacAddr OBJECT-TYPE
        SYNTAX  MacAddress
        ACCESS  read-only
        STATUS  mandatory
        DESCRIPTION
                      	""
        ::= { arpEntry 3 }

        arpMacVid OBJECT-TYPE
        SYNTAX  INTEGER
        ACCESS  read-only
        STATUS  mandatory
        DESCRIPTION
                      	""
        ::= { arpEntry 4 }

        arpType OBJECT-TYPE
        SYNTAX  INTEGER {
        	static(1),
        	dynamic(2)
        }
        ACCESS  read-only
        STATUS  mandatory
        DESCRIPTION
                      	"1-static, 2-dynamic"
        ::= { arpEntry 5 }

-- portOpModeSetup
	portOpModeSetup     	OBJECT IDENTIFIER ::= { ves1616pe54 24 }

-- portOpModePortTable

        portOpModePortTable  OBJECT-TYPE
        SYNTAX	SEQUENCE OF PortOpModePortEntry
        ACCESS  not-accessible
        STATUS  mandatory
        DESCRIPTION
                 	""
        ::= { portOpModeSetup 1 }

	portOpModePortEntry  OBJECT-TYPE
        SYNTAX	PortOpModePortEntry
        ACCESS	not-accessible
        STATUS	mandatory
        DESCRIPTION    	"An entry in portOpModePortTable."
        INDEX          	{ dot1dBasePort }
        ::= { portOpModePortTable 1 }

        PortOpModePortEntry ::=
           SEQUENCE {
        	portOpModePortSpeedDuplex	INTEGER,
        	portOpModePortFlowCntl	INTEGER,
        	portOpModePortName	OCTET STRING,
        	portOpModePortModuleType	INTEGER,
        	portOpModePortLinkUpType	INTEGER,
        	portOpModePortIntrusionLock	EnabledStatus,
        	portOpModePortLBTestSetup	INTEGER,
        	portOpModePortLBTestStatus	INTEGER,
        	portOpModePortSwCounterReset	INTEGER,
        	portOpModePortVdslCounterReset  INTEGER,
        	portOpModePortVdslStatus  		INTEGER,
        	portOpModePortVdslUptime	OCTET STRING
           }

        portOpModePortSpeedDuplex OBJECT-TYPE
        SYNTAX  INTEGER {
        	auto(0),
        	speed_10_half(1),
        	speed_10_full(2),
        	speed_100_half(3),
        	speed_100_full(4),
        	speed_1000_full(5)
        }
        ACCESS  read-write
        STATUS  mandatory
        DESCRIPTION
                      	""
        ::= { portOpModePortEntry 1 }

        portOpModePortFlowCntl OBJECT-TYPE
        SYNTAX  INTEGER {
        	off(0),
        	on(1)
        }
        ACCESS  read-write
        STATUS  mandatory
        DESCRIPTION
                     	""
        ::= { portOpModePortEntry 2 }

        portOpModePortName  OBJECT-TYPE
        SYNTAX  OCTET STRING (SIZE(0..9))
        ACCESS  read-write
        STATUS  mandatory
        DESCRIPTION
                      	""
        ::= { portOpModePortEntry 3 }

        portOpModePortModuleType  OBJECT-TYPE
        SYNTAX  INTEGER {
        	fast_ethernet_10_100(0),
        	gigabit_ethernet_100_1000(1)
        }
        ACCESS  read-only
        STATUS  mandatory
        DESCRIPTION
                      	""
        ::= { portOpModePortEntry 4 }

        portOpModePortLinkUpType  OBJECT-TYPE
        SYNTAX  INTEGER {
        	down(0),
        	copper(1),
        	fiber(2)
        }
        ACCESS  read-only
        STATUS  mandatory
        DESCRIPTION
                      	""
        ::= { portOpModePortEntry 5 }

	portOpModePortIntrusionLock OBJECT-TYPE
        SYNTAX  EnabledStatus
        ACCESS  read-write
        STATUS  mandatory
        DESCRIPTION
                      	""
        ::= { portOpModePortEntry 6 }

   portOpModePortLBTestSetup OBJECT-TYPE
        SYNTAX  INTEGER {
        	internal_loopback_test(1),
        	external_loopback_test(2),
        	vtur_to_vtuo_loopback(3)
        }
        ACCESS  read-write
        STATUS  mandatory
        DESCRIPTION
               "This entry display latest loopback test status of port while performing loopback test."
        ::= { portOpModePortEntry 7 }

   portOpModePortLBTestStatus OBJECT-TYPE
        SYNTAX  INTEGER {
        	none(0),
        	under_testing(1),
        	success(2),
        	fail(3)
        }
        ACCESS  read-only
        STATUS  mandatory
        DESCRIPTION
               "This entry display latest loopback test status of port while performing loopback test."
        ::= { portOpModePortEntry 8 }

	portOpModePortSwCounterReset OBJECT-TYPE
        SYNTAX  INTEGER {
        	enable(1),
        	disable(2)
        }
        ACCESS  read-write
        STATUS  mandatory
        DESCRIPTION
               "This entry resets port SW counter."
        ::= { portOpModePortEntry 9 }

    portOpModePortVdslCounterReset OBJECT-TYPE
        SYNTAX  INTEGER {
        	enable(1),
        	disable(2)
        }
        ACCESS  read-write
        STATUS  mandatory
        DESCRIPTION
               "This entry resets port VDSL counter."
        ::= { portOpModePortEntry 10 }  
     
     portOpModePortVdslStatus OBJECT-TYPE
        SYNTAX INTEGER {
        	idle(1),
        	standby(2),
        	showtime(3)
        }
        ACCESS  read-only
        STATUS  mandatory
        DESCRIPTION
               "This entry reports VDSL link current status."
        ::= { portOpModePortEntry 11 }  

     portOpModePortVdslUptime OBJECT-TYPE
        SYNTAX OCTET STRING
        ACCESS  read-only
        STATUS  mandatory
        DESCRIPTION
               "This entry reports VDSL link current link up time."
        ::= { portOpModePortEntry 12 }          

-- portOpModePortLBTable

        portOpModePortLBTable  OBJECT-TYPE
        SYNTAX	SEQUENCE OF PortOpModePortLBEntry
        ACCESS  not-accessible
        STATUS  mandatory
        DESCRIPTION
                 	""
        ::= { portOpModeSetup 2 }

	portOpModePortLBEntry  OBJECT-TYPE
        SYNTAX	PortOpModePortLBEntry
        ACCESS	not-accessible
        STATUS	mandatory
        DESCRIPTION    	"An entry in portOpModePortLBTable."
        INDEX          	{ dot1dBasePort }
        ::= { portOpModePortLBTable 1 }

        PortOpModePortLBEntry ::=
           SEQUENCE {
        	portOpModePortLBActive	INTEGER,
        	portOpModePortLBNumber	INTEGER,
        	portOpModePortLBCount	INTEGER,
        	portOpModePortLBPktSize	INTEGER
           }

        portOpModePortLBActive OBJECT-TYPE
        SYNTAX  INTEGER {
        	active(1)
        }
        ACCESS  read-write
        STATUS  mandatory
        DESCRIPTION
                      	""
        ::= { portOpModePortLBEntry 1 }

        portOpModePortLBNumber OBJECT-TYPE
        SYNTAX  INTEGER
        ACCESS  read-write
        STATUS  mandatory
        DESCRIPTION
                     	""
        ::= { portOpModePortLBEntry 2 }

        portOpModePortLBCount  OBJECT-TYPE
        SYNTAX  INTEGER
        ACCESS  read-write
        STATUS  mandatory
        DESCRIPTION
                      	""
        ::= { portOpModePortLBEntry 3 }

        portOpModePortLBPktSize  OBJECT-TYPE
        SYNTAX  INTEGER
        ACCESS  read-write
        STATUS  mandatory
        DESCRIPTION
                      	"Packet size range from 64 bytes to 1518 bytes"
        ::= { portOpModePortLBEntry 4 }


-- portOpModePortLBResultTable

        portOpModePortLBResultTable  OBJECT-TYPE
        SYNTAX	SEQUENCE OF PortOpModePortLBResultEntry
        ACCESS  not-accessible
        STATUS  mandatory
        DESCRIPTION
                 	""
        ::= { portOpModeSetup 3 }

	portOpModePortLBResultEntry  OBJECT-TYPE
        SYNTAX	PortOpModePortLBResultEntry
        ACCESS	not-accessible
        STATUS	mandatory
        DESCRIPTION    	"An entry in portOpModePortLBResultTable."
        INDEX          	{ dot1dBasePort }
        ::= { portOpModePortLBResultTable 1 }

        PortOpModePortLBResultEntry ::=
           SEQUENCE {
        	portOpModePortLBMaxRTT	INTEGER,
        	portOpModePortLBMinRTT	INTEGER,
        	portOpModePortLBAvgRTT	INTEGER,
        	portOpModePortLBPktLossRate	INTEGER,
        	portOpModePortLBStatus	INTEGER
           }

        portOpModePortLBMaxRTT OBJECT-TYPE
        SYNTAX  INTEGER
        ACCESS  read-only
        STATUS  mandatory
        DESCRIPTION
                      	""
        ::= { portOpModePortLBResultEntry 1 }

        portOpModePortLBMinRTT OBJECT-TYPE
        SYNTAX  INTEGER
        ACCESS  read-only
        STATUS  mandatory
        DESCRIPTION
                     	""
        ::= { portOpModePortLBResultEntry 2 }

        portOpModePortLBAvgRTT  OBJECT-TYPE
        SYNTAX  INTEGER
        ACCESS  read-only
        STATUS  mandatory
        DESCRIPTION
                      	""
        ::= { portOpModePortLBResultEntry 3 }

        portOpModePortLBPktLossRate  OBJECT-TYPE
        SYNTAX  INTEGER
        ACCESS  read-only
        STATUS  mandatory
        DESCRIPTION
                      	"Loopback Packet loss rate"
        ::= { portOpModePortLBResultEntry 4 }

        portOpModePortLBStatus OBJECT-TYPE
        SYNTAX  INTEGER {
        	idle(0),
        	in_progress(1),
        	complete(2)
        }
        ACCESS  read-only
        STATUS  mandatory
        DESCRIPTION
                      	""
        ::= { portOpModePortLBResultEntry 5 }


-- portBasedVlanSetup
	portBasedVlanSetup     	OBJECT IDENTIFIER ::= { ves1616pe54 25 }

-- portBasedVlanPortListTable

        portBasedVlanPortListTable  OBJECT-TYPE
        SYNTAX	SEQUENCE OF PortBasedVlanPortListEntry
        ACCESS  not-accessible
        STATUS  mandatory
        DESCRIPTION
                 	""
        ::= { portBasedVlanSetup 1 }

	portBasedVlanPortListEntry  OBJECT-TYPE
        SYNTAX	PortBasedVlanPortListEntry
        ACCESS	not-accessible
        STATUS	mandatory
        DESCRIPTION    	"An entry in portBasedVlanPortListTable."
        INDEX          	{ dot1dBasePort }
        ::= { portBasedVlanPortListTable 1 }

        PortBasedVlanPortListEntry ::=
           SEQUENCE {
        	portBasedVlanPortListMembers	OCTET STRING
           }

        portBasedVlanPortListMembers OBJECT-TYPE
        SYNTAX  PortList
        ACCESS  read-write
        STATUS  mandatory
        DESCRIPTION
                      	""
        ::= { portBasedVlanPortListEntry 1 }


--fault MIB
faultMIB MODULE-IDENTITY
    LAST-UPDATED "200411031200Z" -- YYYY/MM/DD, HH/MM
    ORGANIZATION "ZyXEL"
    CONTACT-INFO ""
    DESCRIPTION
            "Fault event table definitions"
    ::= { ves1616pe54 26 }


-- **************************************************************************
-- Local Textual Conventions
-- **************************************************************************

UtcTimeStamp ::= TEXTUAL-CONVENTION
    STATUS current
    DESCRIPTION
           "Universal Time Coordinated as a 32-bit value that designates
            the number of seconds since Jan 1, 1970 12:00AM."
    SYNTAX  Unsigned32

EventIdNumber ::= TEXTUAL-CONVENTION
   STATUS current
   DESCRIPTION
          "This textual convention describes the index that uniquely
           identifies a fault event type in the entire system. Every fault
           event type, e.g. link down, has a unique EventIdNumber."
   SYNTAX  Integer32

EventSeverity ::= TEXTUAL-CONVENTION
   STATUS current
   DESCRIPTION
          "This textual convention describes the severity of a fault event.
           The decreasing order of severity is shown in the textual
           convention."
   SYNTAX  INTEGER{
             critical (1),
             major (2),
             minor (3),
             informational (4)
           }

EventServiceAffective ::= TEXTUAL-CONVENTION
   STATUS current
   DESCRIPTION
          "This textual convention indicates whether an event is immediately
           service affecting or not."
   SYNTAX  INTEGER{
   	     noServiceAffected (1),
	     serviceAffected (2)
           }


InstanceType ::= TEXTUAL-CONVENTION
    STATUS current
    DESCRIPTION
           "This textual convention describes the type of an instanceId
            associated with each event and by that means specifies how
            the instanceId variable should be intepreted.

            Various instanceId types are specified below to enable fault
            monitoring for different kind of devices from fixed
            configuration pizza boxes to multi chassis nodes. All
            instanceId types may not need to be used in every device
            type.

            Note also that instanceId semantics are element type dependent
            (e.g. different kind of interface naming conventions may be used)
            and thus instanceId usage may vary from element to element.

    =========================================================================
    Type            Description                                 Example form
                                                                of InstanceId
    =========================================================================
    unknown    (1)  unknown type                               - Irrelevant-
    -------------------------------------------------------------------------
    node       (2)  Associated with events originating from          1
                    the node. Used for general events that     (Node number)
                    can not be associated with any specific
                    block. InstanceId value 1 is used for
                    single node equipment.
    -------------------------------------------------------------------------
    shelf      (3)  Associated with events originating from          1
                    the shelf. In the case of fixed       	(shelf number)
                    configuration devices this type is used
                    for events that are associated with the
                    physical enclosure, e.g. faults related
                    to fan etc. InstanceId value 1 is used
                    for single self equipment.
    -------------------------------------------------------------------------
    line       (4)  Associated with events originating from
                    physical interfaces or associated
                    components such as line cards.
                    InstanceId usage examples for faults
                    originating from:
                    - Physical port: Simply port number, e.g. .......1
    -------------------------------------------------------------------------
    switch     (5)  Associated with events originating from          1
                    from a switch chip or a switch card.      (switch number)
                    For single switch equipment InstanceId
                    value 1 is used, for multi swich nodes
                    InstanceId semantics if for further
                    study.
    -------------------------------------------------------------------------
    lsp        (6)  Associated with events originating from          1
                    a particular lsp.                           (lsp index)
                    NOTE: In this case the InstanceName
                    contains the lsp name and InstanceId
                    contains lsp index.
    -------------------------------------------------------------------------
    l2Interface(7)  Associated with events originating from        - TBD -
                    a particular layer 2 interface. Used for
                    layer 2 related events such as L2 control
                    protocol faults. InstanceId semantics is
                    for further study.
    -------------------------------------------------------------------------
    l3Interface(8)  Associated with events originating from        - TBD -
                    a particular layer 3 interface. Used for
                    layer 3 related events such as L3 control
                    protocol faults. InstanceId semantics is
                    for further study.
    -------------------------------------------------------------------------
    rowIndex  (9)   Associated with events reporting about a
                    'logical' or conceptual table that consists
                    of rows.  The Instance Id is the index/key
                    for a row in the table.  The format of the
                    Instance Id will simply be a series of decimal
                    numbers seperated by a '.':
    ========================================================================="

    SYNTAX  INTEGER {
              unknown (1),
              node (2),
              shelf (3),
              line (4),
              switch (5),
              lsp (6),
              l2Interface(7),
              l3Interface(8),
              rowIndex(9)
            }


-- *****************************************************************************
-- Top level structure of this MIB.
-- *****************************************************************************

eventObjects        OBJECT IDENTIFIER ::= { faultMIB  1 }


-- *****************************************************************************
-- Event Table
--
-- Event table reports all currently active fault events. Only normal type of
-- faults (i.e. faults that are not automatically and immediately cleared) are
-- present in the event table. Delta faults (i.e. faults that are automatically
-- cleared) are reported only by using trap messages.
-- *****************************************************************************

eventTable OBJECT-TYPE
    SYNTAX      SEQUENCE OF EventEntry
    MAX-ACCESS  not-accessible
    STATUS      current
    DESCRIPTION
            "A list of currently active fault events. All faults
             of normal type regardless of their severity level
             are recorded in the event table. When a normal
             type fault is cleared it is deleted from the event
             table."
    ::= { eventObjects 1 }

eventEntry OBJECT-TYPE
    SYNTAX      EventEntry
    MAX-ACCESS  not-accessible
    STATUS      current
    DESCRIPTION
            "An entry containing information about an
             event in the event table."
    INDEX   { eventSeqNum }
    ::= { eventTable 1 }

EventEntry ::=
    SEQUENCE {
      eventSeqNum           Integer32,
      eventEventId          EventIdNumber,
      eventName             DisplayString,
      eventInstanceType     InstanceType,
      eventInstanceId       DisplayString,
      eventInstanceName     DisplayString,
      eventSeverity         EventSeverity,
      eventSetTime          UtcTimeStamp,
      eventDescription      DisplayString,
      eventServAffective    EventServiceAffective, 
      eventInstanceIdNumber Integer32 
   }

eventSeqNum OBJECT-TYPE
    SYNTAX      Integer32
    MAX-ACCESS  read-only
    STATUS      current
    DESCRIPTION
            "This variable represents the sequence number of an event.
             Sequence number is incremented monotonically starting
             from 0 until it reaches its maximum and wraps around back
             to 0.

             Sequence number is incremented when
             - the state of a normal type fault is set on (the same sequence
             number is present in the events table as well as in the trap
             that is sent to notify about the fault on event)
             - delta event occurs (sequence number present in trap message)
             - the state of a normal type fault is set off (sequence number
             present in trap that is sent to notify for clearing)."
    ::= { eventEntry 1 }

eventEventId OBJECT-TYPE
    SYNTAX      EventIdNumber
    MAX-ACCESS  read-only
    STATUS      current
    DESCRIPTION
            "This variable represents the event ID which uniquely
             identifies the event in the entire system."
    ::= { eventEntry 2 }

eventName OBJECT-TYPE
    SYNTAX      DisplayString (SIZE (0..40))
    MAX-ACCESS  read-only
    STATUS      current
    DESCRIPTION
            "This variable represents the name of the event, for
             example 'Ethernet Link Down'"
    ::= { eventEntry 3 }

eventInstanceType OBJECT-TYPE
    SYNTAX      InstanceType
    MAX-ACCESS  read-only
    STATUS      current
    DESCRIPTION
            "This variable represents the type of InstanceId of a
             particular event in the event table. In brief
             the instanceType refers to the type of sub-component
             generating this event in the system, for example
             switch (5). For more details see the textual
             conventions section.

             AFFECTS:   eventInstanceId,
                        eventInstanceName"
    ::= { eventEntry 4 }

eventInstanceId OBJECT-TYPE
    SYNTAX  DisplayString
    MAX-ACCESS  read-only
    STATUS      current
    DESCRIPTION
            "This variable represents the InstanceId of a particular
             event in the event current table. In brief the instanceId
             refers to the sub-component generating this event in the
             system, for example '1' for port 1. For more details see
             the textual conventions section.

             DEPENDS ON:  eventInstanceType"
    ::= { eventEntry 5 }

eventInstanceName OBJECT-TYPE
    SYNTAX      DisplayString
    MAX-ACCESS  read-only
    STATUS      current
    DESCRIPTION
            "This variable is mainly used to store additional information
             about the sub-component that is generating an event. For
             example this field may specify what cooling fan is faulty.

             DEPENDS ON:  eventInstanceType"
    ::= { eventEntry 6 }

eventSeverity OBJECT-TYPE
    SYNTAX      EventSeverity
    MAX-ACCESS  read-only
    STATUS      current
    DESCRIPTION
            "This variable dictates the urgency of action when a event
             occurs. There are four severity levels - Critical, Major,
             Minor, and Informational.  Critical events are those, which
             require immediate operator intervention to prevent/reduce
             system down time. Major events require quick attention and
             Minor events possibly require some attention. Informational
             events indicate the occurrence of events that may need to be
             investigated."
    ::= { eventEntry 7 }

eventSetTime OBJECT-TYPE
    SYNTAX      UtcTimeStamp
    MAX-ACCESS  read-only
    STATUS      current
    DESCRIPTION
            "This table contains only normal events and this variable
             represents the time when the event become active, i.e. the
             number of seconds since Jan 1, 1970 12:00AM."
    ::= { eventEntry 8 }


eventDescription OBJECT-TYPE
    SYNTAX      DisplayString (SIZE (0..255))
    MAX-ACCESS  read-only
    STATUS      current
    DESCRIPTION
            "This variable contains a description of the event and reasons
             behind the event. This is a free format alpha-numeric string
             that is set by the entity generating this event. This variable
             may be empty if there is no usefull information to report.
             The maximum length of this string is 255 characters."
    ::= { eventEntry 9 }

eventServAffective OBJECT-TYPE
    SYNTAX      EventServiceAffective
    MAX-ACCESS  read-only
    STATUS      current
    DESCRIPTION
            "This variable indicates whether the event is service affective or not"
    ::= { eventEntry 10 }

eventInstanceIdNumber OBJECT-TYPE
    SYNTAX  Integer32
    MAX-ACCESS  read-only
    STATUS      current
    DESCRIPTION
            "This variable represents the InstanceId of a particular 
             event in the event current table. In brief the instanceId 
             refers to the sub-component generating this event in the 
             system, for example '1' for port 1. For more details see 
             the textual conventions section.

             DEPENDS ON:  eventInstanceType"
    ::= { eventEntry 11 }


-- fault Trap MIB
faultTrapsMIB MODULE-IDENTITY
    LAST-UPDATED "200411011200Z" -- YYYY/MM/DD, HH/MM
    ORGANIZATION "ZyXEL"
    CONTACT-INFO ""
    DESCRIPTION
            "Fault event trap definitions"
    ::= { ves1616pe54 27 }

trapInfoObjects             OBJECT IDENTIFIER ::= { faultTrapsMIB 1}
trapNotifications           OBJECT IDENTIFIER ::= { faultTrapsMIB 2}


-- **************************************************************************
-- Local Textual Conventions
-- **************************************************************************

EventPersistence ::= TEXTUAL-CONVENTION
   STATUS current
   DESCRIPTION
          "This textual convention indicates whether the event is delta
           (automatically and immediately cleared) or normal (not
           automatically cleared)."
   SYNTAX  INTEGER{
   	     normal (1),
	     delta (2)
           }


-- **************************************************************************
-- Trap information object definitions
-- **************************************************************************

trapRefSeqNum OBJECT-TYPE
    SYNTAX      Integer32
    MAX-ACCESS  read-only
    STATUS      current
    DESCRIPTION
            "Indicates the former sequence number of a cleared event
             in the event table. Not intended to read but only used in
             trap notifications."
    ::= { trapInfoObjects 1 }

trapPersistence OBJECT-TYPE
    SYNTAX      EventPersistence
    MAX-ACCESS  read-only
    STATUS      current
    DESCRIPTION
            "Indicates whether the event is delta (automatically and
             immediately cleared) or normal (not automatically cleared).
             Not intended to read but only used in trap notifications."
    ::= { trapInfoObjects 2 }

trapSenderNodeId OBJECT-TYPE
    SYNTAX      Integer32
    MAX-ACCESS  read-only
    STATUS      current
    DESCRIPTION
            "Represents the node ID of the sending network element. If not
             supported should be set to 0. Not intended to read but only
             used in trap notifications."
    ::= { trapInfoObjects 3 }

trapSenderStatus OBJECT-TYPE
    SYNTAX      Integer32
    MAX-ACCESS  read-only
    STATUS      current
    DESCRIPTION
            "Represents the trap status. 0 means cleared, 1 means happened."
    ::= { trapInfoObjects 4 }
    


-- ***************************************************************************
-- Trap definitions
-- ***************************************************************************

eventOnTrap NOTIFICATION-TYPE
         OBJECTS {
                  eventSeqNum,
                  eventEventId,
                  eventName,
                  eventSetTime,
                  eventSeverity,
                  eventInstanceType,
                  eventInstanceId,
                  eventInstanceName,
                  eventServAffective,
                  eventDescription,
                  eventInstanceIdNumber,
                  trapPersistence,
                  trapSenderNodeId,
                  trapSenderStatus,                   
                  sysObjectID}
         STATUS current
         DESCRIPTION
           "This trap is used to inform network management system that a delta
           fault event (events that are automatically cleared) has occured
           or a normal fault event (not automatically cleared) state has
           been set on.

           Objects are used as follows:
           - eventSeqNum is the sequence number of the event. For normal
           type of events must equal to the sequence number of the event
           in the events table.
           - eventEventId specifies what fault event has occured.
           - eventName specifies the name of the fault event.
           - eventSetTime indicates when fault event has occured
           (delta events) or when fault has been set on (normal events).
           - eventSeverity reports the severity level of the event.
           - eventInstanceType indicates what kind of object is faulty.
           - eventInstanceId specifies what instance is faulty.
           - eventInstanceName may contain textual description for
           the faulty object.
           - eventServAffective specifies whether the event is
           immediately service affcetive.
           - eventDescription reports possible additional information about the event.
           - trapPersistence tells whether this event is a delta or normal event.
           - trapSenderNodeId specifies the node ID of the sending network element if
           configuring it is supported for the network element, otherwise 0.
           - trapSenderStatus specifes the trap status. 
           - sysObjectID specifies what kind of equipment reports the fault event.

           For more information see the eventTable specification"
         ::= { trapNotifications 1 }

eventClearedTrap NOTIFICATION-TYPE
         OBJECTS {
                  eventSeqNum,
                  eventEventId,
                  eventSetTime,
                  eventInstanceType,
                  eventInstanceId,
                  eventInstanceIdNumber,
                  trapRefSeqNum,
                  trapSenderNodeId,
                  trapSenderStatus,
                  sysObjectID}
         STATUS current
         DESCRIPTION
           "This trap is used to inform network management system that a normal
           type fault event has been cleared (state set off).

           Objects are used as follows:
           - eventSeqNum is the sequence number of the this clearing event. Note that
           the sequence number of the cleared event is reported in the trapRefSeqNum
           object.
           - eventEventId specifies what event has been cleared.
           - eventSetTime indicates when fault event has been cleared.
           - eventInstanceType indicates what kind of object has been
           faulty.
           - eventInstanceId specifies what instance has been faulty.
           - trapRefSeqNum specifies the sequence number of the cleared event (i.e.
           the sequence number was assigned for the event in the events table).
           - trapSenderNodeId specifies the node ID of the sending network element if
           configuring it is supported for the network element, otherwise 0.
           - sysObjectID specifies what kind of equipment reports the clearing event.

           For more information see the eventTable specification"
         ::= { trapNotifications 2 }




--  multicastPortSetup
	multicastPortSetup     	OBJECT IDENTIFIER ::= { ves1616pe54 28 }

        multicastPortTable	OBJECT-TYPE
        SYNTAX	SEQUENCE OF MulticastPortEntry
        ACCESS  not-accessible
        STATUS  mandatory
        DESCRIPTION
                 	""
        ::= { multicastPortSetup 1 }

	multicastPortEntry OBJECT-TYPE
        SYNTAX	MulticastPortEntry
        ACCESS	not-accessible
        STATUS	mandatory
        DESCRIPTION    	"An entry in multicastPortTable."
        INDEX          	{ dot1dBasePort }
        ::= { multicastPortTable 1 }

        MulticastPortEntry ::=
	SEQUENCE {
        	multicastPortImmediateLeave		EnabledStatus,
        	multicastPortMaxGroupLimited		EnabledStatus,
        	multicastPortMaxOfGroup			INTEGER,
        	multicastPortIgmpFilteringProfile	DisplayString,
        	multicastPortQueryMode			INTEGER,
		igmpMsgMaxLimited			EnabledStatus,        	
        	igmpMsgLimit				INTEGER
        }

        multicastPortImmediateLeave OBJECT-TYPE
        SYNTAX  EnabledStatus
        ACCESS  read-write
        STATUS  mandatory
        DESCRIPTION
                      	""
        ::= { multicastPortEntry 1 }

        multicastPortMaxGroupLimited OBJECT-TYPE
        SYNTAX  EnabledStatus
        ACCESS  read-write
        STATUS  mandatory
        DESCRIPTION
                      	""
        ::= { multicastPortEntry 2 }

        multicastPortMaxOfGroup OBJECT-TYPE
        SYNTAX  INTEGER
        ACCESS  read-write
        STATUS  mandatory
        DESCRIPTION
                      	"0..255"
        ::= { multicastPortEntry 3 }

        multicastPortIgmpFilteringProfile OBJECT-TYPE
        SYNTAX  DisplayString
        ACCESS  read-write
        STATUS  mandatory
        DESCRIPTION
                      	""
        ::= { multicastPortEntry 4 }
        
        
        multicastPortQueryMode OBJECT-TYPE
        SYNTAX  INTEGER {
        	auto_mode(1),
        	fix_mode(2),
        	edge_mode(3)
        }
        ACCESS  read-write
        STATUS  mandatory
        DESCRIPTION
                      	"Specify query mode for each port"
        ::= { multicastPortEntry 5 }

        igmpMsgMaxLimited OBJECT-TYPE
        SYNTAX  EnabledStatus
        ACCESS  read-write
        STATUS  mandatory
        DESCRIPTION
                      	""
        ::= { multicastPortEntry 6 }

        igmpMsgLimit OBJECT-TYPE
        SYNTAX  INTEGER
        ACCESS  read-write
        STATUS  mandatory
        DESCRIPTION
                      	"0..255"
        ::= { multicastPortEntry 7 }        

-- multicastStatus
	multicastStatus    	OBJECT IDENTIFIER ::= { ves1616pe54 29 }

        multicastStatusTable	OBJECT-TYPE
        SYNTAX	SEQUENCE OF MulticastStatusEntry
        ACCESS  not-accessible
        STATUS  mandatory
        DESCRIPTION
                 	""
        ::= { multicastStatus 1 }

	multicastStatusEntry OBJECT-TYPE
        SYNTAX	MulticastStatusEntry
        ACCESS	not-accessible
        STATUS	mandatory
        DESCRIPTION    	"An entry in multicastStatusTable."
        INDEX          	{ multicastStatusVlanID, multicastStatusPort, multicastStatusGroup }
        ::= { multicastStatusTable 1 }

        MulticastStatusEntry ::=
	SEQUENCE {
        	multicastStatusIndex    INTEGER,
        	multicastStatusVlanID	INTEGER,
        	multicastStatusPort	INTEGER,
        	multicastStatusGroup	IpAddress,
        	multicastStatusJoinCounter    INTEGER,
        	multicastStatusLeaveCounter    INTEGER
         }

        multicastStatusIndex OBJECT-TYPE
        SYNTAX  INTEGER
        ACCESS  read-only
        STATUS  mandatory
        DESCRIPTION
                      	""
        ::= { multicastStatusEntry 1 }

        multicastStatusVlanID OBJECT-TYPE
        SYNTAX  INTEGER
        ACCESS  read-only
        STATUS  mandatory
        DESCRIPTION
                      	""
        ::= { multicastStatusEntry 2 }

        multicastStatusPort OBJECT-TYPE
        SYNTAX  INTEGER
        ACCESS  read-only
        STATUS  mandatory
        DESCRIPTION
                      	""
        ::= { multicastStatusEntry 3 }

        multicastStatusGroup OBJECT-TYPE
        SYNTAX  IpAddress
        ACCESS  read-only
        STATUS  mandatory
        DESCRIPTION
                      	""
        ::= { multicastStatusEntry 4 }

        multicastStatusJoinCounter OBJECT-TYPE
        SYNTAX  INTEGER
        ACCESS  read-only
        STATUS  mandatory
        DESCRIPTION
                      	""
        ::= { multicastStatusEntry 5 }
        
        multicastStatusLeaveCounter OBJECT-TYPE
        SYNTAX  INTEGER
        ACCESS  read-only
        STATUS  mandatory
        DESCRIPTION
                      	""
        ::= { multicastStatusEntry 6 }        

        igmpCountTable	OBJECT-TYPE
        SYNTAX	SEQUENCE OF IgmpCountEntry
        ACCESS  not-accessible
        STATUS  mandatory
        DESCRIPTION
                 	"A count table of igmp query/report/leave message."
        ::= { multicastStatus 2 }    
             
-- igmpCountStatus    
	igmpCountEntry OBJECT-TYPE
        SYNTAX	IgmpCountEntry
        ACCESS	not-accessible
        STATUS	mandatory
        DESCRIPTION    	"An entry in igmpCountTable."
        INDEX          	{ igmpCountIndex }
        ::= { igmpCountTable 1 }

        IgmpCountEntry ::=
		SEQUENCE {
        	igmpCountIndex    		INTEGER,
        	igmpCountInQuery		INTEGER,
        	igmpCountInReport		INTEGER,
        	igmpCountInLeave		INTEGER,        	
        	igmpCountInQueryDrop   	INTEGER,
        	igmpCountInReportDrop   INTEGER,
        	igmpCountInLeaveDrop   	INTEGER,
        	igmpCountOutQuery   	INTEGER,
        	igmpCountOutReport   	INTEGER,
        	igmpCountOutLeave   	INTEGER
        }

        igmpCountIndex OBJECT-TYPE
        SYNTAX  INTEGER
        ACCESS  read-only
        STATUS  mandatory
        DESCRIPTION
                      	"Index of IgmpCountEntry. 0 means total count in whole system"
        ::= { igmpCountEntry 1 }

        igmpCountInQuery OBJECT-TYPE
        SYNTAX  INTEGER
        ACCESS  read-only
        STATUS  mandatory
        DESCRIPTION
                      	""
        ::= { igmpCountEntry 2 }

        igmpCountInReport OBJECT-TYPE
        SYNTAX  INTEGER
        ACCESS  read-only
        STATUS  mandatory
        DESCRIPTION
                      	""
        ::= { igmpCountEntry 3 }

        igmpCountInLeave OBJECT-TYPE
        SYNTAX  INTEGER
        ACCESS  read-only
        STATUS  mandatory
        DESCRIPTION
                      	""
        ::= { igmpCountEntry 4 }
        
        igmpCountInQueryDrop OBJECT-TYPE
        SYNTAX  INTEGER
        ACCESS  read-only
        STATUS  mandatory
        DESCRIPTION
                      	""
        ::= { igmpCountEntry 5 }
        
        igmpCountInReportDrop OBJECT-TYPE
        SYNTAX  INTEGER
        ACCESS  read-only
        STATUS  mandatory
        DESCRIPTION
                      	""
        ::= { igmpCountEntry 6 }        
        
        igmpCountInLeaveDrop OBJECT-TYPE
        SYNTAX  INTEGER
        ACCESS  read-only
        STATUS  mandatory
        DESCRIPTION
                      	""
        ::= { igmpCountEntry 7 }                

        igmpCountOutQuery OBJECT-TYPE
        SYNTAX  INTEGER
        ACCESS  read-only
        STATUS  mandatory
        DESCRIPTION
                      	""
        ::= { igmpCountEntry 8 }                
        
        igmpCountOutReport OBJECT-TYPE
        SYNTAX  INTEGER
        ACCESS  read-only
        STATUS  mandatory
        DESCRIPTION
                      	""
        ::= { igmpCountEntry 9 }          

        igmpCountOutLeave OBJECT-TYPE
        SYNTAX  INTEGER
        ACCESS  read-only
        STATUS  mandatory
        DESCRIPTION
                      	""
        ::= { igmpCountEntry 10 }     

       multicastVlanStatusTable	OBJECT-TYPE
        SYNTAX	SEQUENCE OF MulticastVlanStatusEntry
        ACCESS  not-accessible
        STATUS  mandatory
        DESCRIPTION
                 	""
        ::= { multicastStatus 3 }

-- multicastVlanStatusTable
	multicastVlanStatusEntry OBJECT-TYPE
        SYNTAX	MulticastVlanStatusEntry
        ACCESS	not-accessible
        STATUS	mandatory
        DESCRIPTION    	"An entry in multicastVlanStatusTable."
        INDEX          	{ multicastVlanStatusVlanID }
        ::= { multicastVlanStatusTable 1 }

        MulticastVlanStatusEntry ::=
	SEQUENCE {
        	multicastVlanStatusVlanID    INTEGER,
        	multicastVlanStatusType	INTEGER,
        	multicastVlanQueryPort	PortList,
        	multicastVlanQuerySrcIp	IpAddress
         }

        multicastVlanStatusVlanID OBJECT-TYPE
        SYNTAX  INTEGER
        ACCESS  read-only
        STATUS  mandatory
        DESCRIPTION
                      	""
        ::= { multicastVlanStatusEntry 1 }

        multicastVlanStatusType OBJECT-TYPE
        SYNTAX  INTEGER {
			dynamic(1),
			mvr (2),
			static(3)
        }
        ACCESS  read-only
        STATUS  mandatory
        DESCRIPTION
                      	""
        ::= { multicastVlanStatusEntry 2 }

        multicastVlanQueryPort OBJECT-TYPE
        SYNTAX  PortList
        ACCESS  read-only
        STATUS  mandatory
        DESCRIPTION
                      	""
        ::= { multicastVlanStatusEntry 3 }
        
        multicastVlanQuerySrcIp OBJECT-TYPE
        SYNTAX  IpAddress
        ACCESS  read-only
        STATUS  mandatory
        DESCRIPTION
                      	""
        ::= { multicastVlanStatusEntry 4 }

-- igmpCounterPortTable

        igmpCounterPortTable OBJECT-TYPE
        SYNTAX	SEQUENCE OF IgmpCounterPortEntry
        ACCESS  not-accessible
        STATUS  mandatory
        DESCRIPTION
                 	""
        ::= { multicastStatus 4 }

	igmpCounterPortEntry OBJECT-TYPE
        SYNTAX	IgmpCounterPortEntry
        ACCESS	not-accessible
        STATUS	mandatory
        DESCRIPTION    	"An entry in igmpCounterPortTable."
        INDEX          	{ dot1dBasePort }
        ::= { igmpCounterPortTable 1 }

        IgmpCounterPortEntry ::=
           SEQUENCE {
        	igmpCounterPortJoin		Counter32,
		igmpCounterPortLeave		Counter32,
		igmpCounterPortActiveGroup	INTEGER,
		igmpCounterPortQuery		Counter32
           }

        igmpCounterPortJoin OBJECT-TYPE
        SYNTAX  Counter32
        ACCESS  read-only
        STATUS  mandatory
        DESCRIPTION
                      	"Join counter for the port."
        ::= { igmpCounterPortEntry 1 }

        igmpCounterPortLeave OBJECT-TYPE
        SYNTAX  Counter32
        ACCESS  read-only
        STATUS  mandatory
        DESCRIPTION
                      	"Leave counter for the port."
        ::= { igmpCounterPortEntry 2 }

        igmpCounterPortActiveGroup OBJECT-TYPE
        SYNTAX  INTEGER
        ACCESS  read-only
        STATUS  mandatory
        DESCRIPTION
                      	"Current active group for the port"
        ::= { igmpCounterPortEntry 3 }
 
        igmpCounterPortQuery OBJECT-TYPE
        SYNTAX  Counter32
        ACCESS  read-only
        STATUS  mandatory
        DESCRIPTION
                      	"Query counter for the port."
        ::= { igmpCounterPortEntry 4 } 
------------------------------------------
--  igmp counters for specific vid
-- igmpCounterVlanTable

        igmpCounterVlanTable OBJECT-TYPE
        SYNTAX	SEQUENCE OF IgmpCounterVlanEntry
        ACCESS  not-accessible
        STATUS  mandatory
        DESCRIPTION
                 	""
        ::= { multicastStatus 5 }

	igmpCounterVlanEntry OBJECT-TYPE
        SYNTAX	IgmpCounterVlanEntry
        ACCESS	not-accessible
        STATUS	mandatory
        DESCRIPTION    	"An entry in igmpCounterVlanTable."
        INDEX          	{ dot1qVlanIndex  }
        ::= { igmpCounterVlanTable 1 }

        IgmpCounterVlanEntry ::=
           SEQUENCE {
        	igmpCounterVlanJoin		Counter32,
		igmpCounterVlanLeave		Counter32,
		igmpCounterVlanActiveGroup	INTEGER,
		igmpCounterVlanQuery		Counter32
           }

        igmpCounterVlanJoin OBJECT-TYPE
        SYNTAX  Counter32
        ACCESS  read-only
        STATUS  mandatory
        DESCRIPTION
                      	"Join counter for the Vlan."
        ::= { igmpCounterVlanEntry 1 }

        igmpCounterVlanLeave OBJECT-TYPE
        SYNTAX  Counter32
        ACCESS  read-only
        STATUS  mandatory
        DESCRIPTION
                      	"Leave counter for the Vlan."
        ::= { igmpCounterVlanEntry 2 }

        igmpCounterVlanActiveGroup OBJECT-TYPE
        SYNTAX  INTEGER
        ACCESS  read-only
        STATUS  mandatory
        DESCRIPTION
                      	"Current active group for the Vlan"
        ::= { igmpCounterVlanEntry 3 }
 
        igmpCounterVlanQuery OBJECT-TYPE
        SYNTAX  Counter32
        ACCESS  read-only
        STATUS  mandatory
        DESCRIPTION
                      	"Query counter for the Vlan."
        ::= { igmpCounterVlanEntry 4 }
 
        multicastCurrentGroupStatusTable	OBJECT-TYPE
        SYNTAX	SEQUENCE OF MulticastCurrentGroupStatusEntry
        ACCESS  not-accessible
        STATUS  mandatory
        DESCRIPTION
                 	""
        ::= { multicastStatus 6 }
             
	multicastCurrentGroupStatusEntry OBJECT-TYPE
        SYNTAX	MulticastCurrentGroupStatusEntry
        ACCESS	not-accessible
        STATUS	mandatory
        DESCRIPTION    	"An entry in multicastCurrentGroupStatusTable."
        INDEX          	{ multicastStatusVlanID, multicastStatusGroup }
        ::= { multicastCurrentGroupStatusTable 1 }

        MulticastCurrentGroupStatusEntry ::=
	SEQUENCE {
        	multicastCurrentNumberOfActivePort    INTEGER
         }

        multicastCurrentNumberOfActivePort OBJECT-TYPE
        SYNTAX  INTEGER
        ACCESS  read-only
        STATUS  mandatory
        DESCRIPTION
                      	"Current number Of active port."
        ::= { multicastCurrentGroupStatusEntry 1 }

-- multicastClientSrcIp

        multicastClientSrcIpTable	OBJECT-TYPE
        SYNTAX	SEQUENCE OF MulticastClientSrcIpEntry
        ACCESS  not-accessible
        STATUS  mandatory
        DESCRIPTION
                 	""
        ::= { multicastStatus 7 }
               
	multicastClientSrcIpEntry OBJECT-TYPE
        SYNTAX	MulticastClientSrcIpEntry
        ACCESS	not-accessible
        STATUS	mandatory
        DESCRIPTION    	"An entry in multicastClientSrcIpTable."
        INDEX          	{ multicastStatusVlanID, multicastStatusPort, multicastStatusGroup, multicastClientSrcIpIndex }
        ::= { multicastClientSrcIpTable 1 }

        MulticastClientSrcIpEntry ::=
	SEQUENCE {
        	multicastClientSrcIpIndex    INTEGER,
        	multicastClientSrcIpAddress	IpAddress
         }

        multicastClientSrcIpIndex OBJECT-TYPE
        SYNTAX  INTEGER
        ACCESS  read-only
        STATUS  mandatory
        DESCRIPTION
                      	""
        ::= { multicastClientSrcIpEntry 1 }

        multicastClientSrcIpAddress OBJECT-TYPE
        SYNTAX  IpAddress
        ACCESS  read-only
        STATUS  mandatory
        DESCRIPTION
                      	""
        ::= { multicastClientSrcIpEntry 2 }
        
-- mgmdStatusTable

        mgmdStatusTable	OBJECT-TYPE
        SYNTAX	SEQUENCE OF MGMDStatusEntry
        ACCESS  not-accessible
        STATUS  mandatory
        DESCRIPTION
                 	""
        ::= { multicastStatus 8 }   
             
	mgmdStatusEntry OBJECT-TYPE
        SYNTAX	MGMDStatusEntry
        ACCESS	not-accessible
        STATUS	mandatory
        DESCRIPTION    	"An entry in mgmdStatusTable."
        INDEX          	{ mgmdStatusVlanID, mgmdStatusPort, mgmdStatusGroupAddressType, mgmdStatusGroupAddress }
        ::= { mgmdStatusTable 1 }

        MGMDStatusEntry ::=
	SEQUENCE {
        	mgmdStatusIndex			INTEGER,
        	mgmdStatusVlanID		INTEGER,
        	mgmdStatusPort			INTEGER,
    		mgmdStatusGroupAddressType	InetAddressType,
   		mgmdStatusGroupAddress		InetAddress ,
   		mgmdStatusGroupFilterMode	INTEGER
         }

        mgmdStatusIndex OBJECT-TYPE
        SYNTAX  INTEGER
        ACCESS  read-only
        STATUS  mandatory
        DESCRIPTION
                      	""
        ::= { mgmdStatusEntry 1 }

        mgmdStatusVlanID OBJECT-TYPE
        SYNTAX  INTEGER
        ACCESS  read-only
        STATUS  mandatory
        DESCRIPTION
                      	""
        ::= { mgmdStatusEntry 2 }

        mgmdStatusPort OBJECT-TYPE
        SYNTAX  INTEGER
        ACCESS  read-only
        STATUS  mandatory
        DESCRIPTION
                      	""
        ::= { mgmdStatusEntry 3 }
        
        mgmdStatusGroupAddressType OBJECT-TYPE
        SYNTAX  InetAddressType { ipv4(1), ipv6(2) }
        ACCESS  read-only
        STATUS  mandatory
        DESCRIPTION
              "The address type of the mgmdStatusGroupAddress entry."
        ::= { mgmdStatusEntry 4 }
        
        mgmdStatusGroupAddress OBJECT-TYPE
        SYNTAX  InetAddress (SIZE(4|16))
        ACCESS  read-only
        STATUS  mandatory
        DESCRIPTION
                      	""
        ::= { mgmdStatusEntry 5 }
        
 	mgmdStatusGroupFilterMode OBJECT-TYPE
    	SYNTAX     INTEGER {include (1),exclude (2) }
	MAX-ACCESS read-only
	STATUS     mandatory
	DESCRIPTION
            "The current cache state, applicable to MGMDv3-compatible
            nodes.  The value indicates whether the state is INCLUDE or
            EXCLUDE."

	::= { mgmdStatusEntry 6 }
	
-- mgmdCountTable    
        mgmdCountTable	OBJECT-TYPE
        SYNTAX	SEQUENCE OF MGMDCountEntry
        ACCESS  not-accessible
        STATUS  mandatory
        DESCRIPTION
                 	"A count table of igmp/MLD query/report/leave message."
        ::= { multicastStatus 9 }    
        
	mgmdCountEntry OBJECT-TYPE
        SYNTAX	MGMDCountEntry
        ACCESS	not-accessible
        STATUS	mandatory
        DESCRIPTION    	"An entry in mgmdCountTable."
        INDEX          	{ mgmdCountIndex }
        ::= { mgmdCountTable 1 }

        MGMDCountEntry ::=
		SEQUENCE {
        	mgmdCountIndex    		INTEGER,
        	mgmdCountInQuery		INTEGER,
        	mgmdCountInReport		INTEGER,
        	mgmdCountInLeave		INTEGER,        	
        	mgmdCountInQueryDrop   	INTEGER,
        	mgmdCountInReportDrop   INTEGER,
        	mgmdCountInLeaveDrop   	INTEGER,
        	mgmdCountOutQuery   	INTEGER,
        	mgmdCountOutReport   	INTEGER,
        	mgmdCountOutLeave   	INTEGER
        }

        mgmdCountIndex OBJECT-TYPE
        SYNTAX  INTEGER
        ACCESS  read-only
        STATUS  mandatory
        DESCRIPTION
                      	"Index of mgmdCountEntry. 0 means total count in whole system"
        ::= { mgmdCountEntry 1 }

        mgmdCountInQuery OBJECT-TYPE
        SYNTAX  INTEGER
        ACCESS  read-only
        STATUS  mandatory
        DESCRIPTION
                      	""
        ::= { mgmdCountEntry 2 }

        mgmdCountInReport OBJECT-TYPE
        SYNTAX  INTEGER
        ACCESS  read-only
        STATUS  mandatory
        DESCRIPTION
                      	""
        ::= { mgmdCountEntry 3 }

        mgmdCountInLeave OBJECT-TYPE
        SYNTAX  INTEGER
        ACCESS  read-only
        STATUS  mandatory
        DESCRIPTION
                      	""
        ::= { mgmdCountEntry 4 }
        
        mgmdCountInQueryDrop OBJECT-TYPE
        SYNTAX  INTEGER
        ACCESS  read-only
        STATUS  mandatory
        DESCRIPTION
                      	""
        ::= { mgmdCountEntry 5 }
        
        mgmdCountInReportDrop OBJECT-TYPE
        SYNTAX  INTEGER
        ACCESS  read-only
        STATUS  mandatory
        DESCRIPTION
                      	""
        ::= { mgmdCountEntry 6 }        
        
        mgmdCountInLeaveDrop OBJECT-TYPE
        SYNTAX  INTEGER
        ACCESS  read-only
        STATUS  mandatory
        DESCRIPTION
                      	""
        ::= { mgmdCountEntry 7 }                

        mgmdCountOutQuery OBJECT-TYPE
        SYNTAX  INTEGER
        ACCESS  read-only
        STATUS  mandatory
        DESCRIPTION
                      	""
        ::= { mgmdCountEntry 8 }                
        
        mgmdCountOutReport OBJECT-TYPE
        SYNTAX  INTEGER
        ACCESS  read-only
        STATUS  mandatory
        DESCRIPTION
                      	""
        ::= { mgmdCountEntry 9 }          

        mgmdCountOutLeave OBJECT-TYPE
        SYNTAX  INTEGER
        ACCESS  read-only
        STATUS  mandatory
        DESCRIPTION
                      	""
        ::= { mgmdCountEntry 10 }     
        
-- mgmdVlanStatusTable
       mgmdVlanStatusTable	OBJECT-TYPE
        SYNTAX	SEQUENCE OF MGMDVlanStatusEntry
        ACCESS  not-accessible
        STATUS  mandatory
        DESCRIPTION
                 	""
        ::= { multicastStatus 10 }


	mgmdVlanStatusEntry OBJECT-TYPE
        SYNTAX	MGMDVlanStatusEntry
        ACCESS	not-accessible
        STATUS	mandatory
        DESCRIPTION    	"An entry in mgmdVlanStatusTable."
        INDEX          	{ mgmdVlanStatusVlanID }
        ::= { mgmdVlanStatusTable 1 }

        MGMDVlanStatusEntry ::=
	SEQUENCE {
        	mgmdVlanStatusVlanID    INTEGER,
        	mgmdVlanStatusType	INTEGER,
        	mgmdVlanQueryPort	PortList,
        	mgmdVlanQuerySrcIpType	InetAddressType,        	
        	mgmdVlanQuerySrcIp	InetAddress
         }

        mgmdVlanStatusVlanID OBJECT-TYPE
        SYNTAX  INTEGER
        ACCESS  read-only
        STATUS  mandatory
        DESCRIPTION
                      	""
        ::= { mgmdVlanStatusEntry 1 }

        mgmdVlanStatusType OBJECT-TYPE
        SYNTAX  INTEGER {
			dynamic(1),
			mvr (2),
			static(3)
        }
        ACCESS  read-only
        STATUS  mandatory
        DESCRIPTION
                      	""
        ::= { mgmdVlanStatusEntry 2 }

        mgmdVlanQueryPort OBJECT-TYPE
        SYNTAX  PortList
        ACCESS  read-only
        STATUS  mandatory
        DESCRIPTION
                      	""
        ::= { mgmdVlanStatusEntry 3 }
 
        mgmdVlanQuerySrcIpType OBJECT-TYPE
        SYNTAX  InetAddressType { ipv4(1), ipv6(2) }
        ACCESS  read-only
        STATUS  mandatory
        DESCRIPTION
              "The address type of the mgmdVlanQuerySrcIp entry."
        ::= { mgmdVlanStatusEntry 4 }
               
        mgmdVlanQuerySrcIp OBJECT-TYPE
        SYNTAX  InetAddress (SIZE(4|16))
        ACCESS  read-only
        STATUS  mandatory
        DESCRIPTION
                      	""
        ::= { mgmdVlanStatusEntry 5 }

-- mgmdCounterPortTable

        mgmdCounterPortTable OBJECT-TYPE
        SYNTAX	SEQUENCE OF MGMDCounterPortEntry
        ACCESS  not-accessible
        STATUS  mandatory
        DESCRIPTION
                 	""
        ::= { multicastStatus 11 }

	mgmdCounterPortEntry OBJECT-TYPE
        SYNTAX	MGMDCounterPortEntry
        ACCESS	not-accessible
        STATUS	mandatory
        DESCRIPTION    	"An entry in mgmdCounterPortTable."
        INDEX          	{ dot1dBasePort }
        ::= { mgmdCounterPortTable 1 }

        MGMDCounterPortEntry ::=
           SEQUENCE {
        	mgmdCounterPortReport		Counter32,
		mgmdCounterPortLeave		Counter32,
		mgmdCounterPortActiveGroup	INTEGER,
		mgmdCounterPortQuery		Counter32
           }

        mgmdCounterPortReport OBJECT-TYPE
        SYNTAX  Counter32
        ACCESS  read-only
        STATUS  mandatory
        DESCRIPTION
                      	"Report counter for the port."
        ::= { mgmdCounterPortEntry 1 }

        mgmdCounterPortLeave OBJECT-TYPE
        SYNTAX  Counter32
        ACCESS  read-only
        STATUS  mandatory
        DESCRIPTION
                      	"Leave counter for the port."
        ::= { mgmdCounterPortEntry 2 }

        mgmdCounterPortActiveGroup OBJECT-TYPE
        SYNTAX  INTEGER
        ACCESS  read-only
        STATUS  mandatory
        DESCRIPTION
                      	"Current active group for the port"
        ::= { mgmdCounterPortEntry 3 }
 
        mgmdCounterPortQuery OBJECT-TYPE
        SYNTAX  Counter32
        ACCESS  read-only
        STATUS  mandatory
        DESCRIPTION
                      	"Query counter for the port."
        ::= { mgmdCounterPortEntry 4 } 
------------------------------------------
--  mgmd counters for specific vid
-- mgmdCounterVlanTable

        mgmdCounterVlanTable OBJECT-TYPE
        SYNTAX	SEQUENCE OF MGMDCounterVlanEntry
        ACCESS  not-accessible
        STATUS  mandatory
        DESCRIPTION
                 	""
        ::= { multicastStatus 12 }

	mgmdCounterVlanEntry OBJECT-TYPE
        SYNTAX	MGMDCounterVlanEntry
        ACCESS	not-accessible
        STATUS	mandatory
        DESCRIPTION    	"An entry in mgmdCounterVlanTable."
        INDEX          	{ dot1qVlanIndex  }
        ::= { mgmdCounterVlanTable 1 }

        MGMDCounterVlanEntry ::=
           SEQUENCE {
        	mgmdCounterVlanReport		Counter32,
		mgmdCounterVlanLeave		Counter32,
		mgmdCounterVlanActiveGroup	INTEGER,
		mgmdCounterVlanQuery		Counter32
           }

        mgmdCounterVlanReport OBJECT-TYPE
        SYNTAX  Counter32
        ACCESS  read-only
        STATUS  mandatory
        DESCRIPTION
                      	"Report counter for the Vlan."
        ::= { mgmdCounterVlanEntry 1 }

        mgmdCounterVlanLeave OBJECT-TYPE
        SYNTAX  Counter32
        ACCESS  read-only
        STATUS  mandatory
        DESCRIPTION
                      	"Leave counter for the Vlan."
        ::= { mgmdCounterVlanEntry 2 }

        mgmdCounterVlanActiveGroup OBJECT-TYPE
        SYNTAX  INTEGER
        ACCESS  read-only
        STATUS  mandatory
        DESCRIPTION
                      	"Current active group for the Vlan"
        ::= { mgmdCounterVlanEntry 3 }
 
        mgmdCounterVlanQuery OBJECT-TYPE
        SYNTAX  Counter32
        ACCESS  read-only
        STATUS  mandatory
        DESCRIPTION
                      	"Query counter for the Vlan."
        ::= { mgmdCounterVlanEntry 4 }
 
 -- mgmdCurrentGroupStatusTable

        mgmdCurrentGroupStatusTable	OBJECT-TYPE
        SYNTAX	SEQUENCE OF MGMDCurrentGroupStatusEntry
        ACCESS  not-accessible
        STATUS  mandatory
        DESCRIPTION
                 	""
        ::= { multicastStatus 13 }
             
	mgmdCurrentGroupStatusEntry OBJECT-TYPE
        SYNTAX	MGMDCurrentGroupStatusEntry
        ACCESS	not-accessible
        STATUS	mandatory
        DESCRIPTION    	"An entry in mgmdCurrentGroupStatusTable."
        INDEX          	{ mgmdStatusVlanID, mgmdStatusGroupAddressType, mgmdStatusGroupAddress }
        ::= { mgmdCurrentGroupStatusTable 1 }

        MGMDCurrentGroupStatusEntry ::=
	SEQUENCE {
        	mgmdCurrentNumberOfActivePort    INTEGER
         }

        mgmdCurrentNumberOfActivePort OBJECT-TYPE
        SYNTAX  INTEGER
        ACCESS  read-only
        STATUS  mandatory
        DESCRIPTION
                      	"Current number Of active port."
        ::= { mgmdCurrentGroupStatusEntry 1 }

-- mgmdClientSrcIp

        mgmdClientSrcIpTable	OBJECT-TYPE
        SYNTAX	SEQUENCE OF MGMDClientSrcIpEntry
        ACCESS  not-accessible
        STATUS  mandatory
        DESCRIPTION
                 	""
        ::= { multicastStatus 14 }
               
	mgmdClientSrcIpEntry OBJECT-TYPE
        SYNTAX	MGMDClientSrcIpEntry
        ACCESS	not-accessible
        STATUS	mandatory
        DESCRIPTION    	"An entry in mgmdClientSrcIpTable."
        INDEX          	{mgmdClientSrcIpAddressType,mgmdClientSrcIpIndex, mgmdStatusVlanID, mgmdStatusPort,  mgmdStatusGroupAddress}
        ::= { mgmdClientSrcIpTable 1 }

        MGMDClientSrcIpEntry ::=
	SEQUENCE {
        	mgmdClientSrcIpIndex    	INTEGER,
        	mgmdClientSrcIpAddressType	InetAddressType,  	
        	mgmdClientSrcIpAddress		InetAddress
         }

        mgmdClientSrcIpIndex OBJECT-TYPE
        SYNTAX  INTEGER
        ACCESS  read-only
        STATUS  mandatory
        DESCRIPTION
                      	""
        ::= { mgmdClientSrcIpEntry 1 }

        mgmdClientSrcIpAddressType OBJECT-TYPE
        SYNTAX  InetAddressType { ipv4(1), ipv6(2) }
        ACCESS  read-only
        STATUS  mandatory
        DESCRIPTION
                      	""
        ::= { mgmdClientSrcIpEntry 2 }       
        
        mgmdClientSrcIpAddress OBJECT-TYPE
        SYNTAX  InetAddress (SIZE(4|16))
        ACCESS  read-only
        STATUS  mandatory
        DESCRIPTION
                      	""
        ::= { mgmdClientSrcIpEntry 3 }       
        
 -- mgmdSrcListTable
 
	mgmdSrcListTable OBJECT-TYPE
	SYNTAX     SEQUENCE OF MGMDSrcListEntry
	MAX-ACCESS not-accessible
	STATUS     mandatory
   	DESCRIPTION
            "The (conceptual) table listing the Source List entries
             corresponding to each interface and multicast group pair
             on a host."

	::= { multicastStatus 15 }

	mgmdSrcListEntry OBJECT-TYPE
    	SYNTAX     MGMDSrcListEntry
    	MAX-ACCESS not-accessible
    	STATUS     mandatory
    	DESCRIPTION
            "An entry (conceptual row) in the mgmdSrcListTable."
	INDEX      { mgmdSrcListAddressType, mgmdStatusVlanID, mgmdStatusPort, mgmdStatusGroupAddress, mgmdSrcListAddress }

	::= { mgmdSrcListTable 1 }

	MGMDSrcListEntry ::= SEQUENCE {
    		mgmdSrcListAddressType      InetAddressType,
    		mgmdSrcListAddress          InetAddress
--		mgmdSrcListExpire           TimeTicks
	}

	mgmdSrcListAddressType OBJECT-TYPE
    	SYNTAX     InetAddressType { ipv4(1), ipv6(2) }
    	MAX-ACCESS not-accessible
    	STATUS     mandatory
	DESCRIPTION
            "The address type of the InetAddress variables in this
            table.  This value applies to the mgmdStatusGroupAddress
            and mgmdSrcListAddress entries."

	::= { mgmdSrcListEntry 1 }

	mgmdSrcListAddress OBJECT-TYPE
    	SYNTAX      InetAddress (SIZE(4|16))
    	MAX-ACCESS not-accessible
    	STATUS     mandatory
   	DESCRIPTION
            "The IP multicast group address for which this entry
            contains information."

	::= { mgmdSrcListEntry 2 }

--	mgmdSrcListExpire OBJECT-TYPE
--    	SYNTAX     TimeTicks
--    	MAX-ACCESS read-only
--    	STATUS     mandatory
--    	DESCRIPTION
--            "This value indicates the relevance of the SrcList entry,
--            whereby a non-zero value indicates this is an INCLUDE state
--            value, and a zero value indicates this to be an EXCLUDE
--            state value."

--	::= { mgmdHostSrcListEntry 3 }
	
------------------------------------------
--  igmpFilteringProfileSetup
	igmpFilteringProfileSetup     	OBJECT IDENTIFIER ::= { ves1616pe54 30 }

	igmpFilteringMaxNumberOfProfile OBJECT-TYPE
        SYNTAX  INTEGER
        ACCESS  read-only
        STATUS  mandatory
        DESCRIPTION
                      	""
        ::= { igmpFilteringProfileSetup 1 }

        igmpFilteringProfileTable	OBJECT-TYPE
        SYNTAX	SEQUENCE OF IgmpFilteringProfileEntry
        ACCESS  not-accessible
        STATUS  mandatory
        DESCRIPTION
                 	""
        ::= { igmpFilteringProfileSetup 2 }

	igmpFilteringProfileEntry OBJECT-TYPE
        SYNTAX	IgmpFilteringProfileEntry
        ACCESS	not-accessible
        STATUS	mandatory
        DESCRIPTION    	"An entry in igmpFilteringProfileTable."
        INDEX          	{ igmpFilteringProfileName, igmpFilteringProfileStartAddress, igmpFilteringProfileEndAddress }
        ::= { igmpFilteringProfileTable 1 }

        IgmpFilteringProfileEntry ::=
	SEQUENCE {
        	igmpFilteringProfileName		DisplayString,
        	igmpFilteringProfileStartAddress	IpAddress,
        	igmpFilteringProfileEndAddress		IpAddress,
        	igmpFilteringProfileRowStatus		RowStatus
        }

        igmpFilteringProfileName OBJECT-TYPE
        SYNTAX  DisplayString
        ACCESS  read-only
        STATUS  mandatory
        DESCRIPTION
                      	""
        ::= { igmpFilteringProfileEntry 1 }

        igmpFilteringProfileStartAddress OBJECT-TYPE
        SYNTAX  IpAddress
        ACCESS  read-only
        STATUS  mandatory
        DESCRIPTION
                      	""
        ::= { igmpFilteringProfileEntry 2 }

        igmpFilteringProfileEndAddress OBJECT-TYPE
        SYNTAX  IpAddress
        ACCESS  read-only
        STATUS  mandatory
        DESCRIPTION
                      	""
        ::= { igmpFilteringProfileEntry 3 }

        igmpFilteringProfileRowStatus OBJECT-TYPE
        SYNTAX  RowStatus
        ACCESS  read-create
        STATUS  mandatory
        DESCRIPTION
                      	""
        ::= { igmpFilteringProfileEntry 4 }

        mgmdFilterProfileTable	OBJECT-TYPE
        SYNTAX	SEQUENCE OF MgmdFilterProfileEntry
        ACCESS  not-accessible
        STATUS  mandatory
        DESCRIPTION
                 	""
        ::= { igmpFilteringProfileSetup 3 }
        
	mgmdFilterProfileEntry OBJECT-TYPE
        SYNTAX	MgmdFilterProfileEntry
        ACCESS	not-accessible
        STATUS	mandatory
        DESCRIPTION    	"An entry in mgmdFilterProfileTable.For v4 and v6 address"
        INDEX          	{ 
        		mgmdFilterProfileName, 
        		mgmdFilterProfileAddressType, 
        		mgmdFilterProfileStartAddress,
        		mgmdFilterProfileEndAddress }        		
        ::= { mgmdFilterProfileTable 1 }

        MgmdFilterProfileEntry ::=
	SEQUENCE {
        	mgmdFilterProfileName			DisplayString,
        	mgmdFilterProfileAddressType		InetAddressType,
        	mgmdFilterProfileStartAddress		InetAddress,
        	mgmdFilterProfileEndAddress		InetAddress,
        	mgmdFilterProfileRowStatus		RowStatus
        }

        mgmdFilterProfileName OBJECT-TYPE
        SYNTAX  DisplayString
        ACCESS  read-only
        STATUS  mandatory
        DESCRIPTION
                      	""
        ::= { mgmdFilterProfileEntry 1 }
        
        mgmdFilterProfileAddressType OBJECT-TYPE
        SYNTAX  InetAddressType
        ACCESS  read-only
        STATUS  mandatory
        DESCRIPTION
		"The type of the mgmdFilterProfileStartAddress and mgmdFilterProfileEndAddress address, as defined
            in the InetAddress MIB."
            
        ::= { mgmdFilterProfileEntry 2 }
        
        mgmdFilterProfileStartAddress OBJECT-TYPE
        SYNTAX  InetAddress
        ACCESS  read-only
        STATUS  mandatory
        DESCRIPTION
		"The Start IP address of this profile."
        ::= { mgmdFilterProfileEntry 3 }

        
        mgmdFilterProfileEndAddress OBJECT-TYPE
        SYNTAX  InetAddress
        ACCESS  read-only
        STATUS  mandatory
        DESCRIPTION
		"The End IP address of this profile."
        ::= { mgmdFilterProfileEntry 4 }

        mgmdFilterProfileRowStatus OBJECT-TYPE
        SYNTAX  RowStatus
        ACCESS  read-create
        STATUS  mandatory
        DESCRIPTION
                      	""
        ::= { mgmdFilterProfileEntry 5 }



--  MVRSetup
	mvrSetup     	OBJECT IDENTIFIER ::= { ves1616pe54 31 }

	maxNumberOfMVR OBJECT-TYPE
        SYNTAX  INTEGER
        ACCESS  read-only
        STATUS  mandatory
        DESCRIPTION
                      	""
        ::= { mvrSetup 1 }

        mvrTable	OBJECT-TYPE
        SYNTAX	SEQUENCE OF MvrEntry
        ACCESS  not-accessible
        STATUS  mandatory
        DESCRIPTION
                 	""
        ::= { mvrSetup 2 }

	mvrEntry OBJECT-TYPE
        SYNTAX	MvrEntry
        ACCESS	not-accessible
        STATUS	mandatory
        DESCRIPTION    	"An entry in mvrTable."
        INDEX          	{ mvrVlanID }
        ::= { mvrTable 1 }

        MvrEntry ::=
	SEQUENCE {
        	mvrVlanID	INTEGER,
        	mvrName		DisplayString,
        	mvrMode		INTEGER,
        	mvrRowStatus	RowStatus,
        	mvr8021pPriority	INTEGER
        	
        }

        mvrVlanID OBJECT-TYPE
        SYNTAX  INTEGER
        ACCESS  read-only
        STATUS  mandatory
        DESCRIPTION
                      	"1..4094"
        ::= { mvrEntry 1 }

        mvrName OBJECT-TYPE
        SYNTAX  DisplayString
        ACCESS  read-write
        STATUS  mandatory
        DESCRIPTION
                      	""
        ::= { mvrEntry 2 }

        mvrMode OBJECT-TYPE
        SYNTAX  INTEGER {
        	dynamic(0),
        	compatible(1)
        	}
        ACCESS  read-write
        STATUS  mandatory
        DESCRIPTION
                      	""
        ::= { mvrEntry 3 }

        mvrRowStatus OBJECT-TYPE
        SYNTAX  RowStatus
        ACCESS  read-create
        STATUS  mandatory
        DESCRIPTION
                      	""
        ::= { mvrEntry 4 }

        mvr8021pPriority OBJECT-TYPE
        SYNTAX  INTEGER
        ACCESS  read-write
        STATUS  mandatory
        DESCRIPTION
                      	"Set the 802.1p priority of control messages within MVR (0~7)"
        ::= { mvrEntry 5 }
        

        mvrPortTable	OBJECT-TYPE
        SYNTAX	SEQUENCE OF MvrPortEntry
        ACCESS  not-accessible
        STATUS  mandatory
        DESCRIPTION
                 	""
        ::= { mvrSetup 3 }

	mvrPortEntry OBJECT-TYPE
        SYNTAX	MvrPortEntry
        ACCESS	not-accessible
        STATUS	mandatory
        DESCRIPTION    	"An entry in mvrPortTable."
        INDEX          	{ mvrVlanID, dot1dBasePort }
        ::= { mvrPortTable 1 }

        MvrPortEntry ::=
	SEQUENCE {
        	mvrPortRole	INTEGER,
        	mvrPortTagging	EnabledStatus
        }

        mvrPortRole OBJECT-TYPE
        SYNTAX  INTEGER {
        	none(1),
        	source_port(2),
        	receiver_port(3)
        }
        ACCESS  read-write
        STATUS  mandatory
        DESCRIPTION
                      	""
        ::= { mvrPortEntry 1 }

        mvrPortTagging OBJECT-TYPE
        SYNTAX  EnabledStatus
        ACCESS  read-write
        STATUS  mandatory
        DESCRIPTION
                      	""
        ::= { mvrPortEntry 2 }

	maxNumberOfMvrGroup OBJECT-TYPE
        SYNTAX  INTEGER
        ACCESS  read-only
        STATUS  mandatory
        DESCRIPTION
                      	""
        ::= { mvrSetup 4 }

        mvrGroupTable	OBJECT-TYPE
        SYNTAX	SEQUENCE OF MvrGroupEntry
        ACCESS  not-accessible
        STATUS  mandatory
        DESCRIPTION
                 	""
        ::= { mvrSetup 5 }

	mvrGroupEntry OBJECT-TYPE
        SYNTAX	MvrGroupEntry
        ACCESS	not-accessible
        STATUS	mandatory
        DESCRIPTION    	"An entry in mvrGroupTable."
        INDEX          	{ mvrVlanID, mvrGroupName }
        ::= { mvrGroupTable 1 }

        MvrGroupEntry ::=
	SEQUENCE {
        	mvrGroupName		DisplayString,
        	mvrGroupStartAddress	IpAddress,
        	mvrGroupEndAddress	IpAddress,
        	mvrGroupRowStatus	RowStatus
        }

        mvrGroupName OBJECT-TYPE
        SYNTAX  DisplayString
        ACCESS  read-only
        STATUS  mandatory
        DESCRIPTION
                      	""
        ::= { mvrGroupEntry 1 }

        mvrGroupStartAddress OBJECT-TYPE
        SYNTAX  IpAddress
        ACCESS  read-write
        STATUS  mandatory
        DESCRIPTION
                      	""
        ::= { mvrGroupEntry 2 }

        mvrGroupEndAddress OBJECT-TYPE
        SYNTAX  IpAddress
        ACCESS  read-write
        STATUS  mandatory
        DESCRIPTION
                      	""
        ::= { mvrGroupEntry 3 }

        mvrGroupRowStatus OBJECT-TYPE
        SYNTAX  RowStatus
        ACCESS  read-create
        STATUS  mandatory
        DESCRIPTION
                      	""
        ::= { mvrGroupEntry 4 }

    mvrBehavior OBJECT-TYPE
        SYNTAX  INTEGER {
         		igmp_snooping(1),
         		igmp_proxy(2)
        }
        ACCESS  read-write
        STATUS  mandatory
        DESCRIPTION
                      ""
        ::= { mvrSetup 6 }


        mvrMgmdGroupTable	OBJECT-TYPE
        SYNTAX	SEQUENCE OF MvrMgmdGroupEntry
        ACCESS  not-accessible
        STATUS  mandatory
        DESCRIPTION
                 	""
        ::= { mvrSetup 7 }

	mvrMgmdGroupEntry OBJECT-TYPE
        SYNTAX	MvrMgmdGroupEntry
        ACCESS	not-accessible
        STATUS	mandatory
        DESCRIPTION    	"An entry in mvrMgmdGroupTable."
        INDEX          	{ mvrVlanID, mvrMgmdGroupName }
        ::= { mvrMgmdGroupTable 1 }

        MvrMgmdGroupEntry ::=
	SEQUENCE {
        	mvrMgmdGroupName		DisplayString,
        	mvrMgmdGroupAddressType		InetAddressType,
        	mvrMgmdGroupStartAddress	InetAddress,
        	mvrMgmdGroupEndAddress		InetAddress,
        	mvrMgmdGroupRowStatus		RowStatus
        }

        mvrMgmdGroupName OBJECT-TYPE
        SYNTAX  DisplayString
        ACCESS  read-only
        STATUS  mandatory
        DESCRIPTION
                      	""
        ::= { mvrMgmdGroupEntry 1 }

        mvrMgmdGroupAddressType OBJECT-TYPE
        SYNTAX  InetAddressType
        ACCESS  read-write
        STATUS  mandatory
        DESCRIPTION
                      	""
        ::= { mvrMgmdGroupEntry 2 }


        mvrMgmdGroupStartAddress OBJECT-TYPE
        SYNTAX  InetAddress
        ACCESS  read-write
        STATUS  mandatory
        DESCRIPTION
                      	""
        ::= { mvrMgmdGroupEntry 3 }

        mvrMgmdGroupEndAddress OBJECT-TYPE
        SYNTAX  InetAddress
        ACCESS  read-write
        STATUS  mandatory
        DESCRIPTION
                      	""
        ::= { mvrMgmdGroupEntry 4 }

        mvrMgmdGroupRowStatus OBJECT-TYPE
        SYNTAX  RowStatus
        ACCESS  read-create
        STATUS  mandatory
        DESCRIPTION
                      	""
        ::= { mvrMgmdGroupEntry 5 }

--  sysLogSetup
	sysLogSetup     	OBJECT IDENTIFIER ::= { ves1616pe54 33 }
	
	sysLogState OBJECT-TYPE
        SYNTAX  EnabledStatus
        ACCESS  read-write
        STATUS  mandatory
        DESCRIPTION
                      	"sysLog enabled/disabled for the switch."
        ::= { sysLogSetup 1 }
            	
--  sysLogTypeTable
       	sysLogTypeTable	OBJECT-TYPE
        SYNTAX	SEQUENCE OF SysLogTypeEntry
        ACCESS  not-accessible
        STATUS  mandatory
        DESCRIPTION
                 	""
        ::= { sysLogSetup 2 }
        
	sysLogTypeEntry OBJECT-TYPE
        SYNTAX	SysLogTypeEntry
        ACCESS	not-accessible
        STATUS	mandatory
        DESCRIPTION    	"An entry in sysLogTypeTable."
        INDEX          	{ sysLogTypeIndex }
        ::= { sysLogTypeTable 1 }

        SysLogTypeEntry ::=
           SEQUENCE {
         	sysLogTypeIndex		INTEGER,
        	sysLogTypeName		DisplayString,
        	sysLogTypeState		EnabledStatus,
        	sysLogTypeFacility	INTEGER
           }
       
        sysLogTypeIndex OBJECT-TYPE
        SYNTAX  INTEGER
        ACCESS  not-accessible
        STATUS  mandatory
        DESCRIPTION
                      	""
        ::= { sysLogTypeEntry 1 }

        sysLogTypeName OBJECT-TYPE
        SYNTAX  DisplayString 
        ACCESS  read-only
        STATUS  mandatory
        DESCRIPTION
                      	""
        ::= { sysLogTypeEntry 2 }

        sysLogTypeState OBJECT-TYPE
        SYNTAX  EnabledStatus
        ACCESS  read-write
        STATUS  mandatory
        DESCRIPTION
                      	""
        ::= { sysLogTypeEntry 3 }

   	sysLogTypeFacility OBJECT-TYPE
        SYNTAX  INTEGER {
        	local_user0(0),
        	local_user1(1),
        	local_user2(2),
        	local_user3(3),
        	local_user4(4),
        	local_user5(5),
        	local_user6(6),
        	local_user7(7)
        }
        ACCESS  read-write
        STATUS  mandatory
        DESCRIPTION
                      	""
        ::= { sysLogTypeEntry 4 }

--  sysLogServerTable
       	sysLogServerTable	OBJECT-TYPE
        SYNTAX	SEQUENCE OF SysLogServerEntry
        ACCESS  not-accessible
        STATUS  mandatory
        DESCRIPTION
                 	""
        ::= { sysLogSetup 3 }
        
	sysLogServerEntry OBJECT-TYPE
        SYNTAX	SysLogServerEntry
        ACCESS	not-accessible
        STATUS	mandatory
        DESCRIPTION    	"An entry in sysLogServerTable."
        INDEX          	{ sysLogServerAddress }
        ::= { sysLogServerTable 1 }

        SysLogServerEntry ::=
           SEQUENCE {
         	sysLogServerAddress		IpAddress,
        	sysLogServerLogLevel	INTEGER,
        	sysLogServerRowStatus	RowStatus
           }
       
        sysLogServerAddress OBJECT-TYPE
        SYNTAX  IpAddress
        ACCESS  not-accessible
        STATUS  mandatory
        DESCRIPTION
                      	""
        ::= { sysLogServerEntry 1 }

        sysLogServerLogLevel OBJECT-TYPE
        SYNTAX  INTEGER {
        	level0(0),
        	level0-1(1),
        	level0-2(2),
        	level0-3(3),
        	level0-4(4),
        	level0-5(5),
        	level0-6(6),
        	level0-7(7)
        }
        ACCESS  read-write
        STATUS  mandatory
        DESCRIPTION
                      	""
        ::= { sysLogServerEntry 2 }

        sysLogServerRowStatus OBJECT-TYPE
        SYNTAX  RowStatus
        ACCESS  read-create
        STATUS  mandatory
        DESCRIPTION
                      	""
        ::= { sysLogServerEntry 3 }
                                             
--  sysLogServerInfoTable
   	sysLogServerInfoTable	OBJECT-TYPE
        SYNTAX	SEQUENCE OF SysLogServerInfoEntry
        ACCESS  not-accessible
        STATUS  mandatory
        DESCRIPTION
                 	""
        ::= { sysLogSetup 4 }
        
	sysLogServerInfoEntry OBJECT-TYPE
        SYNTAX	SysLogServerInfoEntry
        ACCESS	not-accessible
        STATUS	mandatory
        DESCRIPTION    	"An entry in sysLogServerInfoTable."
        INDEX          	{ sysLogServerInfoIpAddrType, sysLogServerInfoIpAddr }
        ::= { sysLogServerInfoTable 1 }

        SysLogServerInfoEntry ::=
			SEQUENCE {
				sysLogServerInfoIpAddrType	InetAddressType,
				sysLogServerInfoIpAddr		InetAddress,
				sysLogServerInfoLogLevel	INTEGER,
				sysLogServerInfoRowStatus	RowStatus
			}
       
        sysLogServerInfoIpAddrType OBJECT-TYPE
        SYNTAX  InetAddressType { ipv4(1), ipv6(2) }
        ACCESS  not-accessible
        STATUS  mandatory
        DESCRIPTION
                      	""
        ::= { sysLogServerInfoEntry 1 }
        
        sysLogServerInfoIpAddr OBJECT-TYPE
        SYNTAX  InetAddress
        ACCESS  not-accessible
        STATUS  mandatory
        DESCRIPTION
                      	""
        ::= { sysLogServerInfoEntry 2 }

        sysLogServerInfoLogLevel OBJECT-TYPE
        SYNTAX  INTEGER {
        	level0(0),
        	level0-1(1),
        	level0-2(2),
        	level0-3(3),
        	level0-4(4),
        	level0-5(5),
        	level0-6(6),
        	level0-7(7)
        }
        ACCESS  read-write
        STATUS  mandatory
        DESCRIPTION
                      	""
        ::= { sysLogServerInfoEntry 3 }

        sysLogServerInfoRowStatus OBJECT-TYPE
        SYNTAX  RowStatus
        ACCESS  read-create
        STATUS  mandatory
        DESCRIPTION
                      	""
        ::= { sysLogServerInfoEntry 4 }
                                             
-- diffservSetup
	diffservSetup     	OBJECT IDENTIFIER ::= { ves1616pe54 34 }

        diffservState OBJECT-TYPE
        SYNTAX  EnabledStatus
        ACCESS  read-write
        STATUS  mandatory
        DESCRIPTION
                      ""
        ::= { diffservSetup 1 }
        
-- diffservMapTable
        diffservMapTable OBJECT-TYPE
        SYNTAX	SEQUENCE OF DiffservMapEntry
        ACCESS  not-accessible
        STATUS  mandatory
        DESCRIPTION
                 	""
        ::= { diffservSetup 2 }
        
	diffservMapEntry OBJECT-TYPE
        SYNTAX	DiffservMapEntry
        ACCESS	not-accessible
        STATUS	mandatory
        DESCRIPTION    	"An entry in diffservMapTable."
        INDEX          	{ diffservMapDscp }
        ::= { diffservMapTable 1 }

        DiffservMapEntry ::=
           SEQUENCE {
        	diffservMapDscp		INTEGER,
        	diffservMapPriority	INTEGER
           }

        diffservMapDscp OBJECT-TYPE
        SYNTAX  INTEGER
        ACCESS  read-only
        STATUS  mandatory
        DESCRIPTION
                      	"0-63"
        ::= { diffservMapEntry 1 }

        diffservMapPriority OBJECT-TYPE
        SYNTAX  INTEGER
        ACCESS  read-write
        STATUS  mandatory
        DESCRIPTION
                      	"0-7"
        ::= { diffservMapEntry 2 }

-- diffservPortTable
        diffservPortTable OBJECT-TYPE
        SYNTAX	SEQUENCE OF DiffservPortEntry
        ACCESS  not-accessible
        STATUS  mandatory
        DESCRIPTION
                 	""
        ::= { diffservSetup 3 }
        
	diffservPortEntry OBJECT-TYPE
        SYNTAX	DiffservPortEntry
        ACCESS	not-accessible
        STATUS	mandatory
        DESCRIPTION    	"An entry in diffservPortTable."
        INDEX          	{ dot1dBasePort }
        ::= { diffservPortTable 1 }

        DiffservPortEntry ::=
           SEQUENCE {
        	diffservPortState	EnabledStatus
           }

        diffservPortState OBJECT-TYPE
        SYNTAX  EnabledStatus
        ACCESS  read-write
        STATUS  mandatory
        DESCRIPTION
                      	""
        ::= { diffservPortEntry 1 }




-- vturSwitchSetup
	vturSwitchSetup     	OBJECT IDENTIFIER ::= { ves1616pe54 35 }

-- vturLayer2Setup
		vturLayer2Setup     	OBJECT IDENTIFIER ::= { vturSwitchSetup 1 }

	layer2Table OBJECT-TYPE
       	SYNTAX	SEQUENCE OF Layer2Entry
       	ACCESS  not-accessible
       	STATUS  mandatory
       	DESCRIPTION
      	      	""
       	::= { vturLayer2Setup 1 }

	layer2Entry OBJECT-TYPE
       	SYNTAX	Layer2Entry
       	ACCESS	not-accessible
       	STATUS	mandatory
       	DESCRIPTION    	"An entry in layer2Table."
       	INDEX          	{ dot1dBasePort}
       	::= { layer2Table 1 }

        Layer2Entry ::=
       	SEQUENCE {
       	vturIgmpSnoopingStateSetup	INTEGER
        }

        vturIgmpSnoopingStateSetup OBJECT-TYPE
        SYNTAX  INTEGER {
         		enabled(1),
         		disabled(2)
        }
        ACCESS  read-write
        STATUS  mandatory
        DESCRIPTION
                      ""
        ::= { layer2Entry 2 }

       
       
-- vturPortSetup
		vturPortSetup     	OBJECT IDENTIFIER ::= { vturSwitchSetup 2 }

-- PortTable
    portTable OBJECT-TYPE
       	SYNTAX	SEQUENCE OF PortEntry
       	ACCESS  not-accessible
       	STATUS  mandatory
       	DESCRIPTION
      	      	""
       	::= { vturPortSetup 1 }

	portEntry OBJECT-TYPE
       	SYNTAX	PortEntry
       	ACCESS	not-accessible
       	STATUS	mandatory
       	DESCRIPTION    	"An entry in portTable."
       	INDEX          	{ dot1dBasePort, portNumber }
       	::= { portTable 1 }

    PortEntry ::=
       	SEQUENCE {
       	portNumber	INTEGER,
        portOperStatus	INTEGER,
        portSpeedDuplex	INTEGER,
        portOperSpeed	INTEGER  
        }

    portNumber OBJECT-TYPE
       	SYNTAX  INTEGER
     	ACCESS  read-only
       	STATUS  mandatory
       	DESCRIPTION
                    	"Display all ports we got in CPE side"
        ::= { portEntry 1 }

    portOperStatus OBJECT-TYPE
       	SYNTAX  INTEGER {
       	enable(1),
       	disable(2)
       	}
     	ACCESS  read-only
       	STATUS  mandatory
       	DESCRIPTION
                    	"CPE port's current status."
        ::= { portEntry 3 }

    portSpeedDuplex OBJECT-TYPE
       	SYNTAX  INTEGER {
       	linkdown(0),
       	autoneg(1),
       	half_10M(2),
       	full_10M(3),
       	half_100M(4),
       	full_100M(5)
       	}
       	ACCESS  read-write
       	STATUS  mandatory
       	DESCRIPTION
                     	"Specify each port's speed and duplex in CPE side."
        ::= { portEntry 4 }


    portOperSpeed OBJECT-TYPE
       	SYNTAX  INTEGER {
       	linkdown(0),
       	autoneg(1),
       	half_10M(2),
       	full_10M(3),
       	half_100M(4),
       	full_100M(5)
       	}
       	ACCESS  read-only
       	STATUS  mandatory
       	DESCRIPTION
                     	"CPE port's current speed."
        ::= { portEntry 8 }




-- vturWanSetup
		vturWanSetup     	OBJECT IDENTIFIER ::= { vturSwitchSetup 4 }


-- vturWanTable
vturWan OBJECT IDENTIFIER ::= { vturWanSetup 1 }
   vturWanTable OBJECT-TYPE
       	SYNTAX	SEQUENCE OF VturWanEntry
       	ACCESS  not-accessible
       	STATUS  mandatory
       	DESCRIPTION
      	      	""
       	::= { vturWan 1 }

     vturWanEntry OBJECT-TYPE
       	SYNTAX	VturWanEntry
       	ACCESS	not-accessible
       	STATUS	mandatory
       	DESCRIPTION    	"An entry in vturWanTable."
       	INDEX          	{ dot1dBasePort, vturWanIndex }
       	::= { vturWanTable 1 }

     VturWanEntry ::=
       	SEQUENCE {
        vturWanIndex	INTEGER,
	vturVlanTagging	INTEGER,
	vturVlanID	INTEGER,
	vtur8021p	INTEGER,
	vturPPPUsername	OCTET STRING,
	vturPPPPassword	OCTET STRING,
	vturWanProtocol INTEGER,
	vturWanProtocolSetting BITS,
	vturWanIP IpAddress,
	vturWanSubnetMask IpAddress,
	vturWanService	EnabledStatus,
        vturWanRowStatus  RowStatus
        }

     vturWanIndex OBJECT-TYPE
       	SYNTAX  INTEGER
       	ACCESS  read-only
       	STATUS  mandatory
       	DESCRIPTION
                   	"Display the wan index range from 1 to 4 we got in CPE side"
       	::= { vturWanEntry 1 }

     vturVlanTagging OBJECT-TYPE
       	SYNTAX  INTEGER
       	{
       	disable(1),
       	vlan_mux(2),
       	auto_vlan(3)
       	}
       	ACCESS  read-write
       	STATUS  mandatory
       	DESCRIPTION
                   	"Display the vlan tagging we got in CPE side"
       	::= { vturWanEntry 2 }

     vturVlanID OBJECT-TYPE
       	SYNTAX  INTEGER
       	ACCESS  read-write
       	STATUS  mandatory
       	DESCRIPTION
                   	"Display the vlan id range from 1 to 4094 we got in CPE side"
       	::= { vturWanEntry 3 }       	

     vtur8021p OBJECT-TYPE
       	SYNTAX  INTEGER
       	ACCESS  read-write
       	STATUS  mandatory
       	DESCRIPTION
                   	"Display the 802.1p value range from 0 to 7 we got in CPE side"
       	::= { vturWanEntry 4 }

     vturPPPUsername OBJECT-TYPE
       	SYNTAX  OCTET STRING
       	ACCESS  read-write
       	STATUS  mandatory
       	DESCRIPTION
                   	"Display the PPP username we got in CPE side"
       	::= { vturWanEntry 5 }
       	
     vturPPPPassword OBJECT-TYPE
       	SYNTAX  OCTET STRING
       	ACCESS  read-write
       	STATUS  mandatory
       	DESCRIPTION
                   	"Display the PPP password we got in CPE side"
       	::= { vturWanEntry 6 }
       	
     vturWanProtocol OBJECT-TYPE
       	SYNTAX  INTEGER
       	{
       	pppoe(1),
       	mer(2),
       	bridge(3)
       	}
       	ACCESS  read-write
       	STATUS  mandatory
       	DESCRIPTION
                   	"Display the wan protocol info we got in CPE side"
       	::= { vturWanEntry 7 }

     vturWanProtocolSetting OBJECT-TYPE
       	SYNTAX  BITS
       	{
		dhcp_client_(0),
		nat(1),
		firewall(2),
		igmp(3)
	}       	
       	ACCESS  read-write
       	STATUS  mandatory
       	DESCRIPTION
                   	"Display the wan service enable/disable status we got in CPE side"
       	::= { vturWanEntry 8 }       	       	       	       	      
          
      vturWanIP OBJECT-TYPE
        SYNTAX  IpAddress
        ACCESS  read-create
        STATUS  mandatory
        DESCRIPTION
                      	"Display the wan IP setting we got in CPE side"
        ::= { vturWanEntry 9 }

      vturWanSubnetMask OBJECT-TYPE
        SYNTAX  IpAddress
        ACCESS  read-create
        STATUS  mandatory
        DESCRIPTION
                      	"Display the wan subnet mask we got in CPE side"
        ::= { vturWanEntry 10 }

     vturWanService OBJECT-TYPE
       	SYNTAX  EnabledStatus
       	ACCESS  read-write
       	STATUS  mandatory
       	DESCRIPTION
                   	"Display the wan service enable/disable status we got in CPE side"
       	::= { vturWanEntry 11 }       	       	       	       	      

      vturWanRowStatus OBJECT-TYPE
        SYNTAX  RowStatus
        ACCESS  read-create
        STATUS  mandatory
        DESCRIPTION
                      	""
        ::= { vturWanEntry 12 }        

	vturWanCommon OBJECT IDENTIFIER ::= { vturWanSetup 2 }

        vturWanCommonTable  OBJECT-TYPE
        SYNTAX	SEQUENCE OF VturWanCommonEntry
       	ACCESS  not-accessible
       	STATUS  mandatory
       	DESCRIPTION
      	      	""
        ::= { vturWanCommon 1 }

	vturWanCommonEntry OBJECT-TYPE
       	SYNTAX	VturWanCommonEntry
       	ACCESS	not-accessible
       	STATUS	mandatory
       	DESCRIPTION    	"An entry in vturWanCommonTable."
       	INDEX          	{ dot1dBasePort}
       	::= { vturWanCommonTable 1 }

        VturWanCommonEntry ::=
       	SEQUENCE {
       	vturWanQoS			EnabledStatus,
       	vturEnableAutoDefaultGateway	EnabledStatus,
        vturDefaultGatewayIP		IpAddress,
        vturVitualPortEnable		EnabledStatus
        }


        vturWanQoS OBJECT-TYPE
        SYNTAX  EnabledStatus
        ACCESS  read-write
        STATUS  mandatory
        DESCRIPTION
                      ""
        ::= { vturWanCommonEntry 1 }

        vturEnableAutoDefaultGateway OBJECT-TYPE
        SYNTAX  EnabledStatus 
        ACCESS  read-write
        STATUS  mandatory
        DESCRIPTION
                      "Display the enable auto default gateay setting we get from CPE side"
        ::= { vturWanCommonEntry 2 }

        vturDefaultGatewayIP OBJECT-TYPE
       	SYNTAX  IpAddress 
     	ACCESS  read-write
       	STATUS  mandatory
       	DESCRIPTION
       		"Display the default gateway setting we get from CPE side"
        ::= { vturWanCommonEntry 3 }

        vturVitualPortEnable OBJECT-TYPE
        SYNTAX  EnabledStatus
        ACCESS  read-write
        STATUS  mandatory
        DESCRIPTION
                      "Display Enable/Disable virtual port on eth1 setting we get on CPE side"
        ::= { vturWanCommonEntry 4 }


-- vturClassificationSetup
		vturClassificationSetup     	OBJECT IDENTIFIER ::= { vturSwitchSetup 5 }


-- vturClassificationTable
    vturClassificationTable OBJECT-TYPE
       	SYNTAX	SEQUENCE OF VturClassificationEntry
       	ACCESS  not-accessible
       	STATUS  mandatory
       	DESCRIPTION
      	      	""
       	::= { vturClassificationSetup 1 }

     vturClassificationEntry OBJECT-TYPE
       	SYNTAX	VturClassificationEntry
       	ACCESS	not-accessible
       	STATUS	mandatory
       	DESCRIPTION    	"An entry in vturClassificationTable."
       	INDEX          	{ dot1dBasePort, vturClassificationIndex }
       	::= { vturClassificationTable 1 }

     VturClassificationEntry ::=
       	SEQUENCE {
        vturClassificationIndex	INTEGER,
	vturClassificationRuleEnable	EnabledStatus,
	vturWanInterface		INTEGER,
	vturClassificationQueue		INTEGER,
	vturClassification8021p		INTEGER,
	vturClassificationVid		INTEGER,
	vturFilterPhysicalPort		INTEGER,
	vturFilterProtocol		INTEGER,
	vturFilterSourceIP		IpAddress,
	vturFilterSourceSubnetMask	IpAddress,
	vturFilterDestinationIP		IpAddress,
	vturFilterDestinationSubnetMask	IpAddress,
	vturFilterSourcePortStart	INTEGER,
	vturFilterSourcePortEnd		INTEGER,
	vturFilterDestinationPortStart	INTEGER,
	vturFilterDestinationPortEnd	INTEGER,
	vturFilterSourceMACAddr		OCTET STRING,
	vturFilterSourceMACMask		OCTET STRING,
	vturFilterDestinationMACAddr	OCTET STRING,
	vturFilterDestinationMACMask	OCTET STRING,
	vturFilter8021p			INTEGER,
	vturFilterProtocolType		INTEGER,
	vturPolicyGatewayIP		IpAddress,
        vturClassificationRowStatus  RowStatus
        }

     vturClassificationIndex OBJECT-TYPE
       	SYNTAX  INTEGER
       	ACCESS  read-only
       	STATUS  mandatory
       	DESCRIPTION
                   	"Display the classification index range from 1 to 8 we got in CPE side"
       	::= { vturClassificationEntry 1 }

     vturClassificationRuleEnable OBJECT-TYPE
       	SYNTAX  EnabledStatus
       	ACCESS  read-write
       	STATUS  mandatory
       	DESCRIPTION
                   	"Display the classification enable/disable status we got in CPE side"
       	::= { vturClassificationEntry 2 }

     vturWanInterface OBJECT-TYPE
       	SYNTAX  INTEGER
       	ACCESS  read-write
       	STATUS  mandatory
       	DESCRIPTION
                   	"Display the wan interface index range from 1 to 4 we got in CPE side"
       	::= { vturClassificationEntry 3 }       	

     vturClassificationQueue OBJECT-TYPE
       	SYNTAX  INTEGER
       	ACCESS  read-write
       	STATUS  mandatory
       	DESCRIPTION
                   	"Display the assigned queue (1-4)802.1p value we got in CPE side"
       	::= { vturClassificationEntry 4 }
      
     vturClassification8021p OBJECT-TYPE
       	SYNTAX  INTEGER
       	ACCESS  read-write
       	STATUS  mandatory
       	DESCRIPTION
                   	"Mark 802.1p if 802.1q is enabled [0-7]"
       	::= { vturClassificationEntry 5 }

     vturClassificationVid OBJECT-TYPE
       	SYNTAX  INTEGER
       	ACCESS  read-write
       	STATUS  mandatory
       	DESCRIPTION
                   	"Display the 802.1Q VLAN ID: [1-4094]"
       	::= { vturClassificationEntry 6 }
       	
     vturFilterPhysicalPort OBJECT-TYPE
       	SYNTAX  INTEGER
       	ACCESS  read-write
       	STATUS  mandatory
       	DESCRIPTION
                   	" Physical LAN Port number"
       	::= { vturClassificationEntry 7 }

     vturFilterProtocol OBJECT-TYPE
                SYNTAX  INTEGER{
		tcp-udp(1),
       	tcp(2),
       	udp(3),
       	icmp(4)
       	}
       	ACCESS  read-write
       	STATUS  mandatory
       	DESCRIPTION
                   	"Protocol: [TCP/UDP, TCP, UDP, ICMP]  1-4"
       	::= { vturClassificationEntry 8 }       	       	       	       	      

     vturFilterSourceIP OBJECT-TYPE
       	SYNTAX  IpAddress
       	ACCESS  read-only
       	STATUS  mandatory
       	DESCRIPTION
                   	"Display the filtering source IP we got in CPE side"
       	::= { vturClassificationEntry 9 }

     vturFilterSourceSubnetMask OBJECT-TYPE
       	SYNTAX  IpAddress
       	ACCESS  read-write
       	STATUS  mandatory
       	DESCRIPTION
                   	"Display the filtering source subnet mask we got in CPE side"
       	::= { vturClassificationEntry 10 }

     vturFilterDestinationIP OBJECT-TYPE
       	SYNTAX  IpAddress
       	ACCESS  read-write
       	STATUS  mandatory
       	DESCRIPTION
                   	"Display the filtering destination IP we got in CPE side"
       	::= { vturClassificationEntry 11 }       	

     vturFilterDestinationSubnetMask OBJECT-TYPE
       	SYNTAX  IpAddress
       	ACCESS  read-write
       	STATUS  mandatory
       	DESCRIPTION
                   	"Display the filtering destination subnet mask we got in CPE side"
       	::= { vturClassificationEntry 12 }
       	
     vturFilterSourcePortStart OBJECT-TYPE
       	SYNTAX  INTEGER
       	ACCESS  read-write
       	STATUS  mandatory
       	DESCRIPTION
                   	"Display the filtering source port start we got in CPE side"
       	::= { vturClassificationEntry 13 }
       	
     vturFilterSourcePortEnd OBJECT-TYPE
       	SYNTAX  INTEGER
       	ACCESS  read-write
       	STATUS  mandatory
       	DESCRIPTION
                   	"Display the filtering source port end we got in CPE side"
       	::= { vturClassificationEntry 14 }

     vturFilterDestinationPortStart OBJECT-TYPE
       	SYNTAX  INTEGER
       	ACCESS  read-write
       	STATUS  mandatory
       	DESCRIPTION
                   	"Display the filtering destination port start we got in CPE side"
       	::= { vturClassificationEntry 15 }
       	
     vturFilterDestinationPortEnd OBJECT-TYPE
       	SYNTAX  INTEGER
       	ACCESS  read-write
       	STATUS  mandatory
       	DESCRIPTION
                   	"Display the filtering destination end port we got in CPE side"
       	::= { vturClassificationEntry 16 }       	

     vturFilterSourceMACAddr OBJECT-TYPE
       	SYNTAX  OCTET STRING
       	ACCESS  read-write
       	STATUS  mandatory
       	DESCRIPTION
                   	"Display the filtering source MAC addr we got in CPE side"
       	::= { vturClassificationEntry 17 }
       	
     vturFilterSourceMACMask OBJECT-TYPE
       	SYNTAX  OCTET STRING
       	ACCESS  read-write
       	STATUS  mandatory
       	DESCRIPTION
                   	"Display the filtering source MAC mask we got in CPE side"
       	::= { vturClassificationEntry 18 }      

     vturFilterDestinationMACAddr OBJECT-TYPE
       	SYNTAX  OCTET STRING
       	ACCESS  read-write
       	STATUS  mandatory
       	DESCRIPTION
                   	"Display the filtering destination MAC addr we got in CPE side"
       	::= { vturClassificationEntry 19 }
       	
     vturFilterDestinationMACMask OBJECT-TYPE
       	SYNTAX  OCTET STRING
       	ACCESS  read-write
       	STATUS  mandatory
       	DESCRIPTION
                   	"Display the filtering destination MAC mask we got in CPE side"
       	::= { vturClassificationEntry 20 }  

     vturFilter8021p OBJECT-TYPE
       	SYNTAX  INTEGER
       	ACCESS  read-write
       	STATUS  mandatory
       	DESCRIPTION
                   	"Display the filtering 802.1p value we got in CPE side"
       	::= { vturClassificationEntry 21 }
       	
     vturFilterProtocolType OBJECT-TYPE
       	SYNTAX  INTEGER
       	ACCESS  read-write
       	STATUS  mandatory
       	DESCRIPTION
                   	"Display the filtering protocol type we got in CPE side"
       	::= { vturClassificationEntry 22 } 

     vturPolicyGatewayIP OBJECT-TYPE
       	SYNTAX  IpAddress
       	ACCESS  read-write
       	STATUS  mandatory
       	DESCRIPTION
                   	"Display the filtering protocol type we got in CPE side"
       	::= { vturClassificationEntry 23 } 

      vturClassificationRowStatus OBJECT-TYPE
        SYNTAX  RowStatus
        ACCESS  read-create
        STATUS  mandatory
        DESCRIPTION
                      	""
        ::= { vturClassificationEntry 24 }
           


-- vturMiscSetup
		vturMiscSetup     	OBJECT IDENTIFIER ::= { vturSwitchSetup 6 }


-- vturMntTable
    vturMntTable OBJECT-TYPE
       	SYNTAX	SEQUENCE OF VturMntEntry
       	ACCESS  not-accessible
       	STATUS  mandatory
       	DESCRIPTION
      	      	""
       	::= { vturMiscSetup 1 }

	vturMntEntry OBJECT-TYPE
       	SYNTAX	VturMntEntry
       	ACCESS	not-accessible
       	STATUS	mandatory
       	DESCRIPTION    	"An entry in VTUR Misc Table."
       	INDEX          	{ dot1dBasePort }
       	::= { vturMntTable 1 }

    VturMntEntry ::=
       	SEQUENCE {
        mntOperation	INTEGER,    
        mntCommit		INTEGER,
        mntStatus		INTEGER
        }

    mntOperation OBJECT-TYPE
       	SYNTAX  INTEGER {
       	layer2Setup(1),
       	portSetup(2),
       	priorityQueueSetup(3),
       	dot1qVlanSetup(4),
       	portBasedVlanSetup(5),
       	loadFactoryDefault(6),
       	resetSW(7),
        apBasicSetup(8),
        apSecuritySetup(9),
        apRadiusSetup(10),
        apMacFilterSetup(11),
        apMacFilterAddrSetup(12),
        reinit(13),
        consoleSetup(14),
        remoteFunctionSetup(15),         
        regetstatue(16),         
        protocolBasedVlanSetup(17),
        vturWanSetup(18),
        vturClassificationSetup(19),
        vturLanSetup(20),
        vturResetCounter(21),
        loadDefaultWithoutIP(22)
       	}
       	ACCESS  read-write
       	STATUS  mandatory
       	DESCRIPTION
                   	"Specify the operation of VTUR"
       	::= { vturMntEntry 1 }
    
    mntCommit OBJECT-TYPE
       	SYNTAX  INTEGER {
       	idle(0),
       	commit(1)
       	}
       	ACCESS  read-write
       	STATUS  mandatory
       	DESCRIPTION
                    	"Apply maintenance setting to vtur"
        ::= { vturMntEntry 2 }
    
    mntStatus OBJECT-TYPE
       	SYNTAX  INTEGER {
       	in-progress(0),
       	success(1),
       	fail(2)
       	}
       	ACCESS  read-only
       	STATUS  mandatory
       	DESCRIPTION
                    	"Display the current status regarding to the operation."
        ::= { vturMntEntry 3 }

-- vturAPSetup
	vturAPSetup     	OBJECT IDENTIFIER ::= { vturSwitchSetup 7 }
	
-- vturAPGeneral
        vturAPGeneral OBJECT IDENTIFIER ::= { vturAPSetup 1 }

-- vturAPGeneralStatisticsTable

        vturAPGeneralStatisticsTable  OBJECT-TYPE
        SYNTAX	SEQUENCE OF VturAPGeneralStatisticsEntry
        ACCESS  not-accessible
        STATUS  mandatory
        DESCRIPTION
                 	""
        ::= { vturAPGeneral 1 }

		vturAPGeneralStatisticsEntry OBJECT-TYPE
       		SYNTAX	VturAPGeneralStatisticsEntry
       		ACCESS	not-accessible
       		STATUS	mandatory
	       	DESCRIPTION    	"An entry in VTUR AP General Statistics Table."
	       	INDEX          	{ dot1dBasePort }
	       	::= { vturAPGeneralStatisticsTable 1 }

		VturAPGeneralStatisticsEntry ::=
	       	SEQUENCE {
	        lanRxBytes	Counter32,
	        lanRxPkts	Counter32,
	        lanTxBytes	Counter32,
	        lanTxPkts	Counter32,
	        vdslRxBytes	Counter32,
	        vdslRxPkts	Counter32,
	        vdslTxBytes	Counter32,
	        vdslTxPkts	Counter32,
	        wlanRxBytes	Counter32,
	        wlanRxPkts	Counter32,
	        wlanRxErrs	Counter32,
	        wlanRxDrops	Counter32,
	        wlanTxBytes	Counter32,
	        wlanTxPkts	Counter32,
	        wlanTxErrs	Counter32,
	        wlanTxDrops	Counter32
	        }


		        lanRxBytes OBJECT-TYPE
        		SYNTAX  Counter32
        		ACCESS  read-only
        		STATUS  mandatory
        		DESCRIPTION
                      		"Received bytes on LAN"
        		::= { vturAPGeneralStatisticsEntry 1 }

		        lanRxPkts OBJECT-TYPE
        		SYNTAX  Counter32
        		ACCESS  read-only
        		STATUS  mandatory
        		DESCRIPTION
                      		"Received frames on LAN"
        		::= { vturAPGeneralStatisticsEntry 2 }


		        lanTxBytes OBJECT-TYPE
        		SYNTAX  Counter32
        		ACCESS  read-only
        		STATUS  mandatory
        		DESCRIPTION
                      		"Transmitted bytes on LAN"
        		::= { vturAPGeneralStatisticsEntry 3 }

		        lanTxPkts OBJECT-TYPE
        		SYNTAX  Counter32
        		ACCESS  read-only
        		STATUS  mandatory
        		DESCRIPTION
                      		"Transmitted frames on LAN"
        		::= { vturAPGeneralStatisticsEntry 4 }

		        vdslRxBytes OBJECT-TYPE
        		SYNTAX  Counter32
        		ACCESS  read-only
        		STATUS  mandatory
        		DESCRIPTION
                      		"Received bytes on VDSL"
        		::= { vturAPGeneralStatisticsEntry 5 }

		        vdslRxPkts OBJECT-TYPE
        		SYNTAX  Counter32
        		ACCESS  read-only
        		STATUS  mandatory
        		DESCRIPTION
                      		"Received frames on VDSL"
        		::= { vturAPGeneralStatisticsEntry 6 }

		        vdslTxBytes OBJECT-TYPE
        		SYNTAX  Counter32
        		ACCESS  read-only
        		STATUS  mandatory
        		DESCRIPTION
                      		"Transmitted bytes on VDSL"
        		::= { vturAPGeneralStatisticsEntry 7 }

		        vdslTxPkts OBJECT-TYPE
        		SYNTAX  Counter32
        		ACCESS  read-only
        		STATUS  mandatory
        		DESCRIPTION
                      		"Transmitted frames on VDSL"
        		::= { vturAPGeneralStatisticsEntry 8 }

		        wlanRxBytes OBJECT-TYPE
        		SYNTAX  Counter32
        		ACCESS  read-only
        		STATUS  mandatory
        		DESCRIPTION
                      		"Received bytes on WLAN"
        		::= { vturAPGeneralStatisticsEntry 9 }

		        wlanRxPkts OBJECT-TYPE
        		SYNTAX  Counter32
        		ACCESS  read-only
        		STATUS  mandatory
        		DESCRIPTION
                      		"Received frames on WLAN "
        		::= { vturAPGeneralStatisticsEntry 10 }

		        wlanRxErrs OBJECT-TYPE
        		SYNTAX  Counter32
        		ACCESS  read-only
        		STATUS  mandatory
        		DESCRIPTION
                      		"Received error frames on WLAN "
        		::= { vturAPGeneralStatisticsEntry 11 }

		        wlanRxDrops OBJECT-TYPE
        		SYNTAX  Counter32
        		ACCESS  read-only
        		STATUS  mandatory
        		DESCRIPTION
                      		"Received drop frames on WLAN "
        		::= { vturAPGeneralStatisticsEntry 12 }

		        wlanTxBytes OBJECT-TYPE
        		SYNTAX  Counter32
        		ACCESS  read-only
        		STATUS  mandatory
        		DESCRIPTION
                      		"Transmitted bytes on WLAN "
        		::= { vturAPGeneralStatisticsEntry 13 }

		        wlanTxPkts OBJECT-TYPE
        		SYNTAX  Counter32
        		ACCESS  read-only
        		STATUS  mandatory
        		DESCRIPTION
                      		"Transmitted frames on WLAN "
        		::= { vturAPGeneralStatisticsEntry 14 }

		        wlanTxErrs OBJECT-TYPE
        		SYNTAX  Counter32
        		ACCESS  read-only
        		STATUS  mandatory
        		DESCRIPTION
                      		"Transmitted error frames on WLAN "
        		::= { vturAPGeneralStatisticsEntry 15 }

		        wlanTxDrops OBJECT-TYPE
        		SYNTAX  Counter32
        		ACCESS  read-only
        		STATUS  mandatory
        		DESCRIPTION
                      		"Transmitted drop frames on WLAN "
        		::= { vturAPGeneralStatisticsEntry 16 }

        vturAPWlan OBJECT IDENTIFIER ::= { vturAPSetup 2 }

-- vturAPWlanBasicTable

        vturAPWlanBasicTable  OBJECT-TYPE
        SYNTAX	SEQUENCE OF VturAPWlanBasicEntry
        ACCESS  not-accessible
        STATUS  mandatory
        DESCRIPTION
                 	""
        ::= { vturAPWlan 1 }

		vturAPWlanBasicEntry OBJECT-TYPE
       		SYNTAX	VturAPWlanBasicEntry
       		ACCESS	not-accessible
       		STATUS	mandatory
	       	DESCRIPTION    	"An entry in VTUR AP Wlan Basic Table."
	       	INDEX          	{ dot1dBasePort }
	       	::= { vturAPWlanBasicTable 1 }

		VturAPWlanBasicEntry ::=
	       	SEQUENCE {
	        enable	INTEGER,
	        ssid	DisplayString,
	        bssid	MacAddress,
	        hidden	INTEGER,
	        channel	INTEGER,
	        mode	INTEGER,
	        txPower	INTEGER,
	        multicastRate	INTEGER
	        }


		        enable OBJECT-TYPE
        		SYNTAX  INTEGER
        		ACCESS  read-write
        		STATUS  mandatory
        		DESCRIPTION
                      		"0: disable wlan
                      		 1: enable wlan"
        		::= { vturAPWlanBasicEntry 1 }

		        ssid OBJECT-TYPE
        		SYNTAX  DisplayString
        		ACCESS  read-write
        		STATUS  mandatory
        		DESCRIPTION
                      		"SSID of the AP"
        		::= { vturAPWlanBasicEntry 2 }

		        bssid OBJECT-TYPE
        		SYNTAX  MacAddress
        		ACCESS  read-only
        		STATUS  mandatory
        		DESCRIPTION
                      		"Mac address of AP"
        		::= { vturAPWlanBasicEntry 3 }

		        hidden OBJECT-TYPE
        		SYNTAX  INTEGER
        		ACCESS  read-write
        		STATUS  mandatory
        		DESCRIPTION
                      		"0: not hide AP's SSID
                      		 1: hide AP's SSID"
        		::= { vturAPWlanBasicEntry 4 }

		        channel OBJECT-TYPE
        		SYNTAX  INTEGER
        		ACCESS  read-write
        		STATUS  mandatory
        		DESCRIPTION
                      		"Channel number of the AP"
        		::= { vturAPWlanBasicEntry 5 }

		        mode OBJECT-TYPE
        		SYNTAX  INTEGER
        		ACCESS  read-write
        		STATUS  mandatory
        		DESCRIPTION
                      		"1: B or G mix mode
                      		 2: Pure G mode
                      		 3: Pure B mode"
        		::= { vturAPWlanBasicEntry 6 }

		        txPower OBJECT-TYPE
        		SYNTAX  INTEGER
        		ACCESS  read-write
        		STATUS  mandatory
        		DESCRIPTION
                      		"Transmit power
                      		 1: 30 mW
                      		 2: 15 mW"
        		::= { vturAPWlanBasicEntry 7 }

		        multicastRate OBJECT-TYPE
        		SYNTAX  INTEGER
        		ACCESS  read-write
        		STATUS  mandatory
        		DESCRIPTION
                      		"Transmit rate of multicast packets. If the value not zero, transmit rate is value * 500kbps
                      		 0: auto
                      		 2, 4, 11, 22: Transmit rate = 1, 2, 5.5, 11 Mbps when mode = pure B mode
                      		 12, 18, 24, 36, 48, 96, 108: Transmit rate = 6, 9, 12, 18, 24, 36, 48, 54 Mbps when mode = pure G mode2, 4, 11, 12, 18, 22, 24, 36, 48, 96, 108: Transmit rate = 1, 2, 5.5, 6, 9, 11, 12, 18, 24, 36, 48, 54 Mbps when mode = B or G mix mode"
        		::= { vturAPWlanBasicEntry 8 }

-- vturAPWlanSecurityTable

        vturAPWlanSecurityTable  OBJECT-TYPE
        SYNTAX	SEQUENCE OF VturAPWlanSecurityEntry
        ACCESS  not-accessible
        STATUS  mandatory
        DESCRIPTION
                 	""
        ::= { vturAPWlan 2 }

		vturAPWlanSecurityEntry OBJECT-TYPE
       		SYNTAX	VturAPWlanSecurityEntry
       		ACCESS	not-accessible
       		STATUS	mandatory
	       	DESCRIPTION    	"An entry in VTUR AP Wlan Security Table."
	       	INDEX          	{ dot1dBasePort }
	       	::= { vturAPWlanSecurityTable 1 }

		VturAPWlanSecurityEntry ::=
	       	SEQUENCE {
	        securityMode	INTEGER,
	        wepEncryp	INTEGER,
	        keyId		INTEGER,
	        key1		DisplayString,
	        key2		DisplayString,
	        key3		DisplayString,
	        key4		DisplayString,
	        psk		DisplayString,
	        wpaMix		INTEGER,
	        reAuthTime	INTEGER,
	        idleTime	INTEGER,
	        gtkTime		INTEGER
	        }

		        securityMode OBJECT-TYPE
        		SYNTAX  INTEGER
        		ACCESS  read-write
        		STATUS  mandatory
        		DESCRIPTION
                      		"1: No security
                      		 2: Static WEP
                      		 3: WPA-PSK
                      		 4: WPA
                      		 5: WPA2
                      		 6: WPA2-PSK"
        		::= { vturAPWlanSecurityEntry 1 }

		        wepEncryp OBJECT-TYPE
        		SYNTAX  INTEGER
        		ACCESS  read-write
        		STATUS  mandatory
        		DESCRIPTION
                      		"This field is for SecurityMode = static WEP.
                      		 1: 64-Bit
                      		 2: 128-Bit"
        		::= { vturAPWlanSecurityEntry 2 }

		        keyId OBJECT-TYPE
        		SYNTAX  INTEGER
        		ACCESS  read-write
        		STATUS  mandatory
        		DESCRIPTION
                      		"This field is for SecurityMode = static WEP. It indicate which key will be used for encryption. 
                      		 If KeyId is equal to 1, AP will use Key1 to encrypt frame."
        		::= { vturAPWlanSecurityEntry 3 }

		        key1 OBJECT-TYPE
        		SYNTAX  DisplayString
        		ACCESS  read-write
        		STATUS  mandatory
        		DESCRIPTION
                      		"This field is for SecurityMode = static WEP.
                      		 If WEPEncryp is 64-Bit, key1 will be 10 heximal digits.
                      		 If WEPEncryp is 128-Bit, key1 will be 26 heximal digits."
        		::= { vturAPWlanSecurityEntry 4 }

		        key2 OBJECT-TYPE
        		SYNTAX  DisplayString
        		ACCESS  read-write
        		STATUS  mandatory
        		DESCRIPTION
                      		"This field is for SecurityMode = static WEP.
                      		 If WEPEncryp is 64-Bit, key2 will be 10 heximal digits.
                      		 If WEPEncryp is 128-Bit, key2 will be 26 heximal digits."
        		::= { vturAPWlanSecurityEntry 5 }

		        key3 OBJECT-TYPE
        		SYNTAX  DisplayString
        		ACCESS  read-write
        		STATUS  mandatory
        		DESCRIPTION
                      		"This field is for SecurityMode = static WEP.
                      		 If WEPEncryp is 64-Bit, key3 will be 10 heximal digits.
                      		 If WEPEncryp is 128-Bit, key3 will be 26 heximal digits."
        		::= { vturAPWlanSecurityEntry 6 }

		        key4 OBJECT-TYPE
        		SYNTAX  DisplayString
        		ACCESS  read-write
        		STATUS  mandatory
        		DESCRIPTION
                      		"This field is for SecurityMode = static WEP.
                      		 If WEPEncryp is 64-Bit, key4 will be 10 heximal digits.
                      		 If WEPEncryp is 128-Bit, key4 will be 26 heximal digits."
        		::= { vturAPWlanSecurityEntry 7 }

		        psk OBJECT-TYPE
        		SYNTAX  DisplayString
        		ACCESS  read-write
        		STATUS  mandatory
        		DESCRIPTION
                      		"This field is for SecurityMode = WPA-PSK or WPA2-PSK. It means Pre-Shared Key"
        		::= { vturAPWlanSecurityEntry 8 }

		        wpaMix OBJECT-TYPE
        		SYNTAX  INTEGER
        		ACCESS  read-write
        		STATUS  mandatory
        		DESCRIPTION
                      		"This field is for SecurityMode = WPA2 or WPA2-PSK. 
                      		 When WPAMix is enable on WPA2, stations with WPA2-AES or WPA-TKIP could connect to AP.
                      		 When WPAMix is enable on WPA2-PSK, stations with WPA2-PSK-AES or WPA-PSK-TKIP could connect to AP.
                      		 0: disable
                      		 1: enable"
        		::= { vturAPWlanSecurityEntry 9 }

		        reAuthTime OBJECT-TYPE
        		SYNTAX  INTEGER
        		ACCESS  read-write
        		STATUS  mandatory
        		DESCRIPTION
                      		"This field is for SecurityMode = WPA-PSK, WPA2-PSK, WPA or WPA2. 
                      		 AP will trigger re-authentication with station every [ReAuthTime] seconds."
        		::= { vturAPWlanSecurityEntry 10 }

		        idleTime OBJECT-TYPE
        		SYNTAX  INTEGER
        		ACCESS  read-write
        		STATUS  mandatory
        		DESCRIPTION
                      		"This field is for SecurityMode = WPA-PSK, WPA2-PSK, WPA or WPA2. 
                      		 AP will flush station’s information if there are no packets from station for [idleTime] seconds."
        		::= { vturAPWlanSecurityEntry 11 }

		        gtkTime OBJECT-TYPE
        		SYNTAX  INTEGER
        		ACCESS  read-write
        		STATUS  mandatory
        		DESCRIPTION
                      		"This field is for SecurityMode = WPA-PSK, WPA2-PSK, WPA or WPA2. 
                      		 AP will trigger the update of group key with station every [GTKTime] seconds."
        		::= { vturAPWlanSecurityEntry 12 }

-- vturAPWlanRadiusTable

        vturAPWlanRadiusTable  OBJECT-TYPE
        SYNTAX	SEQUENCE OF VturAPWlanRadiusEntry
        ACCESS  not-accessible
        STATUS  mandatory
        DESCRIPTION
                 	""
        ::= { vturAPWlan 3 }

		vturAPWlanRadiusEntry OBJECT-TYPE
       		SYNTAX	VturAPWlanRadiusEntry
       		ACCESS	not-accessible
       		STATUS	mandatory
	       	DESCRIPTION    	"An entry in VTUR AP Wlan Security Table."
	       	INDEX          	{ dot1dBasePort }
	       	::= { vturAPWlanRadiusTable 1 }

		VturAPWlanRadiusEntry ::=
	       	SEQUENCE {
	        authServIP	InetAddress,
	        authServPort	INTEGER,
	        authServSecret	DisplayString,
	        accServActive	INTEGER,
	        accServIP	InetAddress,
	        accServPort	INTEGER,
	        accServSecret	DisplayString
	        }


		        authServIP OBJECT-TYPE
			SYNTAX      InetAddress
        		ACCESS  read-write
        		STATUS  mandatory
        		DESCRIPTION
                      		"This field is the IP address of authentication server."
        		::= { vturAPWlanRadiusEntry 1 }

		        authServPort OBJECT-TYPE
        		SYNTAX  INTEGER
        		ACCESS  read-write
        		STATUS  mandatory
        		DESCRIPTION
                      		"This field is the port number of authentication server."
        		::= { vturAPWlanRadiusEntry 2 }

		        authServSecret OBJECT-TYPE
        		SYNTAX  DisplayString
        		ACCESS  read-write
        		STATUS  mandatory
        		DESCRIPTION
                      		"This field is the shared secret of authentication server."
        		::= { vturAPWlanRadiusEntry 3 }

		        accServActive OBJECT-TYPE
        		SYNTAX  INTEGER
        		ACCESS  read-write
        		STATUS  mandatory
        		DESCRIPTION
                      		"This field is for activating or inactivating accounting server.
                      		 0: inactivate accounting server.
                      		 1: activate accounting server"
        		::= { vturAPWlanRadiusEntry 4 }


		        accServIP OBJECT-TYPE
        		SYNTAX      InetAddress
        		ACCESS  read-write
        		STATUS  mandatory
        		DESCRIPTION
                      		"This field is the IP address of accounting server."
        		::= { vturAPWlanRadiusEntry 5 }

		        accServPort OBJECT-TYPE
        		SYNTAX  INTEGER
        		ACCESS  read-write
        		STATUS  mandatory
        		DESCRIPTION
                      		"This field is the port number of accounting server."
        		::= { vturAPWlanRadiusEntry 6 }

		        accServSecret OBJECT-TYPE
        		SYNTAX  DisplayString
        		ACCESS  read-write
        		STATUS  mandatory
        		DESCRIPTION
                      		"This field is the shared secret of accounting server."
        		::= { vturAPWlanRadiusEntry 7 }



       	vturAPWlanMacFilter OBJECT IDENTIFIER ::= { vturAPWlan 4 }
-- vturAPWlanMacFilterTable

        vturAPWlanMacFilterTable  OBJECT-TYPE
        SYNTAX	SEQUENCE OF VturAPWlanMacFilterEntry
        ACCESS  not-accessible
        STATUS  mandatory
        DESCRIPTION
                 	""
        ::= { vturAPWlanMacFilter 1 }

		vturAPWlanMacFilterEntry OBJECT-TYPE
       		SYNTAX	VturAPWlanMacFilterEntry
       		ACCESS	not-accessible
       		STATUS	mandatory
	       	DESCRIPTION    	"An entry in VTUR AP Wlan Mac Filter Table."
	       	INDEX          	{ dot1dBasePort }
	       	::= { vturAPWlanMacFilterTable 1 }

		VturAPWlanMacFilterEntry ::=
	       	SEQUENCE {
	        macFltActive	INTEGER,
	        macFltAction	INTEGER
	        }

		        macFltActive OBJECT-TYPE
        		SYNTAX  INTEGER
        		ACCESS  read-write
        		STATUS  mandatory
        		DESCRIPTION
                      		"Activate or inactivate wlan MAC filter.
                      		 0: Inactive
                      		 1: Active"
        		::= { vturAPWlanMacFilterEntry 1 }

		        macFltAction OBJECT-TYPE
        		SYNTAX  INTEGER
        		ACCESS  read-write
        		STATUS  mandatory
        		DESCRIPTION
                      		"0: allow association for station which matches the address which is defined in MacFltAddr1~MacFltAddr8.
                      		 1: deny association for station which matches the address which is defined in MacFltAddr1~MacFltAddr8."
        		::= { vturAPWlanMacFilterEntry 2 }


-- vturAPWlanMacFltAddrTable

        vturAPWlanMacFltAddrTable  OBJECT-TYPE
        SYNTAX	SEQUENCE OF VturAPWlanMacFltAddrEntry
        ACCESS  not-accessible
        STATUS  mandatory
        DESCRIPTION
                 	""
        ::= { vturAPWlanMacFilter 2 }

		vturAPWlanMacFltAddrEntry OBJECT-TYPE
       		SYNTAX	VturAPWlanMacFltAddrEntry
       		ACCESS	not-accessible
       		STATUS	mandatory
	       	DESCRIPTION    	"An entry in VTUR AP Wlan Security Table."
	       	INDEX          	{ dot1dBasePort, fltStaIndex }
	       	::= { vturAPWlanMacFltAddrTable 1 }
	       	
		VturAPWlanMacFltAddrEntry ::=
	       	SEQUENCE {
	        fltStaIndex	INTEGER,
	        macFltAddr	MacAddress
	        }

		        fltStaIndex  OBJECT-TYPE
        		SYNTAX  INTEGER
        		ACCESS  read-only
        		STATUS  mandatory
        		DESCRIPTION
                      		"The index for Mac filter"
        		::= { vturAPWlanMacFltAddrEntry 1 }

		        macFltAddr  OBJECT-TYPE
        		SYNTAX  MacAddress
        		ACCESS  read-write
        		STATUS  mandatory
        		DESCRIPTION
                      		"The address for Mac filter"
        		::= { vturAPWlanMacFltAddrEntry 2 }


-- vturAPWlanStatisticsTable

	
	vturAPWlanStatisticsTable  OBJECT-TYPE
        SYNTAX	SEQUENCE OF VturAPWlanStatisticsEntry
        ACCESS  not-accessible
        STATUS  mandatory
        DESCRIPTION
                 	""
        ::= { vturAPWlan 5 }

		vturAPWlanStatisticsEntry OBJECT-TYPE
       		SYNTAX	VturAPWlanStatisticsEntry
       		ACCESS	not-accessible
       		STATUS	mandatory
	       	DESCRIPTION    	"An entry in VTUR AP Wlan Security Table."
	       	INDEX          	{ dot1dBasePort }
	       	::= { vturAPWlanStatisticsTable 1 }

		VturAPWlanStatisticsEntry ::=
	       	SEQUENCE {
	        inPkts		INTEGER,
	        inOctets	INTEGER,
	        inUCasts	INTEGER,
	        inMCasts	INTEGER,
	        rxFCSErrors	INTEGER,
	        outPkts		INTEGER,
	        outOctets	INTEGER,
	        outUCasts	INTEGER,
	        outMCasts	INTEGER
	        }

		        inPkts  OBJECT-TYPE
        		SYNTAX  INTEGER
        		ACCESS  read-only
        		STATUS  mandatory
        		DESCRIPTION
                      		"Same as WLANRxPkts in vturAPGeneral.vturAPGeneralStatistics MIB "
        		::= { vturAPWlanStatisticsEntry 1 }

		        inOctets  OBJECT-TYPE
        		SYNTAX  INTEGER
        		ACCESS  read-only
        		STATUS  mandatory
        		DESCRIPTION
                      		"Same as WLANRxBytes in vturAPGeneral.vturAPGeneralStatistics MIB "
        		::= { vturAPWlanStatisticsEntry 2 }

		        inUCasts  OBJECT-TYPE
        		SYNTAX  INTEGER
        		ACCESS  read-only
        		STATUS  mandatory
        		DESCRIPTION
                      		"Received unicast frames"
        		::= { vturAPWlanStatisticsEntry 3 }

		        inMCasts  OBJECT-TYPE
        		SYNTAX  INTEGER
        		ACCESS  read-only
        		STATUS  mandatory
        		DESCRIPTION
                      		"Received multicast frames"
        		::= { vturAPWlanStatisticsEntry 4 }

		        rxFCSErrors  OBJECT-TYPE
        		SYNTAX  INTEGER
        		ACCESS  read-only
        		STATUS  mandatory
        		DESCRIPTION
                      		"Same as WLANRxErrs in vturAPGeneral.vturAPGeneralStatistics MIB"
        		::= { vturAPWlanStatisticsEntry 5 }

		        outPkts  OBJECT-TYPE
        		SYNTAX  INTEGER
        		ACCESS  read-only
        		STATUS  mandatory
        		DESCRIPTION
                      		"Same as WLANTxPkts in vturAPGeneral.vturAPGeneralStatistics MIB"
        		::= { vturAPWlanStatisticsEntry 6 }

		        outOctets  OBJECT-TYPE
        		SYNTAX  INTEGER
        		ACCESS  read-only
        		STATUS  mandatory
        		DESCRIPTION
                      		"Same as WLANTxBytes in vturAPGeneral.vturAPGeneralStatistics MIB"
        		::= { vturAPWlanStatisticsEntry 7 }

		        outUCasts  OBJECT-TYPE
        		SYNTAX  INTEGER
        		ACCESS  read-only
        		STATUS  mandatory
        		DESCRIPTION
                      		"Transmitted unicast frames"
        		::= { vturAPWlanStatisticsEntry 8 }

		        outMCasts  OBJECT-TYPE
        		SYNTAX  INTEGER
        		ACCESS  read-only
        		STATUS  mandatory
        		DESCRIPTION
                      		"Transmitted multicast frames"
        		::= { vturAPWlanStatisticsEntry 9 }


-- vturAPWlanStaListTable


	vturAPWlanStaListTable  OBJECT-TYPE
        SYNTAX	SEQUENCE OF VturAPWlanStaListEntry
        ACCESS  not-accessible
        STATUS  mandatory
        DESCRIPTION
                 	""
        ::= { vturAPWlan 6 }

		vturAPWlanStaListEntry OBJECT-TYPE
       		SYNTAX	VturAPWlanStaListEntry
       		ACCESS	not-accessible
       		STATUS	mandatory
	       	DESCRIPTION    	"An entry in VTUR AP Wlan Security Table."
	       	INDEX          	{ dot1dBasePort, staIndex }
	       	::= { vturAPWlanStaListTable 1 }

		VturAPWlanStaListEntry ::=
	       	SEQUENCE {
	        staIndex	INTEGER,
	        staMacAddr	MacAddress
	        }

		        staIndex  OBJECT-TYPE
        		SYNTAX  INTEGER
        		ACCESS  read-only
        		STATUS  mandatory
        		DESCRIPTION
                      		"The index of associated WLAN STA. Max = 32, Min = 1"
        		::= { vturAPWlanStaListEntry 1 }
        	
		        staMacAddr  OBJECT-TYPE
        		SYNTAX  MacAddress
        		ACCESS  read-only
        		STATUS  mandatory
        		DESCRIPTION
                      		"The address of associated WLAN STA "
        		::= { vturAPWlanStaListEntry 2 }




-- vturConsoleSetup
		vturConsoleSetup     	OBJECT IDENTIFIER ::= { vturSwitchSetup 8 }

		vturConsoleTable OBJECT-TYPE
       	SYNTAX	SEQUENCE OF VturConsoleEntry
       	ACCESS  not-accessible
       	STATUS  mandatory
       	DESCRIPTION
      	      	""
       	::= { vturConsoleSetup 1 }

	vturConsoleEntry OBJECT-TYPE
       	SYNTAX	VturConsoleEntry
       	ACCESS	not-accessible
       	STATUS	mandatory
       	DESCRIPTION    	"An entry in vturConsoleTable."
       	INDEX          	{ dot1dBasePort}
       	::= { vturConsoleTable 1 }

        VturConsoleEntry ::=
       	SEQUENCE {
       	vturConsoleSet			INTEGER,
       	vturConsoleAdminPassword	OCTET STRING,
       	vturConsoleUserPassword		OCTET STRING
        }


        vturConsoleSet OBJECT-TYPE
        SYNTAX  INTEGER {
         		enable(1),
         		disable(2)
        }
        ACCESS  read-write
        STATUS  mandatory
        DESCRIPTION
                      ""
        ::= { vturConsoleEntry 1 }

	vturConsoleAdminPassword OBJECT-TYPE
		SYNTAX  OCTET STRING
		ACCESS  read-write
		STATUS  mandatory
		DESCRIPTION
			"The operation for vtur device admin password"
		::= { vturConsoleEntry 2 }
		
	vturConsoleUserPassword OBJECT-TYPE
		SYNTAX  OCTET STRING
		ACCESS  read-write
		STATUS  mandatory
		DESCRIPTION
			"The operation for vtur device user password"
		::= { vturConsoleEntry 3 }		

-- vturRemoteFunctionSetup
	vturRemoteFunctionSetup     	OBJECT IDENTIFIER ::= { vturSwitchSetup 9 }

	remoteFunctionTable OBJECT-TYPE
       	SYNTAX	SEQUENCE OF RemoteFunctionEntry
       	ACCESS  not-accessible
       	STATUS  mandatory
       	DESCRIPTION
      	      	""
       	::= { vturRemoteFunctionSetup 1 }

	remoteFunctionEntry OBJECT-TYPE
       	SYNTAX	RemoteFunctionEntry
       	ACCESS	not-accessible
       	STATUS	mandatory
       	DESCRIPTION    	"An entry in RemoteFunctionTable."
       	INDEX          	{ dot1dBasePort}
       	::= { remoteFunctionTable 1 }

        RemoteFunctionEntry ::=
       	SEQUENCE {
       	telnet  INTEGER,
       	tftp    INTEGER,
       	web     INTEGER,
       	snmp    INTEGER,
       	ssh     INTEGER,
       	wireless INTEGER
        }


        telnet OBJECT-TYPE
        SYNTAX  INTEGER {
         		enable_all(1),
         		disable_all(2),
         		enable_lan_only(3),
         		enable_wan_only(4)
        }
        ACCESS  read-write
        STATUS  mandatory
        DESCRIPTION
                      ""
        ::= { remoteFunctionEntry 3 }

        tftp OBJECT-TYPE
        SYNTAX  INTEGER {
         		enable_all(1),
         		disable_all(2),
         		enable_lan_only(3),
         		enable_wan_only(4)
        }
        ACCESS  read-write
        STATUS  mandatory
        DESCRIPTION
                      ""
        ::= { remoteFunctionEntry 4 }

        web OBJECT-TYPE
        SYNTAX  INTEGER {
         		enable_all(1),
         		disable_all(2),
         		enable_lan_only(3),
         		enable_wan_only(4)
        }
        ACCESS  read-write
        STATUS  mandatory
        DESCRIPTION
                      ""
        ::= { remoteFunctionEntry 5 }

        snmp OBJECT-TYPE
        SYNTAX  INTEGER {
         		enable_all(1),
         		disable_all(2),
         		enable_lan_only(3),
         		enable_wan_only(4)
        }
        ACCESS  read-write
        STATUS  mandatory
        DESCRIPTION
                      ""
        ::= { remoteFunctionEntry 6 }

        ssh OBJECT-TYPE
        SYNTAX  INTEGER {
           		enable_all(1),
         		disable_all(2),
         		enable_lan_only(3),
         		enable_wan_only(4)
        }
        ACCESS  read-write
        STATUS  mandatory
        DESCRIPTION
                      ""
        ::= { remoteFunctionEntry 7 }

        wireless OBJECT-TYPE
        SYNTAX  INTEGER {
           		disable(1),
         		enable(2)
        }
        ACCESS  read-write
        STATUS  mandatory
        DESCRIPTION
                      ""
        ::= { remoteFunctionEntry 8 }
---------------------------------------------------------------------------
---------------------------------------------------------------------------
-- vturMacTableSetup
	vturMacTableSetup     	OBJECT IDENTIFIER ::= { vturSwitchSetup 10 }

	vturMacTable OBJECT-TYPE
       	SYNTAX	SEQUENCE OF VturMacTableEntry
       	ACCESS  not-accessible
       	STATUS  mandatory
       	DESCRIPTION
      	      	""
       	::= { vturMacTableSetup 1 }

	vturMacTableEntry OBJECT-TYPE
       	SYNTAX	VturMacTableEntry
       	ACCESS	not-accessible
       	STATUS	mandatory
       	DESCRIPTION    	"An entry in vturMacTable."
       	INDEX          	{ dot1dBasePort, staIndex}
       	::= { vturMacTable 1 }


	VturMacTableEntry ::=
       	SEQUENCE {
        vturMacIndex	INTEGER,
        vturMacAddr	MacAddress
        }

	        vturMacIndex  OBJECT-TYPE
       		SYNTAX  INTEGER
       		ACCESS  read-only
       		STATUS  mandatory
       		DESCRIPTION
			"The index of associated vtur STA. Max = 32, Min = 1"
        		::= { vturMacTableEntry 1 }
        	
	        vturMacAddr  OBJECT-TYPE
       		SYNTAX  MacAddress
       		ACCESS  read-only
       		STATUS  mandatory
       		DESCRIPTION
			"The address of associated vtur STA "
        		::= { vturMacTableEntry 2 }


-- vturLanSetup
	vturLanSetup     	OBJECT IDENTIFIER ::= { vturSwitchSetup 11 }

	vturLanTable OBJECT-TYPE
       	SYNTAX	SEQUENCE OF VturLanEntry
       	ACCESS  not-accessible
       	STATUS  mandatory
       	DESCRIPTION
      	      	""
       	::= { vturLanSetup 1 }

	vturLanEntry OBJECT-TYPE
       	SYNTAX	VturLanEntry
       	ACCESS	not-accessible
       	STATUS	mandatory
       	DESCRIPTION    	"An entry in vturLanTable."
       	INDEX          	{ dot1dBasePort }
       	::= { vturLanTable 1 }

        VturLanEntry ::=
       	SEQUENCE {
       	vturLanIP  IpAddress,
       	vturLanSubnetmask    IpAddress,
       	vturDHCPOption     INTEGER,
       	vturDHCPServerStartIPAddr    IpAddress,
       	vturDHCPServerEndIPAddr     IpAddress,
       	vturDHCPServerSubnetmask    IpAddress,
       	vturDHCPServerIPAddr    IpAddress
        }


        vturLanIP OBJECT-TYPE
        SYNTAX  IpAddress
        ACCESS  read-write
        STATUS  mandatory
        DESCRIPTION
                      ""
        ::= { vturLanEntry 1 }

        vturLanSubnetmask OBJECT-TYPE
        SYNTAX  IpAddress
        ACCESS  read-write
        STATUS  mandatory
        DESCRIPTION
                      ""
        ::= { vturLanEntry 2 }

        vturDHCPOption OBJECT-TYPE
        SYNTAX  INTEGER{
			disable_dhcp_server(1),
         	enable_dhcp_server(2),
         	dhcp_server_relay(3)
         	}
        ACCESS  read-write
        STATUS  mandatory
        DESCRIPTION
                      ""
        ::= { vturLanEntry 3 }

        vturDHCPServerStartIPAddr OBJECT-TYPE
        SYNTAX  IpAddress 
        ACCESS  read-write
        STATUS  mandatory
        DESCRIPTION
                      ""
        ::= { vturLanEntry 4 }

        vturDHCPServerEndIPAddr OBJECT-TYPE
        SYNTAX  IpAddress 
        ACCESS  read-write
        STATUS  mandatory
        DESCRIPTION
                      ""
        ::= { vturLanEntry 5 }
        
        vturDHCPServerSubnetmask OBJECT-TYPE
        SYNTAX  IpAddress 
        ACCESS  read-write
        STATUS  mandatory
        DESCRIPTION
                      ""
        ::= { vturLanEntry 6 }

        vturDHCPServerIPAddr OBJECT-TYPE
        SYNTAX  IpAddress 
        ACCESS  read-write
        STATUS  mandatory
        DESCRIPTION
                      ""
        ::= { vturLanEntry 7 }        
-----------------------------------------------------------------------------------------------
-- vturCFMSetup
	vturCFMSetup     	OBJECT IDENTIFIER ::= { vturSwitchSetup 12 }

	vturCFMTable OBJECT-TYPE
       	SYNTAX	SEQUENCE OF VturCFMEntry
       	ACCESS  not-accessible
       	STATUS  mandatory
       	DESCRIPTION
      	      	""
       	::= { vturCFMSetup 1 }

	vturCFMEntry OBJECT-TYPE
       	SYNTAX	VturCFMEntry
       	ACCESS	not-accessible
       	STATUS	mandatory
       	DESCRIPTION    	"An entry in vturCFMTable."
       	INDEX          	{ dot1dBasePort }
       	::= { vturCFMTable 1 }

        VturCFMEntry ::=
       	SEQUENCE {
       	vturCFMCommit	INTEGER,
       	vturCFMMdName  OCTET STRING,
       	vturCFMMaName    OCTET STRING,
       	vturCFMVid     INTEGER,
       	vturCFMMepId    Dot1agCfmMepId,
       	vturCFMMdLevel     INTEGER,
       	vturCFMAction    INTEGER,
       	vturCFMDestMAC    OCTET STRING,
       	vturCFMLBMCount   INTEGER,
       	vturCFMResultSentLBM     INTEGER,
       	vturCFMResultInorderLBM     INTEGER,
	vturCFMResultOutorderLBM     INTEGER,
	vturMACAddr		OCTET STRING,
       	vturCFMReadStatus	INTEGER	
        }

        vturCFMCommit OBJECT-TYPE
        SYNTAX  INTEGER
        {
		commit(1)
        }
        ACCESS  read-write
        STATUS  mandatory
        DESCRIPTION
                      "Set 1 to commit CFM operation and read value always return 0"
        ::= { vturCFMEntry 1 }

        vturCFMMdName OBJECT-TYPE
        SYNTAX  OCTET STRING
        ACCESS  read-write
        STATUS  mandatory
        DESCRIPTION
                      ""
        ::= { vturCFMEntry 2 }

        vturCFMMaName OBJECT-TYPE
        SYNTAX  OCTET STRING
        ACCESS  read-write
        STATUS  mandatory
        DESCRIPTION
                      ""
        ::= { vturCFMEntry 3 }

        vturCFMVid OBJECT-TYPE
        SYNTAX  INTEGER
        ACCESS  read-write
        STATUS  mandatory
        DESCRIPTION
                      ""
        ::= { vturCFMEntry 4 }

        vturCFMMepId OBJECT-TYPE
        SYNTAX  Dot1agCfmMepId 
        ACCESS  read-write
        STATUS  mandatory
        DESCRIPTION
                      ""
        ::= { vturCFMEntry 5 }

        vturCFMMdLevel OBJECT-TYPE
        SYNTAX  INTEGER 
        ACCESS  read-write
        STATUS  mandatory
        DESCRIPTION
                      ""
        ::= { vturCFMEntry 6 }
        
        vturCFMAction OBJECT-TYPE
        SYNTAX  INTEGER
    	{
	 	save(0),    	
        enable_cfm(1),
        disable_cfm(2),
        send_loopback_message(3),
        send_linktrace_message(4),
         reset_configuration(5)
        }        
        ACCESS  read-write
        STATUS  mandatory
        DESCRIPTION
                      "Currently only support 0:save ,3:send loopback message and 5:load cpe cfm default"
        ::= { vturCFMEntry 7 }

        vturCFMDestMAC OBJECT-TYPE
        SYNTAX  OCTET STRING 
        ACCESS  read-write
        STATUS  mandatory
        DESCRIPTION
                      ""
        ::= { vturCFMEntry 8 }    

        vturCFMLBMCount OBJECT-TYPE
        SYNTAX  INTEGER 
        ACCESS  read-write
        STATUS  mandatory
        DESCRIPTION
                      ""
        ::= { vturCFMEntry 9 }            

        vturCFMResultSentLBM OBJECT-TYPE
        SYNTAX  INTEGER 
        ACCESS  read-only
        STATUS  mandatory
        DESCRIPTION
                      ""
        ::= { vturCFMEntry 10 }            

        vturCFMResultInorderLBM OBJECT-TYPE
        SYNTAX  INTEGER 
        ACCESS  read-only
        STATUS  mandatory
        DESCRIPTION
                      ""
        ::= { vturCFMEntry 11 }            

        vturCFMResultOutorderLBM OBJECT-TYPE
        SYNTAX  INTEGER 
        ACCESS  read-only
        STATUS  mandatory
        DESCRIPTION
                      ""
        ::= { vturCFMEntry 12 }  
        
        vturMACAddr OBJECT-TYPE
        SYNTAX  OCTET STRING 
        ACCESS  read-only
        STATUS  mandatory
        DESCRIPTION
                      "CPE MAC address"
        ::= { vturCFMEntry 13 }             
        
        vturCFMReadStatus OBJECT-TYPE
        SYNTAX  INTEGER
        {
       	commit(1)
        }
        ACCESS  read-write
        STATUS  mandatory
        DESCRIPTION
                      "Set 1 to commit CFM Read operation and read value always return 0"
        ::= { vturCFMEntry 14 }               
------------------------------------------------------------------------------------------------

-- vturInfo
		vturInfo     	OBJECT IDENTIFIER ::= { ves1616pe54 37 }

-- vturInfoTable
    vturInfoTable OBJECT-TYPE
       	SYNTAX	SEQUENCE OF VturInfoEntry
       	ACCESS  not-accessible
       	STATUS  mandatory
       	DESCRIPTION
      	      	""
       	::= { vturInfo 1 }

	vturInfoEntry OBJECT-TYPE
       	SYNTAX	VturInfoEntry
       	ACCESS	not-accessible
       	STATUS	mandatory
       	DESCRIPTION    	"An entry in vturInfoTable."
       	INDEX          	{ dot1dBasePort }
       	::= { vturInfoTable 1 }

    VturInfoEntry ::=
       	SEQUENCE {
        vturName	DisplayString,
        vturSysVersion	DisplayString,
        vturModemCodeVersion	DisplayString
        }

    vturName OBJECT-TYPE
        SYNTAX  DisplayString
        ACCESS  read-only
        STATUS  mandatory
        DESCRIPTION
                   	"Display remote device name"
       	::= { vturInfoEntry 1 }

    vturSysVersion OBJECT-TYPE
        SYNTAX  DisplayString
        ACCESS  read-only
        STATUS  mandatory
        DESCRIPTION
                    	"Display remote device system version info"
        ::= { vturInfoEntry 2 }

    vturModemCodeVersion OBJECT-TYPE
        SYNTAX  DisplayString
        ACCESS  read-only
        STATUS  mandatory
        DESCRIPTION
                    	"Display remote device VDSL modem code version info"
        ::= { vturInfoEntry 3 }    

  --  protocol-based VLAN
	protoBasedVlanSetup     	OBJECT IDENTIFIER ::= { ves1616pe54 38 }
	
	    protoBasedVlanTable  OBJECT-TYPE
	    SYNTAX	SEQUENCE OF ProtoBasedVlanEntry 
	    ACCESS  not-accessible
	    STATUS  mandatory
	    DESCRIPTION
	             	""
	    ::= { protoBasedVlanSetup 1 }	

	protoBasedVlanEntry  OBJECT-TYPE
        SYNTAX	ProtoBasedVlanEntry 
        ACCESS	not-accessible
        STATUS	mandatory
        DESCRIPTION    	"An entry in protoBasedVlanTable."
        INDEX          	{ protoBasedVlanPort, protoBasedVlanPacketType, protoBasedVlanEtherType }
        ::= { protoBasedVlanTable 1 }

        ProtoBasedVlanEntry ::=
           SEQUENCE {
            protoBasedVlanPort			INTEGER,
        	protoBasedVlanPacketType	INTEGER,
        	protoBasedVlanEtherType		INTEGER,
        	protoBasedVlanName			DisplayString,
        	protoBasedVlanVid			INTEGER,
        	protoBasedVlanPriority		INTEGER,
        	protoBasedVlanState			RowStatus
           }

        protoBasedVlanPort OBJECT-TYPE
        SYNTAX  INTEGER
        ACCESS  read-only
        STATUS  mandatory
        DESCRIPTION
                      	""
        ::= { protoBasedVlanEntry 1 }

        protoBasedVlanPacketType OBJECT-TYPE
        SYNTAX  INTEGER {
        	etherII(1),
        	snap(2),
        	llc(3)
        }
        ACCESS  read-only
        STATUS  mandatory
        DESCRIPTION
                      	""
        ::= { protoBasedVlanEntry 2 }

        protoBasedVlanEtherType OBJECT-TYPE
        SYNTAX  INTEGER
        ACCESS  read-only
        STATUS  mandatory
        DESCRIPTION
                      	""
        ::= { protoBasedVlanEntry 3 }

        protoBasedVlanName OBJECT-TYPE
        SYNTAX  DisplayString (SIZE (0..31))
        ACCESS  read-write
        STATUS  mandatory
        DESCRIPTION
                      	""
        ::= { protoBasedVlanEntry 4 }

        protoBasedVlanVid OBJECT-TYPE
        SYNTAX  INTEGER (1..4094)
        ACCESS  read-write
        STATUS  mandatory
        DESCRIPTION
                      	""
        ::= { protoBasedVlanEntry 5 }

        protoBasedVlanPriority OBJECT-TYPE
        SYNTAX  INTEGER (0..7)
        ACCESS  read-write
        STATUS  mandatory
        DESCRIPTION
                      	""
        ::= { protoBasedVlanEntry 6 }

        protoBasedVlanState OBJECT-TYPE
        SYNTAX  RowStatus
        ACCESS  read-create
        STATUS  mandatory
        DESCRIPTION
                      	""
        ::= { protoBasedVlanEntry 7 } 
                                             
      
--  classifierSetup
	classifierSetup     	OBJECT IDENTIFIER ::= { ves1616pe54 39 }

        classifierRuleTable	OBJECT-TYPE
        SYNTAX	SEQUENCE OF ClassifierRuleEntry
        ACCESS  not-accessible
        STATUS  mandatory
        DESCRIPTION
                 	""
        ::= { classifierSetup 1 }

		classifierRuleEntry OBJECT-TYPE
        SYNTAX	ClassifierRuleEntry
        ACCESS	not-accessible
        STATUS	mandatory
        DESCRIPTION    	"An entry in classifierRuleTable."
        INDEX          	{classifierName }
        ::= { classifierRuleTable 1 }

      	ClassifierRuleEntry ::=
		SEQUENCE {
        	classifierName		DisplayString,      
        	classifierEnable	INTEGER, 
        	classifierPacketFormat INTEGER,
        	classifierVlanId 	INTEGER,
        	classifier8021pPriority INTEGER,
        	classifierEtherType INTEGER,
        	classifierSrcMAC 	MacAddress,
        	classifierIncomingPort INTEGER,
        	classifierDstMAC 	MacAddress,
        	classifierDSCP		INTEGER,
        	classifierIpProtocol INTEGER,
        	classifierEstablishOnly INTEGER,
        	classifierSrcIp	    IpAddress,
        	classifierSrcIpMask	INTEGER,
        	classifierSrcSocket INTEGER,
        	classifierDstIp		IpAddress,  
        	classifierDstIpMask	INTEGER,  
        	classifierDstSocket INTEGER,
        	classifierRowstatus RowStatus,
        	classifierSrcIpv6	    Ipv6Address,
        	classifierSrcIpv6Mask	INTEGER, 
        	classifierDstIpv6		Ipv6Address,
        	classifierDstIpv6Mask	INTEGER       	
           }                                             
                        
        classifierName OBJECT-TYPE
        SYNTAX  DisplayString
        ACCESS  read-only
        STATUS  mandatory
        DESCRIPTION
                      	"Name of classifier rule."
        ::= { classifierRuleEntry 1 }                        
                        
        classifierEnable OBJECT-TYPE
        SYNTAX  EnabledStatus
        ACCESS  read-write
        STATUS  mandatory
        DESCRIPTION
        	"Classifier rule enabled/disabled."
        ::= { classifierRuleEntry 2 }

        classifierPacketFormat OBJECT-TYPE
        SYNTAX  INTEGER   
        {
      		all(1),
 		ethernetII-untagged(2),
		ethernetII-tagged(3),
     		ethernet802_3-untagged(4),
      		ethernet802_3-tagged(5)
        }
        ACCESS  read-write
        STATUS  mandatory
        DESCRIPTION
        	"Packet format for classifier rule. All(1), 802.3 untagged(2), 802.3 tagged(3), EthernetII untagged(4), EthernetII tagged(5)."
        ::= { classifierRuleEntry 3 }
                                             
   		classifierVlanId OBJECT-TYPE
        SYNTAX  INTEGER
        ACCESS  read-write
        STATUS  mandatory
        DESCRIPTION
                      	"Vlan id for classifer rule, 1~4094."
        ::= { classifierRuleEntry 4 }

   		classifier8021pPriority OBJECT-TYPE
        SYNTAX  INTEGER
        ACCESS  read-write
        STATUS  mandatory
        DESCRIPTION
                      	"802.1p priority for classifier rule, 0~7."
        ::= { classifierRuleEntry 5 }      
        
   		classifierEtherType OBJECT-TYPE
        SYNTAX  INTEGER 
        ACCESS  read-write
        STATUS  mandatory
        DESCRIPTION
                      	"Ether type for classifier rule, in decimal expression."
        ::= { classifierRuleEntry 6 }
         
        classifierSrcMAC OBJECT-TYPE
        SYNTAX  MacAddress
        ACCESS  read-write
        STATUS  mandatory
        DESCRIPTION
                      	"Source mac address for classifier rule"
        ::= { classifierRuleEntry 7 }
     	
        classifierIncomingPort OBJECT-TYPE
        SYNTAX  INTEGER
        ACCESS  read-write
        STATUS  mandatory
        DESCRIPTION
                      	"Incoming Port for classifier rule"                      	
        ::= { classifierRuleEntry 8 }

        classifierDstMAC OBJECT-TYPE
        SYNTAX  MacAddress
        ACCESS  read-write
        STATUS  mandatory
        DESCRIPTION
                      	"Destination mac address for classifier rule"
        ::= { classifierRuleEntry 9 }
         
        classifierDSCP OBJECT-TYPE
        SYNTAX  INTEGER
        ACCESS  read-write
        STATUS  mandatory
        DESCRIPTION
                      	"DSCP for classifier rule"                      	
        ::= { classifierRuleEntry 10 }                              
        
        classifierIpProtocol OBJECT-TYPE
        SYNTAX  INTEGER
        ACCESS  read-write
        STATUS  mandatory
        DESCRIPTION
                      	"IP Protocol for classifier rule"                      	
        ::= { classifierRuleEntry 11 }       
           
        classifierEstablishOnly OBJECT-TYPE
        SYNTAX  EnabledStatus
        ACCESS  read-write
        STATUS  mandatory
        DESCRIPTION
                      	"IP Protocol for EstablishOnly for classifier rule"                      	
        ::= { classifierRuleEntry 12 }  
           
    	classifierSrcIp OBJECT-TYPE
        SYNTAX  IpAddress
        ACCESS  read-write
        STATUS  mandatory
        DESCRIPTION
                      	"Source IP address for classifier rule"
        ::= { classifierRuleEntry 13 }
        
        classifierSrcIpMask OBJECT-TYPE
        SYNTAX  INTEGER
        ACCESS  read-write
        STATUS  mandatory
        DESCRIPTION
                      	"Source IP Mask for classifier rule"
        ::= { classifierRuleEntry 14 }
 
        classifierSrcSocket OBJECT-TYPE
        SYNTAX  INTEGER
        ACCESS  read-write
        STATUS  mandatory
        DESCRIPTION
                      	"Source Socket Number for classifier rule"                      	
        ::= { classifierRuleEntry 15 }
        
        classifierDstIp OBJECT-TYPE
        SYNTAX  IpAddress
        ACCESS  read-write
        STATUS  mandatory
        DESCRIPTION
                      	"Destination IP address for classifier rule"
        ::= { classifierRuleEntry 16 }
        
        classifierDstIpMask OBJECT-TYPE
        SYNTAX  INTEGER
        ACCESS  read-write
        STATUS  mandatory
        DESCRIPTION
                      	"Destination IP Mask for classifier rule"
        ::= { classifierRuleEntry 17 }
 
        classifierDstSocket OBJECT-TYPE
        SYNTAX  INTEGER
        ACCESS  read-write
        STATUS  mandatory
        DESCRIPTION
                      	"Destination Socket Number for classifier rule"                      	
        ::= { classifierRuleEntry 18 }
        
        classifierRowstatus OBJECT-TYPE
        SYNTAX  RowStatus
        ACCESS  read-create
        STATUS  mandatory
        DESCRIPTION
                      	"Row Status for classifier rule"
        ::= { classifierRuleEntry 19 } 
      
        classifierSrcIpv6 OBJECT-TYPE
        SYNTAX  Ipv6Address
        ACCESS  read-write
        STATUS  mandatory
        DESCRIPTION
                      	"Source IPv6 address for classifier rule"
        ::= { classifierRuleEntry 20 }  
        
        classifierSrcIpv6Mask OBJECT-TYPE
        SYNTAX  INTEGER
        ACCESS  read-write
        STATUS  mandatory
        DESCRIPTION
                      	"Source IPv6 Mask for classifier rule"
        ::= { classifierRuleEntry 21 }
        
        classifierDstIpv6 OBJECT-TYPE
        SYNTAX  Ipv6Address
        ACCESS  read-write
        STATUS  mandatory
        DESCRIPTION
                      	"Destination IPv6 address for classifier rule"
        ::= { classifierRuleEntry 22 }  
        
        classifierDstIpv6Mask OBJECT-TYPE
        SYNTAX  INTEGER
        ACCESS  read-write
        STATUS  mandatory
        DESCRIPTION
                      	"Destination IPv6 Mask for classifier rule"
        ::= { classifierRuleEntry 23 }
      
      classifierRuleSet OBJECT-TYPE
        SYNTAX  DisplayString
        ACCESS  read-write
        STATUS  mandatory
        DESCRIPTION
                      	"classifier Rule Set."
        ::= { classifierSetup 2 }

--  policySetup
	policySetup     	OBJECT IDENTIFIER ::= { ves1616pe54 40 }

        policyTable	OBJECT-TYPE
        SYNTAX	SEQUENCE OF PolicyEntry
        ACCESS  not-accessible
        STATUS  mandatory
        DESCRIPTION
                 	""
        ::= { policySetup 1 }  
        
 		policyEntry OBJECT-TYPE
        SYNTAX	PolicyEntry
        ACCESS	not-accessible
        STATUS	mandatory
        DESCRIPTION    	"An entry in policyTable."
        INDEX          	{policyName }
        ::= { policyTable 1 }
       
      	PolicyEntry ::=
		SEQUENCE {
        	policyName			DisplayString,      
        	policyEnable		INTEGER,  
        	policyClassifier  	DisplayString, 
        	policyVlanId		INTEGER,
        	policyEgressPort 	INTEGER,
        	policyOutPktFormat  INTEGER,
        	policy8021pPriority INTEGER,
        	policyDSCP          INTEGER,
        	policyTOS           INTEGER,
        	policyBandwidth     INTEGER,
        	policyOutOfProfileDSCP   INTEGER,
        	policyForwardingAction   INTEGER,
        	policyPriorityAction     INTEGER,
        	policyDiffServAction 	 INTEGER,
        	policyOutgoingAction	 BITS,
        	policyMeteringEnable     INTEGER,
            policyOutOfProfileAction BITS,
            policyRowstatus 		 RowStatus            
        }  
 
        policyName OBJECT-TYPE
        SYNTAX  DisplayString
        ACCESS  read-only
        STATUS  mandatory
        DESCRIPTION
                      	"Name of policy rule."
        ::= { policyEntry 1 }   
         
        policyEnable OBJECT-TYPE
        SYNTAX  EnabledStatus
        ACCESS  read-write
        STATUS  mandatory
        DESCRIPTION
        	"Policy rule enabled/disabled."
        ::= { policyEntry 2 }  
           
        policyClassifier OBJECT-TYPE
        SYNTAX  DisplayString
        ACCESS  read-only
        STATUS  mandatory
        DESCRIPTION
                      	"Classifier of policy rule."
        ::= { policyEntry 3 }      
                                           
        policyVlanId OBJECT-TYPE
        SYNTAX  INTEGER
        ACCESS  read-write
        STATUS  mandatory
        DESCRIPTION
                      	"Vlan id for policy rule, 1~4094."
        ::= { policyEntry 4 } 
        
        policyEgressPort OBJECT-TYPE
        SYNTAX  INTEGER
        ACCESS  read-write
        STATUS  mandatory
        DESCRIPTION
                      	"Egress Port for policy rule"
        ::= { policyEntry 5 }  
         
        policyOutPktFormat OBJECT-TYPE
        SYNTAX  INTEGER
        {   
        	tag(1),
        	untag(2)
        }
        ACCESS  read-write
        STATUS  mandatory
        DESCRIPTION
                      	"Outgoing packet format for Egress port for policy rule"
        ::= { policyEntry 6 } 
        
        policy8021pPriority OBJECT-TYPE
        SYNTAX  INTEGER
        ACCESS  read-write
        STATUS  mandatory
        DESCRIPTION
                      	"802.1p priority for policy rule, 0~7."
        ::= { policyEntry 7 }    
        
        policyDSCP OBJECT-TYPE
        SYNTAX  INTEGER
        ACCESS  read-write
        STATUS  mandatory
        DESCRIPTION
                      	"DSCP for policy rule."
        ::= { policyEntry 8 }   
        
        policyTOS OBJECT-TYPE
        SYNTAX  INTEGER
        ACCESS  read-write
        STATUS  mandatory
        DESCRIPTION
                      	"TOS for policy rule, 0~7"
        ::= { policyEntry 9 }  
        
        policyBandwidth OBJECT-TYPE
        SYNTAX  INTEGER
        ACCESS  read-write
        STATUS  mandatory
        DESCRIPTION
                      	"Bandwidth for policy rule"
        ::= { policyEntry 10 }  
          
        policyOutOfProfileDSCP OBJECT-TYPE
        SYNTAX  INTEGER
        ACCESS  read-write
        STATUS  mandatory
        DESCRIPTION
                      	"Out Of Profile DSCP for policy rule."
        ::= { policyEntry 11 } 
        
        policyForwardingAction OBJECT-TYPE
        SYNTAX  INTEGER
        {   
        	no-change(1),
        	discard-the-packet(2),
        	do-not-drop-the-matching-frame-previously-marked-for-dopping(3)
        }
        ACCESS  read-write
        STATUS  mandatory
        DESCRIPTION
                      	"Forwarding Action for policy rule"
        ::= { policyEntry 12 } 
   
        policyPriorityAction OBJECT-TYPE
        SYNTAX  INTEGER
        {   
        	no-change(1),
        	set-the-packets-802_1-priority(2),
        	send-the-packet-to-priority-queue(3),
        	replace-the-802_1-priority-field-with-the-IP-TOS-value(4) 
        }
        ACCESS  read-write
        STATUS  mandatory
        DESCRIPTION
                      	"Priority Action for policy rule"
        ::= { policyEntry 13}    

        policyDiffServAction OBJECT-TYPE
        SYNTAX  INTEGER
        {   
        	no-change(1),
        	set-the-packets-TOS-field(2),
        	replace-the-IP-TOS-field-with-the-802_1-priority-value(3),
        	set-the-Diffserv-Codepoint-field-in-the-frame(4) 
        }
        ACCESS  read-write
        STATUS  mandatory
        DESCRIPTION
                      	"DiffServ Action for policy rule"
        ::= { policyEntry 14}     
        
        policyOutgoingAction OBJECT-TYPE
		SYNTAX	BITS {
			send-the-packet-to-the-mirror-port(1),
			send-the-packet-to-the-egress-port(2),
			send-the-matching-frames-to-the-egress-port(3),
			set-the-packets-VLAN-ID(4) 
		}
		ACCESS  read-create
		STATUS      current
		DESCRIPTION
	        "Outgoing Action for policy rule"
		::= { policyEntry 15 }

        policyMeteringEnable OBJECT-TYPE
        SYNTAX  INTEGER
        ACCESS  read-write
        STATUS  mandatory
        DESCRIPTION
        	"Metering for Policy rule enabled/disabled."
        ::= { policyEntry 16 }  
        
        policyOutOfProfileAction OBJECT-TYPE
		SYNTAX	BITS {
			drop-the-packet(1),
			change-the-DSCP-value(2),
			set-Out-Drop-Precedence(3),
			do-not-drop-the-matching-frame-previously-marked-for-dropping(4)
		}
		ACCESS  read-create
		STATUS      current
		DESCRIPTION
	        "Out Of Profile Action for policy rule"
		::= { policyEntry 17 }
 
        policyRowstatus OBJECT-TYPE
        SYNTAX  RowStatus
        ACCESS  read-create
        STATUS  mandatory
        DESCRIPTION
                      	"Row Status for policy rule"
        ::= { policyEntry 18 }      

        policyRuleSet OBJECT-TYPE
        SYNTAX  DisplayString
        ACCESS  read-write
        STATUS  mandatory
        DESCRIPTION
                      	"policy Rule Set."
        ::= { policySetup 2 }


--  switchCounterStatus
	switchCounterStatus     	OBJECT IDENTIFIER ::= { ves1616pe54 42 }

vlanCounterTable OBJECT-TYPE
        SYNTAX SEQUENCE OF VlanCounterEntry
        ACCESS  not-accessible
        STATUS  mandatory
        DESCRIPTION
                  ""
        ::= { switchCounterStatus 1 }
 
 vlanCounterEntry OBJECT-TYPE
        SYNTAX VlanCounterEntry
        ACCESS not-accessible
        STATUS mandatory
        DESCRIPTION     "An entry in vlanCounterTable."
        INDEX           { ifIndex, dot1qVlanIndex }
        ::= { vlanCounterTable 1 }
 
        VlanCounterEntry ::=
             SEQUENCE {
                 vlanCounterTxPkts  Counter32,
                 vlanCounterRxPkts  Counter32        
           }
        
        vlanCounterTxPkts  OBJECT-TYPE
        SYNTAX  Counter32
        ACCESS  read-only
        STATUS  mandatory
        DESCRIPTION
        ""
        ::= { vlanCounterEntry 1 }
 
        vlanCounterRxPkts  OBJECT-TYPE
        SYNTAX  Counter32
        ACCESS  read-only
        STATUS  mandatory
        DESCRIPTION
        ""
        ::= { vlanCounterEntry 2 }


-- switchCounterTable

        switchCounterTable OBJECT-TYPE
        SYNTAX	SEQUENCE OF SwitchCounterEntry
        ACCESS  not-accessible
        STATUS  mandatory
        DESCRIPTION
                 	""
        ::= { switchCounterStatus 2 }

	switchCounterEntry OBJECT-TYPE
        SYNTAX	SwitchCounterEntry
        ACCESS	not-accessible
        STATUS	mandatory
        DESCRIPTION    	"An entry in switchCounterTable."
        INDEX          	{ dot1dBasePort }
        ::= { switchCounterTable 1 }

        SwitchCounterEntry ::=
           SEQUENCE {
        	switchUnknownUnicastCounter	Counter32
           }

        switchUnknownUnicastCounter OBJECT-TYPE
        SYNTAX  Counter32
        ACCESS  read-only
        STATUS  mandatory
        DESCRIPTION
        "Unknown unicast counter for the port."
        ::= { switchCounterEntry 1 }

-- vlanCounterResetTable

	vlanCounterResetTable OBJECT-TYPE
        SYNTAX SEQUENCE OF VlanCounterResetEntry
        ACCESS  not-accessible
        STATUS  mandatory
        DESCRIPTION
                  ""
        ::= { switchCounterStatus 3 }
        
       vlanCounterResetEntry OBJECT-TYPE
        SYNTAX VlanCounterResetEntry
        ACCESS not-accessible
        STATUS mandatory
        DESCRIPTION     "An entry in vlanCounterTable."
        INDEX           { dot1qVlanIndex }
        ::= { vlanCounterResetTable 1 }
 
        VlanCounterResetEntry ::=
             SEQUENCE {
                 vlanCounterReset  INTEGER
           }
           
        vlanCounterReset OBJECT-TYPE
        SYNTAX  INTEGER {
        	enable(1),
        	disable(2)
        }
        ACCESS  read-write
        STATUS  mandatory
        DESCRIPTION
               "Clear VLAN counters."
        ::= { vlanCounterResetEntry 1 }


-- vlanCounterSwitchSetup

	vlanCounterSwitchSetup     	OBJECT IDENTIFIER ::= { switchCounterStatus 4 }

        vlanCounterSwitch OBJECT-TYPE
        SYNTAX  INTEGER {
        	enable(1),
        	disable(2)
        }
        ACCESS  read-write
        STATUS  mandatory
        DESCRIPTION
               "Switch VLAN counters on/off."
        ::= { vlanCounterSwitchSetup 1 }

        vlanCounterVlan OBJECT-TYPE
        SYNTAX  INTEGER
        ACCESS  read-write
        STATUS  mandatory
        DESCRIPTION
               "VLAN counter per vlan."
        ::= { vlanCounterSwitchSetup 2 }
           
        vlanCounterPort OBJECT-TYPE
        SYNTAX  INTEGER
        ACCESS  read-write
        STATUS  mandatory
        DESCRIPTION
               "VLAN counters per port."
        ::= { vlanCounterSwitchSetup 3 }
           
        vlanCounterDirection OBJECT-TYPE
        SYNTAX  INTEGER {
        	tx(1),
        	rx(2)
        }
        ACCESS  read-write
        STATUS  mandatory
        DESCRIPTION
               "VLAN counters per direction."
        ::= { vlanCounterSwitchSetup 4 }

--  rateLimitProfilePortSetup
	rateLimitProfilePortSetup     	OBJECT IDENTIFIER ::= { ves1616pe54 43 }

        rateLimitProfilePortTable	OBJECT-TYPE
        SYNTAX	SEQUENCE OF RateLimitProfilePortEntry
        ACCESS  not-accessible
        STATUS  mandatory
        DESCRIPTION
                 	""
        ::= { rateLimitProfilePortSetup 1 }

	rateLimitProfilePortEntry OBJECT-TYPE
        SYNTAX	RateLimitProfilePortEntry
        ACCESS	not-accessible
        STATUS	mandatory
        DESCRIPTION    	"An entry in rateLimitProfilePortTable."
        INDEX          	{ dot1dBasePort }
        ::= { rateLimitProfilePortTable 1 }

        RateLimitProfilePortEntry ::=
	SEQUENCE {
        	rateLimitPortProfile	DisplayString
        }

        rateLimitPortProfile OBJECT-TYPE
        SYNTAX  DisplayString
        ACCESS  read-write
        STATUS  mandatory
        DESCRIPTION
                      	""
        ::= { rateLimitProfilePortEntry 1 }

  perQueueProfilePortTable	OBJECT-TYPE
        SYNTAX	SEQUENCE OF PerQueueProfilePortEntry
        ACCESS  not-accessible
        STATUS  mandatory
        DESCRIPTION
                 	""
        ::= { rateLimitProfilePortSetup 2 }
        
	perQueueProfilePortEntry OBJECT-TYPE
        SYNTAX	PerQueueProfilePortEntry
        ACCESS	not-accessible
        STATUS	mandatory
        DESCRIPTION    	"An entry in perQueueProfilePortTable."
        INDEX          	{ dot1dBasePort }
        ::= { perQueueProfilePortTable 1 }

        PerQueueProfilePortEntry ::=
	SEQUENCE {
        	perQueuePortProfile	DisplayString
        }

        perQueuePortProfile OBJECT-TYPE
        SYNTAX  DisplayString
        ACCESS  read-write
        STATUS  mandatory
        DESCRIPTION
                      	""
        ::= { perQueueProfilePortEntry 1 }        

----------------------------------------------------
--  rateLimitProfileSetup
	rateLimitProfileSetup     	OBJECT IDENTIFIER ::= { ves1616pe54 44 }

	rateLimitMaxNumberOfProfile OBJECT-TYPE
        SYNTAX  INTEGER
        ACCESS  read-only
        STATUS  mandatory
        DESCRIPTION
                      	""
        ::= { rateLimitProfileSetup 1 }

        rateLimitProfileTable	OBJECT-TYPE
        SYNTAX	SEQUENCE OF RateLimitProfileEntry
        ACCESS  not-accessible
        STATUS  mandatory
        DESCRIPTION
                 	""
        ::= { rateLimitProfileSetup 2 }

	rateLimitProfileEntry OBJECT-TYPE
        SYNTAX	RateLimitProfileEntry
        ACCESS	not-accessible
        STATUS	mandatory
        DESCRIPTION    	"An entry in rateLimitMaxNumberOfProfile."
        INDEX          	{ rateLimitProfileName }
        ::= { rateLimitProfileTable 1 }

        RateLimitProfileEntry ::=
	SEQUENCE {
        	rateLimitProfileName		DisplayString,
		rateLimitProfilePeakRate	INTEGER,
		rateLimitProfileEgrRate	INTEGER,
	        rateLimitProfileCommitRate	INTEGER,
			rateLimitProfilePeakState	EnabledStatus,
			rateLimitProfileEgrState	EnabledStatus,
			rateLimitProfileCommitState EnabledStatus,
        	rateLimitProfileRowStatus	RowStatus
        }

        rateLimitProfileName OBJECT-TYPE
        SYNTAX  DisplayString
        ACCESS  read-only
        STATUS  mandatory
        DESCRIPTION
                      	""
        ::= { rateLimitProfileEntry 1 }

        rateLimitProfilePeakRate OBJECT-TYPE
        SYNTAX  INTEGER
        ACCESS  read-write
        STATUS  mandatory
        DESCRIPTION
                      	"Peak rate in Kbit/s.  The range of FE port is between 1 and 100,000. For GE port, the range is between 1 and 1000,000."
        ::= { rateLimitProfileEntry 2 }

        rateLimitProfileEgrRate OBJECT-TYPE
        SYNTAX  INTEGER
        ACCESS  read-write
        STATUS  mandatory
        DESCRIPTION
                      	"Egress rate in Kbit/s.  The range of FE port is between 1 and 100,000. For GE port, the range is between 1 and 1000,000."
        ::= { rateLimitProfileEntry 3 }

        rateLimitProfileCommitRate OBJECT-TYPE
        SYNTAX  INTEGER
        ACCESS  read-write
        STATUS  mandatory
        DESCRIPTION
                      	"Commit rate in Kbit/s.  The range of FE port is between 0 and 100,000. For GE port, the range is between 0 and 1000,000."
        ::= { rateLimitProfileEntry 4 }

        
        rateLimitProfilePeakState OBJECT-TYPE
        SYNTAX  EnabledStatus
        ACCESS  read-write
        STATUS  mandatory
        DESCRIPTION
                      	"Ingress peak rate limiting enabled/disabled on the port."
        ::= { rateLimitProfileEntry 5 }                                              
        
        rateLimitProfileEgrState OBJECT-TYPE
        SYNTAX  EnabledStatus
        ACCESS  read-write
        STATUS  mandatory
        DESCRIPTION
                      	"Egress rate limiting enabled/disabled on the port."
        ::= { rateLimitProfileEntry 6 }        
        
        rateLimitProfileCommitState OBJECT-TYPE
        SYNTAX  EnabledStatus
        ACCESS  read-write
        STATUS  mandatory
        DESCRIPTION
                      	"Ingress commit rate limiting enabled/disabled on the port."
        ::= { rateLimitProfileEntry 7 }
        

        rateLimitProfileRowStatus OBJECT-TYPE
        SYNTAX  RowStatus
        ACCESS  read-create
        STATUS  mandatory
        DESCRIPTION
                      	""
        ::= { rateLimitProfileEntry 8 }

	perQueueMaxNumberOfProfile OBJECT-TYPE
        SYNTAX  INTEGER
        ACCESS  read-only
        STATUS  mandatory
        DESCRIPTION
                      	""
        ::= { rateLimitProfileSetup 3 }

        perQueueProfileTable	OBJECT-TYPE
        SYNTAX	SEQUENCE OF PerQueueProfileEntry
        ACCESS  not-accessible
        STATUS  mandatory
        DESCRIPTION
                 	""
        ::= { rateLimitProfileSetup 4 }

	perQueueProfileEntry OBJECT-TYPE
        SYNTAX	PerQueueProfileEntry
        ACCESS	not-accessible
        STATUS	mandatory
        DESCRIPTION    	"An entry in perQueueMaxNumberOfProfile."
        INDEX          	{ perQueueProfileName }
        ::= { perQueueProfileTable 1 }

        PerQueueProfileEntry ::=
	SEQUENCE {
        	perQueueProfileName		DisplayString,
		perQueueProfileQ0CIR	INTEGER,
		perQueueProfileQ0PIR	INTEGER,
		perQueueProfileQ1CIR	INTEGER,
		perQueueProfileQ1PIR	INTEGER,
		perQueueProfileQ2CIR	INTEGER,
		perQueueProfileQ2PIR	INTEGER,
		perQueueProfileQ3CIR	INTEGER,
		perQueueProfileQ3PIR	INTEGER,
		perQueueProfileQ4CIR	INTEGER,
		perQueueProfileQ4PIR	INTEGER,
		perQueueProfileQ5CIR	INTEGER,
		perQueueProfileQ5PIR	INTEGER,
		perQueueProfileQ6CIR	INTEGER,
		perQueueProfileQ6PIR	INTEGER,
		perQueueProfileQ7CIR	INTEGER,
		perQueueProfileQ7PIR	INTEGER,
        	perQueueProfileRowStatus	RowStatus
        }

        perQueueProfileName OBJECT-TYPE
        SYNTAX  DisplayString
        ACCESS  read-only
        STATUS  mandatory
        DESCRIPTION
                      	""
        ::= { perQueueProfileEntry 1 }

        perQueueProfileQ0CIR OBJECT-TYPE
        SYNTAX  INTEGER
        ACCESS  read-write
        STATUS  mandatory
        DESCRIPTION
                      	"Commit rate of Queue0 in Kbit/s.  The range is between 0 and 1000,000."
        ::= { perQueueProfileEntry 2 }

        perQueueProfileQ0PIR OBJECT-TYPE
        SYNTAX  INTEGER
        ACCESS  read-write
        STATUS  mandatory
        DESCRIPTION
                      	"Peak rate of Queue0 in Kbit/s.  The range is between 0 and 1000,000."
        ::= { perQueueProfileEntry 3 }
        
        perQueueProfileQ1CIR OBJECT-TYPE
        SYNTAX  INTEGER
        ACCESS  read-write
        STATUS  mandatory
        DESCRIPTION
                      	"Commit rate of Queue1 in Kbit/s.  The range is between 0 and 1000,000."
        ::= { perQueueProfileEntry 4 }

        perQueueProfileQ1PIR OBJECT-TYPE
        SYNTAX  INTEGER
        ACCESS  read-write
        STATUS  mandatory
        DESCRIPTION
                      	"Peak rate of Queue1 in Kbit/s.  The range is between 0 and 1000,000."
        ::= { perQueueProfileEntry 5 }
        
        perQueueProfileQ2CIR OBJECT-TYPE
        SYNTAX  INTEGER
        ACCESS  read-write
        STATUS  mandatory
        DESCRIPTION
                      	"Commit rate of Queue2 in Kbit/s.  The range is between 0 and 1000,000."
        ::= { perQueueProfileEntry 6 }

        perQueueProfileQ2PIR OBJECT-TYPE
        SYNTAX  INTEGER
        ACCESS  read-write
        STATUS  mandatory
        DESCRIPTION
                      	"Peak rate of Queue2 in Kbit/s.  The range is between 0 and 1000,000."
        ::= { perQueueProfileEntry 7 }
        
        perQueueProfileQ3CIR OBJECT-TYPE
        SYNTAX  INTEGER
        ACCESS  read-write
        STATUS  mandatory
        DESCRIPTION
                      	"Commit rate of Queue3 in Kbit/s.  The range is between 0 and 1000,000."
        ::= { perQueueProfileEntry 8 }

        perQueueProfileQ3PIR OBJECT-TYPE
        SYNTAX  INTEGER
        ACCESS  read-write
        STATUS  mandatory
        DESCRIPTION
                      	"Peak rate of Queue3 in Kbit/s.  The range is between 0 and 1000,000."
        ::= { perQueueProfileEntry 9 }
        
        perQueueProfileQ4CIR OBJECT-TYPE
        SYNTAX  INTEGER
        ACCESS  read-write
        STATUS  mandatory
        DESCRIPTION
                      	"Commit rate of Queue4 in Kbit/s.  The range is between 0 and 1000,000."
        ::= { perQueueProfileEntry 10 }

        perQueueProfileQ4PIR OBJECT-TYPE
        SYNTAX  INTEGER
        ACCESS  read-write
        STATUS  mandatory
        DESCRIPTION
                      	"Peak rate of Queue4 in Kbit/s.  The range is between 0 and 1000,000."
        ::= { perQueueProfileEntry 11 }
        
        perQueueProfileQ5CIR OBJECT-TYPE
        SYNTAX  INTEGER
        ACCESS  read-write
        STATUS  mandatory
        DESCRIPTION
                      	"Commit rate of Queue5 in Kbit/s.  The range is between 0 and 1000,000."
        ::= { perQueueProfileEntry 12 }

        perQueueProfileQ5PIR OBJECT-TYPE
        SYNTAX  INTEGER
        ACCESS  read-write
        STATUS  mandatory
        DESCRIPTION
                      	"Peak rate of Queue5 in Kbit/s.  The range is between 0 and 1000,000."
        ::= { perQueueProfileEntry 13 }
        
        perQueueProfileQ6CIR OBJECT-TYPE
        SYNTAX  INTEGER
        ACCESS  read-write
        STATUS  mandatory
        DESCRIPTION
                      	"Commit rate of Queue6 in Kbit/s.  The range is between 0 and 1000,000."
        ::= { perQueueProfileEntry 14 }

        perQueueProfileQ6PIR OBJECT-TYPE
        SYNTAX  INTEGER
        ACCESS  read-write
        STATUS  mandatory
        DESCRIPTION
                      	"Peak rate of Queue6 in Kbit/s.  The range is between 0 and 1000,000."
        ::= { perQueueProfileEntry 15 }
        
        perQueueProfileQ7CIR OBJECT-TYPE
        SYNTAX  INTEGER
        ACCESS  read-write
        STATUS  mandatory
        DESCRIPTION
                      	"Commit rate of Queue7 in Kbit/s.  The range is between 0 and 1000,000."
        ::= { perQueueProfileEntry 16 }

        perQueueProfileQ7PIR OBJECT-TYPE
        SYNTAX  INTEGER
        ACCESS  read-write
        STATUS  mandatory
        DESCRIPTION
                      	"Peak rate of Queue7 in Kbit/s.  The range is between 0 and 1000,000."
        ::= { perQueueProfileEntry 17 }
 
        perQueueProfileRowStatus OBJECT-TYPE
        SYNTAX  RowStatus
        ACCESS  read-create
        STATUS  mandatory
        DESCRIPTION
                      	""
        ::= { perQueueProfileEntry 18 }

------------------------
-- vlanSecuritySetup
	vlanSecuritySetup OBJECT IDENTIFIER ::= { ves1616pe54 45 }

        vlanSecurityTable OBJECT-TYPE
        SYNTAX	SEQUENCE OF VlanSecurityEntry
        ACCESS  not-accessible
        STATUS  mandatory
        DESCRIPTION
                 	""
        ::= { vlanSecuritySetup 1 }

	vlanSecurityEntry OBJECT-TYPE
        SYNTAX	VlanSecurityEntry
        ACCESS	not-accessible
        STATUS	mandatory
        DESCRIPTION    	"An entry in vlanSecurityTable."
        INDEX          	{ dot1qVlanIndex  }
        ::= { vlanSecurityTable 1 }

        VlanSecurityEntry ::=
           SEQUENCE {
		vlanSecurityCount		INTEGER
           }

        vlanSecurityCount OBJECT-TYPE
        SYNTAX  INTEGER
        ACCESS  read-write
        STATUS  mandatory
        DESCRIPTION
                      	"Number of (dynamic) MAC addresses that may be learned on the VID."
        ::= { vlanSecurityEntry 1}

----------------------------
-- cfmSetup
	cfmSetup OBJECT IDENTIFIER ::= { ves1616pe54 46 }

-- cfmLoopbackPortTable

        cfmLoopbackPortTable OBJECT-TYPE
        SYNTAX	SEQUENCE OF CfmLoopbackPortEntry
        ACCESS  not-accessible
        STATUS  mandatory
        DESCRIPTION
                 	""
        ::= { cfmSetup 1 }

	cfmLoopbackPortEntry OBJECT-TYPE
        SYNTAX	CfmLoopbackPortEntry
        ACCESS	not-accessible
        STATUS	mandatory
        DESCRIPTION    	"An entry in cfmLoopbackPortTable."
        INDEX          	{ dot1dBasePort }
        ::= { cfmLoopbackPortTable 1 }

        CfmLoopbackPortEntry ::=
           SEQUENCE {
        	cfmLoopbackPortState	EnabledStatus
           }

        cfmLoopbackPortState OBJECT-TYPE
        SYNTAX  EnabledStatus
        ACCESS  read-write
        STATUS  mandatory
        DESCRIPTION
                      	"CFM loopback enabled/disabled on the port."
        ::= { cfmLoopbackPortEntry 1 }
        
        cfmMIPTable	OBJECT-TYPE
        SYNTAX	SEQUENCE OF CfmMIPEntry
        ACCESS  not-accessible
        STATUS  mandatory
        DESCRIPTION
                 	""
        ::= { cfmSetup 2 }

	cfmMIPEntry OBJECT-TYPE
        SYNTAX	CfmMIPEntry
        ACCESS	not-accessible
        STATUS	mandatory
        DESCRIPTION    	"An entry in cfmMIPTable."
        INDEX          	{ cfmLevel, cfmVlanID, cfmPort }
        ::= { cfmMIPTable 1 }

        CfmMIPEntry ::=
	SEQUENCE {
        	cfmPort		INTEGER,
        	cfmVlanID	INTEGER,
        	cfmLevel	INTEGER,
        	cfmMIPRowStatus		RowStatus
        }

        cfmPort OBJECT-TYPE
        SYNTAX  INTEGER
        ACCESS  read-only
        STATUS  mandatory
        DESCRIPTION
                      	""
        ::= { cfmMIPEntry 1 }

        cfmVlanID OBJECT-TYPE
        SYNTAX  INTEGER
        ACCESS  read-only
        STATUS  mandatory
        DESCRIPTION
                      	""
        ::= { cfmMIPEntry 2 }

        cfmLevel OBJECT-TYPE
        SYNTAX  INTEGER
        ACCESS  read-only
        STATUS  mandatory
        DESCRIPTION
                      	""
        ::= { cfmMIPEntry 3 }

        cfmMIPRowStatus OBJECT-TYPE
        SYNTAX  RowStatus
        ACCESS  read-create
        STATUS  mandatory
        DESCRIPTION
                      	""
        ::= { cfmMIPEntry 4 }        
                               
	cfmActionEnableStatus OBJECT-TYPE
        SYNTAX  EnabledStatus
        ACCESS  read-write
        STATUS  mandatory
        DESCRIPTION
                      	"CFM Action enable status for the CO device"
        ::= { cfmSetup 3 }
                    
--  MRSTP
	mrstp     	OBJECT IDENTIFIER ::= { ves1616pe54 48 }
    
    mrstpSetup  OBJECT IDENTIFIER ::= { mrstp 1 }
	                 
	mrstpBridgeTable  OBJECT-TYPE
	SYNTAX	SEQUENCE OF MrstpBridgeEntry 
	ACCESS  not-accessible
	STATUS  mandatory
	DESCRIPTION
		    	""
	    ::= { mrstpSetup 1 }	

	mrstpBridgeEntry  OBJECT-TYPE
        SYNTAX	MrstpBridgeEntry 
        ACCESS	not-accessible
        STATUS	mandatory
        DESCRIPTION    	"An entry in mrstpBridgeTable."
        INDEX          	{ mrstpBridgeIndex }
        ::= { mrstpBridgeTable 1 }

        MrstpBridgeEntry ::=
           SEQUENCE {
           	mrstpBridgeIndex				INTEGER,
           	mrstpState				INTEGER,  
 			mrstpProtocolSpecification		INTEGER,      	
           	mrstpPriority				INTEGER,
        	mrstpTimeSinceTopologyChange		TimeTicks,
        	mrstpTopChanges				Counter,
        	mrstpDesignatedRoot			BridgeId,
        	mrstpRootCost				INTEGER,
        	mrstpRootPort				INTEGER,
        	mrstpMaxAge				Timeout,
        	mrstpHelloTime				Timeout,
        	mrstpHoldTime				INTEGER,
        	mrstpForwardDelay			Timeout,
        	mrstpBridgeMaxAge			Timeout,
        	mrstpBridgeHelloTime			Timeout,
        	mrstpBridgeForwardDelay			Timeout
           }

          -- the dot1dStp group

          -- Implementation of the dot1dStp group is optional.  It is
          -- implemented by those bridges that support the Spanning Tree
          -- Protocol.
          
          mrstpBridgeIndex OBJECT-TYPE
              SYNTAX  INTEGER
              ACCESS  read-only
              STATUS  mandatory
              DESCRIPTION
                      "The tree index of the MRSTP."
              ::= { mrstpBridgeEntry 1 }
			
		  mrstpState OBJECT-TYPE
        	SYNTAX  EnabledStatus
        	ACCESS  read-write
        	STATUS  mandatory
        	DESCRIPTION
                      "Enabled/disabled on the mrstp bridge."
        ::= { mrstpBridgeEntry 2 }
        
          mrstpProtocolSpecification OBJECT-TYPE
              SYNTAX  INTEGER {
                          unknown(1),
                          decLb100(2),
                          ieee8021d(3)
                      }
              ACCESS  read-only
              STATUS  mandatory
              DESCRIPTION
                      "An indication of what version of the Spanning
                      Tree Protocol is being run.  The value
                      'decLb100(2)' indicates the DEC LANbridge 100
                      Spanning Tree protocol.  IEEE 802.1d
                      implementations will return 'ieee8021d(3)'.  If
                      future versions of the IEEE Spanning Tree Protocol
                      are released that are incompatible with the
                      current version a new value will be defined."
              ::= { mrstpBridgeEntry 3 }
        
          mrstpPriority OBJECT-TYPE
              SYNTAX  INTEGER (0..65535)
              ACCESS  read-write
              STATUS  mandatory
              DESCRIPTION
                      "The value of the write-able portion of the Bridge
                      ID, i.e., the first two octets of the (8 octet
                      long) Bridge ID.  The other (last) 6 octets of the
                      Bridge ID are given by the value of
                      dot1dBaseBridgeAddress."
              REFERENCE
                      "IEEE 802.1D-1990: Section 4.5.3.7"
              ::= { mrstpBridgeEntry 4 }

          mrstpTimeSinceTopologyChange OBJECT-TYPE
              SYNTAX  TimeTicks
              ACCESS  read-only
              STATUS  mandatory
              DESCRIPTION
                      "The time (in hundredths of a second) since the
                      last time a topology change was detected by the
                      bridge entity."
              REFERENCE
                      "IEEE 802.1D-1990: Section 6.8.1.1.3"
              ::= { mrstpBridgeEntry 5 }

          mrstpTopChanges OBJECT-TYPE
              SYNTAX  Counter
              ACCESS  read-only
              STATUS  mandatory
              DESCRIPTION
                      "The total number of topology changes detected by
                      this bridge since the management entity was last
                      reset or initialized."
              REFERENCE
                      "IEEE 802.1D-1990: Section 6.8.1.1.3"
              ::= { mrstpBridgeEntry 6 }

          mrstpDesignatedRoot OBJECT-TYPE
              SYNTAX  BridgeId
              ACCESS  read-only
              STATUS  mandatory
              DESCRIPTION
                      "The bridge identifier of the root of the spanning
                      tree as determined by the Spanning Tree Protocol
                      as executed by this node.  This value is used as
                      the Root Identifier parameter in all Configuration
                      Bridge PDUs originated by this node."
              REFERENCE
                      "IEEE 802.1D-1990: Section 4.5.3.1"
              ::= { mrstpBridgeEntry 7 }

          mrstpRootCost OBJECT-TYPE
              SYNTAX  INTEGER
              ACCESS  read-only
              STATUS  mandatory
              DESCRIPTION
                      "The cost of the path to the root as seen from
                      this bridge."
              REFERENCE
                      "IEEE 802.1D-1990: Section 4.5.3.2"
              ::= { mrstpBridgeEntry 8 }

          mrstpRootPort OBJECT-TYPE
              SYNTAX  INTEGER
              ACCESS  read-only
              STATUS  mandatory
              DESCRIPTION
                      "The port number of the port which offers the
                      lowest cost path from this bridge to the root
                      bridge."
              REFERENCE
                      "IEEE 802.1D-1990: Section 4.5.3.3"
              ::= { mrstpBridgeEntry 9 }

          mrstpMaxAge OBJECT-TYPE
              SYNTAX  Timeout
              ACCESS  read-only
              STATUS  mandatory
              DESCRIPTION
                      "The maximum age of Spanning Tree Protocol
                      information learned from the network on any port
                      before it is discarded, in units of hundredths of
                      a second.  This is the actual value that this
                      bridge is currently using."
              REFERENCE
                      "IEEE 802.1D-1990: Section 4.5.3.4"
              ::= { mrstpBridgeEntry 10 }

          mrstpHelloTime OBJECT-TYPE
              SYNTAX  Timeout
              ACCESS  read-only
              STATUS  mandatory
              DESCRIPTION
                      "The amount of time between the transmission of
                      Configuration bridge PDUs by this node on any port
                      when it is the root of the spanning tree or trying
                      to become so, in units of hundredths of a second.
                      This is the actual value that this bridge is
                      currently using."
              REFERENCE
                      "IEEE 802.1D-1990: Section 4.5.3.5"
              ::= { mrstpBridgeEntry 11 }

          mrstpHoldTime OBJECT-TYPE
              SYNTAX  INTEGER
              ACCESS  read-only
              STATUS  mandatory
              DESCRIPTION
                      "This time value determines the interval length
                      during which no more than two Configuration bridge
                      PDUs shall be transmitted by this node, in units
                      of hundredths of a second."
              REFERENCE
                      "IEEE 802.1D-1990: Section 4.5.3.14"
              ::= { mrstpBridgeEntry 12 }

          mrstpForwardDelay OBJECT-TYPE
              SYNTAX  Timeout
              ACCESS  read-only
              STATUS  mandatory
              DESCRIPTION
                      "This time value, measured in units of hundredths
                      of a second, controls how fast a port changes its
                      spanning state when moving towards the Forwarding
                      state.  The value determines how long the port
                      stays in each of the Listening and Learning
                      states, which precede the Forwarding state.  This
                      value is also used, when a topology change has
                      been detected and is underway, to age all dynamic
                      entries in the Forwarding Database.  [Note that
                      this value is the one that this bridge is
                      currently using, in contrast to
                      mrstpBridgeForwardDelay which is the value that
                      this bridge and all others would start using
                      if/when this bridge were to become the root.]"
              REFERENCE
                      "IEEE 802.1D-1990: Section 4.5.3.6"
              ::= { mrstpBridgeEntry 13 }

          mrstpBridgeMaxAge OBJECT-TYPE
              SYNTAX  Timeout (600..4000)
              ACCESS  read-write
              STATUS  mandatory
              DESCRIPTION
                      "The value that all bridges use for MaxAge when
                      this bridge is acting as the root.  Note that
                      802.1D-1990 specifies that the range for this
                      parameter is related to the value of
                      mrstpBridgeHelloTime. The granularity of this
                      timer is specified by 802.1D-1990 to be 1 second.
                      An agent may return a badValue error if a set is
                      attempted to a value which is not a whole number
                      of seconds."
              REFERENCE
                      "IEEE 802.1D-1990: Section 4.5.3.8"
              ::= { mrstpBridgeEntry 14 }

          mrstpBridgeHelloTime OBJECT-TYPE
              SYNTAX  Timeout (100..1000)
              ACCESS  read-write
              STATUS  mandatory
              DESCRIPTION
                      "The value that all bridges use for HelloTime when
                      this bridge is acting as the root.  The
                      granularity of this timer is specified by 802.1D-
                      1990 to be 1 second.  An agent may return a
                      badValue error if a set is attempted to a value
                      which is not a whole number of seconds."
              REFERENCE
                      "IEEE 802.1D-1990: Section 4.5.3.9"
              ::= { mrstpBridgeEntry 15 }

          mrstpBridgeForwardDelay OBJECT-TYPE
              SYNTAX  Timeout (400..3000)
              ACCESS  read-write
              STATUS  mandatory
              DESCRIPTION
                      "The value that all bridges use for ForwardDelay
                      when this bridge is acting as the root.  Note that
                      802.1D-1990 specifies that the range for this
                      parameter is related to the value of
                      mrstpBridgeMaxAge.  The granularity of this
                      timer is specified by 802.1D-1990 to be 1 second.
                      An agent may return a badValue error if a set is
                      attempted to a value which is not a whole number
                      of seconds."
              REFERENCE
                      "IEEE 802.1D-1990: Section 4.5.3.10"
              ::= { mrstpBridgeEntry 16 }

          -- The Spanning Tree Port Table

          mrstpPortTable OBJECT-TYPE
              SYNTAX  SEQUENCE OF MrstpPortEntry
              ACCESS  not-accessible
              STATUS  mandatory
              DESCRIPTION
                      "A table that contains port-specific information
                      for the Spanning Tree Protocol."
              ::= { mrstpSetup 2 }

          mrstpPortEntry OBJECT-TYPE
              SYNTAX  MrstpPortEntry
              ACCESS  not-accessible
              STATUS  mandatory
              DESCRIPTION
                      "A list of information maintained by every port
                      about the Spanning Tree Protocol state for that
                      port."
              INDEX   { mrstpPort }
              ::= { mrstpPortTable 1 }

          MrstpPortEntry ::=
              SEQUENCE {
                  mrstpPort
                      INTEGER,
                  mrstpPortPriority
                      INTEGER,
                  mrstpPortState
                      INTEGER,
                  mrstpPortEnable
                      INTEGER,
                  mrstpPortPathCost
                      INTEGER,
                  mrstpPortDesignatedRoot
                      BridgeId,
                  mrstpPortDesignatedCost
                      INTEGER,
                  mrstpPortDesignatedBridge
                      BridgeId,
                  mrstpPortDesignatedPort
                      OCTET STRING,
                  mrstpPortForwardTransitions
                      Counter,
                  mrstpPortOnBridgeIndex
                      INTEGER
              }

          mrstpPort OBJECT-TYPE
              SYNTAX  INTEGER (1..65535)
              ACCESS  read-only
              STATUS  mandatory
              DESCRIPTION
                      "The port number of the port for which this entry
                      contains Spanning Tree Protocol management
                      information."
              REFERENCE
                      "IEEE 802.1D-1990: Section 6.8.2.1.2"
              ::= { mrstpPortEntry 1 }

          mrstpPortPriority OBJECT-TYPE
              SYNTAX  INTEGER (0..255)
              ACCESS  read-write
              STATUS  mandatory
              DESCRIPTION
                      "The value of the priority field which is
                      contained in the first (in network byte order)
                      octet of the (2 octet long) Port ID.  The other
                      octet of the Port ID is given by the value of
                      mrstpPort."
              REFERENCE
                      "IEEE 802.1D-1990: Section 4.5.5.1"
              ::= { mrstpPortEntry 2 }

          mrstpPortState OBJECT-TYPE
              SYNTAX  INTEGER {
                          disabled(1),
                          blocking(2),
                          listening(3),
                          learning(4),
                          forwarding(5),
                          broken(6)
                      }
              ACCESS  read-only
              STATUS  mandatory
              DESCRIPTION
                      "The port's current state as defined by
                      application of the Spanning Tree Protocol.  This
                      state controls what action a port takes on
                      reception of a frame.  If the bridge has detected
                      a port that is malfunctioning it will place that
                      port into the broken(6) state.  For ports which
                      are disabled (see mrstpPortEnable), this object
                      will have a value of disabled(1)."
              REFERENCE
                      "IEEE 802.1D-1990: Section 4.5.5.2"
              ::= { mrstpPortEntry 3 }

          mrstpPortEnable OBJECT-TYPE
              SYNTAX  INTEGER {
                          enabled(1),
                          disabled(2)
                      }
              ACCESS  read-write
              STATUS  mandatory
              DESCRIPTION
                      "The enabled/disabled status of the port."
              REFERENCE
                      "IEEE 802.1D-1990: Section 4.5.5.2"
              ::= { mrstpPortEntry 4 }

          mrstpPortPathCost OBJECT-TYPE
              SYNTAX  INTEGER (1..65535)
              ACCESS  read-write
              STATUS  mandatory
              DESCRIPTION
                      "The contribution of this port to the path cost of
                      paths towards the spanning tree root which include
                      this port.  802.1D-1990 recommends that the
                      default value of this parameter be in inverse
                      proportion to the speed of the attached LAN."
              REFERENCE
                      "IEEE 802.1D-1990: Section 4.5.5.3"
              ::= { mrstpPortEntry 5 }

          mrstpPortDesignatedRoot OBJECT-TYPE
              SYNTAX  BridgeId
              ACCESS  read-only
              STATUS  mandatory
              DESCRIPTION
                      "The unique Bridge Identifier of the Bridge
                      recorded as the Root in the Configuration BPDUs
                      transmitted by the Designated Bridge for the
                      segment to which the port is attached."
              REFERENCE
                      "IEEE 802.1D-1990: Section 4.5.5.4"
              ::= { mrstpPortEntry 6 }

          mrstpPortDesignatedCost OBJECT-TYPE
              SYNTAX  INTEGER
              ACCESS  read-only
              STATUS  mandatory
              DESCRIPTION
                      "The path cost of the Designated Port of the
                      segment connected to this port.  This value is
                      compared to the Root Path Cost field in received
                      bridge PDUs."
              REFERENCE
                      "IEEE 802.1D-1990: Section 4.5.5.5"
              ::= { mrstpPortEntry 7 }

          mrstpPortDesignatedBridge OBJECT-TYPE
              SYNTAX  BridgeId
              ACCESS  read-only
              STATUS  mandatory
              DESCRIPTION
                      "The Bridge Identifier of the bridge which this
                      port considers to be the Designated Bridge for
                      this port's segment."
              REFERENCE
                      "IEEE 802.1D-1990: Section 4.5.5.6"
              ::= { mrstpPortEntry 8 }

          mrstpPortDesignatedPort OBJECT-TYPE
              SYNTAX  OCTET STRING (SIZE (2))
              ACCESS  read-only
              STATUS  mandatory
              DESCRIPTION
                      "The Port Identifier of the port on the Designated
                      Bridge for this port's segment."
              REFERENCE
                      "IEEE 802.1D-1990: Section 4.5.5.7"
              ::= { mrstpPortEntry 9 }

          mrstpPortForwardTransitions OBJECT-TYPE
              SYNTAX  Counter
              ACCESS  read-only
              STATUS  mandatory
              DESCRIPTION
                      "The number of times this port has transitioned
                      from the Learning state to the Forwarding state."
              ::= { mrstpPortEntry 10 }

          mrstpPortOnBridgeIndex OBJECT-TYPE
              SYNTAX  INTEGER
              ACCESS  read-write
              STATUS  mandatory
              DESCRIPTION
                      "Indetify the bridge index that this port joined to in MRSTP."
              ::= { mrstpPortEntry 11 }
              
--  MRSTP Trap
	mrstpNotifications     	OBJECT IDENTIFIER ::= { mrstp 2 }              
	
	 newRoot NOTIFICATION-TYPE
      OBJECTS {
        mrstpBridgeIndex
      }
      STATUS  current
      DESCRIPTION
          ""
      ::= { mrstpNotifications 1 }
                                             
    topologyChange NOTIFICATION-TYPE
      OBJECTS {
        mrstpBridgeIndex
      }
      STATUS  current
      DESCRIPTION
          ""
      ::= { mrstpNotifications 2 }                                                              
---------------------------------------------------
--
--  dhcp snooping
--
---------------------------------------------------

	dhcpSnp     	OBJECT IDENTIFIER ::= { ves1616pe54 49 }
	

--
--  dhcp snooping vlan table
--
	
        dhcpSnpVlanTable	OBJECT-TYPE
        SYNTAX	SEQUENCE OF DhcpSnpVlanEntry
        ACCESS  not-accessible
        STATUS  mandatory
        DESCRIPTION
                 	""
        ::= { dhcpSnp 1 }

	dhcpSnpVlanEntry OBJECT-TYPE
        SYNTAX	DhcpSnpVlanEntry
        ACCESS	not-accessible
        STATUS	mandatory
        DESCRIPTION    	""
        INDEX          	{ dhcpSnpVlanEntryVid }
        ::= { dhcpSnpVlanTable 1 }

        DhcpSnpVlanEntry ::=
	SEQUENCE {
        	dhcpSnpVlanEntryVid		INTEGER,
        	dhcpSnpVlanEntryEnable		EnabledStatus,
        	dhcpSnpVlanEntryOption82Enable	EnabledStatus,
        	dhcpSnpVlanEntryInfo		EnabledStatus
        }

        dhcpSnpVlanEntryVid OBJECT-TYPE
        SYNTAX  INTEGER (1..4094)
        ACCESS  read-only
        STATUS  mandatory
        DESCRIPTION
                      	""
        ::= { dhcpSnpVlanEntry 1 }

        dhcpSnpVlanEntryEnable OBJECT-TYPE
        SYNTAX  EnabledStatus
        ACCESS  read-write
        STATUS  mandatory
        DESCRIPTION
                      	""
        ::= { dhcpSnpVlanEntry 2 }
        
        dhcpSnpVlanEntryOption82Enable OBJECT-TYPE
        SYNTAX  EnabledStatus
        ACCESS  read-write
        STATUS  mandatory
        DESCRIPTION
                      	""
        ::= { dhcpSnpVlanEntry 3 }
        
        dhcpSnpVlanEntryInfo OBJECT-TYPE
        SYNTAX  EnabledStatus
        ACCESS  read-write
        STATUS  mandatory
        DESCRIPTION
                      	""
        ::= { dhcpSnpVlanEntry 4 }

--
--  dhcp snooping interface table
--

        dhcpSnpPortTable	OBJECT-TYPE
        SYNTAX	SEQUENCE OF DhcpSnpPortEntry
        ACCESS  not-accessible
        STATUS  mandatory
        DESCRIPTION
                 	""
        ::= { dhcpSnp 2 }

	dhcpSnpPortEntry OBJECT-TYPE
        SYNTAX	DhcpSnpPortEntry
        ACCESS	not-accessible
        STATUS	mandatory
        DESCRIPTION    	""
        INDEX          	{ dhcpSnpPortEntryPort }
        ::= { dhcpSnpPortTable 1 }

        DhcpSnpPortEntry ::=
	SEQUENCE {
        	dhcpSnpPortEntryPort		INTEGER,
        	dhcpSnpPortEntryTrust		EnabledStatus,
        	dhcpSnpPortEntryRate		INTEGER
        }

        dhcpSnpPortEntryPort OBJECT-TYPE
        SYNTAX  INTEGER
        ACCESS  read-only
        STATUS  mandatory
        DESCRIPTION
                      	""
        ::= { dhcpSnpPortEntry 1 }

        dhcpSnpPortEntryTrust OBJECT-TYPE
        SYNTAX  EnabledStatus
        ACCESS  read-write
        STATUS  mandatory
        DESCRIPTION
                      	""
        ::= { dhcpSnpPortEntry 2 }

        dhcpSnpPortEntryRate OBJECT-TYPE
        SYNTAX  INTEGER (0..2048)
        ACCESS  read-write
        STATUS  mandatory
        DESCRIPTION
                      	"0 means unlimited"
        ::= { dhcpSnpPortEntry 3 }
--
--  dhcp snooping binding table
--

        dhcpSnpBindTable	OBJECT-TYPE
        SYNTAX	SEQUENCE OF DhcpSnpBindEntry
        ACCESS  not-accessible
        STATUS  mandatory
        DESCRIPTION
                 	""
        ::= { dhcpSnp 3 }

	dhcpSnpBindEntry OBJECT-TYPE
        SYNTAX	DhcpSnpBindEntry
        ACCESS	not-accessible
        STATUS	mandatory
        DESCRIPTION    	""
        INDEX          	{ dhcpSnpBindEntryMac, dhcpSnpBindEntryVid }
        ::= { dhcpSnpBindTable 1 }

        DhcpSnpBindEntry ::=
	SEQUENCE {
        	dhcpSnpBindEntryMac		MacAddress,
        	dhcpSnpBindEntryVid		INTEGER,
        	dhcpSnpBindEntryIP		IpAddress,
        	dhcpSnpBindEntryLease		INTEGER,
        	dhcpSnpBindEntryType		INTEGER,
        	dhcpSnpBindEntryPort		INTEGER
        }

        dhcpSnpBindEntryMac OBJECT-TYPE
        SYNTAX  MacAddress
        ACCESS  read-only
        STATUS  mandatory
        DESCRIPTION
                      	""
        ::= { dhcpSnpBindEntry 1 }

        dhcpSnpBindEntryVid OBJECT-TYPE
        SYNTAX  INTEGER
        ACCESS  read-only
        STATUS  mandatory
        DESCRIPTION
                      	""
        ::= { dhcpSnpBindEntry 2 }
        
        dhcpSnpBindEntryIP OBJECT-TYPE
        SYNTAX  IpAddress
        ACCESS  read-only
        STATUS  mandatory
        DESCRIPTION
                      	""
        ::= { dhcpSnpBindEntry 3 }

        dhcpSnpBindEntryLease OBJECT-TYPE
        SYNTAX  INTEGER
        ACCESS  read-only
        STATUS  mandatory
        DESCRIPTION
                      	""
        ::= { dhcpSnpBindEntry 4 }

        dhcpSnpBindEntryType OBJECT-TYPE
        SYNTAX  INTEGER { dynamic(2) }
        ACCESS  read-only
        STATUS  mandatory
        DESCRIPTION
                      	""
        ::= { dhcpSnpBindEntry 5 }

        dhcpSnpBindEntryPort OBJECT-TYPE
        SYNTAX  INTEGER
        ACCESS  read-only
        STATUS  mandatory
        DESCRIPTION
                      	""
        ::= { dhcpSnpBindEntry 6 }

--
--  dhcp snooping
--

	dhcpSnpEnable OBJECT-TYPE
	SYNTAX  EnabledStatus
	ACCESS  read-write
	STATUS  mandatory
	DESCRIPTION
	              ""
	::= { dhcpSnp 4 }                                      

--
--  dhcp snooping database
--

	
	dhcpSnpDb     	OBJECT IDENTIFIER ::= { dhcpSnp 5 }
	
	dhcpSnpDbAbort OBJECT-TYPE
	SYNTAX  INTEGER (1..65535)
	ACCESS  read-write
	STATUS  mandatory
	DESCRIPTION
	              ""
	::= { dhcpSnpDb 1 }                                      	

	dhcpSnpDbWriteDelay OBJECT-TYPE
	SYNTAX  INTEGER (1..65535)
	ACCESS  read-write
	STATUS  mandatory
	DESCRIPTION
	              ""
	::= { dhcpSnpDb 2 }                                      
	
	dhcpSnpDbUrl OBJECT-TYPE
	SYNTAX  DisplayString (SIZE (0..255))
	ACCESS  read-write
	STATUS  mandatory
	DESCRIPTION
	              ""
	::= { dhcpSnpDb 3 }

	dhcpSnpDbUrlRenew OBJECT-TYPE
	SYNTAX  DisplayString (SIZE (0..255))
	ACCESS  read-write
	STATUS  mandatory
	DESCRIPTION
	              ""
	::= { dhcpSnpDb 4 }

	dhcpSnpDbStat     	OBJECT IDENTIFIER ::= { dhcpSnpDb 5 }

	dhcpSnpDbStatClear OBJECT-TYPE
	SYNTAX  EnabledStatus
	ACCESS  read-write
	STATUS  mandatory
	DESCRIPTION
	              ""
	::= { dhcpSnpDbStat 1 }  
		
	dhcpSnpDbStatAgentRunning OBJECT-TYPE
	SYNTAX  INTEGER { none(0), read(1), write(2) }
	ACCESS  read-only
	STATUS  mandatory
	DESCRIPTION
	              ""
	::= { dhcpSnpDbStat 2 }                                      	

	dhcpSnpDbStatDelayExpiry OBJECT-TYPE
	SYNTAX  INTEGER 
	ACCESS  read-only
	STATUS  mandatory
	DESCRIPTION
	              ""
	::= { dhcpSnpDbStat 3 }	

	dhcpSnpDbStatAbortExpiry OBJECT-TYPE
	SYNTAX  INTEGER
	ACCESS  read-only
	STATUS  mandatory
	DESCRIPTION
	              ""
	::= { dhcpSnpDbStat 4 }

	dhcpSnpDbStatLastSuccTime OBJECT-TYPE
	SYNTAX  DisplayString
	ACCESS  read-only
	STATUS  mandatory
	DESCRIPTION
	              ""
	::= { dhcpSnpDbStat 5 }
	
	dhcpSnpDbStatLastFailTime OBJECT-TYPE
	SYNTAX  DisplayString
	ACCESS  read-only
	STATUS  mandatory
	DESCRIPTION
	              ""
	::= { dhcpSnpDbStat 6 }
	
	dhcpSnpDbStatLastFailReason OBJECT-TYPE
	SYNTAX  DisplayString
	ACCESS  read-only
	STATUS  mandatory
	DESCRIPTION
	              ""
	::= { dhcpSnpDbStat 7 }

	dhcpSnpDbStatTotalAttempt OBJECT-TYPE
	SYNTAX  INTEGER
	ACCESS  read-only
	STATUS  mandatory
	DESCRIPTION
	              ""
	::= { dhcpSnpDbStat 8 }
	
	dhcpSnpDbStatStartupFail OBJECT-TYPE
	SYNTAX  INTEGER
	ACCESS  read-only
	STATUS  mandatory
	DESCRIPTION
	              ""
	::= { dhcpSnpDbStat 9 }

	dhcpSnpDbStatSuccTrans OBJECT-TYPE
	SYNTAX  INTEGER
	ACCESS  read-only
	STATUS  mandatory
	DESCRIPTION
	              ""
	::= { dhcpSnpDbStat 10 }
	
	dhcpSnpDbStatFailTrans OBJECT-TYPE
	SYNTAX  INTEGER
	ACCESS  read-only
	STATUS  mandatory
	DESCRIPTION
	              ""
	::= { dhcpSnpDbStat 11 }

	dhcpSnpDbStatSuccRead OBJECT-TYPE
	SYNTAX  INTEGER
	ACCESS  read-only
	STATUS  mandatory
	DESCRIPTION
	              ""
	::= { dhcpSnpDbStat 12 }

	dhcpSnpDbStatFailRead OBJECT-TYPE
	SYNTAX  INTEGER
	ACCESS  read-only
	STATUS  mandatory
	DESCRIPTION
	              ""
	::= { dhcpSnpDbStat 13 }

	dhcpSnpDbStatSuccWrite OBJECT-TYPE
	SYNTAX  INTEGER
	ACCESS  read-only
	STATUS  mandatory
	DESCRIPTION
	              ""
	::= { dhcpSnpDbStat 14 }

	dhcpSnpDbStatFailWrite OBJECT-TYPE
	SYNTAX  INTEGER
	ACCESS  read-only
	STATUS  mandatory
	DESCRIPTION
	              ""
	::= { dhcpSnpDbStat 15 }

	dhcpSnpDbStatFirstSuccAccess OBJECT-TYPE
	SYNTAX  INTEGER { none(0), read(1), write(2) }
	ACCESS  read-only
	STATUS  mandatory
	DESCRIPTION
	              ""
	::= { dhcpSnpDbStat 16 }

	dhcpSnpDbStatLastIgnoreBindCol OBJECT-TYPE
	SYNTAX  INTEGER
	ACCESS  read-only
	STATUS  mandatory
	DESCRIPTION
	              "Last ignored: binding collision"
	::= { dhcpSnpDbStat 17 }

	dhcpSnpDbStatLastIgnoreExpireLease OBJECT-TYPE
	SYNTAX  INTEGER
	ACCESS  read-only
	STATUS  mandatory
	DESCRIPTION
	              "Last ignored: expired leases"
	::= { dhcpSnpDbStat 18 }

	dhcpSnpDbStatLastIgnoreInvalidIntf OBJECT-TYPE
	SYNTAX  INTEGER
	ACCESS  read-only
	STATUS  mandatory
	DESCRIPTION
	              "Last ignored: invalid interface"
	::= { dhcpSnpDbStat 19 }

	dhcpSnpDbStatLastIgnoreUnsuppVlan OBJECT-TYPE
	SYNTAX  INTEGER
	ACCESS  read-only
	STATUS  mandatory
	DESCRIPTION
	              "Last ignored: unsupported vlans"
	::= { dhcpSnpDbStat 20 }

	dhcpSnpDbStatLastIgnoreParse OBJECT-TYPE
	SYNTAX  INTEGER
	ACCESS  read-only
	STATUS  mandatory
	DESCRIPTION
	              "Last ignored: parsing error"
	::= { dhcpSnpDbStat 21 }

	dhcpSnpDbStatTotalIgnoreBindCol OBJECT-TYPE
	SYNTAX  INTEGER
	ACCESS  read-only
	STATUS  mandatory
	DESCRIPTION
	              "Total ignored: binding collision"
	::= { dhcpSnpDbStat 22 }

	dhcpSnpDbStatTotalIgnoreExpireLease OBJECT-TYPE
	SYNTAX  INTEGER
	ACCESS  read-only
	STATUS  mandatory
	DESCRIPTION
	              "Total ignored: expired leases"
	::= { dhcpSnpDbStat 23 }

	dhcpSnpDbStatTotalIgnoreInvalidIntf OBJECT-TYPE
	SYNTAX  INTEGER
	ACCESS  read-only
	STATUS  mandatory
	DESCRIPTION
	              "Total ignored: invalid interface"
	::= { dhcpSnpDbStat 24 }

	dhcpSnpDbStatTotalIgnoreUnsuppVlan OBJECT-TYPE
	SYNTAX  INTEGER
	ACCESS  read-only
	STATUS  mandatory
	DESCRIPTION
	              "Total ignored: unsupported vlans"
	::= { dhcpSnpDbStat 25 }

	dhcpSnpDbStatTotalIgnoreParse OBJECT-TYPE
	SYNTAX  INTEGER
	ACCESS  read-only
	STATUS  mandatory
	DESCRIPTION
	              "Total ignored: parsing error"
	::= { dhcpSnpDbStat 26 }


	dhcpSnpDbStatFirstSuccessAccess OBJECT-TYPE
	SYNTAX INTEGER{
        		none(0),
        		read(1),
        		write(2)
        }
	ACCESS  read-only
	STATUS  mandatory
	DESCRIPTION
	              "First Success Access"
	::= { dhcpSnpDbStat 27 }

--
--  dhcp snooping dhcp vlan
--

	dhcpSnpDhcpVlan     	OBJECT IDENTIFIER ::= { dhcpSnp 6 }

	dhcpSnpDhcpVlanVid OBJECT-TYPE
	SYNTAX  INTEGER (0..4094)
	ACCESS  read-write
	STATUS  mandatory
	DESCRIPTION
	              "0: disable DHCP VLAN."
	::= { dhcpSnpDhcpVlan 1 }
	
-- --------------------------------------------------------------
--
-- ip source guard
--
-- --------------------------------------------------------------

	ipsg OBJECT IDENTIFIER ::= { ves1616pe54 50 }
	
	    ipsgTable  OBJECT-TYPE
	    SYNTAX	SEQUENCE OF IpsgEntry 
	    ACCESS  not-accessible
	    STATUS  mandatory
	    DESCRIPTION
	             	""
	    ::= { ipsg 1 }	

	ipsgEntry  OBJECT-TYPE
        SYNTAX	IpsgEntry 
        ACCESS	not-accessible
        STATUS	mandatory
        DESCRIPTION    	""
        INDEX          	{ ipsgEntryMac, ipsgEntryVid }
        ::= { ipsgTable 1 }

        IpsgEntry ::=
           SEQUENCE {
            ipsgEntryMac		MacAddress,
        	ipsgEntryVid		INTEGER,
        	ipsgEntryIp			IpAddress,
        	ipsgEntryLease		INTEGER,
        	ipsgEntryType		INTEGER,
        	ipsgEntryPort		INTEGER,
        	ipsgEntryState		RowStatus
           }

        ipsgEntryMac OBJECT-TYPE
        SYNTAX  MacAddress
        ACCESS  read-only
        STATUS  mandatory
        DESCRIPTION
                      	""
        ::= { ipsgEntry 1 }

        ipsgEntryVid OBJECT-TYPE
        SYNTAX  INTEGER (1.. 4094)
        ACCESS  read-only
        STATUS  mandatory
        DESCRIPTION
                      	""
        ::= { ipsgEntry 2 }

        ipsgEntryIp OBJECT-TYPE
        SYNTAX  IpAddress
        ACCESS  read-write
        STATUS  mandatory
        DESCRIPTION
                      	""
        ::= { ipsgEntry 3 }

        ipsgEntryLease OBJECT-TYPE
        SYNTAX  INTEGER
        ACCESS  read-only
        STATUS  mandatory
        DESCRIPTION
                      	"second"
        ::= { ipsgEntry 4 }

        ipsgEntryType OBJECT-TYPE
        SYNTAX  INTEGER { static(1), dhcp(2) }
        ACCESS  read-only
        STATUS  mandatory
        DESCRIPTION
                      	""
        ::= { ipsgEntry 5 }

        ipsgEntryPort OBJECT-TYPE
        SYNTAX  INTEGER 
        ACCESS  read-write
        STATUS  mandatory
        DESCRIPTION
                      	"0 means any port"
        ::= { ipsgEntry 6 }

        ipsgEntryState OBJECT-TYPE
        SYNTAX  RowStatus
        ACCESS  read-create
        STATUS  mandatory
        DESCRIPTION
                      	""
        ::= { ipsgEntry 7 } 

-- --------------------------------------------------------------
--
-- arpInspect
--
-- --------------------------------------------------------------

	arpInspect     	OBJECT IDENTIFIER ::= { ves1616pe54 51 }

	arpInspectSetup  OBJECT IDENTIFIER ::= { arpInspect 1 }

        arpInspectState OBJECT-TYPE
        SYNTAX  EnabledStatus
        ACCESS  read-write
        STATUS  mandatory
        DESCRIPTION
                      ""
        ::= { arpInspectSetup 1 }

        arpInspectFilterAgingTime OBJECT-TYPE
        SYNTAX  INTEGER (0..2147483647)
        ACCESS  read-write
        STATUS  mandatory
        DESCRIPTION
                      ""
        ::= { arpInspectSetup 2 }

	arpInspectLog  OBJECT IDENTIFIER ::= { arpInspectSetup 3 }
	
        arpInspectLogEntries OBJECT-TYPE
        SYNTAX  INTEGER	(0..1024)
        ACCESS  read-write
        STATUS  mandatory
        DESCRIPTION
                      ""
        ::= { arpInspectLog 1 }

        arpInspectLogRate OBJECT-TYPE
        SYNTAX  INTEGER (0..1024)
        ACCESS  read-write
        STATUS  mandatory
        DESCRIPTION
                      ""
        ::= { arpInspectLog 2 }
        
        arpInspectLogInterval OBJECT-TYPE
        SYNTAX  INTEGER (0..2147483647)
        ACCESS  read-write
        STATUS  mandatory
        DESCRIPTION
                      ""
        ::= { arpInspectLog 3 }                	

	--arpInspectVlanTable
        arpInspectVlanTable OBJECT-TYPE
        SYNTAX	SEQUENCE OF ArpInspectVlanEntry
        ACCESS  not-accessible
        STATUS  mandatory
        DESCRIPTION
                 	""
        ::= { arpInspectSetup 4 }
        
	arpInspectVlanEntry OBJECT-TYPE
        SYNTAX	ArpInspectVlanEntry
        ACCESS	not-accessible
        STATUS	mandatory
        DESCRIPTION    	""
        INDEX          	{ arpInspectVlanVid }
        ::= { arpInspectVlanTable 1 }

        ArpInspectVlanEntry ::=
           SEQUENCE {
        	arpInspectVlanVid	INTEGER,
        	arpInspectVlanLog	INTEGER,
			arpInspectVlanStatus	INTEGER       	
           }

        arpInspectVlanVid OBJECT-TYPE
        SYNTAX  INTEGER (1..4094)
        ACCESS  read-only
        STATUS  mandatory
        DESCRIPTION
                      	""
        ::= { arpInspectVlanEntry 1 }

        arpInspectVlanLog OBJECT-TYPE
        SYNTAX  INTEGER {
        		all (1),
        		none (2),
        		permit (3),
        		deny (4)
        }
        		
        ACCESS  read-write
        STATUS  mandatory
        DESCRIPTION
                      	""
        ::= { arpInspectVlanEntry 2 }

        arpInspectVlanStatus OBJECT-TYPE
        SYNTAX  INTEGER {
        		enabled(1),
        		disabled(2)
        }
        ACCESS  read-write
        STATUS  mandatory
        DESCRIPTION
                      	""
        ::= { arpInspectVlanEntry 3 }

	--arpInspectPortTable
        arpInspectPortTable OBJECT-TYPE
        SYNTAX	SEQUENCE OF ArpInspectPortEntry
        ACCESS  not-accessible
        STATUS  mandatory
        DESCRIPTION
                 	""
        ::= { arpInspectSetup 5 }
        
	arpInspectPortEntry OBJECT-TYPE
        SYNTAX	ArpInspectPortEntry
        ACCESS	not-accessible
        STATUS	mandatory
        DESCRIPTION    	""
        INDEX          	{ arpInspectPortIndex }
        ::= { arpInspectPortTable 1 }

        ArpInspectPortEntry ::=
           SEQUENCE {
        	arpInspectPortIndex	INTEGER,
        	arpInspectPortTrust	INTEGER,
			arpInspectPortRate	INTEGER,       	
			arpInspectPortInterval	INTEGER
           }

        arpInspectPortIndex OBJECT-TYPE
        SYNTAX  INTEGER
        ACCESS  read-only
        STATUS  mandatory
        DESCRIPTION
                      	""
        ::= { arpInspectPortEntry 1 }

        arpInspectPortTrust OBJECT-TYPE
        SYNTAX  INTEGER {
        		trusted(1),
        		untrusted(2)
        }
        ACCESS  read-write
        STATUS  mandatory
        DESCRIPTION
                      	""
        ::= { arpInspectPortEntry 2 }

        arpInspectPortRate OBJECT-TYPE
        SYNTAX  INTEGER	(0..2048)
        ACCESS  read-write
        STATUS  mandatory
        DESCRIPTION
                      	""
        ::= { arpInspectPortEntry 3 }

        arpInspectPortInterval OBJECT-TYPE
        SYNTAX  INTEGER	(1..15)
        ACCESS  read-write
        STATUS  mandatory
        DESCRIPTION
                      	""
        ::= { arpInspectPortEntry 4 }

	arpInspectStatus  OBJECT IDENTIFIER ::= { arpInspect 2 }

        arpInspectFilterClear OBJECT-TYPE
        SYNTAX  EnabledStatus
        ACCESS  read-write
        STATUS  mandatory
        DESCRIPTION
                      ""
        ::= { arpInspectStatus 1 }

        arpInspectLogClear OBJECT-TYPE
        SYNTAX  EnabledStatus
        ACCESS  read-write
        STATUS  mandatory
        DESCRIPTION
                      ""
        ::= { arpInspectStatus 2 }

	--arpInspectFilterTable
        arpInspectFilterTable OBJECT-TYPE
        SYNTAX	SEQUENCE OF ArpInspectFilterEntry
        ACCESS  not-accessible
        STATUS  mandatory
        DESCRIPTION
                 	""
        ::= { arpInspectStatus 3 }
        
	arpInspectFilterEntry OBJECT-TYPE
        SYNTAX	ArpInspectFilterEntry
        ACCESS	not-accessible
        STATUS	mandatory
        DESCRIPTION    	""
        INDEX          	{ arpInspectFilterMac, arpInspectFilterVid }
        ::= { arpInspectFilterTable 1 }

        ArpInspectFilterEntry ::=
           SEQUENCE {
        	arpInspectFilterMac	MacAddress,
        	arpInspectFilterVid	INTEGER,
			arpInspectFilterPort	INTEGER,       	
			arpInspectFilterExpiry	INTEGER,
			arpInspectFilterReason	INTEGER,
			arpInspectFilterRowStatus RowStatus
           }

        arpInspectFilterMac OBJECT-TYPE
        SYNTAX  MacAddress
        ACCESS  read-only
        STATUS  mandatory
        DESCRIPTION
                      	""
        ::= { arpInspectFilterEntry 1 }

        arpInspectFilterVid OBJECT-TYPE
        SYNTAX  INTEGER (1..4094)
        ACCESS  read-only
        STATUS  mandatory
        DESCRIPTION
                      	""
        ::= { arpInspectFilterEntry 2 }

        arpInspectFilterPort OBJECT-TYPE
        SYNTAX  INTEGER
        ACCESS  read-only
        STATUS  mandatory
        DESCRIPTION
                      	""
        ::= { arpInspectFilterEntry 3 }

        arpInspectFilterExpiry OBJECT-TYPE
        SYNTAX  INTEGER
        ACCESS  read-only
        STATUS  mandatory
        DESCRIPTION
                      	""
        ::= { arpInspectFilterEntry 4 }	

        arpInspectFilterReason OBJECT-TYPE
        SYNTAX  INTEGER {
        		macVid(1),
        		port(2),
        		ip(3)
        }
        ACCESS  read-only
        STATUS  mandatory
        DESCRIPTION
                      	""
        ::= { arpInspectFilterEntry 5 }		
        
       arpInspectFilterRowStatus OBJECT-TYPE
        SYNTAX  RowStatus
        ACCESS  read-create
        STATUS  mandatory
        DESCRIPTION
                      	""
        ::= { arpInspectFilterEntry 6 }	

	--arpInspectLogTable
        arpInspectLogTable OBJECT-TYPE
        SYNTAX	SEQUENCE OF ArpInspectLogEntry
        ACCESS  not-accessible
        STATUS  mandatory
        DESCRIPTION
                 	""
        ::= { arpInspectStatus 4 }
        
	arpInspectLogEntry OBJECT-TYPE
        SYNTAX	ArpInspectLogEntry
        ACCESS	not-accessible
        STATUS	mandatory
        DESCRIPTION    	""
        INDEX          	{ arpInspectLogMac, arpInspectLogVid, arpInspectLogPort, arpInspectLogIp, arpInspectLogReason }
        ::= { arpInspectLogTable 1 }

        ArpInspectLogEntry ::=
           SEQUENCE {
        	arpInspectLogMac	MacAddress,
        	arpInspectLogVid	INTEGER,
			arpInspectLogPort	INTEGER,       	
			arpInspectLogIp	IpAddress,
			arpInspectLogNumPkt	INTEGER,
			arpInspectLogReason	INTEGER,
			arpInspectLogTime	DateAndTime
           }

        arpInspectLogMac OBJECT-TYPE
        SYNTAX  MacAddress
        ACCESS  read-only
        STATUS  mandatory
        DESCRIPTION
                      	""
        ::= { arpInspectLogEntry 1 }

        arpInspectLogVid OBJECT-TYPE
        SYNTAX  INTEGER (1..4094)
        ACCESS  read-only
        STATUS  mandatory
        DESCRIPTION
                      	""
        ::= { arpInspectLogEntry 2 }

        arpInspectLogPort OBJECT-TYPE
        SYNTAX  INTEGER
        ACCESS  read-only
        STATUS  mandatory
        DESCRIPTION
                      	""
        ::= { arpInspectLogEntry 3 }

        arpInspectLogIp OBJECT-TYPE
        SYNTAX  IpAddress
        ACCESS  read-only
        STATUS  mandatory
        DESCRIPTION
                      	""
        ::= { arpInspectLogEntry 4 }	

        arpInspectLogNumPkt OBJECT-TYPE
        SYNTAX  INTEGER
        ACCESS  read-only
        STATUS  mandatory
        DESCRIPTION
                      	""
        ::= { arpInspectLogEntry 5 }		

        arpInspectLogReason OBJECT-TYPE
        SYNTAX  INTEGER {
        		deny (1),
        		denyStatic (2),
        		denyDHCP (3),
        		permitStatic (4),
        		permitDHCP (5)
        }
        ACCESS  read-only
        STATUS  mandatory
        DESCRIPTION
                      	""
        ::= { arpInspectLogEntry 6 }		
        
        arpInspectLogTime OBJECT-TYPE
        SYNTAX  DateAndTime
        ACCESS  read-only
        STATUS  mandatory
        DESCRIPTION
                      	""
        ::= { arpInspectLogEntry 7 }		
        
	--arpInspectStatisticsTable
        arpInspectStatisticsTable OBJECT-TYPE
        SYNTAX	SEQUENCE OF ArpInspectStatisticsEntry
        ACCESS  not-accessible
        STATUS  mandatory
        DESCRIPTION
                 	""
        ::= { arpInspectStatus 5 }
        
	arpInspectStatisticsEntry OBJECT-TYPE
        SYNTAX	ArpInspectStatisticsEntry
        ACCESS	not-accessible
        STATUS	mandatory
        DESCRIPTION    	""
        INDEX          	{ arpInspectStatisticsVid }
        ::= { arpInspectStatisticsTable 1 }

        ArpInspectStatisticsEntry ::=
           SEQUENCE {
        	arpInspectStatisticsVid	INTEGER,
			arpInspectStatisticsReceived	Counter,       	
			arpInspectStatisticsRequest	Counter,
			arpInspectStatisticsReply	Counter,
			arpInspectStatisticsForward	Counter,
			arpInspectStatisticsDrop	Counter,
			arpInspectStatisticsClear	EnabledStatus
           }

        arpInspectStatisticsVid OBJECT-TYPE
        SYNTAX  INTEGER
        ACCESS  read-only
        STATUS  mandatory
        DESCRIPTION
                      	""
        ::= { arpInspectStatisticsEntry 1 }

        arpInspectStatisticsReceived OBJECT-TYPE
        SYNTAX  Counter
        ACCESS  read-only
        STATUS  mandatory
        DESCRIPTION
                      	""
        ::= { arpInspectStatisticsEntry 2 }

        arpInspectStatisticsRequest OBJECT-TYPE
        SYNTAX  Counter
        ACCESS  read-only
        STATUS  mandatory
        DESCRIPTION
                      	""
        ::= { arpInspectStatisticsEntry 3 }

        arpInspectStatisticsReply OBJECT-TYPE
        SYNTAX  Counter
        ACCESS  read-only
        STATUS  mandatory
        DESCRIPTION
                      	""
        ::= { arpInspectStatisticsEntry 4 }	

        arpInspectStatisticsForward OBJECT-TYPE
        SYNTAX  Counter
        ACCESS  read-only
        STATUS  mandatory
        DESCRIPTION
                      	""
        ::= { arpInspectStatisticsEntry 5 }		

        arpInspectStatisticsDrop OBJECT-TYPE
        SYNTAX  Counter
        ACCESS  read-only
        STATUS  mandatory
        DESCRIPTION
                      	""
        ::= { arpInspectStatisticsEntry 6 }		

        arpInspectStatisticsClear OBJECT-TYPE
        SYNTAX  EnabledStatus
        ACCESS  read-write
        STATUS  mandatory
        DESCRIPTION
                      	""
        ::= { arpInspectStatisticsEntry 7 } 

-- trTCMSetup
	trTCMSetup OBJECT IDENTIFIER ::= { ves1616pe54 52 }

        trTCMState OBJECT-TYPE
        SYNTAX  EnabledStatus
        ACCESS  read-write
        STATUS  mandatory
        DESCRIPTION
                      	"Two-rate three color marker enabled/disabled for the switch."
        ::= { trTCMSetup 1 }  
        
        trTCMMode OBJECT-TYPE
        SYNTAX  INTEGER {
        	color-aware(0),
        	color-blind(1)
        	}
        ACCESS  read-write
        STATUS  mandatory
        DESCRIPTION
                      	""
        ::= { trTCMSetup 2 } 

-- trTCMPortTable       
        trTCMPortTable OBJECT-TYPE
        SYNTAX	SEQUENCE OF TrTCMPortEntry
        ACCESS  not-accessible
        STATUS  mandatory
        DESCRIPTION
                 	""
        ::= { trTCMSetup 3 }
        
	trTCMPortEntry OBJECT-TYPE
        SYNTAX	TrTCMPortEntry
        ACCESS	not-accessible
        STATUS	mandatory
        DESCRIPTION    	"An entry in trTCMPortTable."
        INDEX          	{ dot1dBasePort }
        ::= { trTCMPortTable 1 }

        TrTCMPortEntry ::=
           SEQUENCE {
       	trTCMPortState	EnabledStatus,
		trTCMPortCIR	INTEGER,     
		trTCMPortPIR	INTEGER,  
		trTCMPortDscpGreen	INTEGER,  
		trTCMPortDscpYellow	INTEGER,  
		trTCMPortDscpRed	INTEGER
           }

        trTCMPortState OBJECT-TYPE
        SYNTAX  EnabledStatus
        ACCESS  read-create
        STATUS  mandatory
        DESCRIPTION
                      	"Two-rate three color marker enabled/disabled on the port."
        ::= { trTCMPortEntry 1 }
        
        trTCMPortCIR OBJECT-TYPE
        SYNTAX  INTEGER
        ACCESS  read-write
        STATUS  mandatory
        DESCRIPTION
                      	"Allowed CIR in pkts/s."
        ::= { trTCMPortEntry 2 }
        
        trTCMPortPIR OBJECT-TYPE
        SYNTAX  INTEGER
        ACCESS  read-write
        STATUS  mandatory
        DESCRIPTION
                      	"Allowed PIR in pkts/s."
        ::= { trTCMPortEntry 3 }
        
        trTCMPortDscpGreen OBJECT-TYPE
        SYNTAX  INTEGER
        ACCESS  read-write
        STATUS  mandatory
        DESCRIPTION
                      	"0-63"
        ::= { trTCMPortEntry 4 }

        trTCMPortDscpYellow OBJECT-TYPE
        SYNTAX  INTEGER
        ACCESS  read-write
        STATUS  mandatory
        DESCRIPTION
                      	"0-63"
        ::= { trTCMPortEntry 5 }

        trTCMPortDscpRed OBJECT-TYPE
        SYNTAX  INTEGER
        ACCESS  read-write
        STATUS  mandatory
        DESCRIPTION
                      	"0-63"
        ::= { trTCMPortEntry 6 }        


-- loopGuardSetup
	loopGuardSetup     	OBJECT IDENTIFIER ::= { ves1616pe54 53 }
                               
        loopGuardState OBJECT-TYPE
        SYNTAX  EnabledStatus
        ACCESS  read-write
        STATUS  mandatory
        DESCRIPTION
                      	""
        ::= { loopGuardSetup 1 }

                                               
-- loopGuardPortTable

        loopGuardPortTable OBJECT-TYPE
        SYNTAX	SEQUENCE OF LoopGuardPortEntry
        ACCESS  not-accessible
        STATUS  mandatory
        DESCRIPTION
                 	""
        ::= { loopGuardSetup 2 }
        
	loopGuardPortEntry OBJECT-TYPE
        SYNTAX	LoopGuardPortEntry
        ACCESS	not-accessible
        STATUS	mandatory
        DESCRIPTION    	"An entry in loopGuardPortTable."
        INDEX          	{ dot1dBasePort }
        ::= { loopGuardPortTable 1 }

        LoopGuardPortEntry ::=
           SEQUENCE {
        	loopGuardPortState	EnabledStatus,
        	loopGuardPortMode	INTEGER,
        	loopGuardPortRecoverTime	INTEGER
           }

        loopGuardPortState OBJECT-TYPE
        SYNTAX  EnabledStatus
        ACCESS  read-write
        STATUS  mandatory
        DESCRIPTION
                      	""
        ::= { loopGuardPortEntry 1 }

	loopGuardPortMode OBJECT-TYPE
        SYNTAX  INTEGER {
        	fix(1),
        	dynamic(2)
        }
        ACCESS  read-write
        STATUS  mandatory
        DESCRIPTION
                      	"Specify loopguard mode for each port"
        ::= { loopGuardPortEntry 2 }

	loopGuardPortRecoverTime OBJECT-TYPE
        SYNTAX  INTEGER
        ACCESS  read-write
        STATUS  mandatory
        DESCRIPTION
                      	"recover time to activate port in seconds."
        ::= { loopGuardPortEntry 3 }

-- subnetBasedVlanSetup
	subnetBasedVlanSetup OBJECT IDENTIFIER ::= { ves1616pe54 54 }

        subnetBasedVlanState OBJECT-TYPE
        SYNTAX  EnabledStatus
        ACCESS  read-write
        STATUS  mandatory
        DESCRIPTION
        	"subnet-based vlan feature enabled/disabled for the switch."
        ::= { subnetBasedVlanSetup 1 }

        dhcpVlanOverrideState OBJECT-TYPE
        SYNTAX  EnabledStatus
        ACCESS  read-write
        STATUS  mandatory
        DESCRIPTION
        	"dhcp vlan override enabled/disabled when subnet-based vlan is enabled."
        ::= { subnetBasedVlanSetup 2 }
             
             
	    subnetBasedVlanTable  OBJECT-TYPE
	    SYNTAX	SEQUENCE OF SubnetBasedVlanEntry 
	    ACCESS  not-accessible
	    STATUS  mandatory
	    DESCRIPTION
	             	""
	    ::= { subnetBasedVlanSetup 3 }	

		subnetBasedVlanEntry  OBJECT-TYPE
        SYNTAX	SubnetBasedVlanEntry 
        ACCESS	not-accessible
        STATUS	mandatory
        DESCRIPTION    	"An entry in subnetBasedVlanTable."
        INDEX          	{subnetBasedVlanSrcIp , subnetBasedVlanSrcMaskBit}
        ::= { subnetBasedVlanTable 1 }

        SubnetBasedVlanEntry ::=
           SEQUENCE {
            subnetBasedVlanSrcIp			IpAddress,
            subnetBasedVlanSrcMaskBit		INTEGER,
            subnetBasedVlanName				DisplayString,     
            subnetBasedVlanVid				INTEGER,
            subnetBasedVlanPriority			INTEGER,          
            subnetBasedVlanEntryState		RowStatus            
           }

        subnetBasedVlanSrcIp OBJECT-TYPE
        SYNTAX  IpAddress
        ACCESS  not-accessible
        STATUS  mandatory
        DESCRIPTION
                      	"source ip for subnet-based vlan entry"
        ::= { subnetBasedVlanEntry 1 }


        subnetBasedVlanSrcMaskBit OBJECT-TYPE
        SYNTAX  INTEGER (1..32)
        ACCESS  not-accessible
        STATUS  mandatory
        DESCRIPTION
                      	"source ip mask-bits for subnet-based vlan entry"
        ::= { subnetBasedVlanEntry 2 }
             
        subnetBasedVlanName OBJECT-TYPE
        SYNTAX  DisplayString (SIZE (0..32))
        ACCESS  read-write
        STATUS  mandatory
        DESCRIPTION
                      	"name for subnet-based vlan entry"
        ::= { subnetBasedVlanEntry 3 }
                                                   
        subnetBasedVlanVid OBJECT-TYPE
        SYNTAX  INTEGER (1..4094)
        ACCESS  read-write
        STATUS  mandatory
        DESCRIPTION
                      	"vid for subnet-based vlan entry"
        ::= { subnetBasedVlanEntry 4 }


        subnetBasedVlanPriority OBJECT-TYPE
        SYNTAX  INTEGER (0..7)
        ACCESS  read-write
        STATUS  mandatory
        DESCRIPTION
                      	"priority for subnet-based vlan entry"
        ::= { subnetBasedVlanEntry 5 }

        subnetBasedVlanEntryState OBJECT-TYPE
        SYNTAX  RowStatus
        ACCESS  read-create
        STATUS  mandatory
        DESCRIPTION
                      	""
        ::= { subnetBasedVlanEntry 6 } 
        
             
	    subnetBasedVlanInfoTable  OBJECT-TYPE
	    SYNTAX	SEQUENCE OF SubnetBasedVlanInfoEntry 
	    ACCESS  not-accessible
	    STATUS  mandatory
	    DESCRIPTION
	             	""
	    ::= { subnetBasedVlanSetup 4 }	

		subnetBasedVlanInfoEntry  OBJECT-TYPE
        SYNTAX	SubnetBasedVlanInfoEntry 
        ACCESS	not-accessible
        STATUS	mandatory
        DESCRIPTION    	"An entry in subnetBasedVlanInfoTable."
        INDEX          	{subnetBasedVlanInfoSrcIpType , subnetBasedVlanInfoSrcIp , subnetBasedVlanInfoSrcMaskBit}
        ::= { subnetBasedVlanInfoTable 1 }

        SubnetBasedVlanInfoEntry ::=
           SEQUENCE {
            subnetBasedVlanInfoSrcIpType		InetAddressType,
            subnetBasedVlanInfoSrcIp			InetAddress,
            subnetBasedVlanInfoSrcMaskBit		INTEGER, 
            subnetBasedVlanInfoName				DisplayString,     
            subnetBasedVlanInfoVid				INTEGER,
            subnetBasedVlanInfoPriority			INTEGER,          
            subnetBasedVlanInfoEntryState		RowStatus
           }

				subnetBasedVlanInfoSrcIpType OBJECT-TYPE
        SYNTAX  InetAddressType {ipv4(1), ipv6(2)}        
        ACCESS  not-accessible
        STATUS  mandatory
        DESCRIPTION
                      	"Ip type for subnet-based vlan entry"
        ::= { subnetBasedVlanInfoEntry 1 }  

        subnetBasedVlanInfoSrcIp OBJECT-TYPE
        SYNTAX  InetAddress
        ACCESS  not-accessible
        STATUS  mandatory
        DESCRIPTION
                      	"source ip of IPv4 or IPv6 for subnet-based vlan entry"
        ::= { subnetBasedVlanInfoEntry 2 }


        subnetBasedVlanInfoSrcMaskBit OBJECT-TYPE
        SYNTAX  INTEGER (1..32)
        ACCESS  not-accessible
        STATUS  mandatory
        DESCRIPTION
                      	"source ip mask-bits for subnet-based vlan entry"
        ::= { subnetBasedVlanInfoEntry 3 }
             
        subnetBasedVlanInfoName OBJECT-TYPE
        SYNTAX  DisplayString (SIZE (0..32))
        ACCESS  read-write
        STATUS  mandatory
        DESCRIPTION
                      	"name for subnet-based vlan entry"
        ::= { subnetBasedVlanInfoEntry 4 }
                                                   
        subnetBasedVlanInfoVid OBJECT-TYPE
        SYNTAX  INTEGER (1..4094)
        ACCESS  read-write
        STATUS  mandatory
        DESCRIPTION
                      	"vid for subnet-based vlan entry"
        ::= { subnetBasedVlanInfoEntry 5 }


        subnetBasedVlanInfoPriority OBJECT-TYPE
        SYNTAX  INTEGER (0..7)
        ACCESS  read-write
        STATUS  mandatory
        DESCRIPTION
                      	"priority for subnet-based vlan entry"
        ::= { subnetBasedVlanInfoEntry 6 }

        subnetBasedVlanInfoEntryState OBJECT-TYPE
        SYNTAX  RowStatus
        ACCESS  read-create
        STATUS  mandatory
        DESCRIPTION
                      	""
        ::= { subnetBasedVlanInfoEntry 7 } 
        
        
--  MAC Authentication
				 macAuthenticationSetup      OBJECT IDENTIFIER ::= { ves1616pe54 55 }
                               
        macAuthenticationState OBJECT-TYPE
        SYNTAX  EnabledStatus
        ACCESS  read-write
        STATUS  mandatory
        DESCRIPTION
                       ""
        ::= { macAuthenticationSetup 1 }
 
        macAuthenticationNamePrefix OBJECT-TYPE
        SYNTAX  DisplayString
        ACCESS  read-write
        STATUS  mandatory
        DESCRIPTION
                       ""
        ::= { macAuthenticationSetup 2 }
 
        macAuthenticationPassword OBJECT-TYPE
        SYNTAX  DisplayString
        ACCESS  read-write
        STATUS  mandatory
        DESCRIPTION
                       ""
        ::= { macAuthenticationSetup 3 }
 
        macAuthenticationTimeout OBJECT-TYPE
        SYNTAX  INTEGER
        ACCESS  read-write
        STATUS  mandatory
        DESCRIPTION
                       ""
        ::= { macAuthenticationSetup 4 }
                                               
-- macAuthenticationPortTable
 
	macAuthenticationPortTable OBJECT-TYPE
        SYNTAX SEQUENCE OF MacAuthenticationPortEntry
        ACCESS  not-accessible
        STATUS  mandatory
        DESCRIPTION
                  ""
        ::= { macAuthenticationSetup 5 }
        
 	macAuthenticationPortEntry OBJECT-TYPE
        SYNTAX MacAuthenticationPortEntry
        ACCESS not-accessible
        STATUS mandatory
        DESCRIPTION     "An entry in macAuthenticationPortTable."
        INDEX           { dot1dBasePort }
        ::= { macAuthenticationPortTable 1 }
 
		MacAuthenticationPortEntry ::=
		SEQUENCE {
			macAuthenticationPortState EnabledStatus
		}
 
        macAuthenticationPortState OBJECT-TYPE
        SYNTAX  EnabledStatus
        ACCESS  read-write
        STATUS  mandatory
        DESCRIPTION
                       ""
        ::= { macAuthenticationPortEntry 1 }

-- MSTP  
--****************************************************************
-- TEXTUAL-CONVENTIONs
--****************************************************************
		MstiOrCistInstanceIndex ::= TEXTUAL-CONVENTION
      		STATUS       current
    		DESCRIPTION
	            "This textual convention is an extension of the
	            MstiInstanceIndex convention.  This extension permits the
	            additional value of zero, which means Common and Internal
	            Spanning Tree (CIST)."
            SYNTAX      Integer32 (0..16) 
            
        mstp            OBJECT IDENTIFIER ::= { ves1616pe54 56 }    
-- mstpGen group reflects configurations/statuses
-- the Bridge as a unit  
	    mstpGen			OBJECT IDENTIFIER ::= { mstp 1}  
	    
        mstpGenState		OBJECT-TYPE
        SYNTAX    EnabledStatus
        ACCESS    read-write
        STATUS    mandatory
        DESCRIPTION
        "Enabled/disabled on the mrstp bridge."
        ::= { mstpGen 1 }
        
        mstpGenCfgIdName    OBJECT-TYPE
        SYNTAX    DisplayString
        ACCESS    read-write
        STATUS    mandatory 
        DESCRIPTION 
        "The configuration name that identifies the MST
         region and is used as one of the inputs in the 
         computation of the MST Configuration Identifier." 
        REFERENCE
            "12.12.3.4.2.b)"
        ::= { mstpGen 2 }
        
        mstpGenCfgIdRevLevel OBJECT-TYPE
        SYNTAX    Integer32
        ACCESS    read-write
        STATUS    mandatory 
        DESCRIPTION 
        "This object identifies the MST revision that
         identifies the MST region and is used as one
         of the inputs in the computation of the MST 
         configuration Identifier."
        REFERENCE
            "12.12.3.4.2.c)"
        ::= { mstpGen 3 }
	    
	    
	   mstpGenCfgIdCfgDigest  OBJECT-TYPE
            SYNTAX    OCTET STRING(SIZE(16))
            ACCESS    read-only
            STATUS    mandatory
            DESCRIPTION
              "Configuration Digest."
            REFERENCE
               "12.12.3.3.3.a.4"
            ::= { mstpGen 4 }
	    
	    mstpGenHelloTime  OBJECT-TYPE
	        SYNTAX    Timeout (1..10)
            ACCESS    read-write
            STATUS    mandatory 
            DESCRIPTION
            ""                  
            ::= { mstpGen 5 }
       
        mstpGenMaxAge    OBJECT-TYPE
            SYNTAX  Timeout (6..40)
            ACCESS  read-write
            STATUS  mandatory 
            DESCRIPTION
            "" 
            ::= { mstpGen 6 }
         
        mstpGenForwardDelay   OBJECT-TYPE 
            SYNTAX  Timeout (4..30)
            ACCESS  read-write
            STATUS  mandatory
            DESCRIPTION
            ""
            ::= {mstpGen 7}
        
        mstpGenMaxHops  OBJECT-TYPE
            SYNTAX      Integer32 (1..255)
            MAX-ACCESS  read-write
            STATUS      mandatory
            DESCRIPTION
               "13.22.f)"
            ::= { mstpGen 8 }
	    
	mstpGenCistRootPathCost  OBJECT-TYPE
            SYNTAX      Integer32
            MAX-ACCESS  read-only
            STATUS      mandatory
            DESCRIPTION
	    "."
            ::= { mstpGen 9 }
	    
	mstpGenCistRootBrid  OBJECT-TYPE
            SYNTAX      OCTET STRING(SIZE(8))
            MAX-ACCESS  read-only
            STATUS      mandatory
            DESCRIPTION
            "."
            ::= { mstpGen 10 }
-- MSTP MAP TABLE
        mstMapTable        OBJECT-TYPE
            SYNTAX      SEQUENCE OF MstMapEntry
            ACCESS  not-accessible
            STATUS      mandatory
            DESCRIPTION
               "This table contains one entry for each instance of MSTP."
            ::= { mstp 20 }	
         
        mstMapEntry        OBJECT-TYPE
            SYNTAX      MstMapEntry
            ACCESS  not-accessible
            STATUS      mandatory
            DESCRIPTION
               "A conceptual row containing the status of the MSTP instance."
            INDEX  { mstMapIndex }
            ::= { mstMapTable 1 }
        
        MstMapEntry ::= SEQUENCE {
                   mstMapIndex             MstiOrCistInstanceIndex,
                   mstMapVlans1k           OCTET STRING,
                   mstMapVlans2k           OCTET STRING,
                   mstMapVlans3k           OCTET STRING,
                   mstMapVlans4k           OCTET STRING,
                   mstMapRowStatus         RowStatus
        }
        
        mstMapIndex    OBJECT-TYPE
            SYNTAX      MstiOrCistInstanceIndex
            MAX-ACCESS  not-accessible
            STATUS      mandatory
            DESCRIPTION
            "Uniquely identifies an instance. The entry of this table with index 0
            presents always, represents CIST. When SET operation "
            ::= { mstMapEntry 1 }  
        
        mstMapVlans1k      OBJECT-TYPE
            SYNTAX      OCTET STRING (SIZE (0..128))
            ACCESS  read-write
            STATUS      mandatory
            DESCRIPTION
           "A string of octets containing one bit per VLAN. The
            first octet corresponds to VLANs with VlanIndex values
            1 through 8; the second octet to VLANs 9 through
            16 etc.  The most significant bit of each octet
            corresponds to the lowest VlanIndex value in that octet.

            For each VLAN that is mapped to this MSTP instance,
            the bit corresponding to that VLAN is set to '1'.
            Empty (zero) most significant octes are not mandatory."
            ::= { mstMapEntry 2 } 
        
        mstMapVlans2k      OBJECT-TYPE
            SYNTAX  OCTET STRING (SIZE (0..128))
            ACCESS  read-write
            STATUS  mandatory
            DESCRIPTION
            "A string of octets containing one bit per VLAN for
             VLANS with VlanIndex values 1024 through 2047. The
             first octet corresponds to VLANs with VlanIndex values
             1024 through 1031; the second octet to VLANs 1032
             through 1039 etc.  The most significant bit of each
             octet corresponds to the lowest VlanIndex value in that
             octet.
             
             For each VLAN that is mapped to this MSTP instance,
             the bit corresponding to that VLAN is set to '1'.

             Empty (zero) most significant octes are not mandatory."
             ::= { mstMapEntry 3 }
        
        mstMapVlans3k      OBJECT-TYPE
            SYNTAX      OCTET STRING (SIZE (0..128))
            ACCESS  read-write
            STATUS      current
            DESCRIPTION
            "A string of octets containing one bit per VLAN for
             VLANS with VlanIndex values 2048 through 3071. The
             first octet corresponds to VLANs with VlanIndex values
             of 2048 through 2055; the second octet to VLANs 2056
             through 2063 etc.  The most significant bit of each
             octet corresponds to the lowest VlanIndex value in that
             octet.

             For each VLAN that is mapped to this MSTP instance,
             the bit corresponding to that VLAN is set to '1'.

             Empty (zero) most significant octes are not mandatory."
             ::= { mstMapEntry 4 }
        
        mstMapVlans4k      OBJECT-TYPE
            SYNTAX      OCTET STRING (SIZE (0..128))
            MAX-ACCESS  read-write
            STATUS      current
            DESCRIPTION
            "A string of octets containing one bit per VLAN for
             VLANS with VlanIndex values 3072 through 4095. The
             first octet corresponds to VLANs with VlanIndex values
             3072 through 3079; the second octet to VLANs 3080
             through 3087 etc.  The most significant bit of each
             octet corresponds to the lowest VlanIndex value in that
             octet.
        
             For each VLAN that is mapped to this MSTP instance,
             the bit corresponding to that VLAN is set to '1'.
           
             Empty (zero) most significant octes are not mandatory."
             ::= { mstMapEntry 5 }   
        
        mstMapRowStatus    OBJECT-TYPE
            SYNTAX  RowStatus
            ACCESS  read-create
            STATUS  mandatory
            DESCRIPTION 
            ""
        ::= {  mstMapEntry 6 }
    	
-- MSTP Vlan Table, map vlan to msti
        mstVlanTable       OBJECT-TYPE
            SYNTAX      SEQUENCE OF MstVlanEntry
            ACCESS  not-accessible
            STATUS      mandatory
            DESCRIPTION
            "This table contains one entry for each VlanId."
            ::= { mstp 30 } 
        
        mstVlanEntry  OBJECT-TYPE
            SYNTAX      MstVlanEntry
            ACCESS      not-accessible
            STATUS      mandatory
            DESCRIPTION
                "Information regarding the instance to which each Vlan is mapped."
            INDEX  { mstVlanIndex }
            ::= { mstVlanTable 1 }
           
        MstVlanEntry ::= SEQUENCE {
              mstVlanIndex         INTEGER,
              mstVlanMstIndex      MstiOrCistInstanceIndex
        }
        
        
        mstVlanIndex     OBJECT-TYPE
            SYNTAX        INTEGER(1..4094)
            ACCESS        not-accessible
            STATUS        mandatory
            DESCRIPTION
                "The VlanId for which this entry contains the instance mapped."
            ::= { mstVlanEntry 1 } 
         
        mstVlanMstIndex    OBJECT-TYPE
             SYNTAX      MstiOrCistInstanceIndex
             ACCESS  read-only
             STATUS      mandatory
             DESCRIPTION
                 "An integer with values ranging from 0 to 64 that identify a 
                      the CIST/MSTI instance to which this VLAN is mapped" 
             ::= { mstVlanEntry 2 }   
-- MSTP Port Table, information for all instance of a port
        mstpPortTable      OBJECT-TYPE
            SYNTAX      SEQUENCE OF MstpPortEntry
            ACCESS  not-accessible
            STATUS      mandatory
            DESCRIPTION
                "A table that contains generic information about
                every port that is associated with this bridge."
            ::= { mstp 40 }
        
        mstpPortEntry      OBJECT-TYPE
            SYNTAX  MstpPortEntry
            ACCESS  not-accessible
            STATUS  mandatory
            DESCRIPTION
            "A list of information for each port of the
            bridge."
            INDEX  { mstpPortIndex }
            ::= { mstpPortTable 1 }
        
        MstpPortEntry ::= SEQUENCE {
             mstpPortIndex                    INTEGER,
             mstpPortOperEdgePort             TruthValue,
             mstpPortOperPointToPointMAC      TruthValue
        }
        
        mstpPortIndex	OBJECT-TYPE
            SYNTAX    INTEGER (1..65535)
            ACCESS  not-accessible
            STATUS      mandatory
            DESCRIPTION
            "A unique value, greater than zero, for each Port.
            The value for each interface sub-layer
            must remain constant at least from one re-initialization
            of the entity's network management system to the next re-
            initialization."
            ::= { mstpPortEntry 1 }
        
        mstpPortOperEdgePort    OBJECT-TYPE
            SYNTAX    TruthValue
            ACCESS    read-only
            STATUS    mandatory 
            DESCRIPTION
            ""
            REFERENCE   ""
            ::= { mstpPortEntry 2 }
        
        mstpPortOperPointToPointMAC    OBJECT-TYPE
            SYNTAX    TruthValue
            ACCESS    read-only
            STATUS    mandatory
            DESCRIPTION
            ""
            REFERENCE    ""
            ::= {mstpPortEntry 3} 
-- MSTP Xst Table, Cist/Mst status/setting
        mstpXstTable  OBJECT-TYPE
              SYNTAX      SEQUENCE OF MstpXstEntry
              ACCESS  not-accessible
              STATUS      mandatory
              DESCRIPTION
                "."
              ::= { mstp 50 }

        mstpXstEntry OBJECT-TYPE
              SYNTAX      MstpXstEntry
              ACCESS  not-accessible
              STATUS      mandatory
              DESCRIPTION
                "."
              INDEX { mstpXstId }
              ::= { mstpXstTable 1 }  
        
       MstpXstEntry ::= SEQUENCE {
	           mstpXstId                      MstiOrCistInstanceIndex,
	           mstpXstBridgePriority          Integer32,
	           mstpXstBridgeId                BridgeId,
	           mstpXstInternalRootCost        Integer32,
	           mstpXstRootPort                INTEGER,
	           mstpXstTimeSinceTopologyChange TimeTicks,
	           mstpXstTopologyChangesCount    Counter32
       }
       
       mstpXstId   OBJECT-TYPE
           SYNTAX      MstiOrCistInstanceIndex
           ACCESS      read-only
           STATUS      mandatory
           DESCRIPTION
             "0 means CIST."
           ::= { mstpXstEntry 1 }
       
       mstpXstBridgePriority   OBJECT-TYPE
           SYNTAX      Integer32 (0..61440)
           ACCESS  read-write
           STATUS      mandatory
           DESCRIPTION
              "Bridge priority, in steps of 4096."
           DEFVAL       { 32768 }
           ::= { mstpXstEntry 2 } 
       
       mstpXstBridgeId   OBJECT-TYPE
           SYNTAX      BridgeId
           ACCESS      read-only
           STATUS      mandatory
           DESCRIPTION
             "."
           ::= { mstpXstEntry 3 }   
        
        
       mstpXstInternalRootCost     OBJECT-TYPE
           SYNTAX      Integer32
           ACCESS      read-only
           STATUS      mandatory
           DESCRIPTION
             "."
           ::= { mstpXstEntry 4 }

       mstpXstRootPort      OBJECT-TYPE
           SYNTAX      INTEGER 
           ACCESS      read-only
           STATUS      mandatory
           DESCRIPTION
           "."
           ::= { mstpXstEntry 5 }
       
       mstpXstTimeSinceTopologyChange  OBJECT-TYPE
           SYNTAX      TimeTicks
           ACCESS      read-only
           STATUS      mandatory
           DESCRIPTION
             "."
           ::= { mstpXstEntry 6 }

       mstpXstTopologyChangesCount     OBJECT-TYPE
           SYNTAX      Counter32
           ACCESS      read-only
           STATUS      mandatory
           DESCRIPTION
             "."
           ::= { mstpXstEntry 7 }  
-- MSTP Xst Port Table, Cist/Mst Port status/setting
       mstpXstPortTable    OBJECT-TYPE
           SYNTAX  SEQUENCE OF MstpXstPortEntry
           ACCESS  not-accessible
           STATUS  mandatory
           DESCRIPTION
             "."
           ::= { mstp 60 }
       
       mstpXstPortEntry    OBJECT-TYPE
           SYNTAX  MstpXstPortEntry
           ACCESS  not-accessible
           STATUS  mandatory
           DESCRIPTION
             "."
           REFERENCE
             "."
           INDEX  { mstpXstPortXstId, mstpXstPortIndex }
           ::= { mstpXstPortTable 1 }
       
        
        MstpXstPortEntry ::=
        SEQUENCE {
         	mstpXstPortXstId                 MstiOrCistInstanceIndex,
          	mstpXstPortIndex                 INTEGER,
          	mstpXstPortEnable                EnabledStatus, 
          	mstpXstPortPriority              Integer32,
          	mstpXstPortPathCost              INTEGER,   
          	mstpXstPortState				 INTEGER,
          	mstpXstPortDesignatedRoot        BridgeId,
          	mstpXstPortDesignatedCost        Integer32,
          	mstpXstPortDesignatedBridge      BridgeId,
          	mstpXstPortDesignatedPort        INTEGER
        }
        
        mstpXstPortXstId     OBJECT-TYPE
            SYNTAX      MstiOrCistInstanceIndex
            ACCESS      not-accessible
            STATUS      mandatory
            DESCRIPTION
              "0 means CIST."
            ::= { mstpXstPortEntry 1 }

        mstpXstPortIndex     OBJECT-TYPE
            SYNTAX      INTEGER(1..65535)
            ACCESS      read-only
            STATUS      mandatory
            DESCRIPTION
              "The value of mstpPortIndex of the Port
              in mstpPortTable."
            ::= { mstpXstPortEntry 2 }
        
        
        mstpXstPortEnable     OBJECT-TYPE
            SYNTAX      EnabledStatus
            ACCESS      read-write
            STATUS      mandatory
            DESCRIPTION
              "."
            ::= { mstpXstPortEntry 3 }
         
         mstpXstPortPriority              OBJECT-TYPE 
             SYNTAX      Integer32 (0..255)
             ACCESS      read-write
             STATUS      mandatory
             DESCRIPTION
               "Port priority, in steps of 16."
             DEFVAL       { 128 }
             ::= { mstpXstPortEntry 4 }
        
         mstpXstPortPathCost              OBJECT-TYPE 
             SYNTAX      INTEGER (1..65535)
             ACCESS      read-write
             STATUS      mandatory
             DESCRIPTION
               "."
             ::= { mstpXstPortEntry 5 }

         mstpXstPortState                 OBJECT-TYPE 
             SYNTAX      INTEGER {
               disabled(0),
               discarding(1),
               learning(2),
               forwarding(3),
               unknown(4)
             }
             ACCESS      read-only
             STATUS      mandatory
             DESCRIPTION
               "."
             ::= { mstpXstPortEntry 6 }
         
         mstpXstPortDesignatedRoot        OBJECT-TYPE 
              SYNTAX      BridgeId
              ACCESS      read-only
              STATUS      mandatory
              DESCRIPTION
              "."
              ::= { mstpXstPortEntry 7 }
         
         mstpXstPortDesignatedCost        OBJECT-TYPE
             SYNTAX      Integer32
             ACCESS      read-only
             STATUS      mandatory
             DESCRIPTION
             "."
             ::= { mstpXstPortEntry 8 }
         
         mstpXstPortDesignatedBridge      OBJECT-TYPE
             SYNTAX      BridgeId
             ACCESS      read-only
             STATUS      mandatory
             DESCRIPTION
             "."
             ::= { mstpXstPortEntry 9 }
        
         mstpXstPortDesignatedPort      OBJECT-TYPE
             SYNTAX      INTEGER
             ACCESS      read-only
             STATUS      mandatory
             DESCRIPTION
             "."
             ::= { mstpXstPortEntry 10 }  
--MSTP Traps 
 	     mstpNotifications     	OBJECT IDENTIFIER ::= { mstp 70 }              
	
	     newRoot NOTIFICATION-TYPE
         OBJECTS {
                mstpXstId
         }
         STATUS  current
         DESCRIPTION
          ""
         ::= { mstpNotifications 1 }
      
         topologyChange NOTIFICATION-TYPE
         OBJECTS {
                mstpXstId
         }
         STATUS  current
         DESCRIPTION
          ""
         ::= { mstpNotifications 2 }
       
--  radiusServerSetup
				radiusServerSetup     	OBJECT IDENTIFIER ::= { ves1616pe54 57 }

        radiusAuthServerSetup OBJECT IDENTIFIER ::= { radiusServerSetup 1 }
        
        radiusAuthServerMode OBJECT-TYPE
        SYNTAX  INTEGER{
        		index-priority(1),
						round-robin(2),
        }
        ACCESS  read-write
        STATUS  mandatory
        DESCRIPTION
                      	""
        ::= { radiusAuthServerSetup 1 }

        radiusAuthServerTimeout OBJECT-TYPE
        SYNTAX  INTEGER
        ACCESS  read-write
        STATUS  mandatory
        DESCRIPTION
                      	""
        ::= { radiusAuthServerSetup 2 }

-- radiusAuthServerTable
        radiusAuthServerTable OBJECT-TYPE
        SYNTAX	SEQUENCE OF RadiusAuthServerEntry
        ACCESS  not-accessible
        STATUS  mandatory
        DESCRIPTION
                 	""
        ::= { radiusAuthServerSetup 3 }
        
	radiusAuthServerEntry OBJECT-TYPE
        SYNTAX	RadiusAuthServerEntry
        ACCESS	not-accessible
        STATUS	mandatory
        DESCRIPTION    	"An entry in radiusAuthServerTable."
        INDEX          	{ radiusAuthServerIndex }
        ::= { radiusAuthServerTable 1 }

        RadiusAuthServerEntry ::=
           SEQUENCE {
        	radiusAuthServerIndex		INTEGER,
        	radiusAuthServerIpAddr		IpAddress,
        	radiusAuthServerUdpPort		INTEGER,
        	radiusAuthServerSharedSecret	DisplayString,
        	radiusAuthServerIpAddressType	InetAddressType,
        	radiusAuthServerIpAddress		InetAddress
           }

        radiusAuthServerIndex OBJECT-TYPE
        SYNTAX  INTEGER
        ACCESS  not-accessible
        STATUS  mandatory
        DESCRIPTION
                      	""
        ::= { radiusAuthServerEntry 1 }

        radiusAuthServerIpAddr OBJECT-TYPE
        SYNTAX  IpAddress
        ACCESS  read-write
        STATUS  mandatory
        DESCRIPTION
                     	"IPv4 only"
        ::= { radiusAuthServerEntry 2 }

        radiusAuthServerUdpPort OBJECT-TYPE
        SYNTAX  INTEGER
        ACCESS  read-write
        STATUS  mandatory
        DESCRIPTION
                     	""
        ::= { radiusAuthServerEntry 3 }

        radiusAuthServerSharedSecret OBJECT-TYPE
        SYNTAX  DisplayString
        ACCESS  read-write
        STATUS  mandatory
        DESCRIPTION
                     	""
        ::= { radiusAuthServerEntry 4 }

        radiusAuthServerIpAddressType OBJECT-TYPE
        SYNTAX  InetAddressType { ipv4(1), ipv6(2) }
        ACCESS  read-only
        STATUS  mandatory
        DESCRIPTION
                     	""
        ::= { radiusAuthServerEntry 5 }
        
        radiusAuthServerIpAddress OBJECT-TYPE
        SYNTAX  InetAddress
        ACCESS  read-write
        STATUS  mandatory
        DESCRIPTION
                     	""
        ::= { radiusAuthServerEntry 6 }
        
        radiusAcctServerSetup OBJECT IDENTIFIER ::= { radiusServerSetup 2 }
        
        radiusAcctServerTimeout OBJECT-TYPE
        SYNTAX  INTEGER
        ACCESS  read-write
        STATUS  mandatory
        DESCRIPTION
                      	""
        ::= { radiusAcctServerSetup 1 }

-- radiusAcctServerTable
        radiusAcctServerTable OBJECT-TYPE
        SYNTAX	SEQUENCE OF RadiusAcctServerEntry
        ACCESS  not-accessible
        STATUS  mandatory
        DESCRIPTION
                 	""
        ::= { radiusAcctServerSetup 2 }
        
	radiusAcctServerEntry OBJECT-TYPE
        SYNTAX	RadiusAcctServerEntry
        ACCESS	not-accessible
        STATUS	mandatory
        DESCRIPTION    	"An entry in radiusAcctServerTable."
        INDEX          	{ radiusAcctServerIndex }
        ::= { radiusAcctServerTable 1 }

        RadiusAcctServerEntry ::=
           SEQUENCE {
        	radiusAcctServerIndex		INTEGER,
        	radiusAcctServerIpAddr		IpAddress,
        	radiusAcctServerUdpPort		INTEGER,
        	radiusAcctServerSharedSecret	DisplayString,
        	radiusAcctServerIpAddressType	InetAddressType,
        	radiusAcctServerIpAddress		InetAddress
           }

        radiusAcctServerIndex OBJECT-TYPE
        SYNTAX  INTEGER
        ACCESS  not-accessible
        STATUS  mandatory
        DESCRIPTION
                      	""
        ::= { radiusAcctServerEntry 1 }

        radiusAcctServerIpAddr OBJECT-TYPE
        SYNTAX  IpAddress
        ACCESS  read-write
        STATUS  mandatory
        DESCRIPTION
                     	"IPv4 only"
        ::= { radiusAcctServerEntry 2 }

        radiusAcctServerUdpPort OBJECT-TYPE
        SYNTAX  INTEGER
        ACCESS  read-write
        STATUS  mandatory
        DESCRIPTION
                     	""
        ::= { radiusAcctServerEntry 3 }

        radiusAcctServerSharedSecret OBJECT-TYPE
        SYNTAX  DisplayString
        ACCESS  read-write
        STATUS  mandatory
        DESCRIPTION
                     	""
        ::= { radiusAcctServerEntry 4 }
        
        radiusAcctServerIpAddressType OBJECT-TYPE
        SYNTAX  InetAddressType { ipv4(1), ipv6(2) }
        ACCESS  read-only
        STATUS  mandatory
        DESCRIPTION
                     	""
        ::= { radiusAcctServerEntry 5 }
        
        radiusAcctServerIpAddress OBJECT-TYPE
        SYNTAX  InetAddress
        ACCESS  read-write
        STATUS  mandatory
        DESCRIPTION
                     	""
        ::= { radiusAcctServerEntry 6 }

--  tacacsServerSetup
	tacacsServerSetup     	OBJECT IDENTIFIER ::= { ves1616pe54 58 }

        tacacsAuthServerSetup OBJECT IDENTIFIER ::= { tacacsServerSetup 1 }
        
        tacacsAuthServerMode OBJECT-TYPE
        SYNTAX  INTEGER{
        		index-priority(1),
		round-robin(2)
        }
        ACCESS  read-write
        STATUS  mandatory
        DESCRIPTION
                      	""
        ::= { tacacsAuthServerSetup 1 }

        tacacsAuthServerTimeout OBJECT-TYPE
        SYNTAX  INTEGER
        ACCESS  read-write
        STATUS  mandatory
        DESCRIPTION
                      	""
        ::= { tacacsAuthServerSetup 2 }

-- tacacsAuthServerTable
        tacacsAuthServerTable OBJECT-TYPE
        SYNTAX	SEQUENCE OF TacacsAuthServerEntry
        ACCESS  not-accessible
        STATUS  mandatory
        DESCRIPTION
                 	""
        ::= { tacacsAuthServerSetup 3 }
        
	tacacsAuthServerEntry OBJECT-TYPE
        SYNTAX	TacacsAuthServerEntry
        ACCESS	not-accessible
        STATUS	mandatory
        DESCRIPTION    	"An entry in tacacsAuthServerTable."
        INDEX          	{ tacacsAuthServerIndex }
        ::= { tacacsAuthServerTable 1 }

        TacacsAuthServerEntry ::=
           SEQUENCE {
        	tacacsAuthServerIndex		INTEGER,
        	tacacsAuthServerIpAddr		IpAddress,
        	tacacsAuthServerTcpPort		INTEGER,
        	tacacsAuthServerSharedSecret	DisplayString,
        	tacacsAuthServerIpAddressType		InetAddressType,
        	tacacsAuthServerIpAddress	InetAddress
           }

        tacacsAuthServerIndex OBJECT-TYPE
        SYNTAX  INTEGER
        ACCESS  not-accessible
        STATUS  mandatory
        DESCRIPTION
                      	""
        ::= { tacacsAuthServerEntry 1 }

        tacacsAuthServerIpAddr OBJECT-TYPE
        SYNTAX  IpAddress
        ACCESS  read-write
        STATUS  mandatory
        DESCRIPTION
                     	"IPv4 only"
        ::= { tacacsAuthServerEntry 2 }

        tacacsAuthServerTcpPort OBJECT-TYPE
        SYNTAX  INTEGER
        ACCESS  read-write
        STATUS  mandatory
        DESCRIPTION
                     	""
        ::= { tacacsAuthServerEntry 3 }

        tacacsAuthServerSharedSecret OBJECT-TYPE
        SYNTAX  DisplayString
        ACCESS  read-write
        STATUS  mandatory
        DESCRIPTION
                     	""
        ::= { tacacsAuthServerEntry 4 }

        tacacsAuthServerIpAddressType OBJECT-TYPE
        SYNTAX  InetAddressType { ipv4(1), ipv6(2) }
        ACCESS  read-only
        STATUS  mandatory
        DESCRIPTION
                     	""
        ::= { tacacsAuthServerEntry 5 }
        
        tacacsAuthServerIpAddress OBJECT-TYPE
        SYNTAX  InetAddress
        ACCESS  read-write
        STATUS  mandatory
        DESCRIPTION
                     	""
        ::= { tacacsAuthServerEntry 6 }
        
        tacacsAcctServerSetup OBJECT IDENTIFIER ::= { tacacsServerSetup 2 }

        tacacsAcctServerTimeout OBJECT-TYPE
        SYNTAX  INTEGER
        ACCESS  read-write
        STATUS  mandatory
        DESCRIPTION
                      	""
        ::= { tacacsAcctServerSetup 1 }

-- tacacsAcctServerTable
        tacacsAcctServerTable OBJECT-TYPE
        SYNTAX	SEQUENCE OF TacacsAcctServerEntry
        ACCESS  not-accessible
        STATUS  mandatory
        DESCRIPTION
                 	""
        ::= { tacacsAcctServerSetup 2 }
        
	tacacsAcctServerEntry OBJECT-TYPE
        SYNTAX	TacacsAcctServerEntry
        ACCESS	not-accessible
        STATUS	mandatory
        DESCRIPTION    	"An entry in tacacsAcctServerTable."
        INDEX          	{ tacacsAcctServerIndex }
        ::= { tacacsAcctServerTable 1 }

        TacacsAcctServerEntry ::=
           SEQUENCE {
        	tacacsAcctServerIndex		INTEGER,
        	tacacsAcctServerIpAddr		IpAddress,
        	tacacsAcctServerTcpPort		INTEGER,
        	tacacsAcctServerSharedSecret	DisplayString,
        	tacacsAcctServerIpAddressType		InetAddressType,
        	tacacsAcctServerIpAddress	InetAddress
           }

        tacacsAcctServerIndex OBJECT-TYPE
        SYNTAX  INTEGER
        ACCESS  not-accessible
        STATUS  mandatory
        DESCRIPTION
                      	""
        ::= { tacacsAcctServerEntry 1 }

        tacacsAcctServerIpAddr OBJECT-TYPE
        SYNTAX  IpAddress
        ACCESS  read-write
        STATUS  mandatory
        DESCRIPTION
                     	"IPv4 only"
        ::= { tacacsAcctServerEntry 2 }

        tacacsAcctServerTcpPort OBJECT-TYPE
        SYNTAX  INTEGER
        ACCESS  read-write
        STATUS  mandatory
        DESCRIPTION
                     	""
        ::= { tacacsAcctServerEntry 3 }

        tacacsAcctServerSharedSecret OBJECT-TYPE
        SYNTAX  DisplayString
        ACCESS  read-write
        STATUS  mandatory
        DESCRIPTION
                     	""
        ::= { tacacsAcctServerEntry 4 }
        
        tacacsAcctServerIpAddressType OBJECT-TYPE
        SYNTAX  InetAddressType { ipv4(1), ipv6(2) }
        ACCESS  read-only
        STATUS  mandatory
        DESCRIPTION
                     	""
        ::= { tacacsAcctServerEntry 5 }
        
        tacacsAcctServerIpAddress OBJECT-TYPE
        SYNTAX  InetAddress
        ACCESS  read-write
        STATUS  mandatory
        DESCRIPTION
                     	""
        ::= { tacacsAcctServerEntry 6 }

--  aaaSetup
	aaaSetup     	OBJECT IDENTIFIER ::= { ves1616pe54 59 }

        authenticationSetup OBJECT IDENTIFIER ::= { aaaSetup 1 }

-- authenticationTypeTable
        authenticationTypeTable OBJECT-TYPE
        SYNTAX	SEQUENCE OF AuthenticationTypeEntry
        ACCESS  not-accessible
        STATUS  mandatory
        DESCRIPTION
                 	""
        ::= { authenticationSetup 1 }
        
	authenticationTypeEntry OBJECT-TYPE
        SYNTAX	AuthenticationTypeEntry
        ACCESS	not-accessible
        STATUS	mandatory
        DESCRIPTION    	"An entry in authenticationTypeTable."
        INDEX          	{ authenticationTypeName }
        ::= { authenticationTypeTable 1 }

        AuthenticationTypeEntry ::=
           SEQUENCE {
        	authenticationTypeName	DisplayString,
        	authenticationTypeMethodList	OCTET STRING
           }

        authenticationTypeName OBJECT-TYPE
        SYNTAX  DisplayString
        ACCESS  read-only
        STATUS  mandatory
        DESCRIPTION
                      	""
        ::= { authenticationTypeEntry 1 }

        authenticationTypeMethodList OBJECT-TYPE
        SYNTAX  OCTET STRING
        ACCESS  read-write
        STATUS  mandatory
        DESCRIPTION
                     	"Enable-local: 1, Login-local: 2, radius: 3, tacacs+: 4"
        ::= { authenticationTypeEntry 2 }

--  VDSL2Extensions

	vdsl2Ext            OBJECT IDENTIFIER ::= { ves1616pe54 60 }
	------------------------------------------------      
	xdsl2ExtNotifications OBJECT IDENTIFIER ::= { vdsl2Ext 0 }
	xdsl2ExtLine          OBJECT IDENTIFIER ::= { vdsl2Ext 1 }
	xdsl2ExtStatus        OBJECT IDENTIFIER ::= { vdsl2Ext 2 }
	--xdsl2ExtInventory     OBJECT IDENTIFIER ::= { vdsl2Ext 3 }
	xdsl2ExtPM            OBJECT IDENTIFIER ::= { vdsl2Ext 4 }
	xdsl2ExtProfile       OBJECT IDENTIFIER ::= { vdsl2Ext 5 }
	--xdsl2ExtScalar        OBJECT IDENTIFIER ::= { vdsl2Ext 6 }
	--xdsl2ExtConformance   OBJECT IDENTIFIER ::= { vdsl2Ext 7 }
	------------------------------------------------
	xdsl2ExtPMLine      OBJECT IDENTIFIER ::= { xdsl2ExtPM 1 }
	xdsl2ExtPMChannel   OBJECT IDENTIFIER ::= { xdsl2ExtPM 2 }
	------------------------------------------------
	xdsl2ExtProfileLine      OBJECT IDENTIFIER ::= { xdsl2ExtProfile 1 }
	xdsl2ExtProfileChannel   OBJECT IDENTIFIER ::= { xdsl2ExtProfile 2 }
	xdsl2ExtProfileAlarmConf OBJECT IDENTIFIER ::= { xdsl2ExtProfile 3 }
	------------------------------------------------
	--xdsl2ExtScalarSC         OBJECT IDENTIFIER ::= { xdsl2Scalar 1 }
	------------------------------------------------


------------------------------------------------
--          xdsl2ExtLineTable                    --
------------------------------------------------
    xdsl2ExtLineTable  OBJECT-TYPE
    SYNTAX      SEQUENCE  OF  Xdsl2ExtLineEntry
    MAX-ACCESS  not-accessible
    STATUS      current
    DESCRIPTION
       "The table xdsl2ExtLineTable extends xdsl2LineTable for ZyXEL product."
    ::= { xdsl2ExtLine 1 }

    xdsl2ExtLineEntry  OBJECT-TYPE
    SYNTAX      Xdsl2ExtLineEntry
    MAX-ACCESS  not-accessible
    STATUS      current
    DESCRIPTION
       "The table xdsl2ExtLineTable contains extra functions besides those in
        xdsl2LineTable."
    INDEX  { ifIndex }
    ::= { xdsl2ExtLineTable 1 }    

    Xdsl2ExtLineEntry  ::=
    SEQUENCE {
       xdsl2LineCmndConfSelt            Xdsl2LineLdsf
    }
   
    xdsl2LineCmndConfSelt  OBJECT-TYPE
    SYNTAX      Xdsl2LineLdsf
    MAX-ACCESS  read-write
    STATUS      current
    DESCRIPTION
       "Trigger a SELT(Single End Loop Test) for the line. Note the loop
        should be open."
    DEFVAL       { inhibit }
    ::= { xdsl2ExtLineEntry 1 } 

------------------------------------------------
--          xdsl2ExtLineBandTable                --
------------------------------------------------
    xdsl2ExtLineBandTable  OBJECT-TYPE
    SYNTAX      SEQUENCE  OF  Xdsl2ExtLineBandEntry
    MAX-ACCESS  not-accessible
    STATUS      current
    DESCRIPTION
       "The table xdsl2ExtLineBandTable extends xdsl2LineBandTable for 
        ZyXEL product."
    ::= { xdsl2ExtLine 2 }

    xdsl2ExtLineBandEntry  OBJECT-TYPE
    SYNTAX      Xdsl2ExtLineBandEntry
    MAX-ACCESS  not-accessible
    STATUS      current
    DESCRIPTION
       "The table xdsl2ExtLineBandTable contains extra per-band line 
        status parameters besides those in xdsl2LineBandTable."
    INDEX  { ifIndex, xdsl2LineBand }
    ::= { xdsl2ExtLineBandTable 1 }
    
    Xdsl2ExtLineBandEntry  ::=
    SEQUENCE {
       xdsl2LineBandStatusActAtp           Integer32,
       xdsl2LineBandStatusActRxPwr         Integer32
    }
    
    xdsl2LineBandStatusActAtp  OBJECT-TYPE
    SYNTAX      Integer32 (-310..310 | 2147483647)
    UNITS       "0.1 dBm"
    MAX-ACCESS  read-only
    STATUS      current
    DESCRIPTION
       "Actual Aggregate Transmit Power per band.
        A value of 0x7FFFFFFF (2147483647) indicates the measurement is
        out of range to be represented."
    DEFVAL       { 2147483646 }
    ::= { xdsl2ExtLineBandEntry 1 } 
        
    xdsl2LineBandStatusActRxPwr  OBJECT-TYPE
    SYNTAX      Integer32 (-255..255 | 2147483647)
    UNITS       "0.1 dBm"
    MAX-ACCESS  read-only
    STATUS      current
    DESCRIPTION
       "Actual Aggregate Receive Power per band.
        A value of 0x7FFFFFFF (2147483647) indicates the measurement is
        out of range to be represented."
    DEFVAL       { 2147483646 }
    ::= { xdsl2ExtLineBandEntry 2 }

------------------------------------------------
--          xdsl2ExtLineSegmentTable             --
------------------------------------------------
    xdsl2ExtLineSegmentTable  OBJECT-TYPE
    SYNTAX      SEQUENCE  OF  Xdsl2ExtLineSegmentEntry
    MAX-ACCESS  not-accessible
    STATUS      current
    DESCRIPTION
       "The table xdsl2ExtLineSegmentTable extends xdsl2LineSegmentTable for 
         ZyXEL product."
    ::= { xdsl2ExtStatus 1 }

    xdsl2ExtLineSegmentEntry  OBJECT-TYPE
    SYNTAX      Xdsl2ExtLineSegmentEntry
    MAX-ACCESS  not-accessible
    STATUS      current
    DESCRIPTION
       "The table xdsl2LineExtSegmentEntry contains extra line segment 
         status parameters besides those in xdsl2LineSegmentTable.

        This table stores HLOG/QLN/SNR measured during initialization."
    INDEX  { ifIndex,
             xdsl2LineSegmentDirection,
             xdsl2LineSegment   }
    ::= { xdsl2ExtLineSegmentTable 1 }
   
    Xdsl2ExtLineSegmentEntry  ::=
    SEQUENCE {
       xdsl2LineSegmentLog         OCTET STRING,
       xdsl2LineSegmentQln         OCTET STRING,
       xdsl2LineSegmentSnr         OCTET STRING,
       xdsl2LineSegmentStatus      BITS,
       xdsl2LineSegmentLogScGroupSize    Unsigned32,
       xdsl2LineSegmentQlnScGroupSize    Unsigned32,
       xdsl2LineSegmentSnrScGroupSize    Unsigned32
    }
    
    xdsl2LineSegmentLog  OBJECT-TYPE
    SYNTAX      OCTET STRING  (SIZE(0..1024))
    UNITS       "dB"
    MAX-ACCESS  read-only
    STATUS      current
    DESCRIPTION
     "This parameter is applicable in initialization and use the same
      format as xdsl2SCStatusSegmentLog."
     ::= { xdsl2ExtLineSegmentEntry 1 }

    xdsl2LineSegmentQln  OBJECT-TYPE
    SYNTAX      OCTET STRING  (SIZE(0..512))
    UNITS       "dBm/Hz"
    MAX-ACCESS  read-only
    STATUS      current
    DESCRIPTION
     "This parameter is applicable in initialization and use the same
      format as xdsl2SCStatusSegmentQln."
     ::= { xdsl2ExtLineSegmentEntry 2 }

    xdsl2LineSegmentSnr  OBJECT-TYPE
    SYNTAX      OCTET STRING  (SIZE(0..512))
    UNITS       "0.5 dB"
    MAX-ACCESS  read-only
    STATUS      current
    DESCRIPTION
     "This parameter is applicable in initialization and use the same
      format as xdsl2SCStatusSegmentSnr."
    ::= { xdsl2ExtLineSegmentEntry 3 }
    
    xdsl2LineSegmentStatus  OBJECT-TYPE
    SYNTAX      BITS {
                  hlogReady(0),
                  qlnReady(1),
                  snrReady(2)
               }
    MAX-ACCESS  read-only
    STATUS      current
    DESCRIPTION
     "This parameter indicates whether the Hlog/Qln/Snr data is ready."
    ::= { xdsl2ExtLineSegmentEntry 4 }

    xdsl2LineSegmentLogScGroupSize OBJECT-TYPE
    SYNTAX      Unsigned32(1 | 2 | 4 | 8)
    MAX-ACCESS  read-only
    STATUS      current
    DESCRIPTION
     "Number of subcarriers per group used to report the H(f)
      logarithmic representation values for the respective
      transmission direction. The valid values are 1, 2, 4 and 8.
      For ADSL, this parameter is equal to one and, for VDSL2, it is
      equal to the size of a subcarrier group used to compute these
      parameters."
    REFERENCE  "ITU-T G.997.1, paragraph #7.5.1.26.5 (HLOGGds)
               and paragraph #7.5.1.26.11 (HLOGGus)"
    ::= { xdsl2ExtLineSegmentEntry 5 }

    xdsl2LineSegmentQlnScGroupSize OBJECT-TYPE
    SYNTAX      Unsigned32(1 | 2 | 4 | 8)
    MAX-ACCESS  read-only
    STATUS      current
    DESCRIPTION
     "Number of subcarriers per group used to report the Quiet
     Line Noise values for the respective transmission direction.
     The valid values are 1, 2, 4 and 8.
     For ADSL, this parameter is equal to one and, for VDSL2, it is
     equal to the size of a subcarrier group used to compute these
     parameters."
    REFERENCE  "ITU-T G.997.1, paragraph #7.5.1.27.2 (QLNGds)
               and paragraph #7.5.1.27.5 (QLNGus)"
    ::= { xdsl2ExtLineSegmentEntry 6 } 
    
    xdsl2LineSegmentSnrScGroupSize OBJECT-TYPE
    SYNTAX      Unsigned32(1 | 2 | 4 | 8)
    MAX-ACCESS  read-only
    STATUS      current
    DESCRIPTION
     "Number of subcarriers per group used to report the SNR values
      on the respective transmission direction.
      The valid values are 1, 2, 4 and 8.
      For ADSL, this parameter is equal to one and, for VDSL2, it is
      equal to the size of a subcarrier group used to compute these
      parameters."
    REFERENCE  "ITU-T G.997.1, paragraph #7.5.1.28.2 (SNRGds)
               and paragraph #7.5.1.28.5 (SNRGus)"
    ::= { xdsl2ExtLineSegmentEntry 7 }


------------------------------------------------
--        xdsl2ExtSCStatusTable                  --
------------------------------------------------

    xdsl2ExtSCStatusTable  OBJECT-TYPE
    SYNTAX      SEQUENCE  OF  Xdsl2ExtSCStatusEntry
    MAX-ACCESS  not-accessible
    STATUS      current
    DESCRIPTION
       "The table xdsl2ExtSCStatusTable extends xdsl2SCStatusTable for 
         ZyXEL product."
    ::= { xdsl2ExtStatus 3 }

    xdsl2ExtSCStatusEntry  OBJECT-TYPE
    SYNTAX      Xdsl2ExtSCStatusEntry
    MAX-ACCESS  not-accessible
    STATUS      current
    DESCRIPTION
       "The table xdsl2ExtSCStatusTable contains extra subcarrier  
        status parameters besides those in xdsl2LineSegmentTable."
    INDEX  { ifIndex, xdsl2SCStatusDirection }
    ::= { xdsl2ExtSCStatusTable 1 }

    Xdsl2ExtSCStatusEntry  ::=
    SEQUENCE {
       xdsl2SCStatusActAtp    Integer32
    }
    
    xdsl2SCStatusActAtp  OBJECT-TYPE
    SYNTAX      Integer32 (-310..310 | 2147483647)
    UNITS       "0.1 dBm"
    MAX-ACCESS  read-only
    STATUS      current
    DESCRIPTION
       "Actual Aggregate Transmit Power Downstream. 
        The total amount of transmit power delivered by the xTU-C at
        the U-C reference point, at the instant of measurement.  It
        ranges from -310 to 310 units of 0.1 dBm (Physical values are -31
        to 31 dBm).
        A value of 0x7FFFFFFF (2147483647) indicates the measurement is
        out of range to be represented.
        This object reflects the value of the parameter following the
        most recent DELT performed on the associated line.  Once the DELT
        process is over, the parameter no longer changes until the row is
        deleted or a new DELT process is initiated.
        "
    DEFVAL       { 2147483647 }
    ::= { xdsl2ExtSCStatusEntry 1 }    
    
------------------------------------------------
--        xdsl2ExtSCStatusBandTable              --
------------------------------------------------

    xdsl2ExtSCStatusBandTable  OBJECT-TYPE
    SYNTAX      SEQUENCE  OF  Xdsl2ExtSCStatusBandEntry
    MAX-ACCESS  not-accessible
    STATUS      current
    DESCRIPTION
       "The table xdsl2ExtSCStatusBandTable extends xdsl2SCStatusBandTable for 
         ZyXEL product."
    ::= { xdsl2ExtStatus 4 }

    xdsl2ExtSCStatusBandEntry  OBJECT-TYPE
    SYNTAX      Xdsl2ExtSCStatusBandEntry
    MAX-ACCESS  not-accessible
    STATUS      current
    DESCRIPTION
       "The table xdsl2ExtSCStatusBandTable contains extra subcarrier  
        status parameters that are grouped per-band besides those in 
        xdsl2SCStatusBandTable."
    INDEX  { ifIndex, xdsl2SCStatusBand }
    ::= { xdsl2ExtSCStatusBandTable 1 }

    Xdsl2ExtSCStatusBandEntry  ::=
    SEQUENCE {
       xdsl2SCStatusBandSnrMargin          Integer32
    }    

    xdsl2SCStatusBandSnrMargin  OBJECT-TYPE
    SYNTAX      Integer32 (-640..630 | 2147483646 | 2147483647)
    UNITS       "0.1 dB"
    MAX-ACCESS  read-only
    STATUS      current
    DESCRIPTION
       "SNR Margin is the maximum increase in dB of the noise power
        received at the xTU (xTU-R for a band in the downstream direction
        and xTU-C for a band in the upstream direction), such that the
        BER requirements are met for all bearer channels received at the
        xTU. Values range from -640 to 630 in units of 0.1 dB (Physical
        values are -64 to 63 dB).
        A special value of 0x7FFFFFFF (2147483647) indicates the SNR
        Margin is out of range to be represented.
        A special value of 0x7FFFFFFE (2147483646) indicates the SNR
        Margin measurement is currently unavailable.
        This object reflects the value of the parameter following the
        most recent DELT performed on the associated line.  Once the DELT
        process is over, the parameter no longer changes until the row is
        deleted or a new DELT process is initiated."
    DEFVAL       { 2147483646 }
    ::= { xdsl2ExtSCStatusBandEntry 1 }


------------------------------------------------
--        xdsl2ExtSeltStatusTable             --
------------------------------------------------

    xdsl2ExtSeltStatusTable  OBJECT-TYPE
    SYNTAX      SEQUENCE  OF  Xdsl2ExtSeltStatusEntry
    MAX-ACCESS  not-accessible
    STATUS      current
    DESCRIPTION
       "The table xdsl2ExtSeltStatusTable contains SELT status."
    ::= { xdsl2ExtStatus 6 }

    xdsl2ExtSeltStatusEntry  OBJECT-TYPE
    SYNTAX      Xdsl2ExtSeltStatusEntry
    MAX-ACCESS  not-accessible
    STATUS      current
    DESCRIPTION
       "The table xdsl2ExtSeltStatusEntry contains SELT status."
    INDEX  { ifIndex }
    ::= { xdsl2ExtSeltStatusTable 1 }

    Xdsl2ExtSeltStatusEntry  ::=
    SEQUENCE {
       xdsl2SeltStatus		Integer32,
       xdsl2SeltStatusLineType	DisplayString, 
       xdsl2SeltStatusLineLength	Integer32
    }    

    xdsl2SeltStatus  OBJECT-TYPE
    SYNTAX  Integer32 {
	idle(0),
	inProgress(1),
	failed(2),
	done(3)
	}
    MAX-ACCESS  read-only
    STATUS      current
    DESCRIPTION
    " "
    ::= { xdsl2ExtSeltStatusEntry 1 }

    xdsl2SeltStatusLineType  OBJECT-TYPE
    SYNTAX  DisplayString
    MAX-ACCESS  read-only
    STATUS      current
    DESCRIPTION
    " "
    ::= { xdsl2ExtSeltStatusEntry 2 }
	
    xdsl2SeltStatusLineLength  OBJECT-TYPE
    SYNTAX  Integer32
    MAX-ACCESS  read-only
    STATUS      current
    DESCRIPTION
    " "
    ::= { xdsl2ExtSeltStatusEntry 3 }
    
    xdsl2ExtSeltReflectionStatusTable  OBJECT-TYPE
    SYNTAX      SEQUENCE  OF  Xdsl2ExtSeltReflectionStatusEntry
    MAX-ACCESS  not-accessible
    STATUS      current
    DESCRIPTION
       "The table xdsl2ExtSeltReflectionStatusTable contains SELT status 
        for each reflection."
    ::= { xdsl2ExtStatus 7 }

    xdsl2ExtSeltReflectionStatusEntry  OBJECT-TYPE
    SYNTAX      Xdsl2ExtSeltReflectionStatusEntry
    MAX-ACCESS  not-accessible
    STATUS      current
    DESCRIPTION
       "The table xdsl2ExtSeltReflectionStatusTable contains SELT status 
        for each reflection."
    INDEX  { ifIndex, xdsl2SeltReflection }
    ::= { xdsl2ExtSeltReflectionStatusTable 1 }

    Xdsl2ExtSeltReflectionStatusEntry  ::=
    SEQUENCE {
      xdsl2SeltReflection		Unsigned32,
      xdsl2SeltDelay		Integer32,
      xdsl2SeltError		Integer32,
      xdsl2SeltAtn180kHz		Integer32,
      xdsl2SeltAtn300kHz		Integer32,
      xdsl2SeltFitError		Integer32, 
      xdsl2SeltFitTermination	Integer32
    }

    xdsl2SeltReflection OBJECT-TYPE
     SYNTAX      Unsigned32
     MAX-ACCESS  not-accessible
     STATUS      current
     DESCRIPTION
     ""
     ::= { xdsl2ExtSeltReflectionStatusEntry 1 }

    xdsl2SeltDelay  OBJECT-TYPE
    SYNTAX      Integer32
    UNITS       "0.1"
    MAX-ACCESS  read-only
    STATUS      current
    DESCRIPTION
    " "
    ::= { xdsl2ExtSeltReflectionStatusEntry 2 }

    xdsl2SeltError  OBJECT-TYPE
    SYNTAX      Integer32
    UNITS       "0.1"
    MAX-ACCESS  read-only
    STATUS      current
    DESCRIPTION
    " "
    ::= { xdsl2ExtSeltReflectionStatusEntry 3 }

    xdsl2SeltAtn180kHz  OBJECT-TYPE
    SYNTAX      Integer32
    UNITS       "0.1"
    MAX-ACCESS  read-only
    STATUS      current
    DESCRIPTION
    " "
    ::= { xdsl2ExtSeltReflectionStatusEntry 4 }

    xdsl2SeltAtn300kHz  OBJECT-TYPE
    SYNTAX      Integer32
    UNITS       "0.1"
    MAX-ACCESS  read-only
    STATUS      current
    DESCRIPTION
    " "
    ::= { xdsl2ExtSeltReflectionStatusEntry 5 }
   
    xdsl2SeltFitError  OBJECT-TYPE
    SYNTAX      Integer32
    UNITS       "0.1"
    MAX-ACCESS  read-only
    STATUS      current
    DESCRIPTION
    " "
    ::= { xdsl2ExtSeltReflectionStatusEntry 6 }

    xdsl2SeltFitTermination  OBJECT-TYPE
    SYNTAX      Integer32
    UNITS       "0.2"
    MAX-ACCESS  read-only
    STATUS      current
    DESCRIPTION
    " "
    ::= { xdsl2ExtSeltReflectionStatusEntry 7 }
    
------------------------------------------------
--      Extended PM line current counters     --
------------------------------------------------
    xdsl2ExtPMLineCurrTable  OBJECT-TYPE
    SYNTAX      SEQUENCE  OF  Xdsl2ExtPMLineCurrEntry
    MAX-ACCESS  not-accessible
    STATUS      current
    DESCRIPTION
       "The table xdsl2ExtPMLineCurrTable extends xdsl2PMLineCurrTable."
    ::= { xdsl2ExtPMLine 1 }

    xdsl2ExtPMLineCurrEntry  OBJECT-TYPE
    SYNTAX      Xdsl2ExtPMLineCurrEntry
    MAX-ACCESS  not-accessible
    STATUS      current
    DESCRIPTION
       "The table xdsl2ExtPMLineCurrTable extends xdsl2PMLineCurrTable."
    INDEX  { ifIndex, xdsl2PMLCurrUnit }
    ::= { xdsl2ExtPMLineCurrTable 1 }

    Xdsl2ExtPMLineCurrEntry  ::=
    SEQUENCE {
       xdsl2PMLSinceLinkFecs   Counter32,
       xdsl2PMLSinceLinkEs     Counter32,
       xdsl2PMLSinceLinkSes    Counter32,
       xdsl2PMLSinceLinkLoss   Counter32,
       xdsl2PMLSinceLinkUas    Counter32,
       xdsl2PMLSinceLinkLofs   Counter32,
       xdsl2PMLSinceLinkLol    Counter32,
       xdsl2PMLSinceLinkLols   Counter32,
       xdsl2PMLSinceLinkLpr    Counter32,
       xdsl2PMLSinceLinkLprs   Counter32,
       xdsl2PMLCurr15MLofs     Counter32,
       xdsl2PMLCurr15MLol      Counter32,
       xdsl2PMLCurr15MLols     Counter32,
       xdsl2PMLCurr15MLpr      Counter32,
       xdsl2PMLCurr15MLprs     Counter32,
       xdsl2PMLCurr1DayLofs    Counter32,
       xdsl2PMLCurr1DayLol     Counter32,
       xdsl2PMLCurr1DayLols    Counter32,
       xdsl2PMLCurr1DayLpr     Counter32,
       xdsl2PMLCurr1DayLprs    Counter32,
       xdsl2PMLSinceLinkInmEqInp	Counter32,
       xdsl2PMLSinceLinkInmIAT		Counter32,
       xdsl2PMLSinceLinkInmME		Counter32,
       xdsl2PMLCurr15MInmEqInp		Counter32,
       xdsl2PMLCurr15MInmIAT		Counter32,
       xdsl2PMLCurr15MInmME			Counter32,
       xdsl2PMLCurr1DayInmEqInp		Counter32,
       xdsl2PMLCurr1DayInmIAT		Counter32,
       xdsl2PMLCurr1DayInmME		Counter32
    }

    xdsl2PMLSinceLinkFecs  OBJECT-TYPE
    SYNTAX      Counter32
    UNITS       "seconds"
    MAX-ACCESS  read-only
    STATUS      current
    DESCRIPTION
       "Count of seconds since last link up that there was at
        least one FEC correction event for one or more bearer channels in
        this line.  This parameter is inhibited during UAS or SES."
    ::= { xdsl2ExtPMLineCurrEntry 1 }

    xdsl2PMLSinceLinkEs  OBJECT-TYPE
    SYNTAX      Counter32
    UNITS       "seconds"
    MAX-ACCESS  read-only
    STATUS      current
    DESCRIPTION
      "Count of seconds since last link up that there was:
          xTU-C: CRC-8 >= 1 for one or more bearer channels OR
                 LOS >= 1 OR SEF >=1 OR LPR >= 1
          xTU-R: FEBE >= 1 for one or more bearer channels OR
                 LOS-FE >=1 OR RDI >=1 OR LPR-FE >=1 .
       This parameter is inhibited during UAS."
    ::= { xdsl2ExtPMLineCurrEntry 2 }

    xdsl2PMLSinceLinkSes  OBJECT-TYPE
    SYNTAX      Counter32
    UNITS       "seconds"
    MAX-ACCESS  read-only
    STATUS      current
    DESCRIPTION
      "Count of seconds since last link up that that there was:
          xTU-C: (CRC-8 anomalies in one or more of the
                 received bearer channels) >= 18 OR LOS >= 1
                 OR SEF >= 1 OR LPR >= 1
          xTU-R: (FEBE anomalies in one or more of the
                 received bearer channels) >= 18 OR LOS-FE >= 1
                 OR RDI >= 1 OR LPR-FE >= 1 .
       This parameter is inhibited during UAS."
    ::= { xdsl2ExtPMLineCurrEntry 3 }

    xdsl2PMLSinceLinkLoss  OBJECT-TYPE
    SYNTAX      Counter32
    UNITS       "seconds"
    MAX-ACCESS  read-only
    STATUS      current
    DESCRIPTION
      "Count of seconds since last link up that there was LOS (or
       LOS-FE for xTU-R)."
    ::= { xdsl2ExtPMLineCurrEntry 4 }

    xdsl2PMLSinceLinkUas  OBJECT-TYPE
    SYNTAX      Counter32
    UNITS       "seconds"
    MAX-ACCESS  read-only
    STATUS      current
    DESCRIPTION
      "Count of seconds in Unavailability State since last line up.
       Unavailability begins at the onset of 10 contiguous
       severely-errored seconds, and ends at the onset of 10 contiguous
       seconds with no severely-errored seconds."
    ::= { xdsl2ExtPMLineCurrEntry 5 }

    xdsl2PMLSinceLinkLofs  OBJECT-TYPE
    SYNTAX      Counter32
    UNITS       "seconds"
    MAX-ACCESS  read-only
    STATUS      current
    DESCRIPTION
      "Count of seconds since last link up that there was LOF."
    ::= { xdsl2ExtPMLineCurrEntry 6 }

    xdsl2PMLSinceLinkLol  OBJECT-TYPE
    SYNTAX      Counter32
    MAX-ACCESS  read-only
    STATUS      current
    DESCRIPTION
      "Count of times the line loss of link since last link up."
    ::= { xdsl2ExtPMLineCurrEntry 7 }

    xdsl2PMLSinceLinkLols  OBJECT-TYPE
    SYNTAX      Counter32
    UNITS       "seconds"
    MAX-ACCESS  read-only
    STATUS      current
    DESCRIPTION
      "Count of seconds since last link up that there 
       was Loss of Link ."
    ::= { xdsl2ExtPMLineCurrEntry 8 }

    xdsl2PMLSinceLinkLpr  OBJECT-TYPE
    SYNTAX      Counter32
    MAX-ACCESS  read-only
    STATUS      current
    DESCRIPTION
      "Count of the line loss of power since last link up."
    ::= { xdsl2ExtPMLineCurrEntry 9 }

    xdsl2PMLSinceLinkLprs  OBJECT-TYPE
    SYNTAX      Counter32
    UNITS       "seconds"
    MAX-ACCESS  read-only
    STATUS      current
    DESCRIPTION
      "Count of seconds since last link up that there 
       was Loss of Power ."
    ::= { xdsl2ExtPMLineCurrEntry 10 }

    xdsl2PMLCurr15MLofs  OBJECT-TYPE
    SYNTAX      Counter32
    UNITS       "seconds"
    MAX-ACCESS  read-only
    STATUS      current
    DESCRIPTION
       "Count of seconds during this interval that there was LOF."
    ::= { xdsl2ExtPMLineCurrEntry 11 }

    xdsl2PMLCurr15MLol  OBJECT-TYPE
    SYNTAX      Counter32
    UNITS       "seconds"
    MAX-ACCESS  read-only
    STATUS      current
    DESCRIPTION
       "Count of times during this interval that the line Loss of Link."
    ::= { xdsl2ExtPMLineCurrEntry 12 }

    xdsl2PMLCurr15MLols  OBJECT-TYPE
    SYNTAX      Counter32
    UNITS       "seconds"
    MAX-ACCESS  read-only
    STATUS      current
    DESCRIPTION
       "Count of seconds during this interval that there was Loss of Link."
    ::= { xdsl2ExtPMLineCurrEntry 13 }

    xdsl2PMLCurr15MLpr  OBJECT-TYPE
    SYNTAX      Counter32
    UNITS       "seconds"
    MAX-ACCESS  read-only
    STATUS      current
    DESCRIPTION
       "Count of times during this interval that the line Loss of Power."
    ::= { xdsl2ExtPMLineCurrEntry 14 }

    xdsl2PMLCurr15MLprs  OBJECT-TYPE
    SYNTAX      Counter32
    UNITS       "seconds"
    MAX-ACCESS  read-only
    STATUS      current
    DESCRIPTION
       "Count of seconds during this interval that there was Loss of Power."
    ::= { xdsl2ExtPMLineCurrEntry 15 }

    xdsl2PMLCurr1DayLofs  OBJECT-TYPE
    SYNTAX      Counter32
    UNITS       "seconds"
    MAX-ACCESS  read-only
    STATUS      current
    DESCRIPTION
       "Count of seconds during this interval that there was LOF."
    ::= { xdsl2ExtPMLineCurrEntry 16 }

    xdsl2PMLCurr1DayLol  OBJECT-TYPE
    SYNTAX      Counter32
    MAX-ACCESS  read-only
    STATUS      current
    DESCRIPTION
       "Count of times during this interval that the line Loss of Link."
    ::= { xdsl2ExtPMLineCurrEntry 17 }

    xdsl2PMLCurr1DayLols  OBJECT-TYPE
    SYNTAX      Counter32
    UNITS       "seconds"
    MAX-ACCESS  read-only
    STATUS      current
    DESCRIPTION
       "Count of seconds during this interval that there was Loss of Link."
    ::= { xdsl2ExtPMLineCurrEntry 18 }

    xdsl2PMLCurr1DayLpr  OBJECT-TYPE
    SYNTAX      Counter32
    MAX-ACCESS  read-only
    STATUS      current
    DESCRIPTION
       "Count of times during this interval that the line Loss of Power."
    ::= { xdsl2ExtPMLineCurrEntry 19 }

    xdsl2PMLCurr1DayLprs  OBJECT-TYPE
    SYNTAX      Counter32
    UNITS       "seconds"
    MAX-ACCESS  read-only
    STATUS      current
    DESCRIPTION
       "Count of seconds during this interval that there was Loss of Power."
    ::= { xdsl2ExtPMLineCurrEntry 20 }
    
    
    xdsl2PMLSinceLinkInmEqInp  OBJECT-TYPE
    SYNTAX      Counter32
    MAX-ACCESS  read-only
    STATUS      current
    DESCRIPTION
       "The INM Equivalent Inp histogram since last link up. An 
    array of 68 octets (each 4 octets means amount of a bin of 
    histogram), designed for supporting from 1 to 17 bins of 
    the histogram. 
       The particular index of the bin incremented by an impulse
    noise event is equal to the computed value of equivalent INP,
    except the 17th of anomaly INPEQ, which logs all equivalent 
    INPs greater than 16.
       Each bin has a value in the range 0x0 to 0xFFFFFFFF"
    REFERENCE    "ITU-T G.993.2 Amd2, paragraph 11.4.2.2.1 (INM 
    			 procedure)"
    ::= { xdsl2ExtPMLineCurrEntry 21 }    
    
    xdsl2PMLSinceLinkInmIAT  OBJECT-TYPE
    SYNTAX      Counter32
    MAX-ACCESS  read-only
    STATUS      current
    DESCRIPTION
       "The INM Inter Arrival Time histogram since last link up. 
    An array of 32 octets (each 4 octets means amount of a bin 
    of histogram), designed for supporting from 0 to 7 bins of 
    the histogram. 
       The index of the particular bin incremented by an complete 
    impulse noise event is determained from the following 
    INMControl parameters.
       Each bin has a value in the range 0x0 to 0xFFFFFFFF"
    REFERENCE    "ITU-T G.993.2 Amd2, paragraph 11.4.2.2.1 (INM 
    			 procedure)"   
    ::= { xdsl2ExtPMLineCurrEntry 22 }    
    
    xdsl2PMLSinceLinkInmME  OBJECT-TYPE
    SYNTAX      Counter32
    UNITS       "symbols"
    MAX-ACCESS  read-only
    STATUS      current
    DESCRIPTION
       "The INM total measurement since last link up. This 
    indication occurs every time a data symbol is processed by 
    the Impulse Noise Sensor.
       The range of the value is from 0x0 to 0xFFFFFFFF" 
    REFERENCE    "ITU-T G.993.2 Amd2, paragraph 11.4.2.2.1 (INM 
    			 procedure)"   
    ::= { xdsl2ExtPMLineCurrEntry 23 }    
    
    xdsl2PMLCurr15MInmEqInp  OBJECT-TYPE
    SYNTAX      Counter32
    MAX-ACCESS  read-only
    STATUS      current
    DESCRIPTION
       "The INM Equivalent Inp histogram during this 15min 
    interval. An array of 68 octets (each 4 octets means amount of
    a bin of histogram), designed for supporting from 1 to 17 bins
    of the histogram. 
       The particular index of the bin incremented by an impulse
    noise event is equal to the computed value of equivalent INP,
    except the 17th of anomaly INPEQ, which logs all equivalent 
    INPs greater than 16.
       Each bin has a value in the range 0x0 to 0xFFFFFFFF"
    REFERENCE    "ITU-T G.993.2 Amd2, paragraph 11.4.2.2.1 (INM 
    			 procedure)"   
    ::= { xdsl2ExtPMLineCurrEntry 24 }    
    
    xdsl2PMLCurr15MInmIAT  OBJECT-TYPE
    SYNTAX      Counter32
    MAX-ACCESS  read-only
    STATUS      current
    DESCRIPTION
       "The INM Inter Arrival Time histogram during this 15min 
    interval. An array of 32 octets (each 4 octets means amount of 
    a bin of histogram), designed for supporting from 0 to 7 bins 
    of the histogram. 
       The index of the particular bin incremented by an complete 
    impulse noise event is determained from the following 
    INMControl parameters.
       Each bin has a value in the range 0x0 to 0xFFFFFFFF"
    REFERENCE    "ITU-T G.993.2 Amd2, paragraph 11.4.2.2.1 (INM 
    			 procedure)"   
    ::= { xdsl2ExtPMLineCurrEntry 25 }    
    
    xdsl2PMLCurr15MInmME  OBJECT-TYPE
    SYNTAX      Counter32
    MAX-ACCESS  read-only
    STATUS      current
    DESCRIPTION
       "The INM total measurement during this 15min interval. 
    This indication occurs every time a data symbol is processed 
    by the Impulse Noise Sensor.
       The range of the value is from 0x0 to 0xFFFFFFFF"
    REFERENCE    "ITU-T G.993.2 Amd2, paragraph 11.4.2.2.1 (INM 
    			 procedure)"   
    ::= { xdsl2ExtPMLineCurrEntry 26 }    
    
    xdsl2PMLCurr1DayInmEqInp  OBJECT-TYPE
    SYNTAX      Counter32
    MAX-ACCESS  read-only
    STATUS      current
    DESCRIPTION
       "The INM Equivalent Inp histogram during this 1Day interval. 
    An array of 68 octets (each 4 octets means amount of a bin of 
    histogram), designed for supporting from 1 to 17 bins of the 
    histogram. 
       The particular index of the bin incremented by an impulse
    noise event is equal to the computed value of equivalent INP,
    except the 17th of anomaly INPEQ, which logs all equivalent 
    INPs greater than 16.
       Each bin has a value in the range 0x0 to 0xFFFFFFFF"
    REFERENCE    "ITU-T G.993.2 Amd2, paragraph 11.4.2.2.1 (INM 
    			 procedure)"   
    ::= { xdsl2ExtPMLineCurrEntry 27 }    
    
    xdsl2PMLCurr1DayInmIAT  OBJECT-TYPE
    SYNTAX      Counter32
    MAX-ACCESS  read-only
    STATUS      current
    DESCRIPTION
       "The INM Inter Arrival Time histogram during this 1Day 
    interval. An array of 32 octets (each 4 octets means amount of 
    a bin of histogram), designed for supporting from 0 to 7 bins 
    of the histogram. 
       The index of the particular bin incremented by an complete 
    impulse noise event is determained from the following 
    INMControl parameters.
       Each bin has a value in the range 0x0 to 0xFFFFFFFF"
    REFERENCE    "ITU-T G.993.2 Amd2, paragraph 11.4.2.2.1 (INM 
    			 procedure)"   
    ::= { xdsl2ExtPMLineCurrEntry 28 }    
    
    xdsl2PMLCurr1DayInmME  OBJECT-TYPE
    SYNTAX      Counter32
    MAX-ACCESS  read-only
    STATUS      current
    DESCRIPTION
       "The INM total measurement during this 1Day interval. 
    This indication occurs every time a data symbol is processed 
    by the Impulse Noise Sensor.
       The range of the value is from 0x0 to 0xFFFFFFFF"
    REFERENCE    "ITU-T G.993.2 Amd2, paragraph 11.4.2.2.1 (INM 
    			 procedure)"   
    ::= { xdsl2ExtPMLineCurrEntry 29 }       
    
    
-------------------------------------------
-- xdsl2 ext PM line history 15 Minutes  --
-------------------------------------------
    xdsl2ExtPMLineHist15MinTable    OBJECT-TYPE
    SYNTAX      SEQUENCE  OF  Xdsl2ExtPMLineHist15MinEntry
    MAX-ACCESS  not-accessible
    STATUS      current
    DESCRIPTION
       "The table xdsl2ExtPMLineHist15MinTable extends xdsl2PMLineHist15MinTable."
    ::= { xdsl2ExtPMLine 3 }

    xdsl2ExtPMLineHist15MinEntry  OBJECT-TYPE
    SYNTAX      Xdsl2ExtPMLineHist15MinEntry
    MAX-ACCESS  not-accessible
    STATUS      current
    DESCRIPTION
       "The table xdsl2ExtPMLineHist15MinTable extends xdsl2PMLineHist15MinTable."
    INDEX  { ifIndex,
            xdsl2PMLHist15MUnit,
             xdsl2PMLHist15MInterval }
    ::= { xdsl2ExtPMLineHist15MinTable 1 }

    Xdsl2ExtPMLineHist15MinEntry  ::=
    SEQUENCE {
       xdsl2PMLHist15MLofs                Counter32,
       xdsl2PMLHist15MLol                 Counter32,
       xdsl2PMLHist15MLols                Counter32,
       xdsl2PMLHist15MLpr                 Counter32,
       xdsl2PMLHist15MLprs                Counter32,
       xdsl2PMLHist15MInmEqInp            Counter32,
       xdsl2PMLHist15MInmIAT              Counter32,
       xdsl2PMLHist15MInmME               Counter32
    }

    xdsl2PMLHist15MLofs  OBJECT-TYPE
    SYNTAX      Counter32
    UNITS       "seconds"
    MAX-ACCESS  read-only
    STATUS      current
    DESCRIPTION
       "Count of seconds during this interval that there was LOF."
    ::= { xdsl2ExtPMLineHist15MinEntry 1 }

    xdsl2PMLHist15MLol  OBJECT-TYPE
    SYNTAX      Counter32
    MAX-ACCESS  read-only
    STATUS      current
    DESCRIPTION
       "Count of times during this interval that the line Loss of Link."
    ::= { xdsl2ExtPMLineHist15MinEntry 2 }

    xdsl2PMLHist15MLols  OBJECT-TYPE
    SYNTAX      Counter32
    UNITS       "seconds"
    MAX-ACCESS  read-only
    STATUS      current
    DESCRIPTION
       "Count of seconds during this interval that the line Loss of Link."
    ::= { xdsl2ExtPMLineHist15MinEntry 3 }

    xdsl2PMLHist15MLpr  OBJECT-TYPE
    SYNTAX      Counter32
    MAX-ACCESS  read-only
    STATUS      current
    DESCRIPTION
       "Count of times during this interval that the line Loss of Power."
    ::= { xdsl2ExtPMLineHist15MinEntry 4 }

    xdsl2PMLHist15MLprs  OBJECT-TYPE
    SYNTAX      Counter32
    UNITS       "seconds"
    MAX-ACCESS  read-only
    STATUS      current
    DESCRIPTION
       "Count of seconds during this interval that the line Loss of Power."
    ::= { xdsl2ExtPMLineHist15MinEntry 5 }

    
    xdsl2PMLHist15MInmEqInp  OBJECT-TYPE
    SYNTAX      Counter32
    MAX-ACCESS  read-only
    STATUS      current
    DESCRIPTION
       "The INM Equivalent Inp histogram during 15min interval. 
    An array of 68 octets (each 4 octets means amount of a bin of 
    histogram), designed for supporting from 1 to 17 bins of the 
    histogram. 
       The particular index of the bin incremented by an impulse
    noise event is equal to the computed value of equivalent INP,
    except the 17th of anomaly INPEQ, which logs all equivalent 
    INPs greater than 16.
       Each bin has a value in the range 0x0 to 0xFFFFFFFF"
    REFERENCE    "ITU-T G.993.2 Amd2, paragraph 11.4.2.2.1 (INM 
    			 procedure)"
    ::= { xdsl2ExtPMLineHist15MinEntry 6 }
       
    xdsl2PMLHist15MInmIAT  OBJECT-TYPE
    SYNTAX      Counter32
    MAX-ACCESS  read-only
    STATUS      current
    DESCRIPTION
       "The INM Inter Arrival Time histogram during 15min 
    interval. An array of 32 octets (each 4 octets means amount of 
    a bin of histogram), designed for supporting from 0 to 7 bins 
    of the histogram. 
       The index of the particular bin incremented by an complete 
    impulse noise event is determained from the following 
    INMControl parameters.
       Each bin has a value in the range 0x0 to 0xFFFFFFFF"
    REFERENCE    "ITU-T G.993.2 Amd2, paragraph 11.4.2.2.1 (INM 
    			 procedure)"
    ::= { xdsl2ExtPMLineHist15MinEntry 7 }

    xdsl2PMLHist15MInmME  OBJECT-TYPE
    SYNTAX      Counter32
    MAX-ACCESS  read-only
    STATUS      current
    DESCRIPTION
       "The INM total measurement during 15min interval. 
    This indication occurs every time a data symbol is processed 
    by the Impulse Noise Sensor.
       The range of the value is from 0x0 to 0xFFFFFFFF"
    REFERENCE    "ITU-T G.993.2 Amd2, paragraph 11.4.2.2.1 (INM 
    			 procedure)"
    ::= { xdsl2ExtPMLineHist15MinEntry 8 }         
    

---------------------------------------
--  Extended  PM line history 1 Day  --
---------------------------------------
    xdsl2ExtPMLineHist1DayTable     OBJECT-TYPE
    SYNTAX      SEQUENCE  OF  Xdsl2ExtPMLineHist1DayEntry
    MAX-ACCESS  not-accessible
    STATUS      current
    DESCRIPTION
       "The table xdsl2ExtPMLineHist1DayTable extends xdsl2PMLineHist1DayTable."
    ::= { xdsl2ExtPMLine 4 }

    xdsl2ExtPMLineHist1DayEntry  OBJECT-TYPE
    SYNTAX      Xdsl2ExtPMLineHist1DayEntry
    MAX-ACCESS  not-accessible
    STATUS      current
    DESCRIPTION
       "The table xdsl2ExtPMLineHist1DayTable extends xdsl2PMLineHist1DayTable."
    INDEX  { ifIndex,
             xdsl2PMLHist1DUnit,
             xdsl2PMLHist1DInterval }
    ::= { xdsl2ExtPMLineHist1DayTable 1 }

    Xdsl2ExtPMLineHist1DayEntry  ::=
    SEQUENCE {
       xdsl2PMLHist1DLofs             Counter32,
       xdsl2PMLHist1DLol              Counter32,
       xdsl2PMLHist1DLols             Counter32,
       xdsl2PMLHist1DLpr              Counter32,
       xdsl2PMLHist1DLprs             Counter32,
       xdsl2PMLHist1DInmEqInp         Counter32,
       xdsl2PMLHist1DInmIAT           Counter32,
       xdsl2PMLHist1DInmME            Counter32
    }

    xdsl2PMLHist1DLofs  OBJECT-TYPE
    SYNTAX      Counter32
    UNITS       "seconds"
    MAX-ACCESS  read-only
    STATUS      current
    DESCRIPTION
       "Count of seconds during this interval that there was LOF."
    ::= { xdsl2ExtPMLineHist1DayEntry 1 }

    xdsl2PMLHist1DLol  OBJECT-TYPE
    SYNTAX      Counter32
    MAX-ACCESS  read-only
    STATUS      current
    DESCRIPTION
       "Count of times during this interval that the line Loss of Link."
    ::= { xdsl2ExtPMLineHist1DayEntry 2 }

    xdsl2PMLHist1DLols  OBJECT-TYPE
    SYNTAX      Counter32
    UNITS       "seconds"
    MAX-ACCESS  read-only
    STATUS      current
    DESCRIPTION
       "Count of seconds during this interval that the line Loss of Link."
    ::= { xdsl2ExtPMLineHist1DayEntry 3 }

    xdsl2PMLHist1DLpr  OBJECT-TYPE
    SYNTAX      Counter32
    MAX-ACCESS  read-only
    STATUS      current
    DESCRIPTION
       "Count of times during this interval that the line Loss of Power."
    ::= { xdsl2ExtPMLineHist1DayEntry 4 }

    xdsl2PMLHist1DLprs  OBJECT-TYPE
    SYNTAX      Counter32
    UNITS       "seconds"
    MAX-ACCESS  read-only
    STATUS      current
    DESCRIPTION
       "Count of seconds during this interval that the line Loss of Power."
    ::= { xdsl2ExtPMLineHist1DayEntry 5 }

    
    xdsl2PMLHist1DInmEqInp  OBJECT-TYPE
    SYNTAX      Counter32
    MAX-ACCESS  read-only
    STATUS      current
    DESCRIPTION
       "The INM Equivalent Inp histogram during 1Day interval. 
    An array of 68 octets (each 4 octets means amount of a bin of 
    histogram), designed for supporting from 1 to 17 bins of the 
    histogram. 
       The particular index of the bin incremented by an impulse
    noise event is equal to the computed value of equivalent INP,
    except the 17th of anomaly INPEQ, which logs all equivalent 
    INPs greater than 16.
       Each bin has a value in the range 0x0 to 0xFFFFFFFF"
    REFERENCE    "ITU-T G.993.2 Amd2, paragraph 11.4.2.2.1 (INM 
    			 procedure)"
    ::= { xdsl2ExtPMLineHist1DayEntry 6 }    
    
    xdsl2PMLHist1DInmIAT  OBJECT-TYPE
    SYNTAX      Counter32
    MAX-ACCESS  read-only
    STATUS      current
    DESCRIPTION
       "The INM Inter Arrival Time histogram during 1Day 
    interval. An array of 32 octets (each 4 octets means amount of 
    a bin of histogram), designed for supporting from 0 to 7 bins 
    of the histogram. 
       The index of the particular bin incremented by an complete 
    impulse noise event is determained from the following 
    INMControl parameters.
       Each bin has a value in the range 0x0 to 0xFFFFFFFF"
    REFERENCE    "ITU-T G.993.2 Amd2, paragraph 11.4.2.2.1 (INM 
    			 procedure)"
    ::= { xdsl2ExtPMLineHist1DayEntry 7 }    
    
    xdsl2PMLHist1DInmME  OBJECT-TYPE
    SYNTAX      Counter32
    MAX-ACCESS  read-only
    STATUS      current
    DESCRIPTION
       "The INM total measurement during this 1Day interval. 
    This indication occurs every time a data symbol is processed 
    by the Impulse Noise Sensor.
       The range of the value is from 0x0 to 0xFFFFFFFF"
    REFERENCE    "ITU-T G.993.2 Amd2, paragraph 11.4.2.2.1 (INM 
    			 procedure)"
    ::= { xdsl2ExtPMLineHist1DayEntry 8 }    
    
    

---------------------------------------------------
--  xdsl2 extended PM channel current counters   --
---------------------------------------------------
    xdsl2ExtPMChCurrTable        OBJECT-TYPE
    SYNTAX      SEQUENCE  OF  Xdsl2ExtPMChCurrEntry
    MAX-ACCESS  not-accessible
    STATUS      current
    DESCRIPTION
       "The table xdsl2PMChCurrTable extends xdsl2PMChCurrTable."
    ::= { xdsl2ExtPMChannel 1 }

    xdsl2ExtPMChCurrEntry  OBJECT-TYPE
    SYNTAX      Xdsl2ExtPMChCurrEntry
    MAX-ACCESS  not-accessible
    STATUS      current
    DESCRIPTION
       "The table xdsl2PMChCurrTable extends xdsl2PMChCurrTable."
    INDEX  { ifIndex, xdsl2PMChCurrUnit }
    ::= { xdsl2ExtPMChCurrTable 1 }

    Xdsl2ExtPMChCurrEntry  ::=
    SEQUENCE {
       xdsl2PMChSinceLinkUncorrectedCWs   Unsigned32,
       xdsl2PMChCurr15MUncorrectedCWs     Unsigned32,
       xdsl2PMChCurr1DayUncorrectedCWs    Unsigned32,
       xdsl2PMChSinceLinkCodingViolations Unsigned32,
       xdsl2PMChSinceLinkCorrectedBlocks  Unsigned32
    }

    xdsl2PMChSinceLinkUncorrectedCWs  OBJECT-TYPE
    SYNTAX      Unsigned32
    MAX-ACCESS  read-only
    STATUS      current
    DESCRIPTION
       "Count of codewords that could not be corrected since last link up."
   ::= { xdsl2ExtPMChCurrEntry 1 }

    xdsl2PMChCurr15MUncorrectedCWs  OBJECT-TYPE
    SYNTAX      Unsigned32
    MAX-ACCESS  read-only
    STATUS      current
    DESCRIPTION
       "Count of codewords that could not be corrected since during this interval."
   ::= { xdsl2ExtPMChCurrEntry 2 }

    xdsl2PMChCurr1DayUncorrectedCWs  OBJECT-TYPE
    SYNTAX      Unsigned32
    MAX-ACCESS  read-only
    STATUS      current
    DESCRIPTION
       "Count of codewords that could not be corrected since during this interval."
   ::= { xdsl2ExtPMChCurrEntry 3 }

    xdsl2PMChSinceLinkCodingViolations  OBJECT-TYPE
    SYNTAX      Unsigned32
    MAX-ACCESS  read-only
    STATUS      current
    DESCRIPTION
       "Count of CRC-8 (FEBE for xTU-R) anomalies occurring in the channel 
        since last link up."
   ::= { xdsl2ExtPMChCurrEntry 4 }

    xdsl2PMChSinceLinkCorrectedBlocks  OBJECT-TYPE
    SYNTAX      Unsigned32
    MAX-ACCESS  read-only
    STATUS      current
    DESCRIPTION
       "Count of FEC (FFEC for xTU-R) anomalies (corrected code words) 
        occurring in the channel since last link up."
   ::= { xdsl2ExtPMChCurrEntry 5 }

--------------------------------------------------
-- xdsl2 entended PM channel history 15 Minutes --
--------------------------------------------------
    xdsl2ExtPMChHist15MinTable         OBJECT-TYPE
    SYNTAX      SEQUENCE  OF  Xdsl2ExtPMChHist15MinEntry
    MAX-ACCESS  not-accessible
    STATUS      current
    DESCRIPTION
       "The table xdsl2ExtPMChHist15MinTable extends xdsl2PMChHist15MinTable."
    ::= { xdsl2ExtPMChannel 2 }

    xdsl2ExtPMChHist15MinEntry  OBJECT-TYPE
    SYNTAX      Xdsl2ExtPMChHist15MinEntry
    MAX-ACCESS  not-accessible
    STATUS      current
    DESCRIPTION
       "The table xdsl2ExtPMChHist15MinTable extends xdsl2PMChHist15MinTable."
    INDEX  { ifIndex,
             xdsl2PMChHist15MUnit,
             xdsl2PMChHist15MInterval }
    ::= { xdsl2ExtPMChHist15MinTable 1 }

    Xdsl2ExtPMChHist15MinEntry  ::=
    SEQUENCE {
       xdsl2PMChHist15MUncorrectedCWs          Unsigned32
    }

    xdsl2PMChHist15MUncorrectedCWs  OBJECT-TYPE
    SYNTAX      Unsigned32
    MAX-ACCESS  read-only
    STATUS      current
    DESCRIPTION
       "Count of codewords that could not be corrected since during this interval."
    ::= { xdsl2ExtPMChHist15MinEntry 1 }

------------------------------------------
--        PM channel history 1 Day      --
------------------------------------------
    xdsl2ExtPMChHist1DTable         OBJECT-TYPE
    SYNTAX      SEQUENCE  OF  Xdsl2ExtPMChHist1DEntry
    MAX-ACCESS  not-accessible
    STATUS      current
    DESCRIPTION
       "The table xdsl2ExtPMChHist1DTable extends xdsl2PMChHist1DTable."
    ::= { xdsl2ExtPMChannel 3 }

    xdsl2ExtPMChHist1DEntry  OBJECT-TYPE
    SYNTAX      Xdsl2ExtPMChHist1DEntry
    MAX-ACCESS  not-accessible
    STATUS      current
    DESCRIPTION
       "The table xdsl2ExtPMChHist1DTable extends xdsl2PMChHist1DTable."
    INDEX  { ifIndex,
             xdsl2PMChHist1DUnit,
             xdsl2PMChHist1DInterval }
    ::= { xdsl2ExtPMChHist1DTable 1 }

    Xdsl2ExtPMChHist1DEntry  ::=
    SEQUENCE {
       xdsl2PMChHist1DayUncorrectedCWs          Unsigned32
    }

    xdsl2PMChHist1DayUncorrectedCWs  OBJECT-TYPE
    SYNTAX      Unsigned32
    MAX-ACCESS  read-only
    STATUS      current
    DESCRIPTION
       "Count of codewords that could not be corrected since during this interval."
    ::= { xdsl2ExtPMChHist1DEntry 1 }

------------------------------------------------
--     xdsl2ExtLineConfTemplateTable          --
------------------------------------------------
    xdsl2ExtLineConfTemplateTable  OBJECT-TYPE
    SYNTAX      SEQUENCE  OF  Xdsl2ExtLineConfTemplateEntry
    MAX-ACCESS  not-accessible
    STATUS      current
    DESCRIPTION
       "The table xdsl2ExtLineConfTemplateTable extends xdsl2LineConfTemplateTable."
    ::= { xdsl2ExtProfileLine 1 }

    xdsl2ExtLineConfTemplateEntry  OBJECT-TYPE
    SYNTAX      Xdsl2ExtLineConfTemplateEntry
    MAX-ACCESS  not-accessible
    STATUS      current
    DESCRIPTION
       "TThe table xdsl2ExtLineConfTemplateTable extends xdsl2LineConfTemplateTable."
    INDEX  { xdsl2LConfTempTemplateName }
    ::= { xdsl2ExtLineConfTemplateTable 1 }

    Xdsl2ExtLineConfTemplateEntry  ::=
    SEQUENCE {
       xdsl2LConfTempPortList      PortList,
       xdsl2LConfTempInmConfProfile  SnmpAdminString
    }

    xdsl2LConfTempPortList  OBJECT-TYPE
    SYNTAX      PortList
    ACCESS      read-only
    STATUS      current
    DESCRIPTION
       "A port list that indicates which ports this template applys for."
    REFERENCE    ""
    ::= { xdsl2ExtLineConfTemplateEntry 1 }

    xdsl2LConfTempInmConfProfile  OBJECT-TYPE
	SYNTAX      SnmpAdminString (SIZE(1..32))
	MAX-ACCESS  read-create
	STATUS      current
	DESCRIPTION   
	  "The value of this object identifies the row in the
       VDSL2/ADSL/ADSL2 and ADSL2+ INM configuration Profile Table,
       (xdsl2ExtInmConfProfTable) that applies for this DSL line."
	DEFVAL       { "DEFVAL" }
	::= { xdsl2ExtLineConfTemplateEntry 2 }


------------------------------------------
--      xdsl2ExtLineConfProfTable       --
------------------------------------------
    xdsl2ExtLineConfProfTable  OBJECT-TYPE
    SYNTAX      SEQUENCE  OF  Xdsl2ExtLineConfProfEntry
    MAX-ACCESS  not-accessible
    STATUS      current
    DESCRIPTION
       "The table xdsl2ExtLineConfProfTable extends xdsl2LineConfProfTable."
    ::= { xdsl2ExtProfileLine 2 }

    xdsl2ExtLineConfProfEntry  OBJECT-TYPE
    SYNTAX      Xdsl2ExtLineConfProfEntry
    MAX-ACCESS  not-accessible
    STATUS      current
    DESCRIPTION
       "The table xdsl2ExtLineConfProfTable extends xdsl2LineConfProfTable."
    INDEX  { xdsl2LConfProfProfileName }
    ::= { xdsl2ExtLineConfProfTable 1 }

    Xdsl2ExtLineConfProfEntry  ::=
    SEQUENCE {
       xdsl2LConfProfBitSwapDs     Unsigned32,
       xdsl2LConfProfBitSwapUs     Unsigned32,
       xdsl2LConfProfPortList      PortList
    }

    xdsl2LConfProfBitSwapDs OBJECT-TYPE
    SYNTAX Unsigned32 
    ACCESS  read-write
    STATUS  current
    DESCRIPTION
       "This configuration parameter indicates if the use of bitswap is
        disabled on downstream direction.
        The possible values are:
        disable(0),
        enable(1)"
    ::= { xdsl2ExtLineConfProfEntry 1 }

    xdsl2LConfProfBitSwapUs OBJECT-TYPE
    SYNTAX Unsigned32 
    ACCESS  read-write
    STATUS  current
    DESCRIPTION
       "This configuration parameter indicates if the use of bitswap is
        disabled on upstream direction.
        The possible values are:
        disable(0),
        enable(1)"
    ::= { xdsl2ExtLineConfProfEntry 2 }

    xdsl2LConfProfPortList  OBJECT-TYPE
    SYNTAX      PortList
    ACCESS      read-only
    STATUS      current
    DESCRIPTION
       "A port list that indicates which ports this profile applys for."
    REFERENCE    ""
    ::= { xdsl2ExtLineConfProfEntry 3 }

    xdsl2MaxNumLineConfTemplate OBJECT-TYPE
    SYNTAX  Unsigned32
    ACCESS  read-only
    STATUS  current
    DESCRIPTION
        "The maximum number of VDSL line template."
    ::= { xdsl2ExtProfileLine 5 }

    xdsl2MaxNumLineConfProfile OBJECT-TYPE
    SYNTAX  Unsigned32
    ACCESS  read-only
    STATUS  current
    DESCRIPTION
        "The maximum number of VDSL line profile."
    ::= { xdsl2ExtProfileLine 6 }

------------------------------------------
--        xdsl2ExtInmConfProfTable      --
------------------------------------------
	xdsl2ExtInmConfProfTable  OBJECT-TYPE
    SYNTAX      SEQUENCE  OF  Xdsl2ExtInmConfProfEntry
    MAX-ACCESS  not-accessible
    STATUS      current
    DESCRIPTION
       "xdsl2ExtInmConfProfTable."
    REFERENCE    "ITU-T G.993.2 Amd2, paragraph 11.4.2.2.1 (INM 
    			 procedure)"   
    ::= { xdsl2ExtProfileLine 7 }

    xdsl2ExtInmConfProfEntry  OBJECT-TYPE
    SYNTAX      Xdsl2ExtInmConfProfEntry
    MAX-ACCESS  not-accessible
    STATUS      current
    DESCRIPTION
       "xdsl2ExtInmConfProfTable." 
    REFERENCE    "ITU-T G.993.2 Amd2, paragraph 11.4.2.2.1 (INM 
    			 procedure)"
    INDEX  { xdsl2ExtInmConfProfProfileName }
    ::= { xdsl2ExtInmConfProfTable 1 }

    Xdsl2ExtInmConfProfEntry  ::=
	SEQUENCE {
      xdsl2ExtInmConfProfProfileName		SnmpAdminString,
      xdsl2ExtInmConfProfVtucInpEq			Unsigned32,
      xdsl2ExtInmConfProfVturInpEq			Unsigned32,
      xdsl2ExtInmConfProfVtucCC            	Unsigned32,
      xdsl2ExtInmConfProfVturCC            	Unsigned32,
      xdsl2ExtInmConfProfVtucIATO			Unsigned32,
      xdsl2ExtInmConfProfVturIATO			Unsigned32,
      xdsl2ExtInmConfProfVtucIATS			Unsigned32,
      xdsl2ExtInmConfProfVturIATS			Unsigned32, 
      xdsl2ExtInmConfProfRowStatus          RowStatus,
      xdsl2ExtInmConfProfPortList			PortList
	}

	xdsl2ExtInmConfProfProfileName  OBJECT-TYPE
	SYNTAX      SnmpAdminString (SIZE(1..32))
	MAX-ACCESS  not-accessible
	STATUS      current
	DESCRIPTION
      "This object identifies a row in this table."
    REFERENCE    "ITU-T G.993.2 Amd2, paragraph 11.4.2.2.1 (INM 
    			 procedure)"
     ::= { xdsl2ExtInmConfProfEntry 1 }

    xdsl2ExtInmConfProfVtucInpEq OBJECT-TYPE
    SYNTAX Unsigned32 (0..3)
    ACCESS  read-write
    STATUS  current
    DESCRIPTION
       "The INM Inmpulse Noise Protection Equivalent Mode. 
    Configuration parameter INM_INPEQ_MODE defines the way of 
    computation of Equivalent INP, as defined in ITU-T G.993.2 Amd2 
    11.4.2.2.1
       This takes a value in the range from 0 to 3."
    REFERENCE    "ITU-T G.993.2 Amd2, paragraph 11.4.2.2.1 (INM 
    			 procedure)"
    DEFVAL       { 0 }
    ::= { xdsl2ExtInmConfProfEntry 2 }

    xdsl2ExtInmConfProfVturInpEq OBJECT-TYPE
    SYNTAX Unsigned32 (0..3)
    ACCESS  read-write
    STATUS  current
    DESCRIPTION
       "The INM Inmpulse Noise Protection Equivalent Mode. 
    Configuration parameter INM_INPEQ_MODE defines the way of 
    computation of Equivalent INP, as defined in ITU-T G.993.2 Amd2 
    11.4.2.2.1
       This takes a value in the range from 0 to 3."
    REFERENCE    "ITU-T G.993.2 Amd2, paragraph 11.4.2.2.1 (INM 
    			 procedure)"
    DEFVAL       { 0 }
    ::= { xdsl2ExtInmConfProfEntry 3 }

    xdsl2ExtInmConfProfVtucCC OBJECT-TYPE
    SYNTAX Unsigned32 
    ACCESS  read-write
    STATUS  current
    DESCRIPTION
       "The INM Cluster Continuation. The valid values for INMCC range 
    from 0 from 64 DMT symbols in steps of 1 DMT symbol.
       Up to and including INMCC nondegraded symbols will be allowed before
    a cluster is deemed to be complete and the impulse noise event over."
    REFERENCE    "ITU-T G.993.2 Amd2, paragraph 11.4.2.2.1 (INM 
    			 procedure)"  
    DEFVAL       { 0 }
    ::= { xdsl2ExtInmConfProfEntry 4 } 
    
    xdsl2ExtInmConfProfVturCC OBJECT-TYPE
    SYNTAX Unsigned32 
    ACCESS  read-write
    STATUS  current
    DESCRIPTION
       "The INM Cluster Continuation. The valid values for INMCC range 
    from 0 from 64 DMT symbols in steps of 1 DMT symbol.
       Up to and including INMCC nondegraded symbols will be allowed before
    a cluster is deemed to be complete and the impulse noise event over."
    REFERENCE    "ITU-T G.993.2 Amd2, paragraph 11.4.2.2.1 (INM 
    			 procedure)"  
    DEFVAL       { 0 }
    ::= { xdsl2ExtInmConfProfEntry 5 }
    
    xdsl2ExtInmConfProfVtucIATO OBJECT-TYPE
    SYNTAX Unsigned32 
    ACCESS  read-write
    STATUS  current
    DESCRIPTION
       "The INM Inter Arrival Time Offset for the IAT anomaly generation. 
    The valid values for INMIATO range from 3 from 511 DMT symbols in steps
    of 1 DMT symbol."
    REFERENCE    "ITU-T G.993.2 Amd2, paragraph 11.4.2.2.1 (INM 
    			 procedure)"     
    DEFVAL       { 3 }    
    ::= { xdsl2ExtInmConfProfEntry 6 }
    
    xdsl2ExtInmConfProfVturIATO OBJECT-TYPE
    SYNTAX Unsigned32 
    ACCESS  read-write
    STATUS  current
    DESCRIPTION
       "The INM Inter Arrival Time Offset for the IAT anomaly generation. 
    The valid values for INMIATO range from 3 from 511 DMT symbols in steps
    of 1 DMT symbol."
    REFERENCE    "ITU-T G.993.2 Amd2, paragraph 11.4.2.2.1 (INM 
    			 procedure)"     
    DEFVAL       { 3 }    
    ::= { xdsl2ExtInmConfProfEntry 7 }    

    xdsl2ExtInmConfProfVtucIATS OBJECT-TYPE
    SYNTAX Unsigned32 
    ACCESS  read-write
    STATUS  current
    DESCRIPTION
       "The INM Inter Arrival Time Step for the IAT anomaly generation. 
    The valid values for INMIATS range from 0 from 7 in steps. The range of 
    values of inter-arrival times recorded in a single bin is 2^(INMIATS).
    All inter-arrival times greater than or equal to INMIATO+6*(2^INMIATS)
    are recorded in the 7th bin of INMAIAT."
    REFERENCE    "ITU-T G.993.2 Amd2, paragraph 11.4.2.2.1 (INM 
    			 procedure)"     
    DEFVAL       { 0 }    
    ::= { xdsl2ExtInmConfProfEntry 8 }

    xdsl2ExtInmConfProfVturIATS OBJECT-TYPE
    SYNTAX Unsigned32 
    ACCESS  read-write
    STATUS  current
    DESCRIPTION
       "The INM Inter Arrival Time Step for the IAT anomaly generation. 
    The valid values for INMIATS range from 0 from 7 in steps. The range of 
    values of inter-arrival times recorded in a single bin is 2^(INMIATS).
    All inter-arrival times greater than or equal to INMIATO+6*(2^INMIATS)
    are recorded in the 7th bin of INMAIAT."
    REFERENCE    "ITU-T G.993.2 Amd2, paragraph 11.4.2.2.1 (INM 
    			 procedure)"     
    DEFVAL       { 0 }    
    ::= { xdsl2ExtInmConfProfEntry 9 }

    xdsl2ExtInmConfProfRowStatus  OBJECT-TYPE
    SYNTAX      RowStatus
    MAX-ACCESS  read-create
    STATUS      current
    DESCRIPTION
      "This object is used to create a new row or to modify or
 	delete an existing row in this table."
    ::= { xdsl2ExtInmConfProfEntry 14 }
    
    xdsl2ExtInmConfProfPortList  OBJECT-TYPE
    SYNTAX      PortList
    ACCESS      read-only
    STATUS      current
    DESCRIPTION
       "A port list that indicates which ports this profile applys for."
    REFERENCE    ""
    ::= { xdsl2ExtInmConfProfEntry 15 }
    
    xdsl2MaxNumInmConfProfile OBJECT-TYPE
    SYNTAX  Unsigned32
    ACCESS  read-only
    STATUS  current
    DESCRIPTION
        "The maximum number of VDSL Inm profile."
    ::= { xdsl2ExtProfileLine 8 }         

------------------------------------------------
--        xdsl2ExtChConfProfileTable          --
------------------------------------------------
    xdsl2ExtChConfProfileTable  OBJECT-TYPE
    SYNTAX      SEQUENCE  OF  Xdsl2ExtChConfProfileEntry
    MAX-ACCESS  not-accessible
    STATUS      current
    DESCRIPTION
       "The table xdsl2ExtChConfProfileTable extends xdsl2ExtChConfProfileTable."
    ::= { xdsl2ExtProfileChannel 1 }

    xdsl2ExtChConfProfileEntry  OBJECT-TYPE
    SYNTAX      Xdsl2ExtChConfProfileEntry
    MAX-ACCESS  not-accessible
    STATUS      current
    DESCRIPTION
       "The table xdsl2ExtChConfProfileTable extends xdsl2ExtChConfProfileTable."
    INDEX  { xdsl2ChConfProfProfileName }
    ::= { xdsl2ExtChConfProfileTable 1 }

    Xdsl2ExtChConfProfileEntry  ::=
    SEQUENCE {
       xdsl2ChConfProfPhyRDs        Unsigned32,
       xdsl2ChConfProfPhyRUs        Unsigned32,
       xdsl2ChConfProfPortList      OCTET STRING
    }

    xdsl2ChConfProfPhyRDs OBJECT-TYPE
    SYNTAX Unsigned32 
    ACCESS  read-create
    STATUS  current
    DESCRIPTION
       "This configuration parameter defines phy retransmission 
        mode on downstream direction. If auto mode is selected,
        PhyR will be disabled if the net data rate in PhyR mode 
        will be lower than in non-PhyR mode under current loop 
        condition and framing paramters.
        The possible values are:
        disable(0),
        enable(1),
        auto(2)"
    ::= { xdsl2ExtChConfProfileEntry 1 }

    xdsl2ChConfProfPhyRUs OBJECT-TYPE
    SYNTAX Unsigned32 
    ACCESS  read-create
    STATUS  current
    DESCRIPTION
       "This configuration parameter defines phy retransmission 
        mode on upstream direction. If auto mode is selected,
        PhyR will be disabled if the net data rate in PhyR mode 
        will be lower than in non-PhyR mode under current loop 
        condition and framing paramters.
        The possible values are:
        disable(0),
        enable(1),
        auto(2)"
    ::= { xdsl2ExtChConfProfileEntry 2 }

    xdsl2ChConfProfPortList  OBJECT-TYPE
    SYNTAX      PortList
    ACCESS      read-only
    STATUS      current
    DESCRIPTION
       "A port list that indicates which ports this profile applys for."
    REFERENCE    ""
    ::= { xdsl2ExtChConfProfileEntry 3 }

    xdsl2MaxNumChConfProfile OBJECT-TYPE
    SYNTAX  Unsigned32
    ACCESS  read-only
    STATUS  current
    DESCRIPTION
        "The maximum number of VDSL channel profile."
    ::= { xdsl2ExtProfileChannel 2 }

------------------------------------------------
--    xdsl2ExtLineAlarmConfTemplateTable      --
------------------------------------------------
    xdsl2ExtLineAlarmConfTemplateTable  OBJECT-TYPE
    SYNTAX      SEQUENCE  OF  Xdsl2ExtLineAlarmConfTemplateEntry
    MAX-ACCESS  not-accessible
    STATUS      current
    DESCRIPTION
       "The table xdsl2ExtLineAlarConfTemplateTable extends 
       xdsl2ExtLineAlarConfTemplateTable."
    ::= { xdsl2ExtProfileAlarmConf 1 }

    xdsl2ExtLineAlarmConfTemplateEntry  OBJECT-TYPE
    SYNTAX      Xdsl2ExtLineAlarmConfTemplateEntry
    MAX-ACCESS  not-accessible
    STATUS      current
    DESCRIPTION
       "The table xdsl2ExtLineAlarConfTemplateTable extends 
       xdsl2ExtLineAlarConfTemplateTable."
   INDEX  { xdsl2LAlarmConfTempTemplateName }
   ::= { xdsl2ExtLineAlarmConfTemplateTable 1 }

    Xdsl2ExtLineAlarmConfTemplateEntry  ::=
    SEQUENCE {
       xdsl2LAlarmConfTempPortList      PortList
    }

    xdsl2LAlarmConfTempPortList  OBJECT-TYPE
    SYNTAX      PortList
    ACCESS      read-only
    STATUS      current
    DESCRIPTION
       "A port list that indicates which ports this template applys for."
    REFERENCE    ""
    ::= { xdsl2ExtLineAlarmConfTemplateEntry 3 }

------------------------------------------------
--   xdsl2ExtLineAlarmConfProfileTable        --
------------------------------------------------

    xdsl2ExtLineAlarmConfProfileTable  OBJECT-TYPE
    SYNTAX      SEQUENCE  OF  Xdsl2ExtLineAlarmConfProfileEntry
    MAX-ACCESS  not-accessible
    STATUS      current
    DESCRIPTION
      "The table xdsl2ExtLineAlarmConfProfileTable extends 
       xdsl2LineAlarmConfProfileTable."
     ::= { xdsl2ExtProfileAlarmConf 2 }

    xdsl2ExtLineAlarmConfProfileEntry  OBJECT-TYPE
    SYNTAX      Xdsl2ExtLineAlarmConfProfileEntry
    MAX-ACCESS  not-accessible
    STATUS      current
    DESCRIPTION
      "The table xdsl2ExtLineAlarmConfProfileTable extends 
       xdsl2LineAlarmConfProfileTable."
    INDEX  { xdsl2LineAlarmConfProfileName }
    ::= { xdsl2ExtLineAlarmConfProfileTable 1 }

    Xdsl2ExtLineAlarmConfProfileEntry ::=
    SEQUENCE {
       xdsl2LineAlarmConfProfileXtucThresh15MinLofs   HCPerfIntervalThreshold,
       xdsl2LineAlarmConfProfileXturThresh15MinLofs   HCPerfIntervalThreshold,
       xdsl2LAlarmConfProfilePortList 				  PortList,
       xdsl2LineAlarmConfProfileXturThresh15MinLprs   HCPerfIntervalThreshold
    }

    xdsl2LineAlarmConfProfileXtucThresh15MinLofs  OBJECT-TYPE
    SYNTAX      HCPerfIntervalThreshold
    UNITS       "seconds"
    MAX-ACCESS  read-create
    STATUS      current
    DESCRIPTION
       "A threshold for the xdsl2PMLCurr15MLofs counter, when
        xdsl2PMLCurrUnit is xtuc {1}.
        The value 0 means that no threshold is specified for the
        associated counter."
    DEFVAL       { 0 }
    ::= { xdsl2ExtLineAlarmConfProfileEntry 1 }

    xdsl2LineAlarmConfProfileXturThresh15MinLofs  OBJECT-TYPE
    SYNTAX      HCPerfIntervalThreshold
    UNITS       "seconds"
    MAX-ACCESS  read-create
    STATUS      current
    DESCRIPTION
       "A threshold for the xdsl2PMLCurr15MLofs counter, when
        xdsl2PMLCurrUnit is xtur {2}.
        The value 0 means that no threshold is specified for the
        associated counter."
    DEFVAL       { 0 }
    ::= { xdsl2ExtLineAlarmConfProfileEntry 2 }

    xdsl2LAlarmConfProfilePortList  OBJECT-TYPE
    SYNTAX      PortList
    ACCESS      read-only
    STATUS      current
    DESCRIPTION
       "A port list that indicates which ports this profile applys for."
    ::= { xdsl2ExtLineAlarmConfProfileEntry 3 }

    xdsl2LineAlarmConfProfileXturThresh15MinLprs  OBJECT-TYPE
    SYNTAX      HCPerfIntervalThreshold
    UNITS       "seconds"
    MAX-ACCESS  read-create
    STATUS      current
    DESCRIPTION
       "A threshold for the xdsl2PMLCurr15MLprs counter, when
        xdsl2PMLCurrUnit is xtur {2}.
        The value 0 means that no threshold is specified for the
        associated counter."
    DEFVAL       { 0 }
    ::= { xdsl2ExtLineAlarmConfProfileEntry 4 }


------------------------------------------------
--    xdsl2ExtChAlarmConfProfileTable         --
------------------------------------------------

    xdsl2ExtChAlarmConfProfileTable  OBJECT-TYPE
    SYNTAX      SEQUENCE  OF  Xdsl2ExtChAlarmConfProfileEntry
    MAX-ACCESS  not-accessible
    STATUS      current
    DESCRIPTION
      "The table xdsl2ExtChAlarmConfProfileTable extends 
       xdsl2ExtChAlarmConfProfileTable."
    ::= { xdsl2ExtProfileAlarmConf 3 }

    xdsl2ExtChAlarmConfProfileEntry  OBJECT-TYPE
    SYNTAX      Xdsl2ExtChAlarmConfProfileEntry
    MAX-ACCESS  not-accessible
    STATUS      current
    DESCRIPTION
      "The table xdsl2ExtChAlarmConfProfileTable extends 
       xdsl2ExtChAlarmConfProfileTable."
    INDEX  { xdsl2ChAlarmConfProfileName }
    ::= { xdsl2ExtChAlarmConfProfileTable 1 }

    Xdsl2ExtChAlarmConfProfileEntry ::=
    SEQUENCE {
       xdsl2ChAlarmConfProfilePortList PortList
    }

    xdsl2ChAlarmConfProfilePortList  OBJECT-TYPE
    SYNTAX      PortList
    ACCESS      read-only
    STATUS      current
    DESCRIPTION
       "A port list that indicates which ports this profileapplys for."
    ::= { xdsl2ExtChAlarmConfProfileEntry 3 }

    xdsl2MaxNumLineAlarmConfTemplate OBJECT-TYPE
    SYNTAX  Unsigned32
    ACCESS  read-only
    STATUS  current
    DESCRIPTION
        "The maximum number of VDSL alarm template."
    ::= { xdsl2ExtProfileAlarmConf 4 }

    xdsl2MaxNumLineAlarmConfProfile OBJECT-TYPE
    SYNTAX  Unsigned32
    ACCESS  read-only
    STATUS  current
    DESCRIPTION
        "The maximum number of VDSL line alarm profile."
    ::= { xdsl2ExtProfileAlarmConf 5 }

    xdsl2MaxNumChAlarmConfProfile OBJECT-TYPE
    SYNTAX  Unsigned32
    ACCESS  read-only
    STATUS  current
    DESCRIPTION
        "The maximum number of VDSL channel alarm profile."
    ::= { xdsl2ExtProfileAlarmConf 6 }
            
-------------------------------------------
--          Notifications Group          --
-------------------------------------------
	xdsl2LinePerfLOFSThreshXtuc NOTIFICATION-TYPE
    OBJECTS
    {
    xdsl2PMLCurr15MLofs,
    xdsl2LineAlarmConfProfileXtucThresh15MinLofs
    }
    STATUS     current
    DESCRIPTION
      "This notification indicates that the LOF seconds threshold
       has been reached/exceeded for the referred xTU-C."
    ::= { xdsl2ExtNotifications 1 }

	xdsl2LinePerfLOFSThreshXtur NOTIFICATION-TYPE
    OBJECTS
    {
    xdsl2PMLCurr15MLofs,
    xdsl2LineAlarmConfProfileXturThresh15MinLofs
    }
    STATUS     current
    DESCRIPTION
      "This notification indicates that the LOF seconds threshold
       has been reached/exceeded for the referred xTU-R."
    ::= { xdsl2ExtNotifications 2 }
    
	xdsl2LinePerfLPRSThreshXtur NOTIFICATION-TYPE
    OBJECTS
    {
    xdsl2PMLCurr15MLprs,
    xdsl2LineAlarmConfProfileXturThresh15MinLprs
    }
    STATUS     current
    DESCRIPTION
      "This notification indicates that the LPR seconds threshold
       has been reached/exceeded for the referred xTU-R."
    ::= { xdsl2ExtNotifications 3 }

--  macBasedVlanSetup
	macBasedVlanSetup     	OBJECT IDENTIFIER ::= { ves1616pe54 61 }

        macBasedVlanTable	OBJECT-TYPE
        SYNTAX	SEQUENCE OF MacBasedVlanEntry
        ACCESS  not-accessible
        STATUS  mandatory
        DESCRIPTION
                 	""
        ::= { macBasedVlanSetup 1 }

		macBasedVlanEntry OBJECT-TYPE
        SYNTAX	MacBasedVlanEntry
        ACCESS	not-accessible
        STATUS	mandatory
        DESCRIPTION    	"An entry in macBasedVlanTable."
        INDEX          	{macBasedVlanMAC }
        ::= { macBasedVlanTable 1 }

      	MacBasedVlanEntry ::=
		SEQUENCE {
        	macBasedVlanName		DisplayString,
        	macBasedVlanMAC 	MacAddress,      
        	macBasedVlanVlanId 	INTEGER,
        	macBasedVlan8021pPriority INTEGER,
        	macBasedVlanRowstatus RowStatus        	
           }                                             
                        
        macBasedVlanName OBJECT-TYPE
        SYNTAX  DisplayString
        ACCESS  read-write
        STATUS  mandatory
        DESCRIPTION
                      	"Name of Mac-Based Vlan."
        ::= { macBasedVlanEntry 1 }                        
                        
        macBasedVlanMAC OBJECT-TYPE
        SYNTAX  MacAddress
        ACCESS  read-only
        STATUS  mandatory
        DESCRIPTION
                      	"Mac address for Mac-Based Vlan"
        ::= { macBasedVlanEntry 2 }
                                             
   		macBasedVlanVlanId OBJECT-TYPE
        SYNTAX  INTEGER
        ACCESS  read-write
        STATUS  mandatory
        DESCRIPTION
                      	"Vlan id for Mac-Based Vlan, 1~4094."
        ::= { macBasedVlanEntry 3 }
        
			macBasedVlan8021pPriority OBJECT-TYPE
        SYNTAX  INTEGER
        ACCESS  read-write
        STATUS  mandatory
        DESCRIPTION
                      	"802.1p priority for Mac-Based Vlan, 0~7."
        ::= { macBasedVlanEntry 4 } 
        
      macBasedVlanRowstatus OBJECT-TYPE
        SYNTAX  RowStatus
        ACCESS  read-create
        STATUS  mandatory
        DESCRIPTION
                      	"Row Status for Mac-Based Vlan"
        ::= { macBasedVlanEntry 5 } 

--  vlanProfileSetup
	vlanProfileSetup     	OBJECT IDENTIFIER ::= { ves1616pe54 62 }

        vlanProfileTable	OBJECT-TYPE
        SYNTAX	SEQUENCE OF VlanProfileEntry
        ACCESS  not-accessible
        STATUS  mandatory
        DESCRIPTION
                 	""
        ::= { vlanProfileSetup 1 }

		vlanProfileEntry OBJECT-TYPE
        SYNTAX	VlanProfileEntry
        ACCESS	not-accessible
        STATUS	mandatory
        DESCRIPTION    	"An entry in vlanProfileTable."
        INDEX          	{vlanProfileName }
        ::= { vlanProfileTable 1 }

      	VlanProfileEntry ::=
		SEQUENCE {
        	vlanProfileName		DisplayString,
        	vlanProfileMacLearning 	INTEGER,      
        	vlanProfileUnknownMulticastDrop		INTEGER, 
        	vlanProfileRowStatus 	RowStatus      	
           }                                             
                        
        vlanProfileName OBJECT-TYPE
        SYNTAX  DisplayString
        ACCESS  read-only
        STATUS  mandatory
        DESCRIPTION
                      	"Name of vlan Profile."
        ::= { vlanProfileEntry 1 }                        
                        
        vlanProfileMacLearning OBJECT-TYPE
        SYNTAX  INTEGER{
                enable(1),
                disable(0)
        }
        ACCESS  read-write
        STATUS  mandatory
        DESCRIPTION
                      	"Mac learning for vlan profile"
        ::= { vlanProfileEntry 2 }
                   
        vlanProfileUnknownMulticastDrop OBJECT-TYPE
        SYNTAX  INTEGER{
        	enable(1),
        	disable(0)
        }
        ACCESS  read-write
        STATUS  mandatory
        DESCRIPTION
                      	"Drop unknown multicast packets."
        ::= { vlanProfileEntry 3 }
                   
        vlanProfileRowStatus OBJECT-TYPE
        SYNTAX  RowStatus
        ACCESS  read-create
        STATUS  mandatory
        DESCRIPTION
                      	"Row status for vlan profile"
        ::= { vlanProfileEntry 4 } 

        vlanTable	OBJECT-TYPE
        SYNTAX	SEQUENCE OF VlanEntry
        ACCESS  not-accessible
        STATUS  mandatory
        DESCRIPTION
                 	""
        ::= { vlanProfileSetup 2 }

	vlanEntry OBJECT-TYPE
        SYNTAX	VlanEntry
        ACCESS	not-accessible
        STATUS	mandatory
        DESCRIPTION    	"An entry in vlanTable."
        INDEX          	{dot1qVlanIndex }
        ::= { vlanTable 1 }

      	VlanEntry ::=
		SEQUENCE {
        	profileName	DisplayString	
           }                                             
                        
        profileName OBJECT-TYPE
        SYNTAX  DisplayString
        ACCESS  read-write
        STATUS  mandatory
        DESCRIPTION
                      	"Name of vlan Profile."
        ::= { vlanEntry 1 }                        

--  DoSPreventionSetup
	dosPreventionSetup     	OBJECT IDENTIFIER ::= { ves1616pe54 63 }                                        
                        
        dosPreventionActive OBJECT-TYPE
        SYNTAX  INTEGER{
                enable(1),
                disable(0)
        }
        ACCESS  read-write
        STATUS  mandatory
        DESCRIPTION
                      	"DoS prevention enabled/disabled for the switch."
        ::= { dosPreventionSetup 1 }                        
                        
        dosPreventionTCPHeaderSize OBJECT-TYPE
        SYNTAX  INTEGER
        ACCESS  read-write
        STATUS  mandatory
        DESCRIPTION
                      	"Minimum TCP header size."
        ::= { dosPreventionSetup 2 }
                   
        dosPreventionICMPPacketSize OBJECT-TYPE
        SYNTAX  INTEGER
        ACCESS  read-write
        STATUS  mandatory
        DESCRIPTION
                      	"Maximum ICMP packet size."
        ::= { dosPreventionSetup 3 } 
             
        dosPreventionMacChecking OBJECT-TYPE
        SYNTAX  INTEGER{
                enable(1),
                disable(0)
        }
        ACCESS  read-write
        STATUS  mandatory
        DESCRIPTION
                      	"Checking MAC enabled/disabled for the switch."
        ::= { dosPreventionSetup 4 }     
             
        dosPreventionIPChecking OBJECT-TYPE
        SYNTAX  INTEGER{
                enable(1),
                disable(0)
        }
        ACCESS  read-write
        STATUS  mandatory
        DESCRIPTION
                      	"Checking IP enabled/disabled for the switch."
        ::= { dosPreventionSetup 5 }    
             
--        dosPreventionDoSIPAttack OBJECT-TYPE
--        SYNTAX  INTEGER{
--                enable(1),
--                disable(0)
--        }
--        ACCESS  read-write
--        STATUS  mandatory
--        DESCRIPTION
--                      	"DoS IP attack enabled/disabled for the switch."
--        ::= { dosPreventionSetup 6 }  
             
        dosPreventionICMPSize OBJECT-TYPE
        SYNTAX  INTEGER{
                enable(1),
                disable(0)
        }
        ACCESS  read-write
        STATUS  mandatory
        DESCRIPTION
                      	"Checking ICMP packet size enabled/disabled for the switch."
        ::= { dosPreventionSetup 7 }  
             
--        dosPreventionDoSICMPAttack OBJECT-TYPE
--        SYNTAX  INTEGER{
--                enable(1),
--                disable(0)
--        }
--        ACCESS  read-write
--        STATUS  mandatory
--        DESCRIPTION
--                      	"DoS ICMP attack enabled/disabled for the switch."
--        ::= { dosPreventionSetup 8 }     
             
        dosPreventionICMPFragment OBJECT-TYPE
        SYNTAX  INTEGER{
                enable(1),
                disable(0)
        }
        ACCESS  read-write
        STATUS  mandatory
        DESCRIPTION
                      	"Dropping fragmented ICMP packets enabled/disabled for the switch."
        ::= { dosPreventionSetup 9 }  
             
--        dosPreventionTCPSize OBJECT-TYPE
--        SYNTAX  INTEGER{
--                enable(1),
--                disable(0)
--        }
--        ACCESS  read-write
--        STATUS  mandatory
--        DESCRIPTION
--                      	"Checking TCP header size enabled/disabled for the switch."
--        ::= { dosPreventionSetup 10 }      
             
        dosPreventionTCPSYN OBJECT-TYPE
        SYNTAX  INTEGER{
                enable(1),
                disable(0)
        }
        ACCESS  read-write
        STATUS  mandatory
        DESCRIPTION
                      	"Checking TCP SYN packets enabled/disabled for the switch."
        ::= { dosPreventionSetup 11 }     
             
--        dosPreventionDoSTCPAttack OBJECT-TYPE
--        SYNTAX  INTEGER{
--                enable(1),
--                disable(0)
--        }
--        ACCESS  read-write
--        STATUS  mandatory
--        DESCRIPTION
--                      	"DoS TCP attack enabled/disabled for the switch."
--        ::= { dosPreventionSetup 12 }     
             
        dosPreventionTCPFragment OBJECT-TYPE
        SYNTAX  INTEGER{
                enable(1),
                disable(0)
        }
        ACCESS  read-write
        STATUS  mandatory
        DESCRIPTION
                      	"Dropping fragmented TCP packets with offset value of 1 enabled/disabled for the switch."
        ::= { dosPreventionSetup 13 }     
             
        dosPreventionTCPControlSN OBJECT-TYPE
        SYNTAX  INTEGER{
                enable(1),
                disable(0)
        }
        ACCESS  read-write
        STATUS  mandatory
        DESCRIPTION
                      	"Dropping TCP packets with control flag of 0 and sequence number of 0 enabled/disabled for the switch."
        ::= { dosPreventionSetup 14 }    
             
        dosPreventionTCPPort OBJECT-TYPE
        SYNTAX  INTEGER{
                enable(1),
                disable(0)
        }
        ACCESS  read-write
        STATUS  mandatory
        DESCRIPTION
                      	"Checking TCP port enabled/disabled for the switch."
        ::= { dosPreventionSetup 15 }  
             
        dosPreventionTCPSF OBJECT-TYPE
        SYNTAX  INTEGER{
                enable(1),
                disable(0)
        }
        ACCESS  read-write
        STATUS  mandatory
        DESCRIPTION
                      	"Checking TCP packets with SYN and FIN bits enabled/disabled for the switch."
        ::= { dosPreventionSetup 16 }      
             
        dosPreventionTCPFUP OBJECT-TYPE
        SYNTAX  INTEGER{
                enable(1),
                disable(0)
        }
        ACCESS  read-write
        STATUS  mandatory
        DESCRIPTION
                      	"Checking TCP packets with FIN, URG, PSH bits and sequence number enabled/disabled for the switch."
        ::= { dosPreventionSetup 17 }      
             
        dosPreventionUDPPort OBJECT-TYPE
        SYNTAX  INTEGER{
                enable(1),
                disable(0)
        }
        ACCESS  read-write
        STATUS  mandatory
        DESCRIPTION
                      	"Checking UDP port enabled/disabled for the switch."
        ::= { dosPreventionSetup 18 }      
             
--        dosPreventionTCPUDPPort OBJECT-TYPE
--        SYNTAX  INTEGER{
--                enable(1),
--                disable(0)
--        }
--        ACCESS  read-write
--        STATUS  mandatory
--        DESCRIPTION
--                      	"Checking TCP/UDP port enabled/disabled for the switch."
--        ::= { dosPreventionSetup 19 }    
   
--  ipv6Setup
	ipv6Setup     	OBJECT IDENTIFIER ::= { ves1616pe54 65 }

--        dnsIpv6Address OBJECT-TYPE
--        SYNTAX  Ipv6Address
--        ACCESS  read-write
--        STATUS  mandatory
--        DESCRIPTION
--                      ""
--        ::= { ipv6Setup 1 }

        defaultMgmt OBJECT-TYPE
        SYNTAX  INTEGER {
        	in_band(0),
        	out_of_band(1)
        }
        ACCESS  read-write
        STATUS  mandatory
        DESCRIPTION
                      ""
        ::= { ipv6Setup 2 }

	inbandIpv6Setup     	OBJECT IDENTIFIER ::= { ipv6Setup 3 }

--        inbandIpType OBJECT-TYPE
--        SYNTAX  INTEGER {
--        	dhcp_client(0),
--        	static_ip(1)
--        }
--        ACCESS  read-write
--        STATUS  mandatory
--        DESCRIPTION
--                      ""
--        ::= { inbandIpv6Setup 1 }

        inbandVid OBJECT-TYPE
        SYNTAX  INTEGER
        ACCESS  read-write
        STATUS  mandatory
        DESCRIPTION
                      ""
        ::= { inbandIpv6Setup 2 }

        inbandStaticIp OBJECT-TYPE
        SYNTAX  Ipv6Address
        ACCESS  read-write
        STATUS  mandatory
        DESCRIPTION
                      ""
        ::= { inbandIpv6Setup 3 }

        inbandStaticSubnetMask OBJECT-TYPE
        SYNTAX  Ipv6Address
        ACCESS  read-write
        STATUS  mandatory
        DESCRIPTION
                      ""
        ::= { inbandIpv6Setup 4 }

        inbandStaticGateway OBJECT-TYPE
        SYNTAX  Ipv6Address
        ACCESS  read-write
        STATUS  mandatory
        DESCRIPTION
                      ""
        ::= { inbandIpv6Setup 5 }

	outOfBandIpv6Setup     	OBJECT IDENTIFIER ::= { ipv6Setup 4 }

        outOfBandIp OBJECT-TYPE
        SYNTAX  Ipv6Address
        ACCESS  read-write
        STATUS  mandatory
        DESCRIPTION
                      ""
        ::= { outOfBandIpv6Setup 1 }

        outOfBandSubnetMask OBJECT-TYPE
        SYNTAX  Ipv6Address
        ACCESS  read-write
        STATUS  mandatory
        DESCRIPTION
                      ""
        ::= { outOfBandIpv6Setup 2 }

        outOfBandGateway OBJECT-TYPE
        SYNTAX  Ipv6Address
        ACCESS  read-write
        STATUS  mandatory
        DESCRIPTION
                      ""
        ::= { outOfBandIpv6Setup 3 }
       
        
---------------------------------------------------
--
--  Layer 2 Protocol Tunneling
--
---------------------------------------------------
 l2ptSetup      OBJECT IDENTIFIER ::= { ves1616pe54 115 }
 
--  l2ptState                               
        l2ptState OBJECT-TYPE
        SYNTAX  EnabledStatus
        ACCESS  read-write
        STATUS  mandatory
        DESCRIPTION
                       "L2PT feature enabled/disabled for the switch"
        ::= { l2ptSetup 1 }
                                
        l2ptMacAddr OBJECT-TYPE
        SYNTAX  MacAddress
        ACCESS  read-write
        STATUS  mandatory
        DESCRIPTION
                       "L2PT destination mac address"
        ::= { l2ptSetup 2 }
                                
-- l2ptTable
 
        l2ptTable OBJECT-TYPE
        SYNTAX SEQUENCE OF L2ptEntry
        ACCESS  not-accessible
        STATUS  mandatory
        DESCRIPTION
                  ""
        ::= { l2ptSetup 3 }
        
 l2ptEntry OBJECT-TYPE
        SYNTAX L2ptEntry
        ACCESS not-accessible
        STATUS mandatory
        DESCRIPTION     "An entry in l2ptTable."
        INDEX           { dot1dBasePort }
        ::= { l2ptTable 1 }
 
        L2ptEntry ::=
           SEQUENCE {
         l2ptProtocolGroup  BITS,
         l2ptPointToPointProtocolGroup BITS,
         l2ptMode   INTEGER
           }
 
     l2ptProtocolGroup OBJECT-TYPE
        SYNTAX BITS {
		  cDP(0),
		  sTP(1),
		  vTP(2)
		 }
        ACCESS  read-write
        STATUS  mandatory
        DESCRIPTION
                       "L2PT protocols enabled/disabled on the port"
        ::= { l2ptEntry 1 }
 
     l2ptPointToPointProtocolGroup OBJECT-TYPE
        SYNTAX BITS {
		  pAGP(0),
		  lACP(1),
		  uDLD(2)
		 }
        ACCESS  read-write
        STATUS  mandatory
        DESCRIPTION
                       "L2PT point-to-point protocols enabled/disabled on the port"
        ::= { l2ptEntry 2 }
                
        l2ptMode OBJECT-TYPE
        SYNTAX  INTEGER {
         access(1),
         tunnel(2)
        }
        ACCESS  read-write
        STATUS  mandatory
        DESCRIPTION
                       "L2PT port role on the port"
        ::= { l2ptEntry 3 }   


---------------------------------------------------
--
--  vlan mapping
--
---------------------------------------------------

-- vlanMappingSetup
	vlanMappingSetup     	OBJECT IDENTIFIER ::= { ves1616pe54 116 }
                               
        vlanMappingState OBJECT-TYPE
        SYNTAX  EnabledStatus
        ACCESS  read-write
        STATUS  mandatory
        DESCRIPTION
                      	""
        ::= { vlanMappingSetup 1 }

                                               
-- vlanMappingPortTable

        vlanMappingPortTable OBJECT-TYPE
        SYNTAX	SEQUENCE OF VlanMappingPortEntry
        ACCESS  not-accessible
        STATUS  mandatory
        DESCRIPTION
                 	""
        ::= { vlanMappingSetup 2 }
        
	vlanMappingPortEntry OBJECT-TYPE
        SYNTAX	VlanMappingPortEntry
        ACCESS	not-accessible
        STATUS	mandatory
        DESCRIPTION    	"An entry in vlanMappingPortTable."
        INDEX          	{ dot1dBasePort }
        ::= { vlanMappingPortTable 1 }

        VlanMappingPortEntry ::=
           SEQUENCE {
        	vlanMappingPortState	EnabledStatus,
        	vlanMappingPortDropMiss	EnabledStatus
           }

        vlanMappingPortState OBJECT-TYPE
        SYNTAX  EnabledStatus
        ACCESS  read-write
        STATUS  mandatory
        DESCRIPTION
                      	""
        ::= { vlanMappingPortEntry 1 }


        vlanMappingPortDropMiss OBJECT-TYPE
        SYNTAX  EnabledStatus
        ACCESS  read-write
        STATUS  mandatory
        DESCRIPTION
                      	""
        ::= { vlanMappingPortEntry 2 }

-- vlanMappingRuleTable
        vlanMappingRuleTable OBJECT-TYPE
        SYNTAX	SEQUENCE OF VlanMappingRuleEntry
        ACCESS  not-accessible
        STATUS  mandatory
        DESCRIPTION
                 	""
        ::= { vlanMappingSetup 3 }
        
	vlanMappingRuleEntry OBJECT-TYPE
        SYNTAX	VlanMappingRuleEntry
        ACCESS	not-accessible
        STATUS	mandatory
        DESCRIPTION    	"An entry in vlan-mapping rule table"
        INDEX          	{ vlanMappingRulePort, vlanMappingRuleVid }
        ::= { vlanMappingRuleTable 1 }

        VlanMappingRuleEntry ::=
           SEQUENCE {
           	vlanMappingRuleName		DisplayString,
        	vlanMappingRulePort		INTEGER,
        	vlanMappingRuleVid		INTEGER,
        	vlanMappingRuleTransVid	INTEGER,
        	vlanMappingRulePriority	INTEGER,
        	vlanMappingRuleRowStatus	RowStatus,
        	vlanMappingRuleReplacePrio	EnabledStatus
           }

        vlanMappingRuleName OBJECT-TYPE
        SYNTAX  DisplayString
        ACCESS  read-write
        STATUS  mandatory
        DESCRIPTION
                      	"The name of vlan-mapping entry"
        ::= { vlanMappingRuleEntry 1 }

        vlanMappingRulePort OBJECT-TYPE
        SYNTAX  INTEGER
        ACCESS  read-only
        STATUS  mandatory
        DESCRIPTION
                     	"interface port id"
        ::= { vlanMappingRuleEntry 2 }

        vlanMappingRuleVid OBJECT-TYPE
        SYNTAX  INTEGER
        ACCESS  read-only
        STATUS  mandatory
        DESCRIPTION
                     	"inner vid"
        ::= { vlanMappingRuleEntry 3 }
        
        vlanMappingRuleTransVid OBJECT-TYPE
        SYNTAX  INTEGER
        ACCESS  read-write
        STATUS  mandatory
        DESCRIPTION
                     	"translated vid"
        ::= { vlanMappingRuleEntry 4 }
        
        vlanMappingRulePriority OBJECT-TYPE
        SYNTAX  INTEGER {
        		prioriry-0(0),
        		prioriry-1(1),
        		prioriry-2(2),
        		prioriry-3(3),
        		prioriry-4(4),
        		prioriry-5(5),
        		prioriry-6(6),
        		prioriry-7(7)
        }

        ACCESS  read-write
        STATUS  mandatory
        DESCRIPTION
                     	"priority"
        ::= { vlanMappingRuleEntry 5 }

        vlanMappingRuleRowStatus OBJECT-TYPE
        SYNTAX  RowStatus
        ACCESS  read-create
        STATUS  mandatory
        DESCRIPTION
                     	""
        ::= { vlanMappingRuleEntry 6 }

        vlanMappingRuleReplacePrio OBJECT-TYPE
        SYNTAX  EnabledStatus
        ACCESS  read-write
        STATUS  mandatory
        DESCRIPTION
                     	"Replace Original Priority"
        ::= { vlanMappingRuleEntry 7 }

-- transceiverInfoTable
	transceiverInfo OBJECT IDENTIFIER ::= { ves1616pe54 117 }

-- transceiverSerialInfoTable
	
        transceiverSerialInfoTable	OBJECT-TYPE
        SYNTAX	SEQUENCE OF TransceiverSerialInfoEntry
        ACCESS  not-accessible
        STATUS  current
        DESCRIPTION
                 	""
        ::= { transceiverInfo 1 }
        
	transceiverSerialInfoEntry OBJECT-TYPE
        SYNTAX	TransceiverSerialInfoEntry
        ACCESS	not-accessible
        STATUS	current
        DESCRIPTION    	"An entry in transceiverSerialInfoTable."
        INDEX          	{ transceiverSerialInfoEntryPort }
        ::= { transceiverSerialInfoTable 1 }

        TransceiverSerialInfoEntry ::=
           SEQUENCE {
        	transceiverSerialInfoEntryPort			INTEGER,
        	transceiverSerialInfoEntryStatus		INTEGER,
        	transceiverSerialInfoEntryVendor		DisplayString,
        	transceiverSerialInfoEntryPartNo		DisplayString,
        	transceiverSerialInfoEntrySerialNo		DisplayString,
        	transceiverSerialInfoEntryRevision		DisplayString,
        	transceiverSerialInfoEntryDateCode		DisplayString,
        	transceiverSerialInfoEntryTransceiver	DisplayString
           }

        transceiverSerialInfoEntryPort OBJECT-TYPE
        SYNTAX  INTEGER
        ACCESS  read-only
        STATUS  current
        DESCRIPTION
                      	"Index of transceiverSerialInfo. It is referred to dot1dBasePort"
        ::= { transceiverSerialInfoEntry 1 }
        
        transceiverSerialInfoEntryStatus OBJECT-TYPE
        SYNTAX  INTEGER {
        		ok_with_DDM(1),
        		ok_without_DDM(2),
        		nonoperational(3)
        }
        ACCESS  read-only
        STATUS  current
        DESCRIPTION
                      	"Transceiver module status."
        ::= { transceiverSerialInfoEntry 2 }


        transceiverSerialInfoEntryVendor OBJECT-TYPE
        SYNTAX  DisplayString
        ACCESS  read-only
        STATUS  current
        DESCRIPTION
                      	"Transceiver module vendor name."
        ::= { transceiverSerialInfoEntry 3 }

        transceiverSerialInfoEntryPartNo OBJECT-TYPE
        SYNTAX  DisplayString
        ACCESS  read-only
        STATUS  current
        DESCRIPTION
                      	"Part number provided by transceiver module vendor."
        ::= { transceiverSerialInfoEntry 4 }
        
        transceiverSerialInfoEntrySerialNo OBJECT-TYPE
        SYNTAX  DisplayString
        ACCESS  read-only
        STATUS  current
        DESCRIPTION
                      	"Serial number provided by transceiver module vendor."
        ::= { transceiverSerialInfoEntry 5 }

        transceiverSerialInfoEntryRevision OBJECT-TYPE
        SYNTAX  DisplayString
        ACCESS  read-only
        STATUS  current
        DESCRIPTION
                      	"Revision level for part number provided by transceiver module vendor."
        ::= { transceiverSerialInfoEntry 6 }

        transceiverSerialInfoEntryDateCode OBJECT-TYPE
        SYNTAX  DisplayString
        ACCESS  read-only
        STATUS  current
        DESCRIPTION
                      	"Transceiver module vendor's manufacturing date code"
        ::= { transceiverSerialInfoEntry 7 }
        
        transceiverSerialInfoEntryTransceiver OBJECT-TYPE
        SYNTAX  DisplayString
        ACCESS  read-only
        STATUS  current
        DESCRIPTION
                      	"Transceiver module type names"
        ::= { transceiverSerialInfoEntry 8 }

-- transceiverDdmInfoTable
	
        transceiverDdmInfoTable	OBJECT-TYPE
        SYNTAX	SEQUENCE OF TransceiverDdmInfoEntry
        ACCESS  not-accessible
        STATUS  current
        DESCRIPTION
                 	""
        ::= { transceiverInfo 2 }
        
		transceiverDdmInfoEntry OBJECT-TYPE
        SYNTAX	TransceiverDdmInfoEntry
        ACCESS	not-accessible
        STATUS	current
        DESCRIPTION    	"An entry in transceiverDdmInfoTable."
        INDEX          	{ transceiverDdmInfoEntryPort, transceiverDdmInfoEntryType }
        ::= { transceiverDdmInfoTable 1 }

        TransceiverDdmInfoEntry ::=
           SEQUENCE {
        	transceiverDdmInfoEntryPort			INTEGER,
        	transceiverDdmInfoEntryType			INTEGER,
        	transceiverDdmInfoEntryAlarmMax		INTEGER,
        	transceiverDdmInfoEntryAlarmMin		INTEGER,
        	transceiverDdmInfoEntryWarnMax		INTEGER,
        	transceiverDdmInfoEntryWarnMin		INTEGER,
        	transceiverDdmInfoEntryCurrent		INTEGER,
        	transceiverDdmInfoEntryDescription	DisplayString
           }

        transceiverDdmInfoEntryPort OBJECT-TYPE
        SYNTAX  INTEGER
        ACCESS  read-only
        STATUS  current
        DESCRIPTION
                      	"Index of transceiverDdmInfo. This will be referred to dot1dBasePort"
        ::= { transceiverDdmInfoEntry 1 }
        
        transceiverDdmInfoEntryType OBJECT-TYPE
        SYNTAX  INTEGER {
        		temperature(1),
        		voltage(2),
        		bias(3),
                txPower(4),
                rxPower(5)
        }
        ACCESS  read-only
        STATUS  current
        DESCRIPTION
                      	"Transceiver module status."
        ::= { transceiverDdmInfoEntry 2 }


        transceiverDdmInfoEntryAlarmMax OBJECT-TYPE
        SYNTAX  INTEGER
        ACCESS  read-only
        STATUS  current
        DESCRIPTION
                      	"Transceiver module vendor name."
        ::= { transceiverDdmInfoEntry 3 }

        transceiverDdmInfoEntryAlarmMin OBJECT-TYPE
        SYNTAX  INTEGER
        ACCESS  read-only
        STATUS  current
        DESCRIPTION
                      	"Part number provided by transceiver module vendor."
        ::= { transceiverDdmInfoEntry 4 }
        
        transceiverDdmInfoEntryWarnMax OBJECT-TYPE
        SYNTAX  INTEGER
        ACCESS  read-only
        STATUS  current
        DESCRIPTION
                      	"Serial number provided by transceiver module vendor."
        ::= { transceiverDdmInfoEntry 5 }

        transceiverDdmInfoEntryWarnMin OBJECT-TYPE
        SYNTAX  INTEGER
        ACCESS  read-only
        STATUS  current
        DESCRIPTION
                      	"Revision level for part number provided by transceiver module vendor."
        ::= { transceiverDdmInfoEntry 6 }

        transceiverDdmInfoEntryCurrent OBJECT-TYPE
        SYNTAX  INTEGER
        ACCESS  read-only
        STATUS  current
        DESCRIPTION
                      	"Transceiver module vendor's manufacturing date code"
        ::= { transceiverDdmInfoEntry 7 }
        
        transceiverDdmInfoEntryDescription OBJECT-TYPE
        SYNTAX  DisplayString
        ACCESS  read-only
        STATUS  current
        DESCRIPTION
                      	"Transceiver module type names"
        ::= { transceiverDdmInfoEntry 8 }  
------------------------------------------------------
        END
